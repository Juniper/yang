/*
 * Copyright (c) 2021 Juniper Networks, Inc.
 * All rights reserved.
 */
 module junos-nfx-conf-tenants {
   namespace "http://yang.juniper.net/junos-nfx/conf/tenants";

   prefix jc-tenants;

   import junos-common-ddl-extensions {
     prefix junos;
     revision-date 2019-01-01;
   }

   import junos-common-types {
     prefix jt;
     revision-date 2019-01-01;
   }

   import junos-nfx-conf-root {
     prefix jc;
     revision-date 2019-01-01;
   }

   organization "Juniper Networks, Inc.";

   contact "yang-support@juniper.net";

   description "Junos tenants configuration module";

   revision 2019-01-01 {
     description "Junos: 21.4R1.12";
   }

   augment /jc:configuration {
     uses tenants-group;
   }
   augment /jc:configuration/jc:groups {
     uses tenants-group;
   }
   grouping tenants-group {
     list tenants {
       key name;
       description "Tenants defined in this system";
       uses juniper-tenant;
     }
   }
   grouping juniper-tenant {
     description "Logical system tenants configuration";
     leaf name {
       description "Tenant name";
       junos:must "(!(\"logical-systems $$\"))";
       junos:must-message "Root tenant name cannot be the same as logical-system name";
       type string {
         junos:posix-pattern "![^a-zA-Z0-9-]|(^(all|.{64,})$)";
         junos:pattern-message "Tenant name is a string consisting of up to 63 letters, numbers and dashes";
       }
     }
     uses apply-advanced;
     container interfaces {
       description "Interface configuration";
       uses apply-advanced;
       list interface {
         key name;
         uses tenant_interfaces_type;
       }
     }
     container routing-instances {
       description "Routing instance configuration";
       uses apply-advanced;
       list instance {
         key name;
         uses juniper-routing-instance;
       }
     }
     container security {
       description "Security configuration";
       uses apply-advanced;
       container alarms {
         description "Configure security alarms";
         uses apply-advanced;
         container audible {
           presence "enable audible";
           description "Beep when new security alarms arrive";
           uses apply-advanced;
           leaf continuous {
             description "Keep beeping until all security alarms have been cleared";
             type empty;
           }
         }
         container potential-violation {
           description "Configure potential security violations";
           uses apply-advanced;
           leaf authentication {
             description "Raise alarm for specified number of authentication failures";
             type union {
               type string {
                 pattern "<.*>|$.*";
               }
               type uint32 {
                 range "2 .. 10";
               }
             }
           }
           leaf cryptographic-self-test {
             description "Raise alarm for cryptographic self test failures";
             type empty;
           }
           container decryption-failures {
             presence "enable decryption-failures";
             description "No. of decryption failures before which an alarm needs to be raised";
             uses apply-advanced;
             leaf threshold {
               description "Threshold value [default is 1000]";
               default "1000";
               type union {
                 type string {
                   pattern "<.*>|$.*";
                 }
                 type uint32 {
                   range "1 .. 1000000000";
                 }
               }
             }
           }
           container encryption-failures {
             presence "enable encryption-failures";
             description "No. of encryption failures before which an alarm needs to be raised";
             uses apply-advanced;
             leaf threshold {
               description "Threshold value [default is 1000]";
               default "1000";
               type union {
                 type string {
                   pattern "<.*>|$.*";
                 }
                 type uint32 {
                   range "1 .. 1000000000";
                 }
               }
             }
           }
           container ike-phase1-failures {
             presence "enable ike-phase1-failures";
             description "No. of IKE Phase-1 failures before which an alarm needs to be raised";
             uses apply-advanced;
             leaf threshold {
               description "Threshold value [default is 20]";
               default "20";
               type union {
                 type string {
                   pattern "<.*>|$.*";
                 }
                 type uint32 {
                   range "1 .. 1000000000";
                 }
               }
             }
           }
           container ike-phase2-failures {
             presence "enable ike-phase2-failures";
             description "No. of IKE Phase-2 failures before which an alarm needs to be raised";
             uses apply-advanced;
             leaf threshold {
               description "Threshold value [default is 20]";
               default "20";
               type union {
                 type string {
                   pattern "<.*>|$.*";
                 }
                 type uint32 {
                   range "1 .. 1000000000";
                 }
               }
             }
           }
           leaf key-generation-self-test {
             description "Raise alarm for key generation self test failures";
             type empty;
           }
           leaf non-cryptographic-self-test {
             description "Raise alarm for non-cryptographic self test failures";
             type empty;
           }
           container policy {
             description "Raise alarm for flow policy violations";
             uses apply-advanced;
             container source-ip {
               presence "enable source-ip";
               description "Configure source address type of policy violation";
               uses apply-advanced;
               leaf threshold {
                 description "Number of source IP address matches to raise alarm";
                 default "1000";
                 type union {
                   type string {
                     pattern "<.*>|$.*";
                   }
                   type uint32 {
                     range "1 .. 4294967295";
                   }
                 }
               }
               leaf duration {
                 description "Time window matches must occur within";
                 default "1";
                 units "seconds";
                 type union {
                   type string {
                     pattern "<.*>|$.*";
                   }
                   type uint32 {
                     range "1 .. 3600";
                   }
                 }
               }
               leaf size {
                 description "Total source IP address number that can be done policy violation check concurrently";
                 default "1024";
                 type union {
                   type string {
                     pattern "<.*>|$.*";
                   }
                   type uint32 {
                     range "1 .. 10240";
                   }
                 }
               }
             }
             container destination-ip {
               presence "enable destination-ip";
               description "Configure destination address type of policy violation";
               uses apply-advanced;
               leaf threshold {
                 description "Number of destination IP address matches to raise alarm";
                 default "1000";
                 type union {
                   type string {
                     pattern "<.*>|$.*";
                   }
                   type uint32 {
                     range "1 .. 4294967295";
                   }
                 }
               }
               leaf duration {
                 description "Time window matches must occur within";
                 default "1";
                 units "seconds";
                 type union {
                   type string {
                     pattern "<.*>|$.*";
                   }
                   type uint32 {
                     range "1 .. 3600";
                   }
                 }
               }
               leaf size {
                 description "Total destination IP address number that can be done policy violation check concurrently";
                 default "1024";
                 type union {
                   type string {
                     pattern "<.*>|$.*";
                   }
                   type uint32 {
                     range "1 .. 10240";
                   }
                 }
               }
             }
             container application {
               presence "enable application";
               description "Configure application type of policy violation";
               uses apply-advanced;
               leaf threshold {
                 description "Number of application matches to raise alarm";
                 default "1000";
                 type union {
                   type string {
                     pattern "<.*>|$.*";
                   }
                   type uint32 {
                     range "1 .. 4294967295";
                   }
                 }
               }
               leaf duration {
                 description "Time window matches must occur within";
                 default "1";
                 units "seconds";
                 type union {
                   type string {
                     pattern "<.*>|$.*";
                   }
                   type uint32 {
                     range "1 .. 3600";
                   }
                 }
               }
               leaf size {
                 description "Total application number that can be done policy violation check concurrently";
                 default "1024";
                 type union {
                   type string {
                     pattern "<.*>|$.*";
                   }
                   type uint32 {
                     range "1 .. 10240";
                   }
                 }
               }
             }
             container policy-match {
               presence "enable policy-match";
               description "Configure policy type of policy violation";
               uses apply-advanced;
               leaf threshold {
                 description "Number of policy matches to raise alarm";
                 default "100";
                 type union {
                   type string {
                     pattern "<.*>|$.*";
                   }
                   type uint32 {
                     range "1 .. 4294967295";
                   }
                 }
               }
               leaf duration {
                 description "Time window matches must occur within";
                 default "1";
                 units "seconds";
                 type union {
                   type string {
                     pattern "<.*>|$.*";
                   }
                   type uint32 {
                     range "1 .. 3600";
                   }
                 }
               }
               leaf size {
                 description "Total concurrent number of policy check violations";
                 default "1024";
                 type union {
                   type string {
                     pattern "<.*>|$.*";
                   }
                   type uint32 {
                     range "1 .. 10240";
                   }
                 }
               }
             }
           }
           container replay-attacks {
             presence "enable replay-attacks";
             description "No. of Replay attacks before which an alarm needs to be raised";
             uses apply-advanced;
             leaf threshold {
               description "Replay threshold value";
               default "1000";
               type union {
                 type string {
                   pattern "<.*>|$.*";
                 }
                 type uint32 {
                   range "1 .. 1000000000";
                 }
               }
             }
           }
           leaf security-log-percent-full {
             description "Raise alarm when security log exceeds this percent capacity";
             type union {
               type string {
                 pattern "<.*>|$.*";
               }
               type uint8 {
                 range "0 .. 100";
               }
             }
           }
           leaf idp {
             description "Raise alarm for idp attack";
             type empty;
           }
         }
       }
       container log {
         description "Configure security log";
         uses log-object;
       }
       container certificates {
         description "X.509 certificate configuration";
         uses apply-advanced;
         list local {
           key name;
           ordered-by user;
           description "Local X.509 certificate configuration";
           uses certificate-object;
         }
         leaf path-length {
           description "Maximum certificate path length";
           default "15";
           type union {
             type string {
               pattern "<.*>|$.*";
             }
             type uint32 {
               range "0 .. 15";
             }
           }
         }
         leaf maximum-certificates {
           description "Maximum number of certificates to cache";
           default "1024";
           type union {
             type string {
               pattern "<.*>|$.*";
             }
             type uint32 {
               range "64 .. 4294967295";
             }
           }
         }
         leaf cache-size {
           description "Maximum size of certificate cache";
           units "bytes";
           type string;
         }
         leaf cache-timeout-negative {
           description "Time in seconds to cache negative responses";
           default "20";
           type union {
             type string {
               pattern "<.*>|$.*";
             }
             type uint32 {
               range "10 .. 4294967295";
             }
           }
         }
         leaf enrollment-retry {
           description "Number of retry attempts for an enrollment request";
           type union {
             type string {
               pattern "<.*>|$.*";
             }
             type uint32 {
               range "0 .. 1080";
             }
           }
         }
         list certification-authority {
           key name;
           ordered-by user;
           description "CA X.509 certificate configuration";
           leaf name {
             description "CA profile name";
             type string {
               junos:posix-pattern "^.{1,32}$";
               junos:pattern-message "Must be string of 32 characters or less";
             }
           }
           uses apply-advanced;
           leaf ca-name {
             description "CA name";
             type string;
           }
           leaf file {
             description "File to read certificate from";
             type string;
           }
           leaf crl {
             description "File to read crl from";
             type string;
           }
           leaf enrollment-url {
             description "URL";
             type string;
           }
           leaf ldap-url {
             description "URL";
             type string;
           }
           leaf encoding {
             description "Encoding to use for certificate or CRL on disk";
             default "binary";
             type enumeration {
               enum "binary" {
                 description "DER encoding";
               }
               enum "pem" {
                 description "Privacy-enhanced-mail encoding, base64";
               }
             }
           }
         }
       }
       container authentication-key-chains {
         description "Authentication key chain configuration";
         uses security-authentication-key-chains;
       }
       container ssh-known-hosts {
         description "SSH known host list";
         uses apply-advanced;
         list host {
           key name;
           ordered-by user;
           description "SSH known host entry";
           leaf name {
             description "Host name";
             type string;
           }
           uses apply-advanced;
           leaf rsa1-key {
             description "Base64 encoded RSA key (protocol version 1)";
             type string;
           }
           leaf rsa-key {
             description "Base64 encoded RSA key";
             type string;
           }
           leaf dsa-key {
             description "Base64 encoded DSA key";
             type string;
           }
           leaf ecdsa-key {
             description "Base64 encoded ECDSA key";
             status deprecated;
             type string;
           }
           leaf ecdsa-sha2-nistp256-key {
             description "Base64 encoded ECDSA-SHA2-NIST256 key";
             type string;
           }
           leaf ecdsa-sha2-nistp384-key {
             description "Base64 encoded ECDSA-SHA2-NIST384 key";
             type string;
           }
           leaf ecdsa-sha2-nistp521-key {
             description "Base64 encoded ECDSA-SHA2-NIST521 key";
             type string;
           }
           leaf ed25519-key {
             description "Base64 encoded ED25519 key";
             type string;
           }
         }
       }
       container pki {
         description "PKI service configuration";
         presence "enable pki";
         uses security-pki;
       }
       container distribution-profile {
         description "IPSec Tunnels distribution profile";
         uses apply-advanced;
         list profile-entity {
           key name;
           ordered-by user;
           description "IPSec Tunnels distribution profile container";
           uses security-distribution-profile;
         }
         leaf fat-core {
           description "Power Mode IPSec fat-tunnel mode";
           type empty;
         }
       }
       container ike {
         description "IKE configuration";
         uses security-ike;
       }
       container ipsec {
         description "IPSec configuration";
         uses security-ipsec-vpn;
       }
       container group-vpn {
         description "Group VPN configuration";
         uses security-group-vpn;
       }
       container ipsec-policy {
         description "IPSec policy configuration";
         uses security-ipsec-policies;
       }
       container idp {
         description "Configure IDP";
         list idp-policy {
           key name;
           ordered-by user;
           description "Configure IDP policy";
           uses idp-policy-type;
         }
         leaf active-policy {
           description "Set active policy";
           status deprecated;
           junos:must "(\"security idp idp-policy $$\")";
           junos:must-message "Policy must be defined under [security idp idp-policy] ";
           type string;
         }
         leaf default-policy {
           description "Set active policy";
           junos:must "(\"security idp idp-policy $$\")";
           junos:must-message "Policy must be defined under [security idp idp-policy] ";
           type string;
         }
         list custom-attack {
           key name;
           ordered-by user;
           description "Configure custom attacks";
           uses custom-attack-type;
         }
         list custom-attack-group {
           key name;
           ordered-by user;
           description "Configure custom attack groups";
           uses custom-attack-group-type;
         }
         list dynamic-attack-group {
           key name;
           ordered-by user;
           description "Configure dynamic attack groups";
           uses dynamic-attack-group-type;
         }
         container traceoptions {
           description "Trace options for idp services";
           uses idpd-traceoptions-type;
         }
         container security-package {
           description "Security package options";
           uses apply-advanced;
           leaf url {
             description "URL of Security package download";
             type string;
           }
           leaf source-address {
             description "Source address to be used for sending download request";
             type jt:ipv4addr;
           }
           leaf proxy-profile {
             description "Proxy profile of security package download";
             junos:must "(\"services proxy profile $$\")";
             junos:must-message "Referenced Proxy profile must be defined under [services proxy profile] path";
             type string {
               length "1 .. 64";
             }
           }
           leaf routing-instance {
             description "Routing instance for security-package download";
             junos:must "(\"routing-instances $$\")";
             junos:must-message "Routing-instance must be defined";
             type string;
           }
           container install {
             presence "enable install";
             description "Configure install command";
             uses apply-advanced;
             leaf ignore-version-check {
               description "Skip version check  when attack database gets installed";
               type empty;
             }
             leaf ignore-appid-failure {
               description "Continue idp installation even if appid installation fails";
               type empty;
             }
           }
           container automatic {
             presence "enable automatic";
             description "Scheduled download and update";
             uses apply-advanced;
             leaf start-time {
               description "Start time (YYYY-MM-DD.HH:MM:SS)";
               type jt:time;
             }
             leaf interval {
               description "Interval";
               units "hours";
               type union {
                 type string {
                   pattern "<.*>|$.*";
                 }
                 type uint32 {
                   range "1 .. 336";
                 }
               }
             }
             leaf download-timeout {
               description "Maximum time for download to complete";
               status deprecated;
               default "1";
               units "minutes";
               type union {
                 type string {
                   pattern "<.*>|$.*";
                 }
                 type uint32 {
                   range "1 .. 60";
                 }
               }
             }
             choice enable-disable {
               case case_1 {
                 leaf enable {
                   description "Enable";
                   type empty;
                 }
               }
             }
           }
         }
         container sensor-configuration {
           description "IDP Sensor Configuration";
           container log {
             description "IDP Log Configuration";
             uses apply-advanced;
             leaf cache-size {
               description "Log cache size";
               type union {
                 type string {
                   pattern "<.*>|$.*";
                 }
                 type uint32;
               }
             }
             container suppression {
               presence "enable suppression";
               description "Log suppression";
               uses apply-advanced;
               choice enable-disable {
                 case case_1 {
                   leaf disable {
                     description "Disable log suppression";
                     type empty;
                   }
                 }
               }
               choice include-destination-address-choice {
                 leaf include-destination-address {
                   description "Include destination address while performing a log suppression";
                   type empty;
                 }
                 leaf no-include-destination-address {
                   description "Don't include destination address while performing a log suppression";
                   type empty;
                 }
               }
               leaf start-log {
                 description "Suppression start log";
                 type union {
                   type string {
                     pattern "<.*>|$.*";
                   }
                   type uint32;
                 }
               }
               leaf max-logs-operate {
                 description "Maximum logs can be operate on";
                 type union {
                   type string {
                     pattern "<.*>|$.*";
                   }
                   type uint32;
                 }
               }
               leaf max-time-report {
                 description "Time after suppressed logs will be reported";
                 type union {
                   type string {
                     pattern "<.*>|$.*";
                   }
                   type uint32;
                 }
               }
             }
           }
           container packet-log {
             description "IDP Packetlog Configuration";
             uses apply-advanced;
             container total-memory {
               description "Total memory unit(%)";
               uses apply-advanced;
               leaf percentage-value {
                 type union {
                   type string {
                     pattern "<.*>|$.*";
                   }
                   type uint32;
                 }
               }
               leaf per-logical-domain {
                 type union {
                   type string {
                     pattern "<.*>|$.*";
                   }
                   type uint32;
                 }
               }
             }
             container max-sessions {
               description "Max num of sessions in unit(%)";
               uses apply-advanced;
               leaf percentage-value {
                 type union {
                   type string {
                     pattern "<.*>|$.*";
                   }
                   type uint32;
                 }
               }
               leaf per-logical-domain {
                 type union {
                   type string {
                     pattern "<.*>|$.*";
                   }
                   type uint32;
                 }
               }
             }
             leaf threshold-logging-interval {
               description "Interval of logs for max limit session/memory reached in minutes";
               type union {
                 type string {
                   pattern "<.*>|$.*";
                 }
                 type uint32;
               }
             }
             leaf source-address {
               description "Source IP address used to transport packetlog to a host";
               type jt:ipv4addr;
             }
             container host {
               description "Destination host to send packetlog to";
               uses apply-advanced;
               leaf ipaddr {
                 description "IP address";
                 type jt:ipv4addr;
               }
               leaf port {
                 description "UDP port number";
                 type union {
                   type uint16;
                   type string {
                     pattern "<.*>|$.*";
                   }
                 }
               }
             }
           }
           container application-identification {
             presence "enable application-identification";
             description "Application identification";
             uses apply-advanced;
             choice enable-disable {
               case case_1 {
                 leaf disable {
                   description "Disable application identification";
                   type empty;
                 }
               }
             }
             choice application-system-cache-choice {
               leaf application-system-cache {
                 description "Application system cache";
                 type empty;
               }
               leaf no-application-system-cache {
                 description "Don't application system cache";
                 type empty;
               }
             }
             leaf max-tcp-session-packet-memory {
               description "Max TCP session memory";
               status deprecated;
               type union {
                 type string {
                   pattern "<.*>|$.*";
                 }
                 type uint32;
               }
             }
             leaf max-udp-session-packet-memory {
               description "Max UDP session memory";
               status deprecated;
               type union {
                 type string {
                   pattern "<.*>|$.*";
                 }
                 type uint32;
               }
             }
             leaf max-sessions {
               description "Max sessions that can run AI at the same time";
               status deprecated;
               type union {
                 type string {
                   pattern "<.*>|$.*";
                 }
                 type uint32;
               }
             }
             leaf max-packet-memory {
               description "Max packet memory";
               status deprecated;
               type union {
                 type string {
                   pattern "<.*>|$.*";
                 }
                 type uint32;
               }
             }
             leaf max-packet-memory-ratio {
               description "Max packet memory ratio";
               type union {
                 type string {
                   pattern "<.*>|$.*";
                 }
                 type uint32;
               }
             }
             leaf max-reass-packet-memory-ratio {
               description "Max reass packet memory ratio";
               status deprecated;
               type union {
                 type string {
                   pattern "<.*>|$.*";
                 }
                 type uint32;
               }
             }
             leaf application-system-cache-timeout {
               description "Application system cache timeout";
               type union {
                 type string {
                   pattern "<.*>|$.*";
                 }
                 type uint32;
               }
             }
           }
           container flow {
             description "Flow configuration";
             uses apply-advanced;
             choice log-errors-choice {
               leaf log-errors {
                 description "Flow log errors";
                 type empty;
               }
               leaf no-log-errors {
                 description "Don't flow log errors";
                 type empty;
               }
             }
             choice allow-icmp-without-flow-choice {
               leaf allow-icmp-without-flow {
                 description "Allow icmp without flow";
                 status deprecated;
                 type empty;
               }
               leaf no-allow-icmp-without-flow {
                 description "Don't allow icmp without flow";
                 status deprecated;
                 type empty;
               }
             }
             leaf hash-table-size {
               description "Flow hash table size";
               type union {
                 type string {
                   pattern "<.*>|$.*";
                 }
                 type uint32;
               }
             }
             leaf reject-timeout {
               description "Flow reject timeout";
               type union {
                 type string {
                   pattern "<.*>|$.*";
                 }
                 type uint32;
               }
             }
             leaf max-timers-poll-ticks {
               description "Maximum timers poll ticks";
               type union {
                 type string {
                   pattern "<.*>|$.*";
                 }
                 type uint32;
               }
             }
             leaf fifo-max-size {
               description "Maximum fifo size";
               type union {
                 type string {
                   pattern "<.*>|$.*";
                 }
                 type uint32;
               }
             }
             leaf udp-anticipated-timeout {
               description "Maximum udp anticipated timeout";
               type union {
                 type string {
                   pattern "<.*>|$.*";
                 }
                 type uint32;
               }
             }
             leaf allow-nonsyn-connection {
               description "Allow TCP non-syn connection";
               type empty;
             }
             leaf drop-on-limit {
               description "Drop connections on exceeding resource limits";
               type empty;
             }
             leaf drop-on-failover {
               description "Drop traffic on HA failover sessions";
               type empty;
             }
             leaf drop-if-no-policy-loaded {
               description "Drop all traffic till IDP policy gets loaded";
               type empty;
             }
             leaf max-sessions-offset {
               description "Maximum session offset limit percentage";
               type union {
                 type string {
                   pattern "<.*>|$.*";
                 }
                 type uint32;
               }
             }
             leaf min-objcache-limit-lt {
               description "Memory lower threshold limit percentage";
               type union {
                 type string {
                   pattern "<.*>|$.*";
                 }
                 type uint32;
               }
             }
             leaf min-objcache-limit-ut {
               description "Memory upper threshold limit percentage";
               type union {
                 type string {
                   pattern "<.*>|$.*";
                 }
                 type uint32;
               }
             }
             leaf session-steering {
               description "Session steering for session anticipation";
               type empty;
             }
             leaf idp-bypass-cpu-usg-overload {
               description "Enable IDP bypass of sessions/packets on CPU usage overload";
               type empty;
             }
             leaf idp-bypass-cpu-threshold {
               description "Threshold of CPU usage in percentage for IDP bypass";
               default "85";
               type union {
                 type string {
                   pattern "<.*>|$.*";
                 }
                 type uint32;
               }
             }
             leaf idp-bypass-cpu-tolerance {
               description "Tolerance of CPU usage in percentage for IDP bypass";
               default "5";
               type union {
                 type string {
                   pattern "<.*>|$.*";
                 }
                 type uint32;
               }
             }
             leaf intel-inspect-enable {
               description "Minimizes IDP processing during system overload";
               type empty;
             }
             leaf intel-inspect-cpu-usg-threshold {
               description "CPU usage threshold percentage for intelligent inspection";
               default "80";
               type union {
                 type string {
                   pattern "<.*>|$.*";
                 }
                 type uint32;
               }
             }
             leaf intel-inspect-cpu-usg-tolerance {
               description "CPU usage tolerance percentage for intelligent inspection";
               default "5";
               type union {
                 type string {
                   pattern "<.*>|$.*";
                 }
                 type uint32;
               }
             }
             leaf intel-inspect-free-mem-threshold {
               description "Free memory threshold percentage for intelligent inspection";
               default "15";
               type union {
                 type string {
                   pattern "<.*>|$.*";
                 }
                 type uint32;
               }
             }
             leaf intel-inspect-mem-tolerance {
               description "Memory tolerance percentage for intelligent inspection";
               default "5";
               type union {
                 type string {
                   pattern "<.*>|$.*";
                 }
                 type uint32;
               }
             }
             leaf intel-inspect-disable-content-decompress {
               description "Disables payload content decompression";
               type empty;
             }
             leaf intel-inspect-session-bytes-depth {
               description "Session bytes scanning depth";
               default "0";
               type union {
                 type string {
                   pattern "<.*>|$.*";
                 }
                 type uint32;
               }
             }
             leaf-list intel-inspect-protocols {
               ordered-by user;
               description "Protocols to be processed in Intelligent Inspection mode";
               type string;
             }
             leaf-list intel-inspect-signature-severity {
               ordered-by user;
               description "Signature severities to be considered for IDP processing";
               junos:must "(\"security idp sensor-configuration flow intel-inspect-enable\")";
               junos:must-message "intelligent inspection must be enabled under [security idp sensor-configuration flow]";
               type enumeration {
                 enum "minor" {
                 }
                 enum "major" {
                 }
                 enum "critical" {
                 }
               }
             }
           }
           container re-assembler {
             description "Re-assembler configuration";
             uses apply-advanced;
             choice drop-on-syn-in-window-choice {
               leaf drop-on-syn-in-window {
                 description "Drop session when SYN is seen in the window";
                 type empty;
               }
               leaf no-drop-on-syn-in-window {
                 description "Don't drop session when SYN is seen in the window";
                 type empty;
               }
             }
             choice ignore-memory-overflow-choice {
               leaf ignore-memory-overflow {
                 description "Ignore memory overflow";
                 type empty;
               }
               leaf no-ignore-memory-overflow {
                 description "Don't ignore memory overflow";
                 type empty;
               }
             }
             choice ignore-reassembly-memory-overflow-choice {
               leaf ignore-reassembly-memory-overflow {
                 description "Ignore packet reassembly memory overflow";
                 type empty;
               }
               leaf no-ignore-reassembly-memory-overflow {
                 description "Don't ignore packet reassembly memory overflow";
                 type empty;
               }
             }
             leaf ignore-reassembly-overflow {
               description "Ignore global reassembly overflow";
               type empty;
             }
             leaf max-packet-mem {
               description "Maximum packet memory";
               status deprecated;
               type union {
                 type string {
                   pattern "<.*>|$.*";
                 }
                 type uint32;
               }
             }
             leaf max-flow-mem {
               description "Maximum flow memory";
               type union {
                 type string {
                   pattern "<.*>|$.*";
                 }
                 type uint32;
               }
             }
             leaf max-packet-mem-ratio {
               description "Maximum packet memory ratio";
               type union {
                 type string {
                   pattern "<.*>|$.*";
                 }
                 type uint32;
               }
             }
             leaf action-on-reassembly-failure {
               description "Select the action on reassembly failures";
               default "drop";
               type enumeration {
                 enum "ignore" {
                   description "No action is taken.";
                 }
                 enum "drop" {
                   description "Drop the packet.";
                 }
                 enum "drop-session" {
                   description "Drop the session.";
                 }
               }
             }
             choice tcp-error-logging-choice {
               leaf tcp-error-logging {
                 description "Enable logging on tcp errors";
                 type empty;
               }
               leaf no-tcp-error-logging {
                 description "Don't enable logging on tcp errors";
                 type empty;
               }
             }
             leaf max-synacks-queued {
               description "Maximum syn-acks queued with different SEQ numbers ";
               type union {
                 type string {
                   pattern "<.*>|$.*";
                 }
                 type uint32;
               }
             }
             choice force-tcp-window-checks-choice {
               leaf force-tcp-window-checks {
                 description "Force TCP window checks if uni-directional policy is configured";
                 type empty;
               }
               leaf no-force-tcp-window-checks {
                 description "Don't force TCP window checks if uni-directional policy is configured";
                 type empty;
               }
             }
           }
           container ips {
             description "Ips configuration";
             uses apply-advanced;
             choice process-override-choice {
               leaf process-override {
                 description "Process override";
                 type empty;
               }
               leaf no-process-override {
                 description "Don't process override";
                 type empty;
               }
             }
             choice detect-shellcode-choice {
               leaf detect-shellcode {
                 description "Detect shellcode";
                 type empty;
               }
               leaf no-detect-shellcode {
                 description "Don't detect shellcode";
                 type empty;
               }
             }
             choice process-ignore-s2c-choice {
               leaf process-ignore-s2c {
                 description "Process ignore s2c";
                 type empty;
               }
               leaf no-process-ignore-s2c {
                 description "Don't process ignore s2c";
                 type empty;
               }
             }
             choice ignore-regular-expression-choice {
               leaf ignore-regular-expression {
                 description "Ignore regular expression";
                 type empty;
               }
               leaf no-ignore-regular-expression {
                 description "Don't ignore regular expression";
                 type empty;
               }
             }
             leaf process-port {
               description "Process port";
               type union {
                 type string {
                   pattern "<.*>|$.*";
                 }
                 type uint32;
               }
             }
             leaf fifo-max-size {
               description "Maximum fifo size";
               type union {
                 type string {
                   pattern "<.*>|$.*";
                 }
                 type uint32;
               }
             }
             leaf log-supercede-min {
               description "Minimum log supercede";
               type union {
                 type string {
                   pattern "<.*>|$.*";
                 }
                 type uint32;
               }
             }
             leaf content-decompression-max-memory-kb {
               description "Maximum memory usage in kilo bytes";
               type union {
                 type string {
                   pattern "<.*>|$.*";
                 }
                 type uint32;
               }
             }
             leaf content-decompression-max-ratio {
               description "Maximum decompression ratio supported";
               type union {
                 type string {
                   pattern "<.*>|$.*";
                 }
                 type uint32;
               }
             }
             leaf session-pkt-depth {
               description "Session pkt scanning depth";
               type union {
                 type string {
                   pattern "<.*>|$.*";
                 }
                 type uint32;
               }
             }
           }
           container global {
             description "Global configuration";
             uses apply-advanced;
             choice enable-packet-pool-choice {
               leaf enable-packet-pool {
                 description "Enable packet pool";
                 type empty;
               }
               leaf no-enable-packet-pool {
                 description "Don't enable packet pool";
                 type empty;
               }
             }
             leaf log-xff-header {
               description "Log xff header";
               type empty;
             }
             choice enable-all-qmodules-choice {
               leaf enable-all-qmodules {
                 description "Enable all qmodules";
                 type empty;
               }
               leaf no-enable-all-qmodules {
                 description "Don't enable all qmodules";
                 type empty;
               }
             }
             choice policy-lookup-cache-choice {
               leaf policy-lookup-cache {
                 description "Policy lookup cache";
                 type empty;
               }
               leaf no-policy-lookup-cache {
                 description "Don't policy lookup cache";
                 type empty;
               }
             }
             leaf memory-limit-percent {
               description "Memory limit percentage";
               type union {
                 type string {
                   pattern "<.*>|$.*";
                 }
                 type uint32;
               }
             }
             leaf disable-idp-processing {
               description "Flag to disable IDP processing";
               type empty;
             }
             leaf intelligent-offload {
               description "Intelligently offload the flow";
               type enumeration {
                 enum "disable" {
                   description "Disable flow offload";
                 }
                 enum "conservative" {
                   description "Increases scrutiny of flows prior to offload";
                 }
               }
             }
           }
           container detector {
             description "Detector Configuration";
             uses apply-advanced;
             list protocol-name {
               key name;
               ordered-by user;
               description "Apropriate help string";
               uses proto-object;
             }
           }
           container ssl-inspection {
             description "SSL inspection";
             uses apply-advanced;
             leaf sessions {
               description "Number of SSL sessions to inspect";
               default "10000";
               type union {
                 type string {
                   pattern "<.*>|$.*";
                 }
                 type uint32;
               }
             }
             leaf session-id-cache-timeout {
               description "Timeout value for SSL session ID cache";
               default "600";
               units "seconds";
               type union {
                 type string {
                   pattern "<.*>|$.*";
                 }
                 type uint32;
               }
             }
             leaf maximum-cache-size {
               description "Maximum SSL session ID cache size";
               default "100000";
               units "sessions";
               type union {
                 type string {
                   pattern "<.*>|$.*";
                 }
                 type uint32;
               }
             }
             leaf cache-prune-chunk-size {
               description "Number of cache entries to delete when pruning SSL session ID cache";
               default "100";
               type union {
                 type string {
                   pattern "<.*>|$.*";
                 }
                 type uint32;
               }
             }
             leaf key-protection {
               description "Enable SSL key protection";
               type empty;
             }
           }
           leaf disable-low-memory-handling {
             description "Do not abort IDP operations under low memory condition";
             type empty;
           }
           container high-availability {
             description "High availability configuration";
             uses apply-advanced;
             leaf no-policy-cold-synchronization {
               description "Disable policy cold synchronization";
               type empty;
             }
           }
           container security-configuration {
             description "IDP security configuration";
             uses apply-advanced;
             leaf protection-mode {
               description "Enable security protection mode";
               type enumeration {
                 enum "datacenter" {
                   description "Security protection mode for datacenter";
                 }
                 enum "datacenter-full" {
                   description "Full security protection mode for datacenter";
                 }
                 enum "perimeter" {
                   description "Security protection mode for perimeter";
                 }
                 enum "perimeter-full" {
                   description "Full security protection mode for perimeter";
                 }
               }
             }
           }
         }
         leaf max-sessions {
           description "Max number of IDP sessions";
           type union {
             type uint32;
             type string {
               pattern "<.*>|$.*";
             }
           }
         }
         list logical-system {
           key name;
           ordered-by user;
           description "Configure max IDP sessions for the logial system";
           uses logical-system-type;
         }
         list tenant-system {
           key name;
           ordered-by user;
           description "Configure max IDP sessions for the tenant";
           uses tenant-system-type;
         }
         uses apply-advanced;
         container processes {
           description "Configure IDP Processes";
           uses apply-advanced;
         }
       }
       list address-book {
         key name;
         ordered-by user;
         description "Security address book";
         max-elements 4096;
         uses named-address-book-type;
       }
       container alg {
         description "Configure ALG security options";
         uses alg-object;
       }
       container application-firewall {
         presence "enable application-firewall";
         description "Configure application-firewall rule-sets";
         status deprecated;
         uses apply-advanced;
         container traceoptions {
           description "Rule-sets Tracing Options";
           uses apply-advanced;
           leaf no-remote-trace {
             description "Disable remote tracing";
             junos:must "(\"system tracing\")";
             junos:must-message "'no-remote-trace' is valid only when [system tracing] is configured";
             type empty;
           }
           container file {
             description "Trace file information";
             leaf filename {
               description "Name of file in which to write trace information";
               type string {
                 length "1 .. 1024";
                 junos:posix-pattern "![/ %]";
                 junos:pattern-message "Must not contain '/', % or a space";
               }
             }
             leaf size {
               description "Maximum trace file size";
               type string;
             }
             leaf files {
               description "Maximum number of trace files";
               default "3";
               type union {
                 type string {
                   pattern "<.*>|$.*";
                 }
                 type uint32 {
                   range "2 .. 1000";
                 }
               }
             }
             choice world-readable-choice {
               leaf world-readable {
                 description "Allow any user to read the log file";
                 type empty;
               }
               leaf no-world-readable {
                 description "Don't allow any user to read the log file";
                 type empty;
               }
             }
             leaf match {
               description "Regular expression for lines to be logged";
               type jt:regular-expression;
             }
           }
           list flag {
             key name;
             ordered-by user;
             description "Tracing parameters";
             leaf name {
               type enumeration {
                 enum "configuration" {
                   description "Trace configuration events";
                 }
                 enum "lookup" {
                   description "Trace lookup events";
                 }
                 enum "compilation" {
                   description "Rule-sets compilation events";
                 }
                 enum "ipc" {
                   description "Inter-process communication events";
                 }
                 enum "all" {
                   description "Trace everything";
                 }
               }
             }
           }
         }
         list profile {
           key name;
           ordered-by user;
           description "Configure application-firewall profile";
           leaf name {
             description "Surf control integrated profile name";
             type string {
               length "1 .. 63";
             }
           }
           uses apply-advanced;
           container block-message {
             description "Block message settings";
             uses apply-advanced;
             container type {
               description "Type of block message desired";
               uses apply-advanced;
               choice type-choice {
                 case case_1 {
                   container custom-text {
                     description "Custom defined block message";
                     uses apply-advanced;
                     leaf content {
                       description "Content of custom-text";
                       type string {
                         length "1 .. 511";
                       }
                     }
                   }
                 }
                 case case_2 {
                   container custom-redirect-url {
                     description "Custom redirect URL server";
                     uses apply-advanced;
                     leaf content {
                       description "URL of block message";
                       type string {
                         length "1 .. 1023";
                         junos:posix-pattern "^https?://.*";
                         junos:pattern-message "URL must begin with http:// or https://";
                       }
                     }
                   }
                 }
               }
             }
           }
         }
         list rule-sets {
           key name;
           ordered-by user;
           description "Configure application-firewall rule-sets";
           leaf name {
             description "Application firewall rule-set name";
             type string {
               length "1 .. 63";
             }
           }
           uses apply-advanced;
           list rule {
             key name;
             ordered-by user;
             description "Rule";
             uses appfw_rule_type;
           }
           container default-rule {
             presence "enable default-rule";
             description "Specify default rule for a rule-set";
             uses apply-advanced;
             choice action {
               case case_1 {
                 leaf permit {
                   description "Permit packets";
                   type empty;
                 }
               }
               case case_2 {
                 container deny {
                   presence "enable deny";
                   description "Deny packets";
                   uses apply-advanced;
                   leaf block-message {
                     description "Block message";
                     type empty;
                   }
                 }
               }
               case case_3 {
                 container reject {
                   presence "enable reject";
                   description "Reject packets";
                   uses apply-advanced;
                   leaf block-message {
                     description "Block message";
                     type empty;
                   }
                 }
               }
             }
           }
           leaf profile {
             description "Profile for block message";
             junos:must "(\"security application-firewall profile $$\")";
             junos:must-message "Application-firewall profile must be defined";
             type string;
           }
         }
         container nested-application {
           presence "enable nested-application";
           description "Configure nested application dynamic lookup";
           status deprecated;
           uses apply-advanced;
           container dynamic-lookup {
             presence "enable dynamic-lookup";
             description "Configure dynamic lookup";
             uses apply-advanced;
             leaf enable {
               description "Enable dynamic lookup";
               type empty;
             }
           }
         }
       }
       container application-tracking {
         presence "enable application-tracking";
         description "Application tracking configuration";
         uses apply-advanced;
         leaf disable {
           description "Disable Application tracking";
           type empty;
         }
         choice update-interval {
           case case_1 {
             leaf first-update-interval {
               description "Interval when the first update message is sent";
               units "minutes";
               type union {
                 type uint32;
                 type string {
                   pattern "<.*>|$.*";
                 }
               }
             }
           }
           case case_2 {
             leaf first-update {
               description "Generate Application tracking initial message when a session is created";
               status deprecated;
               type empty;
             }
           }
         }
         leaf session-update-interval {
           description "Frequency in which Application tracking update messages are generated";
           units "minutes";
           type union {
             type uint32;
             type string {
               pattern "<.*>|$.*";
             }
           }
         }
         leaf log-session-create {
           description "Generate Application tracking session create log";
           type empty;
         }
         leaf log-session-close {
           description "Generate Application tracking session close log";
           type empty;
         }
         leaf no-volume-updates {
           description "Disable session volume update log";
           type empty;
         }
       }
       container utm {
         description "Content security service configuration";
         uses apply-advanced;
         container traceoptions {
           description "Trace options for utm";
           uses utm-traceoptions;
         }
         container application-proxy {
           description "Application proxy settings";
           uses apply-advanced;
           container traceoptions {
             description "Trace options for application proxy";
             uses utm-apppxy-traceoptions;
           }
         }
         container ipc {
           description "IPC settings";
           uses apply-advanced;
           container traceoptions {
             description "Trace options for IPC";
             uses utm-ipc-traceoptions;
           }
         }
         container custom-objects {
           description "Custom-objects settings";
           uses apply-advanced;
           container category-package {
             description "Category package download and install options";
             uses apply-advanced;
             leaf url {
               description "HTTPS URL of category package download";
               type string;
             }
             leaf proxy-profile {
               description "Proxy profile";
               junos:must "(\"services proxy profile $$\")";
               junos:must-message "Referenced Proxy profile must be defined";
               type string {
                 length "1 .. 64";
               }
             }
             leaf routing-instance {
               description "Routing instance name";
               junos:must "(\"routing-instances $$\")";
               junos:must-message "Routing-instance must be defined";
               type string;
             }
             container automatic {
               description "Scheduled download and install";
               uses apply-advanced;
               leaf start-time {
                 description "Start time (YYYY-MM-DD.HH:MM:SS)";
                 type jt:time;
               }
               leaf interval {
                 description "Interval in hours";
                 default "168";
                 type union {
                   type string {
                     pattern "<.*>|$.*";
                   }
                   type uint32 {
                     range "1 .. 336";
                   }
                 }
               }
               leaf enable {
                 description "Enable automatic download and install";
                 type empty;
               }
             }
           }
           list mime-pattern {
             key name;
             ordered-by user;
             description "Configure mime-list object";
             uses mime-list-type;
           }
           list filename-extension {
             key name;
             ordered-by user;
             description "Configure extension-list object";
             status deprecated;
             uses extension-list-type;
           }
           list url-pattern {
             key name;
             ordered-by user;
             description "Configure url-list object";
             uses url-list-type;
           }
           list custom-url-category {
             key name;
             ordered-by user;
             description "Configure category-list object";
             uses category-list-type;
           }
           list protocol-command {
             key name;
             ordered-by user;
             description "Configure command-list object";
             status deprecated;
             uses command-list-type;
           }
           list custom-message {
             key name;
             ordered-by user;
             description "Configure custom-message object";
             uses custom-message-type;
           }
         }
         container default-configuration {
           description "Global default UTM configurations";
           uses apply-advanced;
           container anti-virus {
             description "Configure anti-virus feature";
             uses default-anti-virus-feature;
           }
           container web-filtering {
             description "Configure web-filtering feature";
             uses default-webfilter-feature;
           }
           container anti-spam {
             description "Configure anti-spam feature";
             uses default-anti-spam-feature;
           }
           container content-filtering {
             description "Configure content filtering feature";
             uses default-content-filtering-feature;
           }
         }
         container feature-profile {
           description "Feature-profile settings";
           uses apply-advanced;
           container anti-virus {
             description "Configure anti-virus feature";
             uses anti-virus-feature;
           }
           container web-filtering {
             description "Configure web-filtering feature";
             uses webfilter-feature;
           }
           container anti-spam {
             description "Configure anti-spam feature";
             uses anti-spam-feature;
           }
           container content-filtering {
             description "Configure content filtering feature";
             status deprecated;
             uses content-filtering-feature;
           }
         }
         list utm-policy {
           key name;
           ordered-by user;
           description "Configure profile ";
           uses profile-setting;
         }
       }
       container dynamic-address {
         presence "enable dynamic-address";
         description "Configure security dynamic address";
         uses apply-advanced;
         container traceoptions {
           description "Security dynamic address tracing options";
           uses apply-advanced;
           leaf no-remote-trace {
             description "Disable remote tracing";
             junos:must "(\"system tracing\")";
             junos:must-message "'no-remote-trace' is valid only when [system tracing] is configured";
             type empty;
           }
           container file {
             description "Trace file information";
             leaf filename {
               description "Name of file in which to write trace information";
               type string {
                 length "1 .. 1024";
                 junos:posix-pattern "![/ %]";
                 junos:pattern-message "Must not contain '/', % or a space";
               }
             }
             leaf size {
               description "Maximum trace file size";
               type string;
             }
             leaf files {
               description "Maximum number of trace files";
               default "3";
               type union {
                 type string {
                   pattern "<.*>|$.*";
                 }
                 type uint32 {
                   range "2 .. 1000";
                 }
               }
             }
             choice world-readable-choice {
               leaf world-readable {
                 description "Allow any user to read the log file";
                 type empty;
               }
               leaf no-world-readable {
                 description "Don't allow any user to read the log file";
                 type empty;
               }
             }
             leaf match {
               description "Regular expression for lines to be logged";
               type jt:regular-expression;
             }
           }
           leaf level {
             description "Level of debugging output";
             type enumeration {
               enum "error" {
                 description "Match error conditions";
               }
               enum "warning" {
                 description "Match warning messages";
               }
               enum "notice" {
                 description "Match conditions that should be handled specially";
               }
               enum "info" {
                 description "Match informational messages";
               }
               enum "verbose" {
                 description "Match verbose messages";
               }
               enum "all" {
                 description "Match all levels";
               }
             }
           }
           list flag {
             key name;
             ordered-by user;
             description "Tracing parameters";
             leaf name {
               type enumeration {
                 enum "configuration" {
                   description "Configuration details";
                 }
                 enum "control" {
                   description "Daemon control message";
                 }
                 enum "ipc" {
                   description "IPC message sending and receiving";
                 }
                 enum "ip-entry" {
                   description "IP entry management";
                 }
                 enum "file-retrieval" {
                   description "File retrieval";
                 }
                 enum "lookup" {
                   description "Lookup detail";
                 }
                 enum "all" {
                   description "Trace everything";
                 }
               }
             }
           }
         }
         list feed-server {
           key name;
           ordered-by user;
           description "Security dynamic address feed-server";
           leaf name {
             description "Security dynamic address feed-server name";
             type string {
               length "1 .. 16";
               junos:posix-pattern "^[[:alnum:]._-]+$";
               junos:pattern-message "Must be a string consisting of letters, numbers, dashes and underscores";
             }
           }
           uses apply-advanced;
           leaf description {
             description "Text description of feed-server";
             type string {
               length "1 .. 900";
               junos:posix-pattern "^[^&<>\n]+$";
               junos:pattern-message "Must be a string excluding '&', '<', '>' and '\n'";
             }
           }
           choice hostname-or-url {
             case case_1 {
               leaf hostname {
                 description "Hostname or IP address of feed-server";
                 type string {
                   length "1 .. 256";
                 }
               }
             }
             case case_2 {
               leaf url {
                 description "URL,example:example.url.com;1.1.1.1/<folder-or-file-path>;Browser can verify its validity";
                 type string {
                   length "1 .. 256";
                 }
               }
             }
           }
           leaf update-interval {
             description "Interval to retrieve update";
             default "300";
             units "seconds";
             type union {
               type string {
                 pattern "<.*>|$.*";
               }
               type uint32 {
                 range "30 .. 4294967295";
               }
             }
           }
           leaf hold-interval {
             description "Time to keep IP entry when update failed";
             default "86400";
             units "seconds";
             type union {
               type string {
                 pattern "<.*>|$.*";
               }
               type uint32 {
                 range "0 .. 4294967295";
               }
             }
           }
           leaf tls-profile {
             description "TLS profile";
             junos:must "(\"services ssl initiation profile $$\")";
             junos:must-message "Referenced SSL initiation profile is not defined";
             type string;
           }
           container validate-certificate-attributes {
             junos:must "(\".. tls-profile\")";
             junos:must-message "tls-profile is not configured";
             description "Validate some certificate attributes";
             uses apply-advanced;
             leaf subject-or-subject-alternative-names {
               description "One of them must match feed server host name";
               type empty;
             }
           }
           list feed-name {
             key name;
             ordered-by user;
             description "Feed name in feed-server";
             leaf name {
               description "Security dynamic address feed name in feed-server";
               type string {
                 length "1 .. 240";
                 junos:posix-pattern "^[[:alnum:]._-]+$";
                 junos:pattern-message "Must be a string consisting of letters, numbers, dashes and underscores";
               }
             }
             uses apply-advanced;
             leaf description {
               description "Text description of feed in feed-server";
               type string {
                 length "1 .. 900";
                 junos:posix-pattern "^[^&<>\n]+$";
                 junos:pattern-message "Must be a string excluding '&', '<', '>' and '\n'";
               }
             }
             leaf path {
               description "Path of feed, appended to feed-server to form a complete URL";
               type string {
                 length "1 .. 1024";
               }
             }
             leaf update-interval {
               description "Interval to retrieve update";
               units "seconds";
               type union {
                 type string {
                   pattern "<.*>|$.*";
                 }
                 type uint32 {
                   range "30 .. 4294967295";
                 }
               }
             }
             leaf hold-interval {
               description "Time to keep IP entry when update failed";
               units "seconds";
               type union {
                 type string {
                   pattern "<.*>|$.*";
                 }
                 type uint32 {
                   range "0 .. 4294967295";
                 }
               }
             }
           }
         }
         list address-name {
           key name;
           ordered-by user;
           description "Security dynamic address name";
           leaf name {
             description "Security dynamic address name";
             type string {
               length "1 .. 240";
               junos:posix-pattern "^[[:alnum:]._-]+$";
               junos:pattern-message "Must be a string consisting of letters, numbers, dashes and underscores";
             }
           }
           uses apply-advanced;
           leaf description {
             description "Text description of dynamic address";
             type string {
               length "1 .. 900";
               junos:posix-pattern "^[^&<>\n]+$";
               junos:pattern-message "Must be a string excluding '&', '<', '>' and '\n'";
             }
           }
           container profile {
             presence "enable profile";
             description "Information to categorize feed data into this dynamic address";
             uses apply-advanced;
             list feed-name {
               key name;
               ordered-by user;
               description "Name of feed in feed-server for this dynamic address";
               max-elements 1;
               leaf name {
                 description "Name of feed in feed-server which is mapped to this dynamic address";
                 type string {
                   length "1 .. 240";
                   junos:posix-pattern "^[[:alnum:]._-]+$";
                   junos:pattern-message "Must be a string consisting of letters, numbers, dashes and underscores";
                 }
               }
               uses apply-advanced;
             }
             list category {
               key name;
               ordered-by user;
               description "Name of category";
               junos:must "(!(\".. feed-name\"))";
               junos:must-message "Feed-name can not coexist with category";
               max-elements 1;
               leaf name {
                 description "Name of category";
                 type string {
                   length "1 .. 32";
                   junos:posix-pattern "^[[:alnum:]._-]+$";
                   junos:pattern-message "Must be a string consisting of letters, numbers, dashes and underscores";
                 }
               }
               uses apply-advanced;
               leaf feed {
                 description "Name of feed under category";
                 type string {
                   length "1 .. 32";
                   junos:posix-pattern "^[[:alnum:]._-]+$";
                   junos:pattern-message "Must be a string consisting of letters, numbers, dashes and underscores";
                 }
               }
               list property {
                 key name;
                 ordered-by user;
                 description "Property to match";
                 max-elements 3;
                 leaf name {
                   description "Name of property";
                   type string {
                     length "1 .. 32";
                   }
                 }
                 uses apply-advanced;
                 choice property-value {
                   case case_1 {
                     list string {
                       key name;
                       ordered-by user;
                       description "Value type is strings";
                       max-elements 256;
                       leaf name {
                         description "String value";
                         type string {
                           length "1 .. 32";
                         }
                       }
                       uses apply-advanced;
                     }
                   }
                 }
               }
             }
           }
           leaf session-scan {
             description "Trigger session scan when the IP address is added";
             type empty;
           }
         }
         container session-scan {
           presence "enable session-scan";
           description "Trigger session scan for all the dynamic addresses";
           uses apply-advanced;
           leaf hold-interval {
             description "Time interval before the session scan request";
             default "10";
             units "seconds";
             type union {
               type string {
                 pattern "<.*>|$.*";
               }
               type uint32 {
                 range "1 .. 3600";
               }
             }
           }
         }
       }
       container remote-access {
         junos:must "((\"system services web-management\" && \"access firewall-authentication\"))";
         junos:must-message "web-management and firewall-authentication must be enabled for remote-access";
         description "Configure remote access";
         uses apply-advanced;
         container global-options {
           description "Global remote-access configuration";
           uses apply-advanced;
           leaf auth-token-valid-time {
             description "Authentication token valid time (seconds) :default 60";
             default "60";
             units "seconds";
             type union {
               type string {
                 pattern "<.*>|$.*";
               }
               type uint32 {
                 range "1 .. 300";
               }
             }
           }
           leaf config-file-size {
             description "Set the Config file buffer size (default size 5120 bytes)";
             default "5120";
             units "bytes";
             type union {
               type string {
                 pattern "<.*>|$.*";
               }
               type uint32 {
                 range "5120 .. 10240";
               }
             }
           }
         }
         list profile {
           key name;
           ordered-by user;
           description "Remote access profile";
           uses remote-access-profile-config;
         }
         list client-config {
           key name;
           ordered-by user;
           description "Remote-access client configuration";
           uses remote-access-client-config;
         }
         container traceoptions {
           description "Remote-access trace configuration";
           uses remote-access-traceoptions;
         }
         leaf default-profile {
           description "Configure default profile";
           junos:must "(\"security remote-access profile $$\")";
           junos:must-message "Remote access default profile should configure";
           type string;
         }
       }
       container dynamic-application {
         presence "enable dynamic-application";
         description "Configure dynamic-application";
         uses apply-advanced;
         container traceoptions {
           description "Dynamic application tracing options";
           uses apply-advanced;
           leaf no-remote-trace {
             description "Disable remote tracing";
             junos:must "(\"system tracing\")";
             junos:must-message "'no-remote-trace' is valid only when [system tracing] is configured";
             type empty;
           }
           container file {
             description "Trace file information";
             leaf filename {
               description "Name of file in which to write trace information";
               type string {
                 length "1 .. 1024";
                 junos:posix-pattern "![/ %]";
                 junos:pattern-message "Must not contain '/', % or a space";
               }
             }
             leaf size {
               description "Maximum trace file size";
               type string;
             }
             leaf files {
               description "Maximum number of trace files";
               default "3";
               type union {
                 type string {
                   pattern "<.*>|$.*";
                 }
                 type uint32 {
                   range "2 .. 1000";
                 }
               }
             }
             choice world-readable-choice {
               leaf world-readable {
                 description "Allow any user to read the log file";
                 type empty;
               }
               leaf no-world-readable {
                 description "Don't allow any user to read the log file";
                 type empty;
               }
             }
             leaf match {
               description "Regular expression for lines to be logged";
               type jt:regular-expression;
             }
           }
           list flag {
             key name;
             ordered-by user;
             description "Tracing parameters";
             leaf name {
               type enumeration {
                 enum "configuration" {
                   description "Trace configuration events";
                 }
                 enum "lookup" {
                   description "Trace lookup events";
                 }
                 enum "compilation" {
                   description "Rule-sets compilation events";
                 }
                 enum "ipc" {
                   description "Inter-process communication events";
                 }
                 enum "all" {
                   description "Trace everything";
                 }
               }
             }
           }
         }
         list profile {
           key name;
           ordered-by user;
           description "Configure application-firewall profile";
           leaf name {
             description "Surf control integrated profile name";
             type string {
               length "1 .. 63";
             }
           }
           uses apply-advanced;
           container redirect-message {
             description "Redirect message settings";
             uses apply-advanced;
             container type {
               description "Type of redirect message desired";
               uses apply-advanced;
               choice type-choice {
                 case case_1 {
                   container custom-text {
                     description "Custom defined text block message";
                     uses apply-advanced;
                     leaf content {
                       description "Content of custom-text";
                       type string {
                         length "1 .. 511";
                       }
                     }
                   }
                 }
                 case case_2 {
                   container redirect-url {
                     description "Custom redirect URL server";
                     uses apply-advanced;
                     leaf content {
                       description "URL of block message";
                       type string {
                         length "1 .. 1023";
                         junos:posix-pattern "^https?://.*";
                         junos:pattern-message "URL must begin with http:// or https://";
                       }
                     }
                   }
                 }
               }
             }
           }
         }
       }
       container softwires {
         description "Configure softwire feature";
         uses softwires-object;
       }
       container forwarding-options {
         description "Security-forwarding-options configuration";
         uses apply-advanced;
         container family {
           description "Security forwarding-options for family";
           uses apply-advanced;
           container inet6 {
             description "Family IPv6";
             uses apply-advanced;
             leaf mode {
               description "Forwarding mode";
               type enumeration {
                 enum "packet-based" {
                   description "Enable packet-based forwarding";
                 }
                 enum "flow-based" {
                   description "Enable flow-based forwarding";
                 }
                 enum "drop" {
                   description "Disable forwarding";
                 }
               }
             }
           }
           container mpls {
             description "Family MPLS";
             uses apply-advanced;
             leaf mode {
               description "Forwarding mode";
               type enumeration {
                 enum "packet-based" {
                   description "Enable packet-based forwarding";
                   junos:must "(!(\"security policies\"))";
                   junos:must-message "MPLS mode packet-based not allowed when [security policies] are configured.";
                 }
                 enum "flow-based" {
                   description "Enable flow-based forwarding for mpls";
                 }
               }
             }
           }
           container iso {
             description "Family ISO";
             uses apply-advanced;
             leaf mode {
               description "Forwarding mode";
               type enumeration {
                 enum "packet-based" {
                   description "Enable packet-based forwarding";
                 }
               }
             }
           }
         }
         list mirror-filter {
           key name;
           ordered-by user;
           description "Security mirror filters";
           max-elements 15;
           uses mirror-filter-type;
         }
         list secure-wire {
           key name;
           description "Secure-wire cross connections";
           uses secure-wire-type;
         }
         container mode {
           description "Tap or sniffer mode";
           uses apply-advanced;
           container tap {
             description "Tap mode";
             uses apply-advanced;
             leaf-list interface {
               ordered-by user;
               description "Tap enabled interface";
               type union {
                 type jt:interface-name;
                 type string {
                   pattern "<.*>|$.*";
                 }
               }
             }
             container inspect-pass-through-tunnel {
               description "Inspect pass-through tunnel";
               uses apply-advanced;
               leaf ipip {
                 description "IPIP";
                 type empty;
               }
               leaf gre {
                 description "GRE";
                 type empty;
               }
             }
           }
         }
         container receive-side-scaling {
           description "Receive side scaling";
           uses apply-advanced;
           container software-rss {
             description "Software RSS options";
             uses apply-advanced;
             leaf mode {
               description "Mode of Software RSS";
               default "automatic";
               type enumeration {
                 enum "automatic" {
                   description "Auto select Software RSS mode (default)";
                 }
                 enum "enable" {
                   description "Software RSS would be enabled";
                 }
                 enum "disable" {
                   description "Software RSS would be disabled";
                 }
               }
             }
             leaf io-thread-number {
               description "Software-RSS IO thread number";
               junos:must "(\"security forwarding-options receive-side-scaling software-rss mode enable\")";
               junos:must-message "The IO threads configuration will take effect only when software RSS mode is set to enable, please set it.";
               type union {
                 type string {
                   pattern "<.*>|$.*";
                 }
                 type uint32 {
                   range "1 .. 8";
                 }
               }
             }
           }
           container nic-rss {
             description "NIC RSS options";
             uses apply-advanced;
             leaf mode {
               description "Mode of NIC RSS";
               type enumeration {
                 enum "disable" {
                   description "NIC RSS would be disabled";
                 }
               }
             }
           }
         }
         container security-service {
           description "Security service actions when memory resource is in shortage";
           uses apply-advanced;
           leaf fail-open {
             description "Packet will bypass all the application services ";
             type empty;
           }
         }
         container resource-manager {
           description "Manage the resource for special usage";
           uses apply-advanced;
           container cpu {
             description "The CPU resource";
             uses apply-advanced;
             leaf re {
               description "The count of vCPUs assigned to RE (default is 1)";
               type union {
                 type string {
                   pattern "<.*>|$.*";
                 }
                 type uint32 {
                   range "2 .. 3";
                 }
               }
             }
           }
         }
         leaf no-allow-dataplane-sleep {
           description "Disable dataplane sleep";
           type empty;
         }
         container services-offload {
           description "Service offload option";
           uses apply-advanced;
           leaf disable {
             description "Disable services-offload";
             type empty;
           }
         }
       }
       container advanced-services {
         description "Advanced services configuration";
         uses apply-advanced;
         container data-plane {
           description "Data plane configuration";
           uses apply-advanced;
           container memory {
             description "Data plane memory configuration";
             uses apply-advanced;
             leaf low {
               description "Reduce data plane memory";
               type empty;
             }
           }
         }
       }
       container flow {
         description "FLOW configuration";
         uses apply-advanced;
         leaf enhanced-routing-mode {
           description "Enable enhanced route scaling";
           type empty;
         }
         container traceoptions {
           description "Trace options for flow services";
           uses flow-traceoptions-object;
         }
         leaf pending-sess-queue-length {
           description "Maximum queued length per pending session";
           default "normal";
           type enumeration {
             enum "normal" {
               description "Normal number of sessions queued";
             }
             enum "moderate" {
               description "Allow more queued sessions than normal";
             }
             enum "high" {
               description "Maximum number of queued sessions";
             }
           }
         }
         container enable-reroute-uniform-link-check {
           description "Enable reroute check with uniform link";
           uses apply-advanced;
           leaf nat {
             description "Enable NAT check";
             type empty;
           }
         }
         leaf allow-dns-reply {
           description "Allow unmatched incoming DNS reply packet";
           type empty;
         }
         leaf route-change-timeout {
           description "Timeout value for route change to nonexistent route";
           default "30";
           units "seconds";
           type union {
             type string {
               pattern "<.*>|$.*";
             }
             type uint32 {
               range "6 .. 1800";
             }
           }
         }
         leaf nh-resolve-timeout {
           description "Timeout value for nexthop resolve";
           default "10000";
           units "milliseconds";
           type union {
             type string {
               pattern "<.*>|$.*";
             }
             type uint32 {
               range "1 .. 20000";
             }
           }
         }
         leaf multicast-nh-resolve-retry {
           description "Retry count for nexthop resolve";
           default "0";
           type union {
             type string {
               pattern "<.*>|$.*";
             }
             type uint32 {
               range "0 .. 20";
             }
           }
         }
         leaf syn-flood-protection-mode {
           description "TCP SYN flood protection mode";
           default "syn-cookie";
           type enumeration {
             enum "syn-cookie" {
               description "Enable SYN cookie protection";
             }
             enum "syn-proxy" {
               description "Enable SYN proxy protection";
             }
           }
         }
         leaf allow-embedded-icmp {
           description "Allow embedded ICMP packets not matching a session to pass through";
           type empty;
         }
         leaf mcast-buffer-enhance {
           description "Allow to hold more packets during multicast session creation";
           type empty;
         }
         leaf strict-packet-order {
           description "Maintain arrival ordering when packets departing";
           type empty;
         }
         leaf allow-reverse-ecmp {
           description "Allow reverse ECMP route lookup";
           type empty;
         }
         leaf no-local-favor-ecmp {
           description "Not prefer local node in HA ECMP route lookup";
           type empty;
         }
         leaf sync-icmp-session {
           description "Allow icmp sessions to sync to peer node";
           type empty;
         }
         leaf ipsec-performance-acceleration {
           description "Accelerate the IPSec traffic performance";
           type empty;
         }
         leaf gre-performance-acceleration {
           description "Accelerate the GRE traffic performance";
           type empty;
         }
         container aging {
           description "Aging configuration";
           uses apply-advanced;
           leaf early-ageout {
             description "Delay before device declares session invalid";
             default "20";
             units "seconds";
             type union {
               type string {
                 pattern "<.*>|$.*";
               }
               type uint32 {
                 range "1 .. 65535";
               }
             }
           }
           leaf low-watermark {
             description "Percentage of session-table capacity at which aggressive aging-out ends";
             default "100";
             units "percent";
             type union {
               type string {
                 pattern "<.*>|$.*";
               }
               type uint32 {
                 range "0 .. 100";
               }
             }
           }
           leaf high-watermark {
             description "Percentage of session-table capacity at which aggressive aging-out starts";
             default "100";
             units "percent";
             type union {
               type string {
                 pattern "<.*>|$.*";
               }
               type uint32 {
                 range "0 .. 100";
               }
             }
           }
         }
         container ethernet-switching {
           description "Ethernet-switching configuration for flow";
           uses apply-advanced;
           leaf block-non-ip-all {
             description "Block all non-IP and non-ARP traffic including broadcast/multicast";
             type empty;
           }
           leaf bypass-non-ip-unicast {
             description "Allow all non-IP (including unicast) traffic";
             junos:must "(!(\".. block-non-ip-all\"))";
             junos:must-message "'bypass-non-ip-unicast' cannot coexist with 'block-non-ip-all'";
             type empty;
           }
           container no-packet-flooding {
             presence "enable no-packet-flooding";
             description "Stop IP flooding, send ARP/ICMP to trigger MAC learning";
             uses apply-advanced;
             leaf no-trace-route {
               description "Don't send ICMP to trigger MAC learning";
               type empty;
             }
           }
           leaf bpdu-vlan-flooding {
             description "Set 802.1D BPDU flooding based on VLAN";
             type empty;
           }
         }
         container tcp-mss {
           description "TCP maximum segment size configuration";
           uses apply-advanced;
           container all-tcp {
             description "Enable MSS override for all packets";
             uses apply-advanced;
             leaf mss {
               description "MSS value";
               type union {
                 type string {
                   pattern "<.*>|$.*";
                 }
                 type uint32 {
                   range "64 .. 65535";
                 }
               }
             }
           }
           container ipsec-vpn {
             presence "enable ipsec-vpn";
             description "Enable MSS override for all packets entering IPSec tunnel";
             uses apply-advanced;
             leaf mss {
               description "MSS value";
               default "1320";
               type union {
                 type string {
                   pattern "<.*>|$.*";
                 }
                 type uint32 {
                   range "64 .. 65535";
                 }
               }
             }
           }
           container gre-in {
             presence "enable gre-in";
             description "Enable MSS override for all GRE packets coming out of an IPSec tunnel";
             uses apply-advanced;
             leaf mss {
               description "MSS value";
               default "1320";
               type union {
                 type string {
                   pattern "<.*>|$.*";
                 }
                 type uint32 {
                   range "64 .. 65535";
                 }
               }
             }
           }
           container gre-out {
             presence "enable gre-out";
             description "Enable MSS override for all GRE packets entering an IPsec tunnel";
             uses apply-advanced;
             leaf mss {
               description "MSS value";
               default "1320";
               type union {
                 type string {
                   pattern "<.*>|$.*";
                 }
                 type uint32 {
                   range "64 .. 65535";
                 }
               }
             }
           }
         }
         container tcp-session {
           description "Transmission Control Protocol session configuration";
           uses apply-advanced;
           leaf rst-invalidate-session {
             description "Immediately end session on receipt of reset (RST) segment";
             type empty;
           }
           leaf fin-invalidate-session {
             description "Immediately end session on receipt of fin (FIN) segment";
             type empty;
           }
           leaf rst-sequence-check {
             description "Check sequence number in reset (RST) segment";
             type empty;
           }
           leaf no-syn-check {
             description "Disable creation-time SYN-flag check";
             type empty;
           }
           leaf strict-syn-check {
             description "Enable strict syn check";
             junos:must "(!((\"security flow tcp-session no-syn-check\" || \"security flow tcp-session no-syn-check-in-tunnel\")))";
             junos:must-message "strict-syn-check not allowed when no-syn-check or no-syn-check-in-tunnel is configured";
             type empty;
           }
           leaf no-syn-check-in-tunnel {
             description "Disable creation-time SYN-flag check for tunnel packets";
             type empty;
           }
           leaf no-sequence-check {
             description "Disable sequence-number checking";
             type empty;
           }
           leaf aggressive-tcp-ack {
             description "Enable aggressive TCP ACK, root lsys only";
             type empty;
           }
           leaf tcp-initial-timeout {
             description "Timeout for TCP session when initialization fails";
             default "20";
             units "seconds";
             type union {
               type string {
                 pattern "<.*>|$.*";
               }
               type uint32 {
                 range "4 .. 300";
               }
             }
           }
           leaf maximum-window {
             description "Maximum TCP proxy scaled receive window, default 256K bytes";
             default "256K";
             type enumeration {
               enum "64K" {
                 description "64K bytes receive window";
               }
               enum "128K" {
                 description "128K bytes receive window";
               }
               enum "256K" {
                 description "256K bytes receive window";
               }
               enum "512K" {
                 description "512K bytes receive window";
               }
               enum "1M" {
                 description "1M bytes receive window";
               }
             }
           }
           container time-wait-state {
             presence "enable time-wait-state";
             description "Session timeout value in time-wait state, default 150 seconds";
             uses apply-advanced;
             choice session-age-option {
               case case_1 {
                 leaf session-ageout {
                   description "Allow session to ageout using service based timeout values";
                   type empty;
                 }
               }
               case case_2 {
                 leaf session-timeout {
                   description "Configure session timeout value for time-wait state";
                   units "seconds";
                   type union {
                     type string {
                       pattern "<.*>|$.*";
                     }
                     type uint32 {
                       range "2 .. 600";
                     }
                   }
                 }
               }
             }
             leaf apply-to-half-close-state {
               description "Apply time-wait-state timeout to half-close state";
               type empty;
             }
           }
         }
         leaf force-ip-reassembly {
           description "Force to reassemble ip fragments";
           type empty;
         }
         leaf preserve-incoming-fragment-size {
           description "Preserve incoming fragment size for egress MTU";
           type empty;
         }
         leaf fragment-limit {
           description "Maximum number of fragments allowed for a packet";
           default "0";
           type union {
             type string {
               pattern "<.*>|$.*";
             }
             type uint32 {
               range "0 .. 250";
             }
           }
         }
         leaf fragment-reassembly-timeout {
           description "Re-assembly timeout (seconds) for fragments of a packet";
           default "0";
           units "seconds";
           type union {
             type string {
               pattern "<.*>|$.*";
             }
             type uint32 {
               range "0 .. 60";
             }
           }
         }
         container log {
           description "Enable log";
           uses apply-advanced;
           leaf dropped-icmp-packet {
             description "Log dropped ICMPv4 packet";
             type empty;
           }
           leaf dropped-illegal-packet {
             description "Log dropped illegal packet";
             type empty;
           }
         }
         container advanced-options {
           description "Flow config advanced options";
           uses apply-advanced;
           leaf drop-matching-reserved-ip-address {
             description "Drop matching reserved source IP address";
             type empty;
           }
           leaf drop-matching-link-local-address {
             description "Drop matching link local address";
             type empty;
           }
           leaf reverse-route-packet-mode-vr {
             description "Allow reverse route lookup with packet mode vr";
             type empty;
           }
         }
         container load-distribution {
           description "Flow config SPU load distribution";
           uses apply-advanced;
           container session-affinity {
             description "SPU load distribution based on the service anchor SPU";
             uses apply-advanced;
             leaf ipsec {
               description "IPsec service";
               type empty;
             }
           }
         }
         container packet-log {
           description "Configure flow packet log";
           uses apply-advanced;
           leaf enable {
             description "Enable log for dropped packet";
             type empty;
           }
           leaf throttle-interval {
             description "Interval should be configured as a power of two";
             default "1024";
             units "milliseconds";
             type union {
               type string {
                 pattern "<.*>|$.*";
               }
               type uint32 {
                 range "0 .. 32768";
               }
             }
           }
           list packet-filter {
             key name;
             ordered-by user;
             description "Configure packet log filter";
             max-elements 64;
             uses flow-filter-type;
           }
         }
         leaf power-mode-disable {
           description "Disable power mode express path processing";
           type empty;
         }
         leaf power-mode-ipsec-qat {
           description "Enable qat in power mode ipsec processing";
           type empty;
         }
       }
       container firewall-authentication {
         description "Firewall authentication parameters";
         uses apply-advanced;
         container traceoptions {
           description "Data-plane firewall authentication tracing options";
           uses apply-advanced;
           list flag {
             key name;
             ordered-by user;
             description "Events to include in trace output";
             leaf name {
               type enumeration {
                 enum "authentication" {
                   description "Data-plane firewall authentication events";
                 }
                 enum "proxy" {
                   description "Data-plane firewall authentication proxy events";
                 }
                 enum "all" {
                   description "All events";
                 }
               }
             }
             choice level {
               case case_1 {
                 leaf terse {
                   description "Include terse amount of output in trace";
                   type empty;
                 }
               }
               case case_2 {
                 leaf detail {
                   description "Include detailed amount of output in trace";
                   type empty;
                 }
               }
               case case_3 {
                 leaf extensive {
                   description "Include extensive amount of output in trace";
                   type empty;
                 }
               }
             }
           }
         }
       }
       container screen {
         description "Configure screen feature";
         uses apply-advanced;
         container trap {
           presence "enable trap";
           description "Configure trap interval";
           leaf interval {
             description "Trap interval";
             default "2";
             units "seconds";
             type union {
               type string {
                 pattern "<.*>|$.*";
               }
               type uint32 {
                 range "1 .. 3600";
               }
             }
           }
         }
         list ids-option {
           key name;
           description "Configure ids-option";
           uses ids-option-type;
         }
         container traceoptions {
           description "Trace options for Network Security Screen";
           uses apply-advanced;
           leaf no-remote-trace {
             description "Disable remote tracing";
             junos:must "(\"system tracing\")";
             junos:must-message "'no-remote-trace' is valid only when [system tracing] is configured";
             type empty;
           }
           container file {
             description "Trace file information";
             leaf filename {
               description "Name of file in which to write trace information";
               type string {
                 length "1 .. 1024";
                 junos:posix-pattern "![/ %]";
                 junos:pattern-message "Must not contain '/', % or a space";
               }
             }
             leaf size {
               description "Maximum trace file size";
               type string;
             }
             leaf files {
               description "Maximum number of trace files";
               default "3";
               type union {
                 type string {
                   pattern "<.*>|$.*";
                 }
                 type uint32 {
                   range "2 .. 1000";
                 }
               }
             }
             choice world-readable-choice {
               leaf world-readable {
                 description "Allow any user to read the log file";
                 type empty;
               }
               leaf no-world-readable {
                 description "Don't allow any user to read the log file";
                 type empty;
               }
             }
             leaf match {
               description "Regular expression for lines to be logged";
               type jt:regular-expression;
             }
           }
           list flag {
             key name;
             ordered-by user;
             description "Tracing parameters";
             leaf name {
               type enumeration {
                 enum "configuration" {
                   description "Trace configuration events";
                 }
                 enum "flow" {
                   description "Trace flow events";
                 }
                 enum "all" {
                   description "Trace everything";
                 }
               }
             }
           }
         }
         list white-list {
           key name;
           description "Set of IP addresses for white list";
           max-elements 32;
           uses ids-wlist-type;
         }
       }
       container nat {
         description "Configure Network Address Translation";
         uses nat-object;
       }
       container forwarding-process {
         description "Configure security forwarding-process options";
         uses apply-advanced;
         leaf enhanced-services-mode {
           description "Enable enhanced application services mode";
           type empty;
         }
         container application-services {
           description "Configure application service options";
           uses apply-advanced;
           leaf maximize-alg-sessions {
             description "Maximize ALG session capacity";
             type empty;
           }
           leaf maximize-persistent-nat-capacity {
             description "Increase persistent NAT capacity by reducing maximum flow sessions";
             type empty;
           }
           container maximize-cp-sessions {
             presence "enable maximize-cp-sessions";
             description "Maximize CP session capacity";
             status deprecated;
             uses apply-advanced;
           }
           leaf session-distribution-mode {
             description "Session distribution mode";
             status deprecated;
             junos:must "(!(\".. maximize-idp-sessions\"))";
             junos:must-message "to configure session-distribution-mode, maximize-idp-sessions must not be set";
             type enumeration {
               enum "normal" {
                 description "Normal mode";
                 status deprecated;
               }
               enum "hash-based" {
                 description "Hash mode";
                 status deprecated;
               }
             }
           }
           leaf enable-gtpu-distribution {
             description "Enable GTP-U distribution";
             type empty;
           }
           leaf packet-ordering-mode {
             description "Packet ordering mode";
             type enumeration {
               enum "hardware" {
                 description "Hardware mode";
               }
               enum "software" {
                 description "Software mode";
               }
             }
           }
           container maximize-idp-sessions {
             presence "enable maximize-idp-sessions";
             description "Run security services in dedicated processes to maximize IDP session capacity";
             uses apply-advanced;
             container weight {
               description "Adjust the weighting of the resources available for idp";
               uses apply-advanced;
               choice weight {
                 case case_1 {
                   leaf equal {
                     description "Equal resources to IDP and firewall";
                     status deprecated;
                     type empty;
                   }
                 }
                 case case_2 {
                   container idp {
                     presence "enable idp";
                     description "IDP has more resources than firewall";
                     uses apply-advanced;
                   }
                 }
                 case case_3 {
                   leaf firewall {
                     description "Firewall has more resources than IDP";
                     type empty;
                   }
                 }
               }
             }
             leaf inline-tap {
               description "Configure IDP in inline tap mode";
               type empty;
             }
           }
           leaf inline-fpga-crypto {
             description "Disable inline FPGA crypto";
             type enumeration {
               enum "disabled" {
                 description "Disable inline FPGA crypto";
               }
               enum "enabled" {
                 description "Enable inline FPGA crypto";
               }
             }
           }
         }
       }
       container policies {
         description "Configure Network Security Policies";
         presence "enable policies";
         uses policy-object-type;
       }
       container tcp-encap {
         presence "enable tcp-encap";
         description "Configure TCP Encapsulation.";
         uses apply-advanced;
         container traceoptions {
           description "Trace options for TCP encapsulation service";
           uses ragw-traceoptions;
         }
         list profile {
           key name;
           ordered-by user;
           description "Configure profile.";
           leaf name {
             description "Profile name identifier.";
             type string {
               length "1 .. 64";
             }
           }
           uses apply-advanced;
           leaf ssl-profile {
             description "SSL Termination profile";
             junos:must "(\"services ssl termination profile $$\")";
             junos:must-message "Referenced SSL termination profile must be defined";
             type string;
           }
           leaf log {
             description "Enable logging for remote-access";
             type empty;
           }
         }
         container global-options {
           description "Global settings for TCP encapsulation";
           leaf enable-tunnel-tracking {
             description "Track ESP tunnels";
             type empty;
           }
         }
       }
       container resource-manager {
         description "Configure resource manager security options";
         uses apply-advanced;
         container traceoptions {
           description "Traceoptions for resource manager";
           uses apply-advanced;
           list flag {
             key name;
             ordered-by user;
             description "Resource manager objects and events to include in trace";
             leaf name {
               type enumeration {
                 enum "client" {
                   description "Trace resource manager client";
                 }
                 enum "group" {
                   description "Trace resource manager group";
                 }
                 enum "resource" {
                   description "Trace resource manager resource";
                 }
                 enum "gate" {
                   description "Trace resource manager created gates";
                 }
                 enum "session" {
                   description "Trace resource manager created session";
                 }
                 enum "chassis cluster" {
                   description "Trace resource manager's chassis cluster events";
                 }
                 enum "messaging" {
                   description "Trace resource manager messaging";
                 }
                 enum "service pinhole" {
                   description "Trace resource manager created service pinholes";
                 }
                 enum "error" {
                   description "Trace all resource manager errors";
                 }
                 enum "all" {
                   description "Trace all resource manager objects and events";
                 }
               }
             }
             choice level {
               case case_1 {
                 leaf terse {
                   description "Set trace verbosity level to terse";
                   type empty;
                 }
               }
               case case_2 {
                 leaf detail {
                   description "Set trace verbosity level to detail";
                   type empty;
                 }
               }
               case case_3 {
                 leaf extensive {
                   description "Set trace verbosity level to extensive";
                   type empty;
                 }
               }
             }
           }
         }
         container services-memory {
           presence "enable services-memory";
           description "Manage services memory resources";
           uses apply-advanced;
           container match {
             presence "enable match";
             uses apply-advanced;
             leaf threshold {
               description "Service Memory Threshold";
               type union {
                 type string {
                   pattern "<.*>|$.*";
                 }
                 type int32 {
                   range "1 .. 100";
                 }
               }
             }
           }
           container then {
             presence "enable then";
             description "Action to take if the conditions are matched";
             uses apply-advanced;
             leaf fail-close {
               description "Enable fail-close";
               junos:must "(!(\".. fail-open\"))";
               junos:must-message "'fail-open' can not be defined with 'fail-close'";
               type empty;
             }
             leaf fail-open {
               description "Enable fail-open";
               junos:must "(!(\".. fail-close\"))";
               junos:must-message "'fail-close' can not be defined with 'fail-open'";
               type empty;
             }
             leaf drop-flows {
               description "Enable drop-flows";
               type empty;
             }
             leaf log {
               description "Enable logs";
               type empty;
             }
             leaf alarm {
               description "Enable Alarm";
               type empty;
             }
           }
         }
         container session-memory {
           presence "enable session-memory";
           description "Manage session memory resources";
           uses apply-advanced;
           container match {
             presence "enable match";
             uses apply-advanced;
             leaf threshold {
               description "Session Memory Threshold";
               type union {
                 type string {
                   pattern "<.*>|$.*";
                 }
                 type int32 {
                   range "1 .. 100";
                 }
               }
             }
           }
           container then {
             presence "enable then";
             description "Action to take if the conditions are matched";
             uses apply-advanced;
             container session-aggressive-ageout {
               presence "enable session-aggressive-ageout";
               description "Session ageout configuration";
               uses apply-advanced;
               leaf early-ageout {
                 description "Delay before device declares session invalid";
                 type union {
                   type string {
                     pattern "<.*>|$.*";
                   }
                   type int32 {
                     range "1 .. 65535";
                   }
                 }
               }
             }
             leaf log {
               description "Enable logs";
               type empty;
             }
             leaf alarm {
               description "Enable alarms";
               type empty;
             }
             leaf drop-flows {
               description "Enable drop-flows";
               type empty;
             }
           }
         }
         container cpu {
           presence "enable cpu";
           description "Manage cpu resources";
           uses apply-advanced;
           leaf disable-management {
             description "Disable Resource Manager CPU Management";
             junos:must "(!(\".. then\"))";
             junos:must-message "Cannot define 'then' with disable-management";
             junos:must "(!(\".. match\"))";
             junos:must-message "Cannot define 'match' with disable-management";
             type empty;
           }
           container match {
             presence "enable match";
             uses apply-advanced;
             leaf threshold {
               description "CPU Useage Threshold";
               type union {
                 type string {
                   pattern "<.*>|$.*";
                 }
                 type int32 {
                   range "1 .. 100";
                 }
               }
             }
           }
           container then {
             presence "enable then";
             description "Action to take if the conditions are matched";
             uses apply-advanced;
             leaf drop-flows {
               description "Enable drop-flows";
               type empty;
             }
             leaf drop-cps {
               description "Enable drop-cps";
               type empty;
             }
             leaf log {
               description "Enable logs";
               type empty;
             }
             leaf alarm {
               description "Enable drop-alarm";
               type empty;
             }
             leaf max-session-setup-rate {
               description "Maximum number of session creations allowed per second";
               type union {
                 type string {
                   pattern "<.*>|$.*";
                 }
                 type int32 {
                   range "0 .. 65535";
                 }
               }
             }
           }
         }
       }
       container analysis {
         description "Configure security analysis";
         uses apply-advanced;
         leaf no-report {
           description "Stops security analysis reporting";
           type empty;
         }
       }
       container traceoptions {
         description "Network security daemon tracing options";
         uses apply-advanced;
         leaf no-remote-trace {
           description "Disable remote tracing";
           junos:must "(\"system tracing\")";
           junos:must-message "'no-remote-trace' is valid only when [system tracing] is configured";
           type empty;
         }
         container file {
           description "Trace file information";
           leaf filename {
             description "Name of file in which to write trace information";
             type string {
               length "1 .. 1024";
               junos:posix-pattern "![/ %]";
               junos:pattern-message "Must not contain '/', % or a space";
             }
           }
           leaf size {
             description "Maximum trace file size";
             type string;
           }
           leaf files {
             description "Maximum number of trace files";
             default "3";
             type union {
               type string {
                 pattern "<.*>|$.*";
               }
               type uint32 {
                 range "2 .. 1000";
               }
             }
           }
           choice world-readable-choice {
             leaf world-readable {
               description "Allow any user to read the log file";
               type empty;
             }
             leaf no-world-readable {
               description "Don't allow any user to read the log file";
               type empty;
             }
           }
           leaf match {
             description "Regular expression for lines to be logged";
             type jt:regular-expression;
           }
         }
         list flag {
           key name;
           ordered-by user;
           description "Tracing parameters";
           leaf name {
             type enumeration {
               enum "configuration" {
                 description "Trace configuration events";
               }
               enum "routing-socket" {
                 description "Trace routing socket events";
               }
               enum "compilation" {
                 description "Trace compilation events";
               }
               enum "all" {
                 description "Trace everything";
               }
             }
           }
         }
         leaf rate-limit {
           description "Limit the incoming rate of trace messages";
           default "0";
           type union {
             type string {
               pattern "<.*>|$.*";
             }
             type uint32 {
               range "0 .. 4294967295";
             }
           }
         }
       }
       container datapath-debug {
         description "Datapath debug options";
         uses apply-advanced;
         container traceoptions {
           description "End to end debug trace options";
           uses apply-advanced;
           leaf no-remote-trace {
             description "Disable remote tracing";
             junos:must "(\"system tracing\")";
             junos:must-message "'no-remote-trace' is valid only when [system tracing] is configured";
             type empty;
           }
           container file {
             description "Trace file information";
             leaf filename {
               description "Name of file in which to write trace information";
               type string {
                 length "1 .. 1024";
                 junos:posix-pattern "![/ %]";
                 junos:pattern-message "Must not contain '/', % or a space";
               }
             }
             leaf size {
               description "Maximum trace file size";
               type string;
             }
             leaf files {
               description "Maximum number of trace files";
               default "3";
               type union {
                 type string {
                   pattern "<.*>|$.*";
                 }
                 type uint32 {
                   range "2 .. 1000";
                 }
               }
             }
             choice world-readable-choice {
               leaf world-readable {
                 description "Allow any user to read the log file";
                 type empty;
               }
               leaf no-world-readable {
                 description "Don't allow any user to read the log file";
                 type empty;
               }
             }
             leaf match {
               description "Regular expression for lines to be logged";
               type jt:regular-expression;
             }
           }
         }
         container capture-file {
           description "Packet capture options";
           leaf filename {
             description "Capture file name";
             type string;
           }
           leaf format {
             description "Capture file format";
             type enumeration {
               enum "pcap" {
                 description "PCAP capture format";
               }
             }
           }
           leaf size {
             description "Maximum file size";
             type string;
           }
           leaf files {
             description "Maximum number of files";
             type union {
               type string {
                 pattern "<.*>|$.*";
               }
               type uint32 {
                 range "1 .. 10";
               }
             }
           }
           choice world-readable-choice {
             leaf world-readable {
               description "Allow any user to read packet-capture files";
               type empty;
             }
             leaf no-world-readable {
               description "Don't allow any user to read packet-capture files";
               type empty;
             }
           }
         }
         leaf maximum-capture-size {
           description "Max packet capture length";
           default "68";
           units "bytes";
           type union {
             type string {
               pattern "<.*>|$.*";
             }
             type uint32 {
               range "68 .. 10000";
             }
           }
         }
         list action-profile {
           key name;
           ordered-by user;
           description "Action profile definitions";
           uses e2e-action-profile;
         }
         list packet-filter {
           key name;
           ordered-by user;
           description "Packet filter configuration";
           max-elements 4;
           uses end-to-end-debug-filter;
         }
       }
       container user-identification {
         description "Configure user-identification";
         uses apply-advanced;
         container traceoptions {
           description "User-identification Tracing Options";
           uses apply-advanced;
           leaf no-remote-trace {
             description "Disable remote tracing";
             junos:must "(\"system tracing\")";
             junos:must-message "'no-remote-trace' is valid only when [system tracing] is configured";
             type empty;
           }
           container file {
             description "Trace file information";
             leaf filename {
               description "Name of file in which to write trace information";
               type string {
                 length "1 .. 1024";
                 junos:posix-pattern "![/ %]";
                 junos:pattern-message "Must not contain '/', % or a space";
               }
             }
             leaf size {
               description "Maximum trace file size";
               type string;
             }
             leaf files {
               description "Maximum number of trace files";
               default "3";
               type union {
                 type string {
                   pattern "<.*>|$.*";
                 }
                 type uint32 {
                   range "2 .. 1000";
                 }
               }
             }
             choice world-readable-choice {
               leaf world-readable {
                 description "Allow any user to read the log file";
                 type empty;
               }
               leaf no-world-readable {
                 description "Don't allow any user to read the log file";
                 type empty;
               }
             }
             leaf match {
               description "Regular expression for lines to be logged";
               type jt:regular-expression;
             }
           }
           list flag {
             key name;
             ordered-by user;
             description "Tracing parameters";
             leaf name {
               type enumeration {
                 enum "all" {
                   description "Trace everything";
                 }
               }
             }
           }
         }
         list authentication-source {
           key name;
           description "Configure user-identification authentication-source";
           uses authentication-source-type;
         }
       }
       container zones {
         description "Zone configuration";
         uses apply-advanced;
         container functional-zone {
           presence "enable functional-zone";
           description "Functional zone";
           container management {
             presence "enable management";
             description "Host for out of band management interfaces";
             uses apply-advanced;
             list interfaces {
               key name;
               ordered-by user;
               description "Interfaces that are part of this zone";
               uses zone-interface-list-type;
             }
             leaf screen {
               description "Name of ids option object applied to the zone";
               junos:must "(\"security screen ids-option $$\")";
               junos:must-message "referenced ids-object must be defined under [security screen ids-option]";
               type string {
                 length "1 .. 64";
               }
             }
             container host-inbound-traffic {
               description "Allowed system services & protocols";
               uses zone_host_inbound_traffic_t;
             }
             leaf description {
               description "Text description of zone";
               type string {
                 length "1 .. 900";
                 junos:posix-pattern "^[^&<>\n]+$";
                 junos:pattern-message "Must be a string excluding '&', '<', '>' and '\n'";
               }
             }
           }
         }
         list security-zone {
           key name;
           ordered-by user;
           description "Security zones";
           uses security-zone-type;
         }
       }
       leaf advanced-connection-tracking-timeout {
         description "System wide timeout value in seconds for advanced-connection-tracking entries";
         type union {
           type uint32;
           type string {
             pattern "<.*>|$.*";
           }
         }
       }
       container advance-policy-based-routing {
         presence "enable advance-policy-based-routing";
         description "Configure Network Security APBR Policies";
         uses apply-advanced;
         container traceoptions {
           description "Advance policy based routing tracing options";
           uses apply-advanced;
           leaf no-remote-trace {
             description "Disable remote tracing";
             junos:must "(\"system tracing\")";
             junos:must-message "'no-remote-trace' is valid only when [system tracing] is configured";
             type empty;
           }
           container file {
             description "Trace file information";
             leaf filename {
               description "Name of file in which to write trace information";
               type string {
                 length "1 .. 1024";
                 junos:posix-pattern "![/ %]";
                 junos:pattern-message "Must not contain '/', % or a space";
               }
             }
             leaf size {
               description "Maximum trace file size";
               type string;
             }
             leaf files {
               description "Maximum number of trace files";
               default "3";
               type union {
                 type string {
                   pattern "<.*>|$.*";
                 }
                 type uint32 {
                   range "2 .. 1000";
                 }
               }
             }
             choice world-readable-choice {
               leaf world-readable {
                 description "Allow any user to read the log file";
                 type empty;
               }
               leaf no-world-readable {
                 description "Don't allow any user to read the log file";
                 type empty;
               }
             }
             leaf match {
               description "Regular expression for lines to be logged";
               type jt:regular-expression;
             }
           }
           list flag {
             key name;
             ordered-by user;
             description "Tracing parameters";
             leaf name {
               type enumeration {
                 enum "configuration" {
                   description "Trace configuration events";
                 }
                 enum "lookup" {
                   description "Trace lookup events";
                 }
                 enum "compilation" {
                   description "Rule-sets compilation events";
                 }
                 enum "ipc" {
                   description "Inter-process communication events";
                 }
                 enum "all" {
                   description "Trace everything";
                 }
               }
             }
           }
         }
         container tunables {
           description "Configure advance policy based routing tunables";
           uses apply-advanced;
           leaf max-route-change {
             description "Maximum route change";
             default "1";
             type union {
               type string {
                 pattern "<.*>|$.*";
               }
               type uint32 {
                 range "0 .. 5";
               }
             }
           }
           leaf drop-on-zone-mismatch {
             description "Drop session if zone mismatches";
             type empty;
           }
           leaf no-l3l4-app-lookup {
             description "Ignore the look up for L3L4 custom app in APBR.";
             type empty;
           }
           leaf enable-logging {
             description "Enable AppTrack logging";
             type empty;
           }
         }
         list profile {
           key name;
           ordered-by user;
           description "Configure advance-policy-based-routing profile";
           leaf name {
             description "Advance policy based routing profile name";
             type string {
               length "1 .. 63";
             }
           }
           uses apply-advanced;
           list rule {
             key name;
             ordered-by user;
             description "Specify an advance policy based routing rule";
             uses apbr_rule_type;
           }
         }
         list active-probe-params {
           key name;
           ordered-by user;
           description "Active probe's settings";
           leaf name {
             description "Active probe setting name";
             type string {
               length "1 .. 63";
             }
           }
           uses apply-advanced;
           container settings {
             description "Settings";
             uses appqoe-probe-params;
           }
         }
         list metrics-profile {
           key name;
           ordered-by user;
           description "Configure metric profiles";
           leaf name {
             description "Profile name";
             type string {
               length "1 .. 63";
             }
           }
           uses apply-advanced;
           container sla-threshold {
             description "Configure SLA metric threshold";
             uses appqoe_sla_metric_profile;
           }
         }
         list underlay-interface {
           key name;
           ordered-by user;
           description "Underlay interface setting";
           status deprecated;
           leaf name {
             description "Underlay Interface name";
             type union {
               type jt:interface-device;
               type string {
                 pattern "<.*>|$.*";
               }
             }
           }
           uses apply-advanced;
           list unit {
             key name;
             description "One of more logical interface unit-numbers";
             leaf name {
               description "Unit number";
               type union {
                 type string {
                   pattern "<.*>|$.*";
                 }
                 type uint32 {
                   range "0 .. 1073741823";
                 }
               }
             }
             uses apply-advanced;
             leaf link-type {
               description "Link type of the interface";
               default "IP";
               type enumeration {
                 enum "IP" {
                   description "Select IP as the link-type";
                 }
                 enum "MPLS" {
                   description "Select MPLS as the link-type";
                 }
               }
             }
             leaf priority {
               description "Configure the priority for selecting this link";
               default "255";
               type union {
                 type string {
                   pattern "<.*>|$.*";
                 }
                 type uint8 {
                   range "1 .. 255";
                 }
               }
             }
             leaf speed {
               description "Speed of this link in Mbps";
               default "1000";
               type union {
                 type string {
                   pattern "<.*>|$.*";
                 }
                 type uint32 {
                   range "1 .. 1000000";
                 }
               }
             }
           }
         }
         list interface {
           key name;
           ordered-by user;
           description "Interface setting";
           junos:must "(!(\".. underlay-interface\"))";
           junos:must-message "interface knob cannot be configured along with underlay-interface";
           leaf name {
             description "Interface name";
             type union {
               type jt:interface-device;
               type string {
                 pattern "<.*>|$.*";
               }
             }
           }
           uses apply-advanced;
           list unit {
             key name;
             description "One of more logical interface unit-numbers";
             leaf name {
               description "Unit number";
               type union {
                 type string {
                   pattern "<.*>|$.*";
                 }
                 type uint32 {
                   range "0 .. 1073741823";
                 }
               }
             }
             uses apply-advanced;
             leaf link-tag {
               description "Configure link-tag. Default is IP";
               type string {
                 length "1 .. 63";
               }
             }
             leaf priority {
               description "Configure the priority for selecting this link";
               default "255";
               type union {
                 type string {
                   pattern "<.*>|$.*";
                 }
                 type uint8 {
                   range "1 .. 255";
                 }
               }
             }
             leaf multipath-bandwidth {
               description "Bandwidth of this link in Mbps";
               default "1000";
               type union {
                 type string {
                   pattern "<.*>|$.*";
                 }
                 type uint32 {
                   range "1 .. 1000000";
                 }
               }
             }
             leaf weight {
               description "Configure the weight for selecting this link";
               default "1";
               type union {
                 type string {
                   pattern "<.*>|$.*";
                 }
                 type uint8 {
                   range "1 .. 255";
                 }
               }
             }
           }
         }
         list overlay-path {
           key name;
           ordered-by user;
           description "List of overlay paths";
           leaf name {
             description "Create a single instance of overlay path";
             type string {
               length "1 .. 63";
             }
           }
           uses apply-advanced;
           container tunnel-path {
             description "Tunnel start & end ip addresses";
             presence "enable tunnel-path";
             uses appqoe-probe-path;
           }
           container probe-path {
             description "Probe start & end ip addresses";
             presence "enable probe-path";
             uses appqoe-probe-path;
           }
         }
         list destination-path-group {
           key name;
           ordered-by user;
           description "Group of tunnels to a particular destination";
           leaf name {
             description "Destination group name";
             type string {
               length "1 .. 63";
             }
           }
           uses apply-advanced;
           container probe-routing-instance {
             presence "enable probe-routing-instance";
             description "Set routing instance for the probe-path";
             uses apply-advanced;
             leaf routing-instance-name {
               description "Name of routing instance";
               type string;
             }
           }
           container inline-gre-encap {
             presence "enable inline-gre-encap";
             description "Enable inline GRE encapsulation";
           }
           container active-probe-properties {
             presence "enable active-probe-properties";
             description "Additional applicable properties for the destination path group";
             uses apply-advanced;
             leaf active-probe-only {
               description "Enable active probing only to the destination path group";
               type empty;
             }
           }
           list overlay-path {
             key name;
             ordered-by user;
             description "List of paths";
             max-elements 20;
             leaf name {
               description "Name of Overlay Path";
               type string;
             }
             uses apply-advanced;
           }
         }
         container sla-options {
           presence "enable sla-options";
           description "Global SLA options";
           uses apply-advanced;
           container local-route-switch {
             presence "enable local-route-switch";
             description "Enable/disable Automatic local route switching";
             status deprecated;
             uses apply-advanced;
             leaf switch-type {
               type enumeration {
                 enum "enabled" {
                   description "Enable";
                 }
                 enum "disabled" {
                   description "Disable";
                 }
               }
             }
           }
           container log {
             presence "enable log";
             description "Choose the logging mechanism";
             uses apply-advanced;
             leaf log-options {
               type enumeration {
                 enum "disabled" {
                   description "Disable logging";
                 }
                 enum "syslog" {
                   description "Choose syslog";
                 }
               }
             }
           }
           container log-type {
             presence "enable log-type";
             description "Choose the logging mechanism";
             status deprecated;
             uses apply-advanced;
             leaf log {
               type enumeration {
                 enum "disabled" {
                   description "Disable logging";
                 }
                 enum "syslog" {
                   description "Choose syslog";
                 }
               }
             }
           }
           container max-passive-probe-limit {
             presence "enable max-passive-probe-limit";
             description "Set max passive probe limits";
             uses apply-advanced;
             container number-of-probes {
               presence "enable number-of-probes";
               description "Number of passive probes to be sent";
               uses apply-advanced;
               leaf probes {
                 description "Number of probes";
                 default "5000";
                 type union {
                   type string {
                     pattern "<.*>|$.*";
                   }
                   type uint32 {
                     range "10 .. 5000";
                   }
                 }
               }
             }
             container interval {
               presence "enable interval";
               description "Interval within which to send";
               uses apply-advanced;
               leaf refresh-interval {
                 description "Interval in milli seconds";
                 default "500";
                 type union {
                   type string {
                     pattern "<.*>|$.*";
                   }
                   type uint32 {
                     range "500 .. 1000";
                   }
                 }
               }
             }
           }
           leaf dynamic-load-balancer {
             description "Enable dynamic load balancer";
             type empty;
           }
         }
         list sla-rule {
           key name;
           ordered-by user;
           description "Create SLA rule";
           leaf name {
             description "Set rule name";
             type string {
               length "1 .. 63";
             }
           }
           uses apply-advanced;
           container link-preferences {
             presence "enable link-preferences";
             junos:must "(!(any \"security advance-policy-based-routing sla-rule <*> link-type-affinity\"))";
             junos:must-message "link-preferences knob cannot be configured along with link-type-affinity";
             junos:must "(!(any \"security advance-policy-based-routing sla-rule <*> preferred-link-type\"))";
             junos:must-message "link-preferences knob cannot be configured along with preferred-link-type";
             description "Configure the link preferences";
             uses apply-advanced;
             leaf preferred-tag {
               description "Configure the link-tag preference";
               type string {
                 length "1 .. 63";
               }
             }
             leaf affinity {
               description "Configure the link-tag affinity";
               type enumeration {
                 enum "strict" {
                   description "Strict link-tag affinity";
                 }
               }
             }
           }
           leaf preferred-link-type {
             description "Configure the link-type preference";
             status deprecated;
             type enumeration {
               enum "IP" {
                 description "IP link-type preference";
                 status deprecated;
               }
               enum "MPLS" {
                 description "MPLS link-type preference";
                 status deprecated;
               }
               enum "Any" {
                 description "Any link-type preference";
                 status deprecated;
               }
             }
           }
           leaf link-type-affinity {
             description "Configure the link-type affinity";
             status deprecated;
             type enumeration {
               enum "strict" {
                 description "Strict link-type affinity";
                 status deprecated;
               }
             }
           }
           container switch-idle-time {
             presence "enable switch-idle-time";
             description "Idle timeout period where no SLA violation will be detected once path switch has happened";
             uses apply-advanced;
             leaf timeout {
               description "Idle timeout period (in seconds)";
               default "60";
               type union {
                 type string {
                   pattern "<.*>|$.*";
                 }
                 type uint32 {
                   range "5 .. 300";
                 }
               }
             }
           }
           container metrics-profile {
             presence "enable metrics-profile";
             junos:must "(\".. active-probe-params\")";
             junos:must-message "active-probe-params must exist for metrics-profile";
             description "Set metrics profile for the SLA";
             uses apply-advanced;
             leaf metrics-profile-name {
               description "Metrics Profile name";
               type string;
             }
           }
           container active-probe-params {
             presence "enable active-probe-params";
             junos:must "(\".. metrics-profile\")";
             junos:must-message "metrics-profile must exist for active-probe-params";
             description "Set Probe params for the overlay-path";
             uses apply-advanced;
             leaf probe-params-name {
               description "Probe parameter's name";
               type string;
             }
           }
           leaf type {
             description "Choose type of SLA";
             junos:must "((\".. active-probe-params\" && \".. metrics-profile\"))";
             junos:must-message "metrics-profile and active-probe-params must exist for saas type SLA";
             type enumeration {
               enum "saas" {
                 description "Choose SaaS probing for the SLA";
               }
             }
           }
           container passive-probe-params {
             presence "enable passive-probe-params";
             junos:must "((\".. active-probe-params\" && \".. metrics-profile\"))";
             junos:must-message "metrics-profile and active-probe-params must exist for passive-probe-params";
             description "Passive probe settings";
             uses apply-advanced;
             container sampling-percentage {
               presence "enable sampling-percentage";
               description "Mininmum percentage of Sessions to be evaluated for the application";
               uses apply-advanced;
               leaf percentage {
                 description "Percentage";
                 default "5";
                 type union {
                   type string {
                     pattern "<.*>|$.*";
                   }
                   type uint32 {
                     range "1 .. 100";
                   }
                 }
               }
             }
             container violation-count {
               presence "enable violation-count";
               description "Number of SLA violations within sampling period to be considered as a violation";
               status deprecated;
               uses apply-advanced;
               leaf count {
                 description "Violation Count";
                 default "5";
                 type union {
                   type string {
                     pattern "<.*>|$.*";
                   }
                   type uint32 {
                     range "1 .. 32";
                   }
                 }
               }
             }
             container sampling-period {
               presence "enable sampling-period";
               description "Time period in which the sampling is done";
               uses apply-advanced;
               leaf period {
                 description "Period (in milli-sec)";
                 default "5000";
                 type union {
                   type string {
                     pattern "<.*>|$.*";
                   }
                   type uint32 {
                     range "2000 .. 60000";
                   }
                 }
               }
             }
             container sla-export-factor {
               presence "enable sla-export-factor";
               description "Enabled sampling window based SLA exporting";
               uses apply-advanced;
               leaf factor {
                 description "No of sampling windows after which to report";
                 default "500";
                 type union {
                   type string {
                     pattern "<.*>|$.*";
                   }
                   type uint32 {
                     range "5 .. 1000";
                   }
                 }
               }
             }
             container type {
               presence "enable type";
               description "Choose type of SLA measurement";
               uses apply-advanced;
               leaf type-val {
                 type enumeration {
                   enum "book-ended" {
                     description "Choose custom method of probing within WAN link";
                   }
                 }
               }
             }
             container sampling-frequency {
               presence "enable sampling-frequency";
               description "Sampling frequency settings";
               uses apply-advanced;
               container interval {
                 presence "enable interval";
                 description "Time based sampling interval";
                 uses apply-advanced;
                 leaf sampling-interval {
                   description "Interval in milli seconds";
                   default "100";
                   type union {
                     type string {
                       pattern "<.*>|$.*";
                     }
                     type uint32 {
                       range "0 .. 500";
                     }
                   }
                 }
               }
               container ratio {
                 presence "enable ratio";
                 description "1:N based sampling ratio";
                 uses apply-advanced;
                 leaf sampling-ratio {
                   description "Value of N";
                   default "200";
                   type union {
                     type string {
                       pattern "<.*>|$.*";
                     }
                     type uint32 {
                       range "0 .. 10000";
                     }
                   }
                 }
               }
             }
           }
           container multipath-rule {
             description "Set AppBased Multipath Routing action";
             uses apply-advanced;
             leaf multipath-rule-name {
               description "Multipath action parameter's name";
               type string;
             }
           }
           container violation-count {
             presence "enable violation-count";
             description "Number of SLA violations within sampling period to be considered as a violation";
             uses apply-advanced;
             leaf count {
               description "Violation Count";
               default "5";
               type union {
                 type string {
                   pattern "<.*>|$.*";
                 }
                 type uint32 {
                   range "1 .. 32";
                 }
               }
             }
           }
         }
         list multipath-rule {
           key name;
           ordered-by user;
           description "APP based MULTIPATH Route Action's settings";
           leaf name {
             description "Multipath rule name";
             type string {
               length "1 .. 63";
             }
           }
           uses apply-advanced;
           leaf number-of-paths {
             description "No. of Paths in Multipath";
             default "2";
             type union {
               type string {
                 pattern "<.*>|$.*";
               }
               type uint32 {
                 range "2 .. 16";
               }
             }
           }
           leaf bandwidth-limit {
             description "Bandwidth limit (bps) on slowest link to avoid saturation (%)";
             default "50";
             type union {
               type string {
                 pattern "<.*>|$.*";
               }
               type uint32 {
                 range "1 .. 100";
               }
             }
           }
           leaf enable-reverse-wing {
             description "Packet copy enabled in reverse direction flow";
             type empty;
           }
           leaf-list application {
             ordered-by user;
             type string;
           }
           leaf-list application-group {
             ordered-by user;
             description "Specify dynamic application group name to match";
             type string;
           }
           leaf-list link-type {
             ordered-by user;
             description "List of underlay interface user defined link types";
             type string {
               length "1 .. 63";
             }
           }
           leaf-list link-preferences {
             ordered-by user;
             description "List of interface for link preferences";
             type union {
               type jt:interface-name;
               type string {
                 pattern "<.*>|$.*";
               }
             }
           }
         }
         list policy {
           key name;
           ordered-by user;
           description "Define a policy context from this zone";
           leaf name {
             description "Source zone";
             junos:must "((\".. .. .. .. security zones security-zone $$\" || \".. .. .. .. .. security zones security-zone $$\"))";
             junos:must-message "Security zone must be defined";
             type string {
               length "1 .. 63";
             }
           }
           uses apply-advanced;
           list policy {
             key name;
             ordered-by user;
             description "Define security policy in specified zone-to-zone direction";
             uses sla_policy_type;
           }
         }
       }
       container gtp {
         description "GPRS tunneling protocol configuration";
         uses gtp-object;
       }
       container sctp {
         description "GPRS stream control transmission protocol configuration";
         presence "enable sctp";
         uses sctp-object;
       }
       container ngfw {
         description "Next generation unified L4/L7 firewall";
         uses apply-advanced;
         container default-profile {
           description "Unified L4/L7 firewall default profile configuration";
           uses apply-advanced;
           container ssl-proxy {
             presence "enable ssl-proxy";
             description "SSL proxy services";
             uses apply-advanced;
             leaf profile-name {
               description "Specify SSL proxy service profile name";
               junos:must "(\"services ssl proxy profile $$\")";
               junos:must-message "Referenced SSL proxy profile is not defined";
               type string;
             }
           }
           container application-traffic-control {
             description "Application traffic control services";
             uses jsf_application_traffic_control_rule_set_type;
           }
         }
       }
       container tunnel-inspection {
         presence "enable tunnel-inspection";
         description "Security tunnel-inspection";
         uses apply-advanced;
         list inspection-profile {
           key name;
           ordered-by user;
           description "Security tunnel-inspection profile";
           max-elements 256;
           uses tunnel-inspection-profile-type;
         }
         list vni {
           key name;
           ordered-by user;
           description "Security tunnel inspection vni";
           max-elements 4096;
           uses tunnel-inspection-vni-type;
         }
         container traceoptions {
           description "Trace options for Network Security tunnel-inspection";
           uses apply-advanced;
           leaf no-remote-trace {
             description "Disable remote tracing";
             junos:must "(\"system tracing\")";
             junos:must-message "'no-remote-trace' is valid only when [system tracing] is configured";
             type empty;
           }
           container file {
             description "Trace file information";
             leaf filename {
               description "Name of file in which to write trace information";
               type string {
                 length "1 .. 1024";
                 junos:posix-pattern "![/ %]";
                 junos:pattern-message "Must not contain '/', % or a space";
               }
             }
             leaf size {
               description "Maximum trace file size";
               type string;
             }
             leaf files {
               description "Maximum number of trace files";
               default "3";
               type union {
                 type string {
                   pattern "<.*>|$.*";
                 }
                 type uint32 {
                   range "2 .. 1000";
                 }
               }
             }
             choice world-readable-choice {
               leaf world-readable {
                 description "Allow any user to read the log file";
                 type empty;
               }
               leaf no-world-readable {
                 description "Don't allow any user to read the log file";
                 type empty;
               }
             }
             leaf match {
               description "Regular expression for lines to be logged";
               type jt:regular-expression;
             }
           }
           list flag {
             key name;
             ordered-by user;
             description "Tracing parameters";
             leaf name {
               type enumeration {
                 enum "configuration" {
                   description "Trace configuration events";
                 }
                 enum "flow" {
                   description "Trace flow events";
                 }
                 enum "all" {
                   description "Trace everything";
                 }
               }
             }
           }
         }
       }
       container l3vpn {
         presence "enable l3vpn";
         uses apply-advanced;
         container traceoptions {
           description "Trace options for Network Security Vrf-group";
           uses apply-advanced;
           leaf no-remote-trace {
             description "Disable remote tracing";
             junos:must "(\"system tracing\")";
             junos:must-message "'no-remote-trace' is valid only when [system tracing] is configured";
             type empty;
           }
           container file {
             description "Trace file information";
             leaf filename {
               description "Name of file in which to write trace information";
               type string {
                 length "1 .. 1024";
                 junos:posix-pattern "![/ %]";
                 junos:pattern-message "Must not contain '/', % or a space";
               }
             }
             leaf size {
               description "Maximum trace file size";
               type string;
             }
             leaf files {
               description "Maximum number of trace files";
               default "3";
               type union {
                 type string {
                   pattern "<.*>|$.*";
                 }
                 type uint32 {
                   range "2 .. 1000";
                 }
               }
             }
             choice world-readable-choice {
               leaf world-readable {
                 description "Allow any user to read the log file";
                 type empty;
               }
               leaf no-world-readable {
                 description "Don't allow any user to read the log file";
                 type empty;
               }
             }
             leaf match {
               description "Regular expression for lines to be logged";
               type jt:regular-expression;
             }
           }
           list flag {
             key name;
             ordered-by user;
             description "Tracing parameters";
             leaf name {
               type enumeration {
                 enum "configuration" {
                   description "Trace configuration events";
                 }
                 enum "flow" {
                   description "Trace flow events";
                 }
                 enum "all" {
                   description "Trace everything";
                 }
               }
             }
           }
         }
         list vrf-group {
           key name;
           description "Configure vrf group";
           uses vrf-group-type;
         }
       }
       container cloud {
         presence "enable cloud";
         description "Configure Cloud security options";
         uses apply-advanced;
         container aws {
           description "Configure AWS security options";
           uses aws-object;
         }
         container high-availability {
           description "Configure AWS HA";
           uses ha-object;
         }
         container traceoptions {
           description "Configure cloudagent trace options";
           uses apply-advanced;
           container file {
             description "Trace file information";
             leaf filename {
               description "Name of file in which to write trace information";
               type string {
                 length "1 .. 64";
                 junos:posix-pattern "![/ %]";
                 junos:pattern-message "Must not contain '/', % or a space";
               }
             }
           }
           container level {
             description "Trace level";
             uses apply-advanced;
             choice level {
               case case_1 {
                 leaf error {
                   description "Error messages";
                   type empty;
                 }
               }
               case case_2 {
                 leaf brief {
                   description "Brief messages";
                   type empty;
                 }
               }
               case case_3 {
                 leaf detail {
                   description "Detail messages";
                   type empty;
                 }
               }
             }
           }
         }
       }
       container macsec {
         description "MAC Security configuration";
         uses security-macsec;
       }
     }
     container applications {
       description "Define applications by protocol characteristics";
       uses apply-advanced;
       list application {
         key name;
         ordered-by user;
         description "Define an application";
         uses application_object;
       }
       list application-set {
         key name;
         ordered-by user;
         description "Define an application set";
         uses application_set_object;
       }
     }
     container schedulers {
       description "Security scheduler";
       uses apply-advanced;
       list scheduler {
         key name;
         ordered-by user;
         description "Scheduler configuration";
         uses scheduler_object_type;
       }
     }
     container access {
       presence "enable access";
       uses apply-advanced;
       container firewall-authentication {
         description "Type of firewall authentication";
         uses apply-advanced;
         container pass-through {
           description "Pass-through firewall authentication settings";
           uses apply-advanced;
           leaf default-profile {
             description "Name of default profile";
             junos:must "((\"access profile $$\" || (\".. .. .. .. .. access profile $$\" && !(\".. .. .. .. .. access disable-tenant-access\"))))";
             junos:must-message "Profile must be defined in the [edit access profile] hierarchy or access to profile is disabled for tenants";
             type string {
               length "1 .. 250";
             }
           }
           container ftp {
             description "FTP banners";
             uses banner-object;
           }
           container telnet {
             description "Telnet banners";
             uses banner-object;
           }
           container http {
             description "HTTP banners";
             uses banner-object;
           }
         }
         container web-authentication {
           description "Web-authentication settings";
           uses apply-advanced;
           leaf default-profile {
             description "Name of profile to use for web-authentication";
             junos:must "((\"access profile $$\" || (\".. .. .. .. .. access profile $$\" && !(\".. .. .. .. .. access disable-tenant-access\"))))";
             junos:must-message "Profile must be defined in the [edit access profile] hierarchy or access to profile is disabled for tenants";
             type string {
               length "1 .. 250";
             }
           }
           container banner {
             uses apply-advanced;
             leaf success {
               description "The message that will be displayed on successful login";
               type string {
                 length "1 .. 250";
               }
             }
           }
           leaf timeout {
             description "Web-authentication timeout value in seconds";
             type union {
               type string {
                 pattern "<.*>|$.*";
               }
               type int32 {
                 range "5 .. 60";
               }
             }
           }
         }
         container traceoptions {
           description "Firewall authentication tracing options";
           uses apply-advanced;
           leaf no-remote-trace {
             description "Disable remote tracing";
             junos:must "(\"system tracing\")";
             junos:must-message "'no-remote-trace' is valid only when [system tracing] is configured";
             type empty;
           }
           container file {
             description "Trace file information";
             leaf filename {
               description "Name of file in which to write trace information";
               type string {
                 length "1 .. 1024";
                 junos:posix-pattern "![/ %]";
                 junos:pattern-message "Must not contain '/', % or a space";
               }
             }
             leaf size {
               description "Maximum trace file size";
               type string;
             }
             leaf files {
               description "Maximum number of trace files";
               default "3";
               type union {
                 type string {
                   pattern "<.*>|$.*";
                 }
                 type uint32 {
                   range "2 .. 1000";
                 }
               }
             }
             choice world-readable-choice {
               leaf world-readable {
                 description "Allow any user to read the log file";
                 type empty;
               }
               leaf no-world-readable {
                 description "Don't allow any user to read the log file";
                 type empty;
               }
             }
             leaf match {
               description "Regular expression for lines to be logged";
               type jt:regular-expression;
             }
           }
           list flag {
             key name;
             ordered-by user;
             description "Tracing parameters";
             leaf name {
               type enumeration {
                 enum "configuration" {
                   description "Trace configuration events";
                 }
                 enum "setup" {
                   description "Trace setup of firewall authentication service";
                 }
                 enum "authentication" {
                   description "Trace authentication events";
                 }
                 enum "all" {
                   description "Trace with all flags enabled";
                 }
               }
             }
           }
         }
       }
       list profile {
         key name;
         ordered-by user;
         description "Set of attributes that define access";
         leaf name {
           description "Profile name";
           type string {
             length "1 .. 63";
           }
         }
         uses apply-advanced;
         leaf-list accounting-order {
           ordered-by user;
           description "Order in which accounting mechanisms are used";
           junos:must "(!(any \".. client <*> l2tp\"))";
           junos:must-message "Not supported in tunnel client profile configuration";
           junos:must "(!(any \".. client <*> ike\"))";
           junos:must-message "Not supported in IKE configuration";
           type enumeration {
             enum "radius" {
               description "Remote Authentication Dial-In User Service";
             }
           }
         }
         leaf-list authentication-order {
           ordered-by user;
           description "Order in which authentication mechanisms are used";
           junos:must "(!(any \".. client <*> ike\"))";
           junos:must-message "Not supported in IKE configuration";
           type enumeration {
             enum "radius" {
               description "Remote Authentication Dial-In User Service";
               junos:must "(!(any \".. .. client <*> l2tp\"))";
               junos:must-message "Authentication-order cannot include RADIUS for tunnel client profile";
             }
             enum "password" {
               description "Locally configured password in access profile";
             }
             enum "none" {
               description "No authentication performed";
             }
             enum "nasreq" {
               description "Diameter based authentication and authorization using NASREQ application protocol";
             }
             enum "nas-5g" {
               description "Authentication and authorization using 3GPP N1 and N2 signaling";
             }
             enum "ldap" {
               description "Lightweight Directory Access Protocol";
               junos:must "((!(any \".. .. client <*> l2tp\") && !(any \".. .. client <*> ppp\")))";
               junos:must-message "Authentication-order cannot include LDAP for tunnel, ppp client profile";
               junos:must "((!(\".. .. authentication-order $$={radius}\") && (!(\".. .. authentication-order $$={securid}\") && !(\".. .. authentication-order $$={s6a}\"))))";
               junos:must-message "Only one of ldap, radius, ecurid or s6a can be specified";
             }
             enum "securid" {
               description "RSA SecurID Authentication";
               junos:must "((!(any \".. .. client <*> l2tp\") && !(any \".. .. client <*> ppp\")))";
               junos:must-message "Authentication-order cannot include securid for tunnel, ppp client profile";
               junos:must "((!(\".. .. authentication-order $$={radius}\") && (!(\".. .. authentication-order $$={ldap}\") && !(\".. .. authentication-order $$={s6a}\"))))";
               junos:must-message "Only one of ldap, radius, securid or s6a can be specified";
             }
             enum "s6a" {
               description "S6a Authentication";
               junos:must "((!(any \".. .. client <*> l2tp\") && !(any \".. .. client <*> ppp\")))";
               junos:must-message "Authentication-order cannot include S6A for tunnel, ppp client profile";
               junos:must "((!(\".. .. authentication-order $$={radius}\") && (!(\".. .. authentication-order $$={securid}\") && !(\".. .. authentication-order $$={ldap}\"))))";
               junos:must-message "Only one of ldap, radius, securid or s6a can be specified";
             }
           }
         }
         leaf-list authorization-order {
           ordered-by user;
           description "Order in which authorization mechanisms are used";
           type enumeration {
             enum "jsrc" {
               description "Diameter based authorization using Juniper's SRC application protocol";
             }
             enum "nasreq" {
               description "Diameter based authorization using NASREQ application protocol";
             }
             enum "none" {
               description "No authorization performed";
             }
           }
         }
         leaf provisioning-order {
           description "Order in which provisioning mechanisms are used";
           type enumeration {
             enum "jsrc" {
               description "Address authorization via SRC";
             }
             enum "gx-plus" {
               description "Policy/service provisioning via GXPLUS";
             }
             enum "pcrf" {
               description "Policy/service provisioning via PCRF";
             }
           }
         }
         leaf-list preauthentication-order {
           ordered-by user;
           description "Order in which preauthentication mechanisms are used";
           junos:must "(!(\".. radius attributes exclude calling-station-id access-request\"))";
           junos:must-message "calling-station-id is excluded from access request";
           type enumeration {
             enum "radius" {
               description "Remote Authentication Dial-In User Service";
             }
           }
         }
         leaf-list charging-service-list {
           ordered-by user;
           description "List of used 3gpp charging servicess";
           junos:must "(\".. provisioning-order pcrf\")";
           junos:must-message "charging-service-list requires provisioning-order pcrf";
           junos:must "(!(\".. service accounting-order\"))";
           junos:must-message "charging-service-list is mutually exclusive with service accounting";
           type enumeration {
             enum "ocs" {
               description "Online charging service";
             }
           }
         }
         list domain-name-server {
           key name;
           ordered-by user;
           description "Default DNS server's IPv4 address";
           leaf name {
             description "Address";
             type jt:ipv4addr;
           }
           uses apply-advanced;
         }
         list domain-name-server-inet {
           key name;
           ordered-by user;
           description "DNS server's IPv4 address";
           leaf name {
             description "Address";
             type jt:ipv4addr;
           }
           uses apply-advanced;
         }
         list domain-name-server-inet6 {
           key name;
           ordered-by user;
           description "DNS server's IPv6 address";
           leaf name {
             description "Address";
             type jt:ipv6addr;
           }
           uses apply-advanced;
         }
         list wins-server {
           key name;
           ordered-by user;
           description "Default WINS server's IPv4 address";
           leaf name {
             description "Address";
             type jt:ipv4addr;
           }
           uses apply-advanced;
         }
         list client {
           key name;
           description "Entity requesting access";
           junos:must "(((!(any \". <*> l2tp\") || !(any \". <*> ppp\")) && ((!(any \". <*> l2tp\") || !(any \". <*> ike\")) && (!(any \". <*> ike\") || !(any \". <*> ppp\")))))";
           junos:must-message "All clients in one profile must be either PPP or L2TP or IKE";
           uses access-client-object;
         }
         container address-assignment {
           description "Address assignment pool";
           uses apply-advanced;
           leaf pool {
             description "Name of address-assignment pool";
             type string {
               length "1 .. 63";
             }
           }
           leaf inet6-pool {
             description "Name of address-assignment pool for family inet6";
             type string {
               length "1 .. 63";
             }
           }
         }
         leaf session-limit-per-username {
           description "Maximum number of sessions allowed per username";
           type union {
             type string {
               pattern "<.*>|$.*";
             }
             type uint32 {
               range "1 .. 16";
             }
           }
         }
         container local {
           description "Set configuration for local reporting - obsolete config";
           status deprecated;
           uses apply-advanced;
           leaf flat-file-profile {
             description "Specifies that the service accounting will be reported as per flat-file profile";
             junos:must "(\"accounting-options flat-file-profile $$\")";
             junos:must-message "referenced flat-file-profile must be defined in accounting-options";
             type string;
           }
         }
         container radius {
           description "Set of RADIUS configurations";
           uses apply-advanced;
           leaf-list authentication-server {
             ordered-by user;
             description "The authentication server list to use in the specified order to send authentication messages";
             type jt:ipaddr;
           }
           leaf-list accounting-server {
             ordered-by user;
             description "The accounting server list to use in the specified order to send accounting messages";
             type jt:ipaddr;
           }
           leaf-list preauthentication-server {
             ordered-by user;
             description "The preauthentication server list to use in the specified order to send preauthentication messages";
             type jt:ipv4addr;
           }
           leaf authentication-server-name {
             description "The authentication server to use to send authentication messages";
             junos:must "(!(\".. authentication-server\"))";
             junos:must-message "cannot have both authentication-server and authentication-server-name";
             junos:must "((\"access radius-server-name $$\" || \".. .. radius-server-name $$\"))";
             junos:must-message "referenced radius-server-name must be defined";
             type string {
               length "4 .. 255";
             }
           }
           leaf accounting-server-name {
             description "The accounting server to use to send accounting messages";
             junos:must "(!(\".. accounting-server\"))";
             junos:must-message "cannot have both accounting-server and accounting-server-name";
             junos:must "((\"access radius-server-name $$\" || \".. .. radius-server-name $$\"))";
             junos:must-message "referenced radius-server-name must be defined";
             type string {
               length "4 .. 255";
             }
           }
           container options {
             description "Specifies the RADIUS options";
             uses apply-advanced;
             leaf ethernet-port-type-virtual {
               description "Type of physical port to authenticate the user is virtual (RADIUS attribute 61)";
               type empty;
             }
             container interface-description-format {
               description "Interface description in the NAS-port-ID attribute";
               uses apply-advanced;
               leaf exclude-sub-interface {
                 description "Exclude sub-interface from interface description";
                 type empty;
               }
               leaf exclude-adapter {
                 description "Exclude adapter from interface description";
                 type empty;
               }
               leaf exclude-channel {
                 description "Exclude channel from interface description";
                 type empty;
               }
             }
             leaf nas-identifier {
               description "NAS-Identifier to be used for authentication and accounting requests (RADIUS attribute 32)";
               type string {
                 length "1 .. 64";
               }
             }
             container nas-port-extended-format {
               description "RADIUS client's use of an extended format for RADIUS attribute 5";
               uses apply-advanced;
               leaf ae-width {
                 description "Number of bits for the aggregated ethernet identifier field";
                 units "bits";
                 type union {
                   type string {
                     pattern "<.*>|$.*";
                   }
                   type uint32 {
                     range "0 .. 32";
                   }
                 }
               }
               leaf slot-width {
                 description "Number of bits for the slot field";
                 units "bits";
                 type union {
                   type string {
                     pattern "<.*>|$.*";
                   }
                   type uint32 {
                     range "0 .. 32";
                   }
                 }
               }
               leaf adapter-width {
                 description "Number of bits for the adapter field";
                 units "bits";
                 type union {
                   type string {
                     pattern "<.*>|$.*";
                   }
                   type uint32 {
                     range "0 .. 32";
                   }
                 }
               }
               leaf port-width {
                 description "Number of bits for the port field";
                 units "bits";
                 type union {
                   type string {
                     pattern "<.*>|$.*";
                   }
                   type uint32 {
                     range "0 .. 32";
                   }
                 }
               }
               leaf pw-width {
                 description "Number of bits for the pseudo-wire field";
                 units "bits";
                 type union {
                   type string {
                     pattern "<.*>|$.*";
                   }
                   type uint32 {
                     range "0 .. 32";
                   }
                 }
               }
               leaf stacked-vlan-width {
                 description "Number of bits for the S-VLAN subinterface field";
                 units "bits";
                 type union {
                   type string {
                     pattern "<.*>|$.*";
                   }
                   type uint32 {
                     range "0 .. 32";
                   }
                 }
               }
               leaf vlan-width {
                 description "Number of bits for the VLAN subinterface field";
                 units "bits";
                 type union {
                   type string {
                     pattern "<.*>|$.*";
                   }
                   type uint32 {
                     range "0 .. 32";
                   }
                 }
               }
               container atm {
                 description "ATM specific parameters for NAS Port";
                 uses apply-advanced;
                 leaf slot-width {
                   description "Number of bits for the ATM slot field";
                   units "bits";
                   type union {
                     type string {
                       pattern "<.*>|$.*";
                     }
                     type uint32 {
                       range "0 .. 32";
                     }
                   }
                 }
                 leaf adapter-width {
                   description "Number of bits for the ATM adapter field";
                   units "bits";
                   type union {
                     type string {
                       pattern "<.*>|$.*";
                     }
                     type uint32 {
                       range "0 .. 32";
                     }
                   }
                 }
                 leaf port-width {
                   description "Number of bits for the ATM port field";
                   units "bits";
                   type union {
                     type string {
                       pattern "<.*>|$.*";
                     }
                     type uint32 {
                       range "0 .. 32";
                     }
                   }
                 }
                 leaf vpi-width {
                   description "Number of bits for the ATM VPI field";
                   units "bits";
                   type union {
                     type string {
                       pattern "<.*>|$.*";
                     }
                     type uint32 {
                       range "0 .. 32";
                     }
                   }
                 }
                 leaf vci-width {
                   description "Number of bits for the ATM VCI field";
                   units "bits";
                   type union {
                     type string {
                       pattern "<.*>|$.*";
                     }
                     type uint32 {
                       range "0 .. 32";
                     }
                   }
                 }
               }
             }
             leaf nas-port-id-delimiter {
               description "Single character delimiter character to use in the NAS-Port-Id";
               type string {
                 length 1;
               }
             }
             container nas-port-id-format {
               description "Format methods for building the NAS-Port-Id radius attribute";
               uses apply-advanced;
               leaf nas-identifier {
                 description "Include the nas-identifier value";
                 type empty;
               }
               leaf interface-description {
                 description "Include the interface-description value";
                 type empty;
               }
               leaf agent-circuit-id {
                 description "Include (ACI) agent-circuit-id value";
                 type empty;
               }
               leaf agent-remote-id {
                 description "Include (ARI) agent-remote-id value";
                 type empty;
               }
               leaf postpend-vlan-tags {
                 description "Include the vlan tag(s) using :<outer>-<inner>";
                 type empty;
               }
               leaf interface-text-description {
                 description "Include the interfaces description string";
                 type empty;
               }
               leaf-list concatenated-vlan-tags {
                 ordered-by user;
                 description "Include the vlan tag(s) as a concatenated string";
                 type enumeration {
                   enum "fixed-size-outer-tag" {
                     description "Fixed size outer VLAN tag value of 4 octets";
                   }
                   enum "fixed-size-inner-tag" {
                     description "Fixed size inner VLAN tag value of 4 octets";
                   }
                 }
               }
               leaf-list order {
                 ordered-by user;
                 description "Order of options for appearance in the NAS-Port-Id string";
                 junos:must "((!(\".. nas-identifier\") && (!(\".. interface-description\") && (!(\".. agent-circuit-id\") && (!(\".. agent-remote-id\") && (!(\".. postpend-vlan-tags\") && (!(\".. concatenated-vlan-tags\") && !(\".. interface-text-description\"))))))))";
                 junos:must-message "Order is mutually exclusive with other nas-port-id-format options";
                 type enumeration {
                   enum "nas-identifier" {
                     description "Include the nas-identifier value";
                   }
                   enum "agent-circuit-id" {
                     description "Include (ACI) agent-circuit-id value";
                   }
                   enum "agent-remote-id" {
                     description "Include (ARI) agent-remote-id value";
                   }
                   enum "interface-description" {
                     description "Include the interface-description value";
                   }
                   enum "interface-text-description" {
                     description "Include the interface's description string";
                   }
                   enum "postpend-vlan-tags" {
                     description "Include the vlan tag(s) using :<outer>-<inner>";
                   }
                 }
               }
             }
             container nas-port-type {
               description "Translation mechanism for changing the NAS-Port-Type radius attribute";
               uses apply-advanced;
               leaf ethernet {
                 description "Translation mechanism for changing the Ethernet value";
                 type string;
               }
             }
             leaf calling-station-id-delimiter {
               description "Single character separator for calling-station-id";
               type string {
                 length 1;
               }
             }
             container calling-station-id-format {
               description "Format method for building the calling-station-id";
               uses apply-advanced;
               leaf nas-identifier {
                 description "Include the nas-identifier value";
                 type empty;
               }
               leaf interface-description {
                 description "Include the interface-description value";
                 type empty;
               }
               leaf agent-circuit-id {
                 description "Include agent-circuit-id value";
                 type empty;
               }
               leaf agent-remote-id {
                 description "Include agent-remote-id value";
                 type empty;
               }
               leaf mac-address {
                 description "Include mac-address value";
                 type empty;
               }
               leaf interface-text-description {
                 description "Include the interfaces description string";
                 type empty;
               }
               leaf stacked-vlan {
                 description "Include the stacked vlan tag value";
                 type empty;
               }
               leaf vlan {
                 description "Include the vlan tag value";
                 type empty;
               }
             }
             leaf remote-circuit-id-delimiter {
               description "Single delimiter character to use in the remote-circuit-id";
               type string {
                 length 1;
               }
             }
             container remote-circuit-id-format {
               description "Format method for building the remote-circuit-id attribute";
               uses apply-advanced;
               leaf agent-circuit-id {
                 description "Include agent-circuit-id (ACI) value";
                 type empty;
               }
               leaf agent-remote-id {
                 description "Include agent-remote-id (ARI) value";
                 type empty;
               }
             }
             leaf remote-circuit-id-fallback {
               description "Configure the fallback for remote-circuit-id attribute";
               junos:must "(\".. override\")";
               junos:must-message "override calling-station-id option must be configured";
               type enumeration {
                 enum "default" {
                   description "Fallback to default underlying-interface";
                 }
                 enum "configured-calling-station-id" {
                   description "Fallback to configured calling-station-id";
                 }
               }
             }
             container override {
               description "Configure RADIUS to override the standard use of an attribute";
               uses apply-advanced;
               container calling-station-id {
                 description "Configure RADIUS value for calling-station-id attribute";
                 leaf remote-circuit-id {
                   description "Configure RADIUS to use remote-circuit-id";
                   junos:must "(\".. .. .. remote-circuit-id-format\")";
                   junos:must-message "remote-circuit-id-format must be configured";
                   type empty;
                 }
               }
               leaf nas-port {
                 description "Configure override RADIUS nas-port with";
                 type enumeration {
                   enum "tunnel-client-nas-port" {
                     description "Tunnel-client-nas-port";
                   }
                 }
               }
               leaf nas-port-type {
                 description "Configure override RADIUS nas-port-type with";
                 type enumeration {
                   enum "tunnel-client-nas-port-type" {
                     description "Tunnel-client-nas-port-type";
                   }
                 }
               }
               leaf nas-ip-address {
                 description "Configure override RADIUS nas-ip-address with";
                 type enumeration {
                   enum "tunnel-client-gateway-address" {
                     description "Tunnel-client-gateway-address";
                   }
                 }
               }
             }
             leaf accounting-session-id-format {
               description "Decimal format or description format for the accounting session ID";
               type enumeration {
                 enum "decimal" {
                   description "Decimal-session-identifier";
                 }
                 enum "description" {
                   description "Description Format: <jnpr> <interface-type> <interface-specifier>:<session-identifier>";
                 }
               }
             }
             leaf accounting-session-id-strict {
               description "Enforce exact match of accounting-session-id in CoA processing";
               type empty;
             }
             leaf revert-interval {
               description "Time after which to revert to primary server";
               units "seconds";
               type union {
                 type string {
                   pattern "<.*>|$.*";
                 }
                 type uint32 {
                   range "0 .. 604800";
                 }
               }
             }
             leaf vlan-nas-port-stacked-format {
               description "Include the S-VLAN ID, in addition to the VLAN ID, for subscribers on Ethernet interfaces";
               type empty;
             }
             leaf client-authentication-algorithm {
               description "Algorithm to access the RADIUS servers for authentication";
               type enumeration {
                 enum "direct" {
                   description "Contacts the first AAA server on the list for each request, the second AAA server if the first one fails, and so on";
                 }
                 enum "round-robin" {
                   description "Contacts the first AAA server for the first request, the second AAA server for the second request, and so on";
                 }
               }
             }
             leaf client-accounting-algorithm {
               description "Algorithm to access the RADIUS servers for accounting";
               type enumeration {
                 enum "direct" {
                   description "Contacts the first AAA server on the list for each request, the second AAA server if the first one fails, and so on";
                 }
                 enum "round-robin" {
                   description "Contacts the first AAA server for the first request, the second AAA server for the second request, and so on";
                 }
               }
             }
             leaf juniper-access-line-attributes {
               description "Include the Juniper (IANA 4874) access line VSAs in requests to RADIUS servers";
               type empty;
             }
             container ip-address-change-notify {
               presence "enable ip-address-change-notify";
               junos:must "(\".. .. .. accounting address-change-immediate-update\")";
               junos:must-message "address-change-immediate-update must be configured";
               description "Include IPv4-Release-Control VSA (26-164) in requests to RADIUS server";
               leaf message {
                 description "Message to be added in IPv4-Release-Control VSA (26-164)";
                 type string {
                   length "1 .. 32";
                 }
               }
             }
             leaf coa-dynamic-variable-validation {
               description "Enable strict dynamic variable validation (no undefined variable) in CoA processing";
               type empty;
             }
             leaf chap-challenge-in-request-authenticator {
               description "Use 16-byte CHAP challenge as Request Authenticator";
               type empty;
             }
             container service-activation {
               description "Service activation requirement for successful login";
               uses apply-advanced;
               leaf extensible-service {
                 description "Service activation of extensible services requirement for successful login";
                 default "optional-at-login";
                 type enumeration {
                   enum "required-at-login" {
                     description "Service activation must succeed to allow subscriber login";
                   }
                   enum "optional-at-login" {
                     description "Service activation success is not required to allow subscriber login";
                   }
                 }
               }
               leaf dynamic-profile {
                 description "Service activation of dynamic-profile services requirement for successful login";
                 default "required-at-login";
                 type enumeration {
                   enum "required-at-login" {
                     description "Service activation must succeed to allow subscriber login";
                   }
                   enum "optional-at-login" {
                     description "Service activation success is not required to allow subscriber login";
                   }
                 }
               }
             }
             leaf accounting-username-original {
               description "Use orignal (un-modified) username in accounting messages";
               type empty;
             }
           }
           container attributes {
             description "Specifies how RADIUS attributes should be handled";
             uses apply-advanced;
             container ignore {
               description "Ignores the specified attribute in RADIUS Access-Accept messages";
               uses apply-advanced;
               leaf output-filter {
                 description "Juniper (IANA 4874) Output-filter / Egress-Policy-Name (VSA 26-11)";
                 type empty;
               }
               leaf input-filter {
                 description "Juniper (IANA 4874) Input-filter / Ingress-Policy-Name (VSA 26-10)";
                 type empty;
               }
               leaf framed-ip-netmask {
                 description "Framed-IP-Netmask (attribute 9)";
                 type empty;
               }
               leaf logical-system-routing-instance {
                 description "Juniper (IANA 4874) Logical-system-routing-instance / Virtual-Router (VSA 26-1)";
                 type empty;
               }
               leaf dynamic-iflset-name {
                 description "Juniper (IANA 4874) Dynamic interface set / Qos-Set-Name (VSA 26-130)";
                 type empty;
               }
               leaf idle-timeout {
                 description "Idle-Timeout (attribute 28)";
                 type empty;
               }
               leaf session-timeout {
                 description "Session-Timeout (attribute 27)";
                 type empty;
               }
               leaf-list standard-attribute {
                 ordered-by user;
                 description "RADIUS standard attribute number";
                 type union {
                   type string {
                     pattern "<.*>|$.*";
                   }
                   type uint32 {
                     range "1 .. 255";
                   }
                 }
               }
               list vendor-id {
                 key name;
                 ordered-by user;
                 description "Specify the vendor-identifier for a vendor-specific attribute (VSA)";
                 leaf name {
                   description "Vendor IANA enterprise number";
                   type union {
                     type string {
                       pattern "<.*>|$.*";
                     }
                     type uint32 {
                       range "1 .. 16777215";
                     }
                   }
                 }
                 uses apply-advanced;
                 leaf-list vendor-attribute {
                   ordered-by user;
                   description "Vendor specific attribute number";
                   type union {
                     type string {
                       pattern "<.*>|$.*";
                     }
                     type uint32 {
                       range "1 .. 255";
                     }
                   }
                 }
               }
             }
             container exclude {
               description "Configures the exclusion of RADIUS attributes in RADIUS messages";
               uses apply-advanced;
               list standard-attribute {
                 key name;
                 ordered-by user;
                 description "Specify RADIUS standard attribute number";
                 leaf name {
                   description "RADIUS standard attribute number";
                   type union {
                     type string {
                       pattern "<.*>|$.*";
                     }
                     type uint32 {
                       range "1 .. 255";
                     }
                   }
                 }
                 uses apply-advanced;
                 leaf-list packet-type {
                   ordered-by user;
                   description "Specify packet types to be excluded";
                   type enumeration {
                     enum "access-request" {
                       description "RADIUS Access-Request message";
                     }
                     enum "accounting-on" {
                       description "RADIUS Accounting-On Message";
                     }
                     enum "accounting-off" {
                       description "RADIUS Accounting-Off message";
                     }
                     enum "accounting-start" {
                       description "RADIUS Accounting-Start message";
                     }
                     enum "accounting-stop" {
                       description "RADIUS Accounting-Stop message";
                     }
                   }
                 }
               }
               list vendor-id {
                 key name;
                 ordered-by user;
                 description "Specify the vendor-identifier for a vendor-specific attribute (VSA)";
                 leaf name {
                   description "Vendor IANA enterprise number";
                   type union {
                     type string {
                       pattern "<.*>|$.*";
                     }
                     type uint32 {
                       range "1 .. 16777215";
                     }
                   }
                 }
                 uses apply-advanced;
                 list vendor-attribute {
                   key name;
                   ordered-by user;
                   description "Specify vendor specific attribute number";
                   leaf name {
                     description "Vendor specific attribute number";
                     type union {
                       type string {
                         pattern "<.*>|$.*";
                       }
                       type uint32 {
                         range "1 .. 255";
                       }
                     }
                   }
                   uses apply-advanced;
                   leaf-list packet-type {
                     ordered-by user;
                     description "Specify packet types to be excluded";
                     type enumeration {
                       enum "access-request" {
                         description "RADIUS Access-Request message";
                       }
                       enum "accounting-on" {
                         description "RADIUS Accounting-On Message";
                       }
                       enum "accounting-off" {
                         description "RADIUS Accounting-Off message";
                       }
                       enum "accounting-start" {
                         description "RADIUS Accounting-Start message";
                       }
                       enum "accounting-stop" {
                         description "RADIUS Accounting-Stop message";
                       }
                     }
                   }
                 }
               }
               leaf-list accounting-authentic {
                 ordered-by user;
                 description "Excludes RADIUS attribute 45, Acct-Authentic";
                 type enumeration {
                   enum "accounting-on" {
                     description "RADIUS Accounting-On Message";
                   }
                   enum "accounting-off" {
                     description "RADIUS Accounting-Off message";
                   }
                   enum "accounting-start" {
                     description "RADIUS Accounting-Start message";
                   }
                   enum "accounting-stop" {
                     description "RADIUS Accounting-Stop message";
                   }
                 }
               }
               leaf-list accounting-delay-time {
                 ordered-by user;
                 description "Excludes RADIUS attribute 41, Acct-Delay-Time";
                 type enumeration {
                   enum "accounting-on" {
                     description "RADIUS Accounting-On Message";
                   }
                   enum "accounting-off" {
                     description "RADIUS Accounting-Off message";
                   }
                   enum "accounting-start" {
                     description "RADIUS Accounting-Start message";
                   }
                   enum "accounting-stop" {
                     description "RADIUS Accounting-Stop message";
                   }
                 }
               }
               leaf-list accounting-session-id {
                 ordered-by user;
                 description "Excludes RADIUS attribute 44, Acct-Session-ID";
                 type enumeration {
                   enum "access-request" {
                     description "RADIUS Access-Request message";
                   }
                 }
               }
               leaf-list accounting-terminate-cause {
                 ordered-by user;
                 description "Excludes RADIUS attribute 49, Acct-Terminate-Cause";
                 type enumeration {
                   enum "accounting-off" {
                     description "RADIUS Accounting-Off message";
                   }
                 }
               }
               leaf-list called-station-id {
                 ordered-by user;
                 description "Excludes RADIUS attribute 30, Called-Station-ID";
                 type enumeration {
                   enum "access-request" {
                     description "RADIUS Access-Request message";
                   }
                   enum "accounting-start" {
                     description "RADIUS Accounting-Start message";
                   }
                   enum "accounting-stop" {
                     description "RADIUS Accounting-Stop message";
                   }
                 }
               }
               leaf-list calling-station-id {
                 ordered-by user;
                 description "Excludes RADIUS attribute 31, Calling-Station-ID";
                 type enumeration {
                   enum "access-request" {
                     description "RADIUS Access-Request message";
                     junos:must "(!(\".. .. .. .. .. preauthentication-order\"))";
                     junos:must-message "Preauthentication-order and exclude calling-station-id in access-request are mutually exclusive";
                   }
                   enum "accounting-start" {
                     description "RADIUS Accounting-Start message";
                   }
                   enum "accounting-stop" {
                     description "RADIUS Accounting-Stop message";
                   }
                 }
               }
               leaf-list class {
                 ordered-by user;
                 description "Excludes RADIUS attribute 25, Class";
                 type enumeration {
                   enum "accounting-start" {
                     description "RADIUS Accounting-Start message";
                   }
                   enum "accounting-stop" {
                     description "RADIUS Accounting-Stop message";
                   }
                 }
               }
               leaf-list delegated-ipv6-prefix {
                 ordered-by user;
                 description "Excludes RADIUS attribute 123, Delegated-IPv6-Prefix";
                 type enumeration {
                   enum "accounting-start" {
                     description "RADIUS Accounting-Start message";
                   }
                   enum "accounting-stop" {
                     description "RADIUS Accounting-Stop message";
                   }
                 }
               }
               leaf-list dhcp-options {
                 ordered-by user;
                 description "Excludes RADIUS attribute 26-55, DHCP-Options";
                 type enumeration {
                   enum "access-request" {
                     description "RADIUS Access-Request message";
                   }
                   enum "accounting-start" {
                     description "RADIUS Accounting-Start message";
                   }
                   enum "accounting-stop" {
                     description "RADIUS Accounting-Stop message";
                   }
                 }
               }
               leaf-list dhcp-gi-address {
                 ordered-by user;
                 description "Excludes RADIUS attribute 26-57, DHCP-GI-Address";
                 type enumeration {
                   enum "access-request" {
                     description "RADIUS Access-Request message";
                   }
                   enum "accounting-start" {
                     description "RADIUS Accounting-Start message";
                   }
                   enum "accounting-stop" {
                     description "RADIUS Accounting-Stop message";
                   }
                 }
               }
               leaf-list dhcp-mac-address {
                 ordered-by user;
                 description "Excludes RADIUS attribute 26-56, DHCP-MAC-Address";
                 type enumeration {
                   enum "access-request" {
                     description "RADIUS Access-Request message";
                   }
                   enum "accounting-start" {
                     description "RADIUS Accounting-Start message";
                   }
                   enum "accounting-stop" {
                     description "RADIUS Accounting-Stop message";
                   }
                 }
               }
               leaf-list output-filter {
                 ordered-by user;
                 description "Excludes RADIUS attribute 26-11, Egress-Policy-Name";
                 type enumeration {
                   enum "accounting-start" {
                     description "RADIUS Accounting-Start message";
                   }
                   enum "accounting-stop" {
                     description "RADIUS Accounting-Stop message";
                   }
                 }
               }
               leaf-list event-time-stamp {
                 ordered-by user;
                 description "Excludes RADIUS attribute 55, Event-Timestamp";
                 type enumeration {
                   enum "accounting-on" {
                     description "RADIUS Accounting-On Message";
                   }
                   enum "accounting-off" {
                     description "RADIUS Accounting-Off message";
                   }
                   enum "accounting-start" {
                     description "RADIUS Accounting-Start message";
                   }
                   enum "accounting-stop" {
                     description "RADIUS Accounting-Stop message";
                   }
                 }
               }
               leaf-list filter-id {
                 ordered-by user;
                 description "Excludes RADIUS attribute 11, Filter-Id";
                 type enumeration {
                   enum "accounting-start" {
                     description "RADIUS Accounting-Start message";
                   }
                   enum "accounting-stop" {
                     description "RADIUS Accounting-Stop message";
                   }
                 }
               }
               leaf-list framed-ip-address {
                 ordered-by user;
                 description "Excludes RADIUS attribute 8, Framed-IP-Address";
                 type enumeration {
                   enum "access-request" {
                     description "RADIUS Access-Request message";
                   }
                   enum "accounting-start" {
                     description "RADIUS Accounting-Start message";
                   }
                   enum "accounting-stop" {
                     description "RADIUS Accounting-Stop message";
                   }
                 }
               }
               leaf-list framed-ip-netmask {
                 ordered-by user;
                 description "Excludes RADIUS attribute 9, Framed-IP-Netmask";
                 type enumeration {
                   enum "access-request" {
                     description "RADIUS Access-Request message";
                   }
                   enum "accounting-start" {
                     description "RADIUS Accounting-Start message";
                   }
                   enum "accounting-stop" {
                     description "RADIUS Accounting-Stop message";
                   }
                 }
               }
               leaf-list framed-ip-route {
                 ordered-by user;
                 description "Excludes RADIUS attribute 22, Framed-Route";
                 type enumeration {
                   enum "accounting-start" {
                     description "RADIUS Accounting-Start message";
                   }
                   enum "accounting-stop" {
                     description "RADIUS Accounting-Stop message";
                   }
                 }
               }
               leaf-list framed-ipv6-address {
                 ordered-by user;
                 description "Excludes RADIUS attribute 168, Framed-IPV6-Address";
                 type enumeration {
                   enum "access-request" {
                     description "RADIUS Access-Request message";
                   }
                   enum "accounting-start" {
                     description "RADIUS Accounting-Start message";
                   }
                   enum "accounting-stop" {
                     description "RADIUS Accounting-Stop message";
                   }
                 }
               }
               leaf-list framed-ipv6-pool {
                 ordered-by user;
                 description "Excludes RADIUS attribute 100, Framed-IPv6-Pool";
                 type enumeration {
                   enum "accounting-start" {
                     description "RADIUS Accounting-Start message";
                   }
                   enum "accounting-stop" {
                     description "RADIUS Accounting-Stop message";
                   }
                 }
               }
               leaf-list framed-ipv6-prefix {
                 ordered-by user;
                 description "Excludes RADIUS attribute 97, Framed-IPv6-Prefix";
                 type enumeration {
                   enum "accounting-start" {
                     description "RADIUS Accounting-Start message";
                   }
                   enum "accounting-stop" {
                     description "RADIUS Accounting-Stop message";
                   }
                 }
               }
               leaf-list framed-ipv6-route {
                 ordered-by user;
                 description "Excludes RADIUS attribute 99, Framed-IPv6-Route";
                 type enumeration {
                   enum "accounting-start" {
                     description "RADIUS Accounting-Start message";
                   }
                   enum "accounting-stop" {
                     description "RADIUS Accounting-Stop message";
                   }
                 }
               }
               leaf-list framed-pool {
                 ordered-by user;
                 description "Excludes RADIUS attribute 88, Framed-Pool";
                 type enumeration {
                   enum "accounting-start" {
                     description "RADIUS Accounting-Start message";
                   }
                   enum "accounting-stop" {
                     description "RADIUS Accounting-Stop message";
                   }
                 }
               }
               leaf-list input-filter {
                 ordered-by user;
                 description "Excludes RADIUS attribute 26-10, Ingress-Policy-Name";
                 type enumeration {
                   enum "accounting-start" {
                     description "RADIUS Accounting-Start message";
                   }
                   enum "accounting-stop" {
                     description "RADIUS Accounting-Stop message";
                   }
                 }
               }
               leaf-list input-gigapackets {
                 ordered-by user;
                 description "Excludes Juniper (IANA 4874) VSA  26-42, Acct-Input-Gigapackets";
                 type enumeration {
                   enum "accounting-stop" {
                     description "RADIUS Accounting-Stop message";
                   }
                 }
               }
               leaf-list input-gigawords {
                 ordered-by user;
                 description "Excludes RADIUS attribute 52, Acct-Input-Gigawords";
                 type enumeration {
                   enum "accounting-stop" {
                     description "RADIUS Accounting-Stop message";
                   }
                 }
               }
               leaf-list input-ipv6-packets {
                 ordered-by user;
                 description "Excludes Juniper (IANA 4874) VSA  26-153, Acct-Input-IPv6-Packets";
                 type enumeration {
                   enum "accounting-stop" {
                     description "RADIUS Accounting-Stop message";
                   }
                 }
               }
               leaf-list input-ipv6-gigawords {
                 ordered-by user;
                 description "Excludes Juniper (IANA 4874) VSA  26-155, Acct-Input-IPv6-Gigawords";
                 type enumeration {
                   enum "accounting-stop" {
                     description "RADIUS Accounting-Stop message";
                   }
                 }
               }
               leaf-list input-ipv6-octets {
                 ordered-by user;
                 description "Excludes Juniper (IANA 4874) VSA  26-151, Acct-Input-IPv6-Octets";
                 type enumeration {
                   enum "accounting-stop" {
                     description "RADIUS Accounting-Stop message";
                   }
                 }
               }
               leaf-list interface-description {
                 ordered-by user;
                 description "Excludes RADIUS attribute 26-63, Interface-Desc";
                 type enumeration {
                   enum "access-request" {
                     description "RADIUS Access-Request message";
                   }
                   enum "accounting-start" {
                     description "RADIUS Accounting-Start message";
                   }
                   enum "accounting-stop" {
                     description "RADIUS Accounting-Stop message";
                   }
                 }
               }
               leaf-list nas-identifier {
                 ordered-by user;
                 description "Excludes RADIUS attribute 32, NAS-identifier";
                 type enumeration {
                   enum "access-request" {
                     description "RADIUS Access-Request message";
                   }
                   enum "accounting-on" {
                     description "RADIUS Accounting-On Message";
                   }
                   enum "accounting-off" {
                     description "RADIUS Accounting-Off message";
                   }
                   enum "accounting-start" {
                     description "RADIUS Accounting-Start message";
                   }
                   enum "accounting-stop" {
                     description "RADIUS Accounting-Stop message";
                   }
                 }
               }
               leaf-list nas-port {
                 ordered-by user;
                 description "Excludes RADIUS attribute 5, NAS-Port";
                 type enumeration {
                   enum "access-request" {
                     description "RADIUS Access-Request message";
                   }
                   enum "accounting-start" {
                     description "RADIUS Accounting-Start message";
                   }
                   enum "accounting-stop" {
                     description "RADIUS Accounting-Stop message";
                   }
                 }
               }
               leaf-list nas-port-id {
                 ordered-by user;
                 description "Excludes RADIUS attribute 87, NAS-Port-ID";
                 type enumeration {
                   enum "access-request" {
                     description "RADIUS Access-Request message";
                   }
                   enum "accounting-start" {
                     description "RADIUS Accounting-Start message";
                   }
                   enum "accounting-stop" {
                     description "RADIUS Accounting-Stop message";
                   }
                 }
               }
               leaf-list nas-port-type {
                 ordered-by user;
                 description "Excludes RADIUS attribute 61, NAS-Port-Type";
                 type enumeration {
                   enum "access-request" {
                     description "RADIUS Access-Request message";
                   }
                   enum "accounting-start" {
                     description "RADIUS Accounting-Start message";
                   }
                   enum "accounting-stop" {
                     description "RADIUS Accounting-Stop message";
                   }
                 }
               }
               leaf-list output-gigapackets {
                 ordered-by user;
                 description "Excludes Juniper (IANA 4874) VSA  26-43, Acct-Output-Gigapackets";
                 type enumeration {
                   enum "accounting-stop" {
                     description "RADIUS Accounting-Stop message";
                   }
                 }
               }
               leaf-list output-gigawords {
                 ordered-by user;
                 description "Excludes RADIUS attribute 53, Acct-Output-Gigawords";
                 type enumeration {
                   enum "accounting-stop" {
                     description "RADIUS Accounting-Stop message";
                   }
                 }
               }
               leaf-list output-ipv6-packets {
                 ordered-by user;
                 description "Excludes Juniper (IANA 4874) VSA  26-154, Acct-Output-IPv6-Packets";
                 type enumeration {
                   enum "accounting-stop" {
                     description "RADIUS Accounting-Stop message";
                   }
                 }
               }
               leaf-list output-ipv6-gigawords {
                 ordered-by user;
                 description "Excludes Juniper (IANA 4874) VSA  26-156, Acct-Output-IPv6-Gigawords";
                 type enumeration {
                   enum "accounting-stop" {
                     description "RADIUS Accounting-Stop message";
                   }
                 }
               }
               leaf-list output-ipv6-octets {
                 ordered-by user;
                 description "Excludes Juniper (IANA 4874) VSA  26-152, Acct-Output-IPv6-Octets";
                 type enumeration {
                   enum "accounting-stop" {
                     description "RADIUS Accounting-Stop message";
                   }
                 }
               }
               leaf-list dynamic-iflset-name {
                 ordered-by user;
                 description "Excludes RADIUS attribute 26-130, Dynamic-Iflset-Name";
                 type enumeration {
                   enum "accounting-start" {
                     description "RADIUS Accounting-Start message";
                   }
                   enum "accounting-stop" {
                     description "RADIUS Accounting-Stop message";
                   }
                 }
               }
               leaf-list dsl-forum-attributes {
                 ordered-by user;
                 description "Excludes DSL Forum RADIUS attributes (RFC 4679)";
                 type enumeration {
                   enum "access-request" {
                     description "RADIUS Access-Request message";
                   }
                   enum "accounting-start" {
                     description "RADIUS Accounting-Start message";
                   }
                   enum "accounting-stop" {
                     description "RADIUS Accounting-Stop message";
                   }
                 }
               }
               leaf-list l2c-upstream-data {
                 ordered-by user;
                 description "Excludes Juniper (IANA 4874) DSL VSA 26-92, L2C-Upstream-Data";
                 type enumeration {
                   enum "access-request" {
                     description "RADIUS Access-Request message";
                   }
                   enum "accounting-start" {
                     description "RADIUS Accounting-Start message";
                   }
                   enum "accounting-stop" {
                     description "RADIUS Accounting-Stop message";
                   }
                 }
               }
               leaf-list l2c-downstream-data {
                 ordered-by user;
                 description "Excludes Juniper (IANA 4874) DSL VSA 26-93, L2C-Downstream-Data";
                 type enumeration {
                   enum "access-request" {
                     description "RADIUS Access-Request message";
                   }
                   enum "accounting-start" {
                     description "RADIUS Accounting-Start message";
                   }
                   enum "accounting-stop" {
                     description "RADIUS Accounting-Stop message";
                   }
                 }
               }
               leaf-list acc-loop-cir-id {
                 ordered-by user;
                 description "Excludes Juniper (IANA 4874) DSL VSA 26-110, Acc-Loop-Cir-Id";
                 type enumeration {
                   enum "access-request" {
                     description "RADIUS Access-Request message";
                   }
                   enum "accounting-start" {
                     description "RADIUS Accounting-Start message";
                   }
                   enum "accounting-stop" {
                     description "RADIUS Accounting-Stop message";
                   }
                 }
               }
               leaf-list acc-aggr-cir-id-bin {
                 ordered-by user;
                 description "Excludes Juniper (IANA 4874) DSL VSA 26-111, Acc-Aggr-Cir-Id-Bin";
                 type enumeration {
                   enum "access-request" {
                     description "RADIUS Access-Request message";
                   }
                   enum "accounting-start" {
                     description "RADIUS Accounting-Start message";
                   }
                   enum "accounting-stop" {
                     description "RADIUS Accounting-Stop message";
                   }
                 }
               }
               leaf-list acc-aggr-cir-id-asc {
                 ordered-by user;
                 description "Excludes Juniper (IANA 4874) DSL VSA 26-112, Acc-Aggr-Cir-Id-Asc";
                 type enumeration {
                   enum "access-request" {
                     description "RADIUS Access-Request message";
                   }
                   enum "accounting-start" {
                     description "RADIUS Accounting-Start message";
                   }
                   enum "accounting-stop" {
                     description "RADIUS Accounting-Stop message";
                   }
                 }
               }
               leaf-list act-data-rate-up {
                 ordered-by user;
                 description "Excludes Juniper (IANA 4874) DSL VSA 26-113, Act-Data-Rate-Up";
                 type enumeration {
                   enum "access-request" {
                     description "RADIUS Access-Request message";
                   }
                   enum "accounting-start" {
                     description "RADIUS Accounting-Start message";
                   }
                   enum "accounting-stop" {
                     description "RADIUS Accounting-Stop message";
                   }
                 }
               }
               leaf-list act-data-rate-dn {
                 ordered-by user;
                 description "Excludes Juniper (IANA 4874) DSL VSA 26-114, Act-Data-Rate-Dn";
                 type enumeration {
                   enum "access-request" {
                     description "RADIUS Access-Request message";
                   }
                   enum "accounting-start" {
                     description "RADIUS Accounting-Start message";
                   }
                   enum "accounting-stop" {
                     description "RADIUS Accounting-Stop message";
                   }
                 }
               }
               leaf-list min-data-rate-up {
                 ordered-by user;
                 description "Excludes Juniper (IANA 4874) DSL VSA 26-115, Min-Data-Rate-Up";
                 type enumeration {
                   enum "access-request" {
                     description "RADIUS Access-Request message";
                   }
                   enum "accounting-start" {
                     description "RADIUS Accounting-Start message";
                   }
                   enum "accounting-stop" {
                     description "RADIUS Accounting-Stop message";
                   }
                 }
               }
               leaf-list min-data-rate-dn {
                 ordered-by user;
                 description "Excludes Juniper (IANA 4874) DSL VSA 26-116, Min-Data-Rate-Dn";
                 type enumeration {
                   enum "access-request" {
                     description "RADIUS Access-Request message";
                   }
                   enum "accounting-start" {
                     description "RADIUS Accounting-Start message";
                   }
                   enum "accounting-stop" {
                     description "RADIUS Accounting-Stop message";
                   }
                 }
               }
               leaf-list att-data-rate-up {
                 ordered-by user;
                 description "Excludes Juniper (IANA 4874) DSL VSA 26-117, Att-Data-Rate-Up";
                 type enumeration {
                   enum "access-request" {
                     description "RADIUS Access-Request message";
                   }
                   enum "accounting-start" {
                     description "RADIUS Accounting-Start message";
                   }
                   enum "accounting-stop" {
                     description "RADIUS Accounting-Stop message";
                   }
                 }
               }
               leaf-list att-data-rate-dn {
                 ordered-by user;
                 description "Excludes Juniper (IANA 4874) DSL VSA 26-118, Att-Data-Rate-Dn";
                 type enumeration {
                   enum "access-request" {
                     description "RADIUS Access-Request message";
                   }
                   enum "accounting-start" {
                     description "RADIUS Accounting-Start message";
                   }
                   enum "accounting-stop" {
                     description "RADIUS Accounting-Stop message";
                   }
                 }
               }
               leaf-list max-data-rate-up {
                 ordered-by user;
                 description "Excludes Juniper (IANA 4874) DSL VSA 26-119, Max-Data-Rate-Up";
                 type enumeration {
                   enum "access-request" {
                     description "RADIUS Access-Request message";
                   }
                   enum "accounting-start" {
                     description "RADIUS Accounting-Start message";
                   }
                   enum "accounting-stop" {
                     description "RADIUS Accounting-Stop message";
                   }
                 }
               }
               leaf-list max-data-rate-dn {
                 ordered-by user;
                 description "Excludes Juniper (IANA 4874) DSL VSA 26-120, Max-Data-Rate-Dn";
                 type enumeration {
                   enum "access-request" {
                     description "RADIUS Access-Request message";
                   }
                   enum "accounting-start" {
                     description "RADIUS Accounting-Start message";
                   }
                   enum "accounting-stop" {
                     description "RADIUS Accounting-Stop message";
                   }
                 }
               }
               leaf-list min-lp-data-rate-up {
                 ordered-by user;
                 description "Excludes Juniper (IANA 4874) DSL VSA 26-121, Min-Lp-Data-Rate-Up";
                 type enumeration {
                   enum "access-request" {
                     description "RADIUS Access-Request message";
                   }
                   enum "accounting-start" {
                     description "RADIUS Accounting-Start message";
                   }
                   enum "accounting-stop" {
                     description "RADIUS Accounting-Stop message";
                   }
                 }
               }
               leaf-list min-lp-data-rate-dn {
                 ordered-by user;
                 description "Excludes Juniper (IANA 4874) DSL VSA 26-122, Min-Lp-Data-Rate-Dn";
                 type enumeration {
                   enum "access-request" {
                     description "RADIUS Access-Request message";
                   }
                   enum "accounting-start" {
                     description "RADIUS Accounting-Start message";
                   }
                   enum "accounting-stop" {
                     description "RADIUS Accounting-Stop message";
                   }
                 }
               }
               leaf-list max-interlv-delay-up {
                 ordered-by user;
                 description "Excludes Juniper (IANA 4874) DSL VSA 26-123, Max-Interlv-Delay-Up";
                 type enumeration {
                   enum "access-request" {
                     description "RADIUS Access-Request message";
                   }
                   enum "accounting-start" {
                     description "RADIUS Accounting-Start message";
                   }
                   enum "accounting-stop" {
                     description "RADIUS Accounting-Stop message";
                   }
                 }
               }
               leaf-list act-interlv-delay-up {
                 ordered-by user;
                 description "Excludes Juniper (IANA 4874) DSL VSA 26-124, Act-Interlv-Delay-Up";
                 type enumeration {
                   enum "access-request" {
                     description "RADIUS Access-Request message";
                   }
                   enum "accounting-start" {
                     description "RADIUS Accounting-Start message";
                   }
                   enum "accounting-stop" {
                     description "RADIUS Accounting-Stop message";
                   }
                 }
               }
               leaf-list max-interlv-delay-dn {
                 ordered-by user;
                 description "Excludes Juniper (IANA 4874) DSL VSA 26-125, Max-Interlv-Delay-Dn";
                 type enumeration {
                   enum "access-request" {
                     description "RADIUS Access-Request message";
                   }
                   enum "accounting-start" {
                     description "RADIUS Accounting-Start message";
                   }
                   enum "accounting-stop" {
                     description "RADIUS Accounting-Stop message";
                   }
                 }
               }
               leaf-list act-interlv-delay-dn {
                 ordered-by user;
                 description "Excludes Juniper (IANA 4874) DSL VSA 26-126, Act-Interlv-Delay-Dn";
                 type enumeration {
                   enum "access-request" {
                     description "RADIUS Access-Request message";
                   }
                   enum "accounting-start" {
                     description "RADIUS Accounting-Start message";
                   }
                   enum "accounting-stop" {
                     description "RADIUS Accounting-Stop message";
                   }
                 }
               }
               leaf-list dsl-line-state {
                 ordered-by user;
                 description "Excludes Juniper (IANA 4874) DSL VSA 26-127, DSL-Line-State";
                 type enumeration {
                   enum "access-request" {
                     description "RADIUS Access-Request message";
                   }
                   enum "accounting-start" {
                     description "RADIUS Accounting-Start message";
                   }
                   enum "accounting-stop" {
                     description "RADIUS Accounting-Stop message";
                   }
                 }
               }
               leaf-list dsl-type {
                 ordered-by user;
                 description "Excludes Juniper (IANA 4874) DSL VSA 26-128, DSL-Type";
                 type enumeration {
                   enum "access-request" {
                     description "RADIUS Access-Request message";
                   }
                   enum "accounting-start" {
                     description "RADIUS Accounting-Start message";
                   }
                   enum "accounting-stop" {
                     description "RADIUS Accounting-Stop message";
                   }
                 }
               }
               leaf-list downstream-calculated-qos-rate {
                 ordered-by user;
                 description "Excludes Juniper (IANA 4874) DSL VSA 26-141, Downstream-Calculated-QoS-Rate";
                 type enumeration {
                   enum "access-request" {
                     description "RADIUS Access-Request message";
                   }
                   enum "accounting-start" {
                     description "RADIUS Accounting-Start message";
                   }
                   enum "accounting-stop" {
                     description "RADIUS Accounting-Stop message";
                   }
                 }
               }
               leaf-list upstream-calculated-qos-rate {
                 ordered-by user;
                 description "Excludes Juniper (IANA 4874) DSL VSA 26-142, Upstream-Calculated-QoS-Rate";
                 type enumeration {
                   enum "access-request" {
                     description "RADIUS Access-Request message";
                   }
                   enum "accounting-start" {
                     description "RADIUS Accounting-Start message";
                   }
                   enum "accounting-stop" {
                     description "RADIUS Accounting-Stop message";
                   }
                 }
               }
               leaf-list cos-shaping-rate {
                 ordered-by user;
                 description "Excludes Juniper (IANA 4874) VSA 26-177, Cos-Shaping-Rate";
                 type enumeration {
                   enum "accounting-start" {
                     description "RADIUS Accounting-Start message";
                   }
                   enum "accounting-stop" {
                     description "RADIUS Accounting-Stop message";
                   }
                 }
               }
               leaf-list framed-interface-id {
                 ordered-by user;
                 description "Excludes RADIUS attribute 96, Framed-Interface-Id";
                 type enumeration {
                   enum "access-request" {
                     description "RADIUS Access-Request message";
                   }
                   enum "accounting-start" {
                     description "RADIUS Accounting-Start message";
                   }
                   enum "accounting-stop" {
                     description "RADIUS Accounting-Stop message";
                   }
                 }
               }
               leaf-list chargeable-user-identity {
                 ordered-by user;
                 description "Excludes RADIUS attribute 89, Chargeable-User-Identity";
                 type enumeration {
                   enum "access-request" {
                     description "RADIUS Access-Request message";
                   }
                 }
               }
               leaf-list l2tp-tx-connect-speed {
                 ordered-by user;
                 description "Excludes Juniper (IANA 4874) VSA 26-162, , L2TP-Tx-Connect-Speed";
                 type enumeration {
                   enum "access-request" {
                     description "RADIUS Access-Request message";
                   }
                   enum "accounting-start" {
                     description "RADIUS Accounting-Start message";
                   }
                   enum "accounting-stop" {
                     description "RADIUS Accounting-Stop message";
                   }
                 }
               }
               leaf-list l2tp-rx-connect-speed {
                 ordered-by user;
                 description "Excludes Juniper (IANA 4874) VSA 26-163, , L2TP-Rx-Connect-Speed";
                 type enumeration {
                   enum "access-request" {
                     description "RADIUS Access-Request message";
                   }
                   enum "accounting-start" {
                     description "RADIUS Accounting-Start message";
                   }
                   enum "accounting-stop" {
                     description "RADIUS Accounting-Stop message";
                   }
                 }
               }
               leaf-list tunnel-type {
                 ordered-by user;
                 description "Excludes RADIUS attribute 64, Tunnel-Type";
                 type enumeration {
                   enum "access-request" {
                     description "RADIUS Access-Request message";
                   }
                   enum "accounting-start" {
                     description "RADIUS Accounting-Start message";
                   }
                   enum "accounting-stop" {
                     description "RADIUS Accounting-Stop message";
                   }
                 }
               }
               leaf-list tunnel-medium-type {
                 ordered-by user;
                 description "Excludes RADIUS attribute 65, Tunnel-Medium-Type";
                 type enumeration {
                   enum "access-request" {
                     description "RADIUS Access-Request message";
                   }
                   enum "accounting-start" {
                     description "RADIUS Accounting-Start message";
                   }
                   enum "accounting-stop" {
                     description "RADIUS Accounting-Stop message";
                   }
                 }
               }
               leaf-list tunnel-client-endpoint {
                 ordered-by user;
                 description "Excludes RADIUS attribute 66, Tunnel-Client-Endpoint";
                 type enumeration {
                   enum "access-request" {
                     description "RADIUS Access-Request message";
                   }
                   enum "accounting-start" {
                     description "RADIUS Accounting-Start message";
                   }
                   enum "accounting-stop" {
                     description "RADIUS Accounting-Stop message";
                   }
                 }
               }
               leaf-list tunnel-server-endpoint {
                 ordered-by user;
                 description "Excludes RADIUS attribute 67, Tunnel-Server-Endpoint";
                 type enumeration {
                   enum "access-request" {
                     description "RADIUS Access-Request message";
                   }
                   enum "accounting-start" {
                     description "RADIUS Accounting-Start message";
                   }
                   enum "accounting-stop" {
                     description "RADIUS Accounting-Stop message";
                   }
                 }
               }
               leaf-list tunnel-assignment-id {
                 ordered-by user;
                 description "Excludes RADIUS attribute 82, Tunnel-Assignment-Id";
                 type enumeration {
                   enum "access-request" {
                     description "RADIUS Access-Request message";
                   }
                   enum "accounting-start" {
                     description "RADIUS Accounting-Start message";
                   }
                   enum "accounting-stop" {
                     description "RADIUS Accounting-Stop message";
                   }
                 }
               }
               leaf-list tunnel-client-auth-id {
                 ordered-by user;
                 description "Excludes RADIUS attribute 90, Tunnel-Client-Auth-Id";
                 type enumeration {
                   enum "access-request" {
                     description "RADIUS Access-Request message";
                   }
                   enum "accounting-start" {
                     description "RADIUS Accounting-Start message";
                   }
                   enum "accounting-stop" {
                     description "RADIUS Accounting-Stop message";
                   }
                 }
               }
               leaf-list tunnel-server-auth-id {
                 ordered-by user;
                 description "Excludes RADIUS attribute 91, Tunnel-Server-Auth-Id";
                 type enumeration {
                   enum "access-request" {
                     description "RADIUS Access-Request message";
                   }
                   enum "accounting-start" {
                     description "RADIUS Accounting-Start message";
                   }
                   enum "accounting-stop" {
                     description "RADIUS Accounting-Stop message";
                   }
                 }
               }
               leaf-list acct-tunnel-connection {
                 ordered-by user;
                 description "Excludes RADIUS attribute 68, Acct-Tunnel-Connection";
                 type enumeration {
                   enum "access-request" {
                     description "RADIUS Access-Request message";
                   }
                   enum "accounting-start" {
                     description "RADIUS Accounting-Start message";
                   }
                   enum "accounting-stop" {
                     description "RADIUS Accounting-Stop message";
                   }
                 }
               }
               leaf-list acc-loop-remote-id {
                 ordered-by user;
                 description "Excludes Juniper (IANA 4874) VSA 26-XXX, ERX-Acc-Loop-Remote-Id";
                 type enumeration {
                   enum "access-request" {
                     description "RADIUS Access-Request message";
                   }
                   enum "accounting-start" {
                     description "RADIUS Accounting-Start message";
                   }
                   enum "accounting-stop" {
                     description "RADIUS Accounting-Stop message";
                   }
                 }
               }
               leaf-list acc-loop-encap {
                 ordered-by user;
                 description "Excludes Juniper (IANA 4874) VSA 26-182, ERX-Acc-Loop-Encap";
                 type enumeration {
                   enum "access-request" {
                     description "RADIUS Access-Request message";
                   }
                   enum "accounting-start" {
                     description "RADIUS Accounting-Start message";
                   }
                   enum "accounting-stop" {
                     description "RADIUS Accounting-Stop message";
                   }
                 }
               }
               leaf-list pppoe-description {
                 ordered-by user;
                 description "Excludes RADIUS attribute 26-24, PPPOE-Description";
                 type enumeration {
                   enum "access-request" {
                     description "RADIUS Access-Request message";
                   }
                   enum "accounting-start" {
                     description "RADIUS Accounting-Start message";
                   }
                   enum "accounting-stop" {
                     description "RADIUS Accounting-Stop message";
                   }
                 }
               }
               leaf-list virtual-router {
                 ordered-by user;
                 description "Excludes Juniper (IANA 4874) VSA 26-1, Virtual-Router";
                 type enumeration {
                   enum "access-request" {
                     description "RADIUS Access-Request message";
                   }
                   enum "accounting-start" {
                     description "RADIUS Accounting-Start message";
                   }
                   enum "accounting-stop" {
                     description "RADIUS Accounting-Stop message";
                   }
                 }
               }
               leaf-list first-relay-ipv4-address {
                 ordered-by user;
                 description "Excludes RADIUS attribute 26-189, DHCP-First-Relay-IPv4-Address";
                 type enumeration {
                   enum "access-request" {
                     description "RADIUS Access-Request message";
                   }
                   enum "accounting-start" {
                     description "RADIUS Accounting-Start message";
                   }
                   enum "accounting-stop" {
                     description "RADIUS Accounting-Stop message";
                   }
                 }
               }
               leaf-list first-relay-ipv6-address {
                 ordered-by user;
                 description "Excludes RADIUS attribute 26-190, DHCP-First-Relay-IPv6-Address";
                 type enumeration {
                   enum "access-request" {
                     description "RADIUS Access-Request message";
                   }
                   enum "accounting-start" {
                     description "RADIUS Accounting-Start message";
                   }
                   enum "accounting-stop" {
                     description "RADIUS Accounting-Stop message";
                   }
                 }
               }
               leaf-list dhcpv6-options {
                 ordered-by user;
                 description "Excludes RADIUS attribute 26-207, DHCPv6-Options";
                 type enumeration {
                   enum "access-request" {
                     description "RADIUS Access-Request message";
                   }
                   enum "accounting-start" {
                     description "RADIUS Accounting-Start message";
                   }
                   enum "accounting-stop" {
                     description "RADIUS Accounting-Stop message";
                   }
                 }
               }
               leaf-list dhcp-header {
                 ordered-by user;
                 description "Excludes RADIUS attribute 26-208, DHCP-Header";
                 type enumeration {
                   enum "access-request" {
                     description "RADIUS Access-Request message";
                   }
                 }
               }
               leaf-list dhcpv6-header {
                 ordered-by user;
                 description "Excludes RADIUS attribute 26-209, DHCPv6-Header";
                 type enumeration {
                   enum "access-request" {
                     description "RADIUS Access-Request message";
                   }
                 }
               }
               leaf-list acct-request-reason {
                 ordered-by user;
                 description "Excludes RADIUS attribute 26-210, Acct-Request-Reason";
                 type enumeration {
                   enum "accounting-start" {
                     description "RADIUS Accounting-Start message";
                   }
                   enum "accounting-stop" {
                     description "RADIUS Accounting-Stop message";
                   }
                 }
               }
             }
           }
         }
         container session-options {
           description "Options for an authenticated client's session";
           uses apply-advanced;
           leaf-list client-group {
             ordered-by user;
             description "One or more groups to which client belongs";
             type string;
           }
           leaf client-idle-timeout {
             description "Time in minutes of idleness after which access is denied";
             units "minutes";
             type union {
               type string {
                 pattern "<.*>|$.*";
               }
               type uint32 {
                 range "10 .. 1440";
               }
             }
           }
           leaf client-idle-timeout-ingress-only {
             description "Idle timeout applies to ingress traffic only";
             type empty;
           }
           leaf client-session-timeout {
             description "Time in minutes since initial access after which access is denied";
             units "minutes";
             type union {
               type string {
                 pattern "<.*>|$.*";
               }
               type uint32 {
                 range "1 .. 527040";
               }
             }
           }
           container strip-user-name {
             description "Options for stripping user name string";
             uses apply-advanced;
             container delimiter {
               description "Allowable delimiter characters for strip user name separation";
               leaf characters {
                 description "Sequence of characters without spaces and commas";
                 type string {
                   length "1 .. 8";
                 }
               }
             }
             container parse-direction {
               description "Strip user name parsing direction";
               choice direction {
                 case case_1 {
                   leaf right-to-left {
                     description "Parse the username from right to left";
                     type empty;
                   }
                 }
                 case case_2 {
                   leaf left-to-right {
                     description "Parse the username field from left to right";
                     type empty;
                   }
                 }
               }
             }
           }
           container pcc-context {
             description "Pcc context configurations";
             uses apply-advanced;
             leaf pcef-profile {
               description "Pcef profile name";
               junos:must "(\"services pcef profile $$\")";
               junos:must-message "Referenced pcef profile must be defined";
               type string;
             }
             leaf input-service-set {
               description "Input service-set name";
               junos:must "(\"services service-set $$\")";
               junos:must-message "Referenced service-set must be defined";
               type string;
             }
             leaf output-service-set {
               description "Output service-set name";
               junos:must "(\"services service-set $$\")";
               junos:must-message "Referenced service-set must be defined";
               type string;
             }
             leaf input-ipv6-service-set {
               description "Input ipv6 service set name";
               junos:must "(\"services service-set $$\")";
               junos:must-message "Referenced service-set must be defined";
               type string;
             }
             leaf output-ipv6-service-set {
               description "Output ipv6 service set name";
               junos:must "(\"services service-set $$\")";
               junos:must-message "Referenced service-set must be defined";
               type string;
             }
             leaf input-service-filter {
               description "Input service filter name";
               junos:must "(\"firewall family inet service-filter $$\")";
               junos:must-message "Referenced service-filter must be defined";
               type string;
             }
             leaf output-service-filter {
               description "Output service filter name";
               junos:must "(\"firewall family inet service-filter $$\")";
               junos:must-message "Referenced service-filter must be defined";
               type string;
             }
             leaf input-ipv6-service-filter {
               description "Input ipv6 service filter name";
               junos:must "(\"firewall family inet6 service-filter $$\")";
               junos:must-message "Referenced service-filter must be defined";
               type string;
             }
             leaf output-ipv6-service-filter {
               description "Output ipv6 service filter name";
               junos:must "(\"firewall family inet6 service-filter $$\")";
               junos:must-message "Referenced service-filter must be defined";
               type string;
             }
           }
         }
         container client-name-filter {
           description "Restrictions on client names";
           uses access-client-name-filter-object;
         }
         container ldap-options {
           description "Lightweight Directory Access Protocol options";
           junos:must "((!(any \".. client <*> l2tp\") && (!(any \".. client <*> ike\") && !(any \".. client <*> ppp\"))))";
           junos:must-message "'ldap-options' statement is not supported in L2TP, IKE, or PPP configuration";
           uses access-ldap-options;
         }
         list ldap-server {
           key name;
           ordered-by user;
           description "Lightweight Directory Access Protocol server";
           junos:must "(\".. ldap-options\")";
           junos:must-message "ldap-options must be configured when ldap-server is configured";
           junos:must "((!(any \".. client <*> l2tp\") && (!(any \".. client <*> ike\") && !(any \".. client <*> ppp\"))))";
           junos:must-message "'ldap-server' statement is not supported in L2TP, IKE, or PPP configuration";
           uses ldap-server-object;
         }
         list radius-server {
           key name;
           ordered-by user;
           description "RADIUS server configuration";
           junos:must "(!(any \".. client <*> l2tp\"))";
           junos:must-message "Not supported in L2TP configuration";
           junos:must "((!(any \".. client <*> l2tp\") && !(any \".. client <*> ike\")))";
           junos:must-message "Not supported in L2TP or IKE configuration";
           uses profile-radius-server-object;
         }
         list radius-server-name {
           key name;
           ordered-by user;
           description "RADIUS server FQDN configuration";
           junos:must "(!(any \".. client <*> l2tp\"))";
           junos:must-message "Not supported in L2TP configuration";
           uses profile-radius-server-name-object;
         }
         container radius-options {
           description "RADIUS options";
           uses access-radius-options;
         }
         container accounting {
           description "Specifies the accounting options";
           uses apply-advanced;
           leaf-list order {
             ordered-by user;
             description "Order in which accounting mechanisms are used";
             type enumeration {
               enum "radius" {
                 description "Remote authentication dial-in user service";
               }
             }
           }
           leaf accounting-stop-on-failure {
             description "Send an Acct-Stop message if a user fails authentication, but AAA-server grants access";
             type empty;
           }
           leaf accounting-stop-on-access-deny {
             description "Send an Acct-Stop message if AAA-server denies access";
             type empty;
           }
           leaf immediate-update {
             description "Send an Acct-Update message on receipt of a Acct-response for the Acct-Start message";
             type empty;
           }
           leaf coa-immediate-update {
             description "Send an Acct-Update message on completion of processing a change of authorization";
             type empty;
           }
           leaf address-change-immediate-update {
             description "Send an Acct-Update message to notify address change";
             type empty;
           }
           leaf update-interval {
             description "The interval in min btw accounting updates(Interim-stats off,if unspecified)";
             units "minutes";
             type union {
               type string {
                 pattern "<.*>|$.*";
               }
               type uint32 {
                 range "10 .. 1440";
               }
             }
           }
           leaf statistics {
             description "Reports set of statistics attributes based on reporting type";
             type enumeration {
               enum "volume-time" {
                 description "Configures the option to report both volume and uptime";
               }
               enum "time" {
                 description "Configures the option to report only uptime";
               }
             }
           }
           leaf wait-for-acct-on-ack {
             description "Wait for ACCT-ON-ACK";
             type empty;
           }
           leaf send-acct-status-on-config-change {
             description "Send ACCT-ON/OFF on config change";
             type empty;
           }
           leaf duplication {
             description "Send duplicated accounting reports if applied";
             type empty;
           }
           leaf-list duplication-filter {
             ordered-by user;
             description "Configure duplication filters";
             type enumeration {
               enum "interim-original" {
                 description "Do not send original accounting interims";
               }
               enum "interim-duplicated" {
                 description "Do not send duplicated accounting interims";
               }
               enum "exclude-attributes" {
                 description "Use duplication access profile exclude attributes";
               }
             }
           }
           container duplication-vrf {
             description "Duplication vrf configurations";
             uses apply-advanced;
             leaf vrf-name {
               description "VRF name";
               type string {
                 length "1 .. 257";
               }
             }
             leaf-list access-profile-name {
               ordered-by user;
               description "Access profile name";
               type string {
                 length "1 .. 63";
               }
               max-elements 5;
             }
           }
           leaf-list duplication-attribute-format {
             ordered-by user;
             description "Use attribute format defined under duplication accouting access-profile";
             type enumeration {
               enum "username" {
                 description "Username";
               }
             }
           }
           leaf ancp-speed-change-immediate-update {
             description "Send an Acct-Update message when ANCP speed change is detected";
             type empty;
           }
           leaf family-state-change-immediate-update {
             description "Send an Acct-Update message to notify address family activation state change";
             type empty;
           }
         }
         container service {
           description "Subscriber service configurations";
           uses apply-advanced;
           leaf accounting-order {
             description "Order in which accounting mechanism service is used";
             type enumeration {
               enum "activation-protocol" {
                 description "Send service accounting reports via service activation protocol";
               }
               enum "radius" {
                 description "Send service accounting reports via radius protocol";
               }
               enum "local" {
                 description "Send service accounting for local reporting - obsolete config";
                 junos:must "(\".. .. local flat-file-profile\")";
                 junos:must-message "local flat-file-profile must be configured under access profile for accounting-order local";
               }
             }
           }
           container accounting {
             description "Specifies the service accounting options";
             uses apply-advanced;
             leaf update-interval {
               description "The interval in minutes between accounting updates(Interim-stats off, if not specified)";
               units "minutes";
               type union {
                 type string {
                   pattern "<.*>|$.*";
                 }
                 type uint32 {
                   range "10 .. 1440";
                 }
               }
             }
             leaf statistics {
               description "Reports set of statistics attributes based on reporting type";
               junos:must "(!(\".. .. accounting-order $$={local}\"))";
               junos:must-message "Statistics configuration is no-op when accounting-order is set to local for flat-file based accounting";
               type enumeration {
                 enum "time" {
                   description "Configures the option to report only uptime";
                 }
                 enum "volume-time" {
                   description "Configures the option to report both volume and uptime";
                 }
               }
             }
           }
         }
         container jsrc {
           description "Set of JSRC configurations";
           uses apply-advanced;
           container attributes {
             description "Specifies how JSRC attributes should be handled";
             uses apply-advanced;
             container exclude {
               description "Configures the exclusion of JSRC attributes in DIAMETER messages";
               uses apply-advanced;
               leaf-list user-name {
                 ordered-by user;
                 description "Excludes Diameter attribute 1, User-Name";
                 type enumeration {
                   enum "authorization-request" {
                     description "Authorization AA-Request message";
                   }
                   enum "provisioning-request" {
                     description "Provisioning AA-Request message";
                   }
                 }
               }
             }
           }
         }
         list subscriber {
           key name;
           description "Locally authenticated subscriber configuration";
           uses localauth-subscriber-object;
         }
       }
     }
     container services {
       presence "enable services";
       uses apply-advanced;
       container icap-redirect {
         description "Configure ICAP redirection service";
         uses apply-advanced;
         list profile {
           key name;
           ordered-by user;
           description "Congifure ICAP service profile";
           uses icap-profile-object;
         }
         container traceoptions {
           description "ICAP redirect trace options";
           uses icap-redirect-traceoptions;
         }
       }
       container security-intelligence {
         uses apply-advanced;
         leaf url {
           description "Configure the url of feed server [https://<ip or hostname>:<port>/<uri>]";
           type string;
         }
         container authentication {
           description "Authenticate to use feed update services";
           uses apply-advanced;
           leaf auth-token {
             description "Token string for authentication";
             type string {
               junos:posix-pattern "^[A-Za-z0-9]{32}$";
               junos:pattern-message "Auth token must be consisted of 32 alphanumeric characters";
             }
           }
           leaf tls-profile {
             description "TLS profile";
             junos:must "(\"services ssl initiation profile $$\")";
             junos:must-message "Referenced SSL initiation profile is not defined";
             type string;
           }
         }
         container traceoptions {
           description "Security intelligence trace options";
           uses secintel-traceoptions;
         }
         container category {
           description "Category to be disabled";
           uses apply-advanced;
           container all {
             presence "enable all";
             description "All categories";
             uses apply-advanced;
             container disable {
               presence "enable disable";
               description "To disable all categories";
             }
           }
           list category-name {
             key name;
             ordered-by user;
             uses secintel-category-disable;
           }
         }
         leaf proxy-profile {
           description "The proxy profile name";
           junos:must "(\"services proxy profile\")";
           junos:must-message "Proxy profile must be defined";
           type string {
             length "1 .. 64";
           }
         }
         leaf http-persist {
           description "Inspect all HTTP requests in a connection";
           type empty;
         }
         list profile {
           key name;
           ordered-by user;
           description "Configure security intelligence profile";
           uses secintel-profile-setting;
         }
         container default-policy {
           description "Configure security intelligence default policy";
           uses apply-advanced;
           list category-profiles {
             key name;
             ordered-by user;
             description "Security intelligence category profiles";
             leaf name {
               description "Name of security intelligence category";
               type enumeration {
                 enum "IPFilter" {
                   description "IPFilter";
                 }
                 enum "GeoIP" {
                   description "GeoIP";
                 }
                 enum "CC" {
                   description "Command and control";
                 }
                 enum "Infected-Hosts" {
                   description "Infected-Hosts";
                 }
                 enum "DNS" {
                   description "DNS";
                 }
               }
             }
             uses apply-advanced;
             leaf profile-name {
               description "Name of profile";
               junos:must "(\"services security-intelligence profile $$\")";
               junos:must-message "security intelligence profile must be defined";
               type string;
             }
           }
         }
         list policy {
           key name;
           ordered-by user;
           description "Configure security intelligence policy";
           uses secintel-policy-setting;
         }
         container global-disable-feed {
           presence "enable global-disable-feed";
           description "Security intelligence global feed disabling setting";
           uses apply-advanced;
           list feed-name {
             key name;
             ordered-by user;
             max-elements 32;
             leaf name {
               description "Name of security intelligence global Command and control feed";
               type string {
                 length "1 .. 63";
               }
             }
             uses apply-advanced;
           }
           container all {
             presence "enable all";
             description "All of security intelligence global Command and control feed";
           }
         }
       }
       container advanced-anti-malware {
         uses apply-advanced;
         container connection {
           presence "enable connection";
           description "Cloud service RE connection, only for master logical domain";
           uses apply-advanced;
           leaf url {
             description "The url of the cloud server [https://<ip or hostname>:<port>]";
             junos:must "(\"services advanced-anti-malware connection authentication tls-profile\")";
             junos:must-message "Authentication profile must be defined";
             type string;
           }
           container authentication {
             description "The authentication profile for using cloud services";
             uses apply-advanced;
             leaf tls-profile {
               description "TLS profile";
               junos:must "((\"services ssl initiation profile $$\" && \"services advanced-anti-malware connection url\"))";
               junos:must-message "Referenced SSL initiation profile and URL must be defined";
               type string;
             }
           }
           leaf proxy-profile {
             description "Proxy profile";
             junos:must "(\"services proxy profile $$\")";
             junos:must-message "Referenced Proxy profile must be defined";
             type string {
               length "1 .. 63";
             }
           }
           leaf source-address {
             description "The source ip for connecting to the cloud server.";
             type jt:ipaddr;
           }
           leaf source-interface {
             description "The source interface for connecting to the cloud server";
             type union {
               type jt:interface-name;
               type string {
                 pattern "<.*>|$.*";
               }
             }
           }
         }
         container default-policy {
           presence "enable default-policy";
           description "Advanced Anti-malware default policy";
           uses apply-advanced;
           container http {
             description "Configure HTTP options";
             uses apply-advanced;
             leaf inspection-profile {
               description "Advanced Anti-malware inspection-profile name (default:default_profile)";
               type string {
                 length "1 .. 63";
               }
             }
             leaf file-verdict-unknown {
               description "Action taken for contents with verdict unknown";
               type enumeration {
                 enum "permit" {
                   description "Allow contents";
                 }
                 enum "block" {
                   description "Disallow contents";
                 }
               }
             }
             leaf action {
               description "Action taken for contents with verdict meet threshold";
               type enumeration {
                 enum "permit" {
                   description "Allow contents";
                 }
                 enum "block" {
                   description "Disallow contents";
                 }
               }
             }
             container client-notify {
               description "Notification action taken for contents with verdict meet threshold";
               uses apply-advanced;
               choice http-choice {
                 case case_1 {
                   leaf file {
                     description "File name for http response to client";
                     type string {
                       length "1 .. 255";
                     }
                   }
                 }
                 case case_2 {
                   leaf message {
                     description "Block message to client";
                     type string {
                       length "1 .. 1023";
                     }
                   }
                 }
                 case case_3 {
                   leaf redirect-url {
                     description "Redirect url to client";
                     type string {
                       length "1 .. 1023";
                       junos:posix-pattern "^https?://.*";
                       junos:pattern-message "URL must begin with http:// or https://";
                     }
                   }
                 }
               }
             }
             container notification {
               description "Notification action taken for contents with verdict meet threshold";
               uses apply-advanced;
               leaf log {
                 description "Logging option for Advanced Anti-malware actions";
                 type empty;
               }
             }
           }
           container smtp {
             description "Configure SMTP options";
             uses apply-advanced;
             leaf inspection-profile {
               description "Advanced Anti-malware inspection-profile name (default:default_profile)";
               type string {
                 length "1 .. 63";
               }
             }
             container notification {
               description "Notification action taken for contents with verdict meet threshold";
               uses apply-advanced;
               leaf log {
                 description "Logging option for Advanced Anti-malware actions";
                 type empty;
               }
             }
           }
           container imap {
             description "Configure IMAP options";
             uses apply-advanced;
             leaf inspection-profile {
               description "Advanced Anti-malware inspection-profile name (default:default_profile)";
               type string {
                 length "1 .. 63";
               }
             }
             container notification {
               description "Notification action taken for contents with verdict meet threshold";
               uses apply-advanced;
               leaf log {
                 description "Logging option for Advanced Anti-malware actions";
                 type empty;
               }
             }
           }
           container smb {
             description "Configure SMB options";
             uses apply-advanced;
             leaf inspection-profile {
               description "Advanced Anti-malware inspection-profile name (default:default_profile)";
               type string {
                 length "1 .. 63";
               }
             }
             leaf action {
               description "Action taken for contents with verdict meet threshold";
               type enumeration {
                 enum "permit" {
                   description "Allow contents";
                 }
                 enum "block" {
                   description "Disallow contents";
                 }
               }
             }
             container notification {
               description "Notification action taken for contents with verdict meet threshold";
               uses apply-advanced;
               leaf log {
                 description "Logging option for Advanced Anti-malware actions";
                 type empty;
               }
             }
           }
           leaf verdict-threshold {
             description "Verdict threshold";
             type enumeration {
               enum "1" {
                 description "Verdict-threshold level 1";
               }
               enum "2" {
                 description "Verdict-threshold level 2";
               }
               enum "3" {
                 description "Verdict-threshold level 3";
               }
               enum "4" {
                 description "Verdict-threshold level 4";
               }
               enum "5" {
                 description "Verdict-threshold level 5";
               }
               enum "6" {
                 description "Verdict-threshold level 6";
               }
               enum "7" {
                 description "Verdict-threshold level 7";
               }
               enum "8" {
                 description "Verdict-threshold level 8";
               }
               enum "9" {
                 description "Verdict-threshold level 9";
               }
               enum "10" {
                 description "Verdict-threshold level 10";
               }
               enum "recommended" {
                 description "Recommended verdict-threshold";
               }
             }
           }
           leaf inspection-profile {
             description "Advanced Anti-malware inspection-profile name";
             status deprecated;
             type string {
               length "1 .. 63";
             }
           }
           container fallback-options {
             description "Fallback options for abnormal conditions";
             uses apply-advanced;
             leaf action {
               description "Action taken for fallback conditions";
               type enumeration {
                 enum "permit" {
                   description "Allow contents";
                 }
                 enum "block" {
                   description "Disallow contents";
                 }
               }
             }
             container notification {
               description "Notification action taken for fallback action";
               uses apply-advanced;
               leaf log {
                 description "Logging option for Advanced Anti-malware fallback action";
                 type empty;
               }
             }
             container service-not-ready {
               description "Service not ready yet";
               uses apply-advanced;
               leaf action {
                 description "Action taken for fallback conditions";
                 type enumeration {
                   enum "permit" {
                     description "Allow contents";
                   }
                   enum "block" {
                     description "Disallow contents";
                   }
                 }
               }
               container notification {
                 description "Notification action taken for fallback action";
                 uses apply-advanced;
                 leaf log {
                   description "Logging option for Advanced Anti-malware fallback action";
                   type empty;
                 }
               }
             }
             container invalid-content-size {
               description "Content size exceed supported range";
               uses apply-advanced;
               leaf action {
                 description "Action taken for fallback conditions";
                 type enumeration {
                   enum "permit" {
                     description "Allow contents";
                   }
                   enum "block" {
                     description "Disallow contents";
                   }
                 }
               }
               container notification {
                 description "Notification action taken for fallback action";
                 uses apply-advanced;
                 leaf log {
                   description "Logging option for Advanced Anti-malware fallback action";
                   type empty;
                 }
               }
             }
             container out-of-resources {
               description "Service out of resources";
               uses apply-advanced;
               leaf action {
                 description "Action taken for fallback conditions";
                 type enumeration {
                   enum "permit" {
                     description "Allow contents";
                   }
                   enum "block" {
                     description "Disallow contents";
                   }
                 }
               }
               container notification {
                 description "Notification action taken for fallback action";
                 uses apply-advanced;
                 leaf log {
                   description "Logging option for Advanced Anti-malware fallback action";
                   type empty;
                 }
               }
             }
             container verdict-timeout {
               description "Verdict timed out";
               uses apply-advanced;
               leaf action {
                 description "Action taken for fallback conditions";
                 type enumeration {
                   enum "permit" {
                     description "Allow contents";
                   }
                   enum "block" {
                     description "Disallow contents";
                   }
                 }
               }
               container notification {
                 description "Notification action taken for fallback action";
                 uses apply-advanced;
                 leaf log {
                   description "Logging option for Advanced Anti-malware fallback action";
                   type empty;
                 }
               }
             }
             container submission-timeout {
               description "Submission timed out";
               uses apply-advanced;
               leaf action {
                 description "Action taken for fallback conditions";
                 type enumeration {
                   enum "permit" {
                     description "Allow contents";
                   }
                   enum "block" {
                     description "Disallow contents";
                   }
                 }
               }
               container notification {
                 description "Notification action taken for fallback action";
                 uses apply-advanced;
                 leaf log {
                   description "Logging option for Advanced Anti-malware fallback action";
                   type empty;
                 }
               }
             }
             container unknown-file {
               description "File type unknown";
               uses apply-advanced;
               leaf action {
                 description "Action taken for fallback conditions";
                 type enumeration {
                   enum "permit" {
                     description "Allow contents";
                   }
                   enum "block" {
                     description "Disallow contents";
                   }
                 }
               }
               container notification {
                 description "Notification action taken for fallback action";
                 uses apply-advanced;
                 leaf log {
                   description "Logging option for Advanced Anti-malware fallback action";
                   type empty;
                 }
               }
             }
           }
           container default-notification {
             description "Notification action taken for action";
             uses apply-advanced;
             leaf log {
               description "Logging option for Advanced Anti-malware action";
               type empty;
             }
           }
           container whitelist-notification {
             description "Whitelist notification logging option";
             uses apply-advanced;
             leaf log {
               description "Logging option for Advanced Anti-malware whitelist hit";
               type empty;
             }
           }
           container blacklist-notification {
             description "Blacklist notification logging option";
             uses apply-advanced;
             leaf log {
               description "Logging option for Advanced Anti-malware blacklist hit";
               type empty;
             }
           }
         }
         list policy {
           key name;
           description "Advanced Anti-malware policy";
           leaf name {
             description "Policy name, default policy must name (default-policy)";
             type string {
               length "1 .. 63";
             }
           }
           uses apply-advanced;
           container match {
             description "Policy match conditions";
             status deprecated;
             uses apply-advanced;
             leaf application {
               description "Application";
               type enumeration {
                 enum "HTTP" {
                   description "HTTP Traffic";
                 }
               }
             }
             leaf verdict-threshold {
               description "Verdict threshold";
               type enumeration {
                 enum "1" {
                   description "Verdict-threshold level 1";
                 }
                 enum "2" {
                   description "Verdict-threshold level 2";
                 }
                 enum "3" {
                   description "Verdict-threshold level 3";
                 }
                 enum "4" {
                   description "Verdict-threshold level 4";
                 }
                 enum "5" {
                   description "Verdict-threshold level 5";
                 }
                 enum "6" {
                   description "Verdict-threshold level 6";
                 }
                 enum "7" {
                   description "Verdict-threshold level 7";
                 }
                 enum "8" {
                   description "Verdict-threshold level 8";
                 }
                 enum "9" {
                   description "Verdict-threshold level 9";
                 }
                 enum "10" {
                   description "Verdict-threshold level 10";
                 }
                 enum "recommended" {
                   description "Recommended verdict-threshold";
                 }
               }
             }
           }
           container then {
             junos:must "(\".. match\")";
             junos:must-message "match must be defined";
             status deprecated;
             uses apply-advanced;
             leaf action {
               description "Action taken for contents with verdict meet threshold";
               type enumeration {
                 enum "permit" {
                   description "Allow contents";
                 }
                 enum "block" {
                   description "Disallow contents";
                 }
               }
             }
             container notification {
               description "Notification action taken for contents with verdict meet threshold";
               uses apply-advanced;
               leaf log {
                 description "Logging option for Advanced Anti-malware actions";
                 type empty;
               }
             }
           }
           container http {
             description "Configure HTTP options";
             uses apply-advanced;
             leaf inspection-profile {
               description "Advanced Anti-malware inspection-profile name (default:default_profile)";
               type string {
                 length "1 .. 63";
               }
             }
             leaf file-verdict-unknown {
               description "Action taken for contents with verdict unknown";
               type enumeration {
                 enum "permit" {
                   description "Allow contents";
                 }
                 enum "block" {
                   description "Disallow contents";
                 }
               }
             }
             leaf action {
               description "Action taken for contents with verdict meet threshold";
               type enumeration {
                 enum "permit" {
                   description "Allow contents";
                 }
                 enum "block" {
                   description "Disallow contents";
                 }
               }
             }
             container client-notify {
               description "Notification action taken for contents with verdict meet threshold";
               uses apply-advanced;
               choice http-choice {
                 case case_1 {
                   leaf file {
                     description "File name for http response to client";
                     type string {
                       length "1 .. 255";
                     }
                   }
                 }
                 case case_2 {
                   leaf message {
                     description "Block message to client";
                     type string {
                       length "1 .. 1023";
                     }
                   }
                 }
                 case case_3 {
                   leaf redirect-url {
                     description "Redirect url to client";
                     type string {
                       length "1 .. 1023";
                       junos:posix-pattern "^https?://.*";
                       junos:pattern-message "URL must begin with http:// or https://";
                     }
                   }
                 }
               }
             }
             container notification {
               description "Notification action taken for contents with verdict meet threshold";
               uses apply-advanced;
               leaf log {
                 description "Logging option for Advanced Anti-malware actions";
                 type empty;
               }
             }
           }
           container smtp {
             description "Configure SMTP options";
             uses apply-advanced;
             leaf inspection-profile {
               description "Advanced Anti-malware inspection-profile name (default:default_profile)";
               type string {
                 length "1 .. 63";
               }
             }
             container notification {
               description "Notification action taken for contents with verdict meet threshold";
               uses apply-advanced;
               leaf log {
                 description "Logging option for Advanced Anti-malware actions";
                 type empty;
               }
             }
           }
           container imap {
             description "Configure IMAP options";
             uses apply-advanced;
             leaf inspection-profile {
               description "Advanced Anti-malware inspection-profile name (default:default_profile)";
               type string {
                 length "1 .. 63";
               }
             }
             container notification {
               description "Notification action taken for contents with verdict meet threshold";
               uses apply-advanced;
               leaf log {
                 description "Logging option for Advanced Anti-malware actions";
                 type empty;
               }
             }
           }
           container smb {
             description "Configure SMB options";
             uses apply-advanced;
             leaf inspection-profile {
               description "Advanced Anti-malware inspection-profile name (default:default_profile)";
               type string {
                 length "1 .. 63";
               }
             }
             container notification {
               description "Notification action taken for contents with verdict meet threshold";
               uses apply-advanced;
               leaf log {
                 description "Logging option for Advanced Anti-malware actions";
                 type empty;
               }
             }
             leaf action {
               description "Action taken for contents with verdict meet threshold";
               type enumeration {
                 enum "permit" {
                   description "Allow contents";
                 }
                 enum "block" {
                   description "Disallow contents";
                 }
               }
             }
           }
           leaf verdict-threshold {
             description "Verdict threshold";
             type enumeration {
               enum "1" {
                 description "Verdict-threshold level 1";
               }
               enum "2" {
                 description "Verdict-threshold level 2";
               }
               enum "3" {
                 description "Verdict-threshold level 3";
               }
               enum "4" {
                 description "Verdict-threshold level 4";
               }
               enum "5" {
                 description "Verdict-threshold level 5";
               }
               enum "6" {
                 description "Verdict-threshold level 6";
               }
               enum "7" {
                 description "Verdict-threshold level 7";
               }
               enum "8" {
                 description "Verdict-threshold level 8";
               }
               enum "9" {
                 description "Verdict-threshold level 9";
               }
               enum "10" {
                 description "Verdict-threshold level 10";
               }
               enum "recommended" {
                 description "Recommended verdict-threshold";
               }
             }
           }
           leaf inspection-profile {
             description "Advanced Anti-malware inspection-profile name";
             status deprecated;
             type string {
               length "1 .. 63";
             }
           }
           container fallback-options {
             description "Fallback options for abnormal conditions";
             uses apply-advanced;
             leaf action {
               description "Action taken for fallback conditions";
               type enumeration {
                 enum "permit" {
                   description "Allow contents";
                 }
                 enum "block" {
                   description "Disallow contents";
                 }
               }
             }
             container notification {
               description "Notification action taken for fallback action";
               uses apply-advanced;
               leaf log {
                 description "Logging option for Advanced Anti-malware fallback action";
                 type empty;
               }
             }
             container service-not-ready {
               description "Service not ready yet";
               uses apply-advanced;
               leaf action {
                 description "Action taken for fallback conditions";
                 type enumeration {
                   enum "permit" {
                     description "Allow contents";
                   }
                   enum "block" {
                     description "Disallow contents";
                   }
                 }
               }
               container notification {
                 description "Notification action taken for fallback action";
                 uses apply-advanced;
                 leaf log {
                   description "Logging option for Advanced Anti-malware fallback action";
                   type empty;
                 }
               }
             }
             container invalid-content-size {
               description "Content size exceed supported range";
               uses apply-advanced;
               leaf action {
                 description "Action taken for fallback conditions";
                 type enumeration {
                   enum "permit" {
                     description "Allow contents";
                   }
                   enum "block" {
                     description "Disallow contents";
                   }
                 }
               }
               container notification {
                 description "Notification action taken for fallback action";
                 uses apply-advanced;
                 leaf log {
                   description "Logging option for Advanced Anti-malware fallback action";
                   type empty;
                 }
               }
             }
             container out-of-resources {
               description "Service out of resources";
               uses apply-advanced;
               leaf action {
                 description "Action taken for fallback conditions";
                 type enumeration {
                   enum "permit" {
                     description "Allow contents";
                   }
                   enum "block" {
                     description "Disallow contents";
                   }
                 }
               }
               container notification {
                 description "Notification action taken for fallback action";
                 uses apply-advanced;
                 leaf log {
                   description "Logging option for Advanced Anti-malware fallback action";
                   type empty;
                 }
               }
             }
             container verdict-timeout {
               description "Verdict timed out";
               uses apply-advanced;
               leaf action {
                 description "Action taken for fallback conditions";
                 type enumeration {
                   enum "permit" {
                     description "Allow contents";
                   }
                   enum "block" {
                     description "Disallow contents";
                   }
                 }
               }
               container notification {
                 description "Notification action taken for fallback action";
                 uses apply-advanced;
                 leaf log {
                   description "Logging option for Advanced Anti-malware fallback action";
                   type empty;
                 }
               }
             }
             container submission-timeout {
               description "Submission timed out";
               uses apply-advanced;
               leaf action {
                 description "Action taken for fallback conditions";
                 type enumeration {
                   enum "permit" {
                     description "Allow contents";
                   }
                   enum "block" {
                     description "Disallow contents";
                   }
                 }
               }
               container notification {
                 description "Notification action taken for fallback action";
                 uses apply-advanced;
                 leaf log {
                   description "Logging option for Advanced Anti-malware fallback action";
                   type empty;
                 }
               }
             }
             container unknown-file {
               description "File type unknown";
               uses apply-advanced;
               leaf action {
                 description "Action taken for fallback conditions";
                 type enumeration {
                   enum "permit" {
                     description "Allow contents";
                   }
                   enum "block" {
                     description "Disallow contents";
                   }
                 }
               }
               container notification {
                 description "Notification action taken for fallback action";
                 uses apply-advanced;
                 leaf log {
                   description "Logging option for Advanced Anti-malware fallback action";
                   type empty;
                 }
               }
             }
           }
           container default-notification {
             description "Notification action taken for action";
             uses apply-advanced;
             leaf log {
               description "Logging option for Advanced Anti-malware action";
               type empty;
             }
           }
           container whitelist-notification {
             description "Whitelist notification logging option";
             uses apply-advanced;
             leaf log {
               description "Logging option for Advanced Anti-malware whitelist hit";
               type empty;
             }
           }
           container blacklist-notification {
             description "Blacklist notification logging option";
             uses apply-advanced;
             leaf log {
               description "Logging option for Advanced Anti-malware blacklist hit";
               type empty;
             }
           }
         }
         container traceoptions {
           description "Advanced Anti-malware trace options";
           uses aamwd-traceoptions;
         }
       }
       container user-identification {
         description "Configure user-identification";
         uses apply-advanced;
         container active-directory-access {
           presence "enable active-directory-access";
           description "Configure active directory access";
           uses apply-advanced;
           container traceoptions {
             description "Active-directory-access Tracing Options";
             uses apply-advanced;
             leaf no-remote-trace {
               description "Disable remote tracing";
               junos:must "(\"system tracing\")";
               junos:must-message "'no-remote-trace' is valid only when [system tracing] is configured";
               type empty;
             }
             container file {
               description "Trace file information";
               leaf filename {
                 description "Name of file in which to write trace information";
                 type string {
                   length "1 .. 1024";
                   junos:posix-pattern "![/ %]";
                   junos:pattern-message "Must not contain '/', % or a space";
                 }
               }
               leaf size {
                 description "Maximum trace file size";
                 type string;
               }
               leaf files {
                 description "Maximum number of trace files";
                 default "3";
                 type union {
                   type string {
                     pattern "<.*>|$.*";
                   }
                   type uint32 {
                     range "2 .. 1000";
                   }
                 }
               }
               choice world-readable-choice {
                 leaf world-readable {
                   description "Allow any user to read the log file";
                   type empty;
                 }
                 leaf no-world-readable {
                   description "Don't allow any user to read the log file";
                   type empty;
                 }
               }
               leaf match {
                 description "Regular expression for lines to be logged";
                 type jt:regular-expression;
               }
             }
             leaf level {
               description "Level of debugging output";
               type enumeration {
                 enum "error" {
                   description "Match error conditions";
                 }
                 enum "warning" {
                   description "Match warning messages";
                 }
                 enum "notice" {
                   description "Match conditions that should be handled specially";
                 }
                 enum "info" {
                   description "Match informational messages";
                 }
                 enum "verbose" {
                   description "Match verbose messages";
                 }
                 enum "all" {
                   description "Match all levels";
                 }
               }
             }
             list flag {
               key name;
               ordered-by user;
               description "Tracing parameters";
               leaf name {
                 type enumeration {
                   enum "active-directory-authentication" {
                     description "Trace active directory auth";
                   }
                   enum "configuration" {
                     description "Trace configuration";
                   }
                   enum "db" {
                     description "Trace db";
                   }
                   enum "ip-user-mapping" {
                     description "Trace ip-user-mapping module";
                   }
                   enum "ip-user-probe" {
                     description "Trace ip-user-probe";
                   }
                   enum "ipc" {
                     description "Trace ipc";
                   }
                   enum "user-group-mapping" {
                     description "Trace user-group-mapping module";
                   }
                   enum "wmic" {
                     description "Trace wmic";
                   }
                   enum "memory" {
                     description "Trace memory";
                   }
                   enum "all" {
                     description "Trace everything";
                   }
                 }
               }
             }
           }
           list domain {
             key name;
             ordered-by user;
             description "Configure active-directory-access domain";
             max-elements 2;
             leaf name {
               description "Domain name";
               type string {
                 length "1 .. 64";
                 junos:posix-pattern "^[[:alnum:]._-]+$|^\\\\*$";
                 junos:pattern-message "Must be a string consisting of letters, numbers, dashes, underscores and dots";
               }
             }
             uses apply-advanced;
             container user {
               description "User name";
               uses apply-advanced;
               leaf user-name {
                 description "User name";
                 type string {
                   length "1 .. 64";
                   junos:posix-pattern "^[[:alnum:]._-]+$|^\\\\*$";
                   junos:pattern-message "Must be a string consisting of letters, numbers, dashes, underscores and dots";
                 }
               }
               leaf password {
                 description "Password string";
                 type string {
                   length "1 .. 128";
                 }
               }
             }
             list domain-controller {
               key name;
               ordered-by user;
               description "Domain controller";
               max-elements 10;
               leaf name {
                 description "Domain controller name";
                 type string {
                   length "1 .. 64";
                   junos:posix-pattern "^[[:alnum:]._-]+$|^\\\\*$";
                   junos:pattern-message "Must be a string consisting of letters, numbers, dashes, underscores and dots";
                 }
               }
               uses apply-advanced;
               leaf address {
                 description "Address of domain controller";
                 type jt:ipaddr;
               }
             }
             container ip-user-mapping {
               description "Ip-user-mapping";
               uses apply-advanced;
               container discovery-method {
                 description "Discovery method";
                 uses apply-advanced;
                 container wmi {
                   presence "enable wmi";
                   description "WMI";
                   uses apply-advanced;
                   leaf event-log-scanning-interval {
                     description "Interval of event log scanning";
                     units "seconds";
                     type union {
                       type string {
                         pattern "<.*>|$.*";
                       }
                       type uint16 {
                         range "5 .. 60";
                       }
                     }
                   }
                   leaf initial-event-log-timespan {
                     description "Event log scanning timespan";
                     units "hours";
                     type union {
                       type string {
                         pattern "<.*>|$.*";
                       }
                       type uint16 {
                         range "1 .. 168";
                       }
                     }
                   }
                 }
               }
             }
             container user-group-mapping {
               description "User-group-mapping";
               uses user-group-mapping-type;
             }
           }
           leaf no-on-demand-probe {
             description "Disable on-demand probe";
             type empty;
           }
           leaf authentication-entry-timeout {
             description "Authentication entry timeout number (0, 10-1440)";
             units "minutes";
             type union {
               type uint16;
               type string {
                 pattern "<.*>|$.*";
               }
             }
           }
           leaf invalid-authentication-entry-timeout {
             description "Invalid authentication entry timeout number (0, 10-1440)";
             units "minutes";
             type union {
               type uint16;
               type string {
                 pattern "<.*>|$.*";
               }
             }
           }
           leaf firewall-authentication-forced-timeout {
             description "Firewallauth fallback authentication entry forced timeout number (10-1440)";
             units "minutes";
             type union {
               type uint16;
               type string {
                 pattern "<.*>|$.*";
               }
             }
           }
           leaf wmi-timeout {
             description "Wmi timeout number";
             units "seconds";
             type union {
               type string {
                 pattern "<.*>|$.*";
               }
               type uint32 {
                 range "3 .. 120";
               }
             }
           }
           leaf thread {
             description "Thread to do PC probe";
             type union {
               type string {
                 pattern "<.*>|$.*";
               }
               type uint16 {
                 range "1 .. 100";
               }
             }
           }
           leaf probe-rate {
             description "PC probe rate per minute";
             type union {
               type string {
                 pattern "<.*>|$.*";
               }
               type uint32 {
                 range "100 .. 1500";
               }
             }
           }
           leaf-list event-log-identifier {
             ordered-by user;
             description "Event log identifier";
             type union {
               type uint16;
               type string {
                 pattern "<.*>|$.*";
               }
             }
           }
           leaf-list logon-type {
             ordered-by user;
             description "Logon type";
             type union {
               type uint16;
               type string {
                 pattern "<.*>|$.*";
               }
             }
           }
           container filter {
             description "Configure filter address or prefix";
             uses apply-advanced;
             list include {
               key name;
               ordered-by user;
               description "Include address";
               max-elements 20;
               leaf name {
                 description "Address or prefix";
                 type jt:ipprefix;
               }
             }
             list exclude {
               key name;
               ordered-by user;
               description "Exclude address";
               max-elements 20;
               leaf name {
                 description "Address or prefix";
                 type jt:ipprefix;
               }
             }
           }
         }
         list authentication-source {
           key name;
           ordered-by user;
           description "Configure authentication-source";
           max-elements 2;
           leaf name {
             description "Authenticaton source name";
             type enumeration {
               enum "aruba-clearpass" {
                 description "Authentication source from Aruba ClearPass";
               }
             }
           }
           uses apply-advanced;
           leaf authentication-entry-timeout {
             description "Aruba ClearPass authentication entry timeout number (0, 10-1440)";
             units "minutes";
             type union {
               type uint16;
               type string {
                 pattern "<.*>|$.*";
               }
             }
           }
           leaf invalid-authentication-entry-timeout {
             description "Invalid authentication entry timeout number (0, 10-1440)";
             units "minutes";
             type union {
               type uint16;
               type string {
                 pattern "<.*>|$.*";
               }
             }
           }
           container traceoptions {
             description "Aruba ClearPass authentication table Tracing Options";
             uses apply-advanced;
             leaf no-remote-trace {
               description "Disable remote tracing";
               junos:must "(\"system tracing\")";
               junos:must-message "'no-remote-trace' is valid only when [system tracing] is configured";
               type empty;
             }
             container file {
               description "Trace file information";
               leaf filename {
                 description "Name of file in which to write trace information";
                 type string {
                   length "1 .. 1024";
                   junos:posix-pattern "![/ %]";
                   junos:pattern-message "Must not contain '/', % or a space";
                 }
               }
               leaf size {
                 description "Maximum trace file size";
                 type string;
               }
               leaf files {
                 description "Maximum number of trace files";
                 default "3";
                 type union {
                   type string {
                     pattern "<.*>|$.*";
                   }
                   type uint32 {
                     range "2 .. 1000";
                   }
                 }
               }
               choice world-readable-choice {
                 leaf world-readable {
                   description "Allow any user to read the log file";
                   type empty;
                 }
                 leaf no-world-readable {
                   description "Don't allow any user to read the log file";
                   type empty;
                 }
               }
               leaf match {
                 description "Regular expression for lines to be logged";
                 type jt:regular-expression;
               }
             }
             leaf level {
               description "Level of debugging output";
               type enumeration {
                 enum "error" {
                   description "Match error conditions";
                 }
                 enum "warning" {
                   description "Match warning messages";
                 }
                 enum "notice" {
                   description "Match conditions that should be handled specially";
                 }
                 enum "info" {
                   description "Match informational messages";
                 }
                 enum "verbose" {
                   description "Match verbose messages";
                 }
                 enum "all" {
                   description "Match all levels";
                 }
               }
             }
             list flag {
               key name;
               ordered-by user;
               description "Tracing parameters";
               leaf name {
                 type enumeration {
                   enum "all" {
                     description "Trace Aruba ClearPass all modules";
                   }
                   enum "clearpass-authentication" {
                     description "Trace Aruba ClearPass auth table management module";
                   }
                   enum "configuration" {
                     description "Trace Aruba ClearPass configuration";
                   }
                   enum "dispatcher" {
                     description "Trace dispatcher module";
                   }
                   enum "ipc" {
                     description "Trace ipc";
                   }
                   enum "user-query" {
                     description "Trace user-query module";
                   }
                   enum "memory" {
                     description "Trace memory";
                   }
                 }
               }
             }
           }
           container user-query {
             description "ClearPass individual user query";
             uses apply-advanced;
             container web-server {
               description "Web server for user query";
               uses apply-advanced;
               leaf server-name {
                 description "Web server name";
                 type string {
                   length "1 .. 64";
                 }
               }
               leaf connect-method {
                 description "Method of connecting to web server";
                 type enumeration {
                   enum "https" {
                     description "HTTPS connection to web server";
                   }
                   enum "http" {
                     description "HTTP connection to web server";
                   }
                 }
               }
               leaf address {
                 description "IP address or hostname of web server";
                 type string {
                   length "1 .. 128";
                 }
               }
               leaf port {
                 description "Web server port";
                 default "443";
                 type union {
                   type string {
                     pattern "<.*>|$.*";
                   }
                   type uint32 {
                     range "1 .. 65535";
                   }
                 }
               }
             }
             leaf ca-certificate {
               description "Ca-certificate file name";
               type string {
                 length "1 .. 256";
               }
             }
             leaf client-id {
               description "Client ID for OAuth2 grant";
               type string {
                 length "1 .. 64";
               }
             }
             leaf client-secret {
               description "Client secret for OAuth2 grant";
               type string {
                 length "1 .. 128";
               }
             }
             leaf token-api {
               description "API of acquiring token for OAuth2 authentication";
               type string {
                 length "1 .. 128";
               }
             }
             leaf query-api {
               description "User query API";
               type string {
                 length "4 .. 128";
               }
             }
             leaf delay-query-time {
               description "Delay time to send user query (0~60sec)";
               default "15";
               units "seconds";
               type union {
                 type string {
                   pattern "<.*>|$.*";
                 }
                 type uint8 {
                   range "0 .. 60";
                 }
               }
             }
           }
           container no-user-query {
             presence "enable no-user-query";
             description "Disable user query from ClearPass";
           }
         }
         container device-information {
           description "Device information configuration";
           uses apply-advanced;
           container authentication-source {
             description "Configure authentication-source";
             uses apply-advanced;
             leaf authentication-source-name {
               default "no-configured";
               type enumeration {
                 enum "active-directory" {
                   description "From windows active directory";
                 }
                 enum "network-access-controller" {
                   description "From network access controller such as Aruba ClearPass or JIMS";
                 }
                 enum "no-configured" {
                   description "No configuring authentication source for device entry";
                 }
               }
             }
           }
           container end-user-profile {
             description "End-user-profile configuration";
             uses apply-advanced;
             list profile-name {
               key name;
               ordered-by user;
               description "End-user-profile profile-name configuration";
               leaf name {
                 description "End-user-profile profile-name";
                 type string {
                   length "1 .. 64";
                   junos:posix-pattern "^[[:alnum:]._-]+$|^\\\\*$";
                   junos:pattern-message "Must be a string consisting of letters, numbers, dashes, underscores and dots";
                 }
               }
               uses apply-advanced;
               leaf domain-name {
                 description "Domain name";
                 type string {
                   length "1 .. 64";
                   junos:posix-pattern "^[[:alnum:]._-]+$|^\\\\*$";
                   junos:pattern-message "Must be a string consisting of letters, numbers, dashes, underscores and dots";
                 }
               }
               list attribute {
                 key name;
                 ordered-by user;
                 description "Attribute";
                 leaf name {
                   description "Attribute name";
                   type string;
                 }
                 uses apply-advanced;
                 choice attribute-value {
                   case case_1 {
                     leaf-list string {
                       ordered-by user;
                       description "Value type is strings";
                       type string;
                       max-elements 20;
                     }
                   }
                   case case_2 {
                     container digital {
                       presence "enable digital";
                       description "Value type is digital";
                       uses apply-advanced;
                       leaf-list value {
                         ordered-by user;
                         description "Digital value";
                         type union {
                           type uint32;
                           type string {
                             pattern "<.*>|$.*";
                           }
                         }
                       }
                       list from {
                         key name;
                         ordered-by user;
                         description "Range of digital value";
                         leaf name {
                           description "Digit range's start value";
                           type union {
                             type uint32;
                             type string {
                               pattern "<.*>|$.*";
                             }
                           }
                         }
                         uses apply-advanced;
                         leaf to {
                           description "Digit range's end value";
                           type union {
                             type uint32;
                             type string {
                               pattern "<.*>|$.*";
                             }
                           }
                         }
                       }
                     }
                   }
                 }
               }
             }
           }
           container traceoptions {
             description "Device info related Tracing Options";
             uses apply-advanced;
             leaf no-remote-trace {
               description "Disable remote tracing";
               junos:must "(\"system tracing\")";
               junos:must-message "'no-remote-trace' is valid only when [system tracing] is configured";
               type empty;
             }
             container file {
               description "Trace file information";
               leaf filename {
                 description "Name of file in which to write trace information";
                 type string {
                   length "1 .. 1024";
                   junos:posix-pattern "![/ %]";
                   junos:pattern-message "Must not contain '/', % or a space";
                 }
               }
               leaf size {
                 description "Maximum trace file size";
                 type string;
               }
               leaf files {
                 description "Maximum number of trace files";
                 default "3";
                 type union {
                   type string {
                     pattern "<.*>|$.*";
                   }
                   type uint32 {
                     range "2 .. 1000";
                   }
                 }
               }
               choice world-readable-choice {
                 leaf world-readable {
                   description "Allow any user to read the log file";
                   type empty;
                 }
                 leaf no-world-readable {
                   description "Don't allow any user to read the log file";
                   type empty;
                 }
               }
               leaf match {
                 description "Regular expression for lines to be logged";
                 type jt:regular-expression;
               }
             }
             leaf level {
               description "Level of debugging output";
               type enumeration {
                 enum "error" {
                   description "Match error conditions";
                 }
                 enum "warning" {
                   description "Match warning messages";
                 }
                 enum "notice" {
                   description "Match conditions that should be handled specially";
                 }
                 enum "info" {
                   description "Match informational messages";
                 }
                 enum "verbose" {
                   description "Match verbose messages";
                 }
                 enum "all" {
                   description "Match all levels";
                 }
               }
             }
             list flag {
               key name;
               ordered-by user;
               description "Tracing parameters";
               leaf name {
                 type enumeration {
                   enum "all" {
                     description "Trace device info all modules";
                   }
                   enum "auth-source" {
                     description "Trace Auth source module";
                   }
                   enum "configuration" {
                     description "Trace Device info configuration";
                   }
                   enum "device-table" {
                     description "Trace device table management module";
                   }
                   enum "ipid-all" {
                     description "Trace IPID all functions";
                   }
                   enum "ipid-db" {
                     description "Trace IPID Database function";
                   }
                   enum "ipid-entry" {
                     description "Trace IPID entry management function";
                   }
                   enum "ipid-ipc" {
                     description "Trace IPID communication processing function";
                   }
                   enum "ipid-message" {
                     description "Trace IPID message processing function";
                   }
                   enum "ipid-others" {
                     description "Trace IPID other function";
                   }
                   enum "ipid-server" {
                     description "Trace IPID server handling function";
                   }
                   enum "ipid-statistics" {
                     description "Trace IPID statistics handling function";
                   }
                   enum "ipid-task" {
                     description "Trace IPID task handling function";
                   }
                   enum "profile-lookup" {
                     description "Trace End-user-profile lookup function";
                   }
                   enum "memory" {
                     description "Trace memory";
                   }
                 }
               }
             }
           }
         }
         container identity-management {
           description "Identity management configuration";
           uses apply-advanced;
           leaf authentication-entry-timeout {
             description "Authentication entry timeout number (0, 10-1440)";
             default "60";
             units "minutes";
             type union {
               type uint16;
               type string {
                 pattern "<.*>|$.*";
               }
             }
           }
           leaf invalid-authentication-entry-timeout {
             description "Invalid authentication entry timeout number (0, 10-1440)";
             default "30";
             units "minutes";
             type union {
               type uint16;
               type string {
                 pattern "<.*>|$.*";
               }
             }
           }
           leaf preserve-valid-user {
             description "Null user will not overwrite valid user for the same ip";
             type empty;
           }
           container connection {
             description "Connection to identity management";
             uses identity-management-connection-type;
           }
           container jims-validator {
             description "Web server from JIMS for Validate or group query request";
             uses jims-validator-type;
           }
           container batch-query {
             description "Batch query parameters";
             uses batch-query-type;
           }
           container ip-query {
             description "IP query parameters";
             uses apply-advanced;
             leaf query-delay-time {
               description "Delay time to send IP query (0~60sec)";
               default "15";
               units "seconds";
               type union {
                 type string {
                   pattern "<.*>|$.*";
                 }
                 type uint8 {
                   range "0 .. 60";
                 }
               }
             }
             container no-ip-query {
               presence "enable no-ip-query";
               description "Disable IP query";
             }
             leaf max-connections {
               description "Max connection number";
               type union {
                 type string {
                   pattern "<.*>|$.*";
                 }
                 type uint32 {
                   range "1 .. 20";
                 }
               }
             }
           }
           container filter {
             description "Filter for query";
             uses apply-advanced;
             list domain {
               key name;
               ordered-by user;
               description "Domain filter";
               max-elements 20;
               leaf name {
                 description "Domain name";
                 type string {
                   length "1 .. 64";
                   junos:posix-pattern "^[[:alnum:]._-]+$|^\\\\*$";
                   junos:pattern-message "Must be a string consisting of letters, numbers, dashes, underscores and dots";
                 }
               }
             }
             container include-ip {
               description "Include IP filter";
               uses address-filter-type;
             }
             container exclude-ip {
               description "Exclude IP filter";
               uses address-filter-type;
             }
           }
           container traceoptions {
             description "Tracing Options";
             uses ims-traceoptions-type;
           }
         }
         container logical-domain-identity-management {
           description "Logical domain identity management configuration";
           uses apply-advanced;
           container active {
             description "Actve mode for logical domain identity management moudule";
             uses apply-advanced;
             leaf authentication-entry-timeout {
               description "Authentication entry timeout number (0, 10-1440)";
               default "60";
               units "minutes";
               type union {
                 type uint16;
                 type string {
                   pattern "<.*>|$.*";
                 }
               }
             }
             leaf invalid-authentication-entry-timeout {
               description "Invalid authentication entry timeout number (0, 10-1440)";
               default "30";
               units "minutes";
               type union {
                 type uint16;
                 type string {
                   pattern "<.*>|$.*";
                 }
               }
             }
             container ip-query {
               description "IP query parameters";
               uses apply-advanced;
               leaf query-delay-time {
                 description "Delay time to send IP query (0~60sec)";
                 default "15";
                 units "seconds";
                 type union {
                   type string {
                     pattern "<.*>|$.*";
                   }
                   type uint8 {
                     range "0 .. 60";
                   }
                 }
               }
             }
             container filter {
               description "Filter for query";
               uses apply-advanced;
               list domain {
                 key name;
                 ordered-by user;
                 description "Domain filter";
                 max-elements 20;
                 leaf name {
                   description "Domain name";
                   type string {
                     length "1 .. 64";
                     junos:posix-pattern "^[[:alnum:]._-]+$|^\\\\*$";
                     junos:pattern-message "Must be a string consisting of letters, numbers, dashes, underscores and dots";
                   }
                 }
               }
               container include-ip {
                 description "Include IP filter";
                 uses address-filter-type;
               }
               container exclude-ip {
                 description "Exclude IP filter";
                 uses address-filter-type;
               }
             }
             list query-server {
               key name;
               ordered-by user;
               description "Query server";
               max-elements 1;
               leaf name {
                 description "Query server name";
                 type string {
                   length "1 .. 64";
                   junos:posix-pattern "^[[:alnum:]._-]+$|^\\\\*$";
                   junos:pattern-message "Must be a string consisting of letters, numbers, dashes, underscores and dots";
                 }
               }
               uses apply-advanced;
               container connection {
                 description "Connection to identity management";
                 uses ims-connection-type;
               }
               container batch-query {
                 description "Batch query parameters";
                 uses batch-query-type;
               }
             }
           }
           container traceoptions {
             description "Tracing Options";
             uses ims-traceoptions-type;
           }
         }
       }
       container security-metadata-streaming {
         uses apply-advanced;
         list policy {
           key name;
           description "Security Metadata Streaming policy";
           leaf name {
             description "Policy name";
             type string {
               length "1 .. 63";
             }
           }
           uses apply-advanced;
           container http {
             description "Configure HTTP options";
             uses apply-advanced;
             container detections {
               description "Type of Detection Methods for DNS Request";
               uses apply-advanced;
               container encryptedc2 {
                 description "Detection on the HTTPS";
                 uses apply-advanced;
                 leaf action {
                   description " Action to take on the HTTPS packet";
                   type enumeration {
                     enum "permit" {
                       description "Allow traffic";
                     }
                   }
                 }
                 leaf notification {
                   description "Notification action taken for traffic";
                   type enumeration {
                     enum "log" {
                       description "Log Everything";
                     }
                     enum "log-detections" {
                       description "Log only Macilious HTTP detections";
                     }
                   }
                 }
                 container fallback-options {
                   description "Fallback options for encryptedc2 detection";
                   uses apply-advanced;
                   container notification {
                     description "Notification action taken for the packet";
                     uses apply-advanced;
                     leaf log {
                       description "Log HTTP Request";
                       type empty;
                     }
                   }
                 }
               }
               container all {
                 junos:must "(!(\" .. encryptedc2\"))";
                 junos:must-message "All can only be configured if no other detection is configured";
                 description "All Detections";
                 uses apply-advanced;
                 leaf action {
                   description "Action for HTTP";
                   type enumeration {
                     enum "permit" {
                       description "Allow traffic";
                     }
                   }
                 }
                 leaf notification {
                   description "Notification action taken for traffic";
                   type enumeration {
                     enum "log" {
                       description "Log Everything";
                     }
                     enum "log-detections" {
                       description "Log only Macilious HTTP detections";
                     }
                   }
                 }
                 container fallback-options {
                   description "Fallback options for the encryptedc2 detection";
                   uses apply-advanced;
                   container notification {
                     description "Notification action taken for the packet";
                     uses apply-advanced;
                     leaf log {
                       description "Log HTTP Request";
                       type empty;
                     }
                   }
                 }
               }
             }
           }
           container dns {
             description "Configure DNS options";
             uses apply-advanced;
             container cache {
               description "Storing DNS in Cache till TTL";
               uses apply-advanced;
               container ttl {
                 presence "enable ttl";
                 description "For setting TTL values";
                 uses apply-advanced;
                 leaf benign {
                   description "Set Benign TTL value";
                   default "86400";
                   units "seconds";
                   type union {
                     type string {
                       pattern "<.*>|$.*";
                     }
                     type uint32 {
                       range "60 .. 172800";
                     }
                   }
                 }
                 leaf c2 {
                   description "Set C2 TTL value";
                   default "86400";
                   units "seconds";
                   type union {
                     type string {
                       pattern "<.*>|$.*";
                     }
                     type uint32 {
                       range "60 .. 172800";
                     }
                   }
                 }
               }
             }
             container detections {
               description "Type of Detection Methods for DNS Request";
               uses apply-advanced;
               container dga {
                 description "Detecting DGA Algorithms on DNS Packets";
                 uses apply-advanced;
                 leaf action {
                   description "Action to take on the DNS tunneled packet";
                   type enumeration {
                     enum "permit" {
                       description "Allow the packet";
                     }
                     enum "deny" {
                       description "Drop the packet";
                     }
                     enum "sinkhole" {
                       description "Sinkhole the packet";
                     }
                   }
                 }
                 leaf verdict-timeout {
                   description "Time to wait for a verdict on DNS Packet";
                   default "100";
                   units "milliseconds";
                   type union {
                     type string {
                       pattern "<.*>|$.*";
                     }
                     type uint32 {
                       range "50 .. 500";
                     }
                   }
                 }
                 leaf notification {
                   description "Notification action taken for DNS DGA Detection";
                   type enumeration {
                     enum "log" {
                       description "Log Everything";
                     }
                     enum "log-detections" {
                       description "Only log malicious DNS activity";
                     }
                   }
                 }
                 container fallback-options {
                   description "Fallback options for DNS DGA detection";
                   uses apply-advanced;
                   container notification {
                     description "Notification action taken for the packet";
                     uses apply-advanced;
                     leaf log {
                       description "Log DNS Request";
                       type empty;
                     }
                   }
                 }
               }
               container tunneling {
                 description "Detecting DNS Tunneling";
                 uses apply-advanced;
                 leaf action {
                   description " Action to take on the DNS tunneled packet";
                   type enumeration {
                     enum "permit" {
                       description "Allow the packet";
                     }
                     enum "deny" {
                       description "Drop the packet";
                     }
                     enum "sinkhole" {
                       description "Sinkhole the packet";
                     }
                   }
                 }
                 leaf notification {
                   description "Notification action taken for DNS Tunneling Detection";
                   type enumeration {
                     enum "log" {
                       description "Log Everything";
                     }
                     enum "log-detections" {
                       description "Only log malicious DNS activity";
                     }
                   }
                 }
                 leaf inspection-depth {
                   description "Number of packets to be inspected for Tunnel Detection";
                   default "4";
                   type union {
                     type string {
                       pattern "<.*>|$.*";
                     }
                     type uint8 {
                       range "0 .. 10";
                     }
                   }
                 }
                 container fallback-options {
                   description "Fallback options for DNS Tunneling detection";
                   uses apply-advanced;
                   container notification {
                     description "Notification action taken for the packet";
                     uses apply-advanced;
                     leaf log {
                       description "Log DNS Request";
                       type empty;
                     }
                   }
                 }
               }
               container all {
                 junos:must "((!(\" .. dga\") && !(\" .. tunneling\")))";
                 junos:must-message "All can only be configured if no other detection is configured";
                 description "All Detections";
                 uses apply-advanced;
                 leaf action {
                   description " Global Action to take on the DNS packet";
                   type enumeration {
                     enum "permit" {
                       description "Allow the packet";
                     }
                     enum "deny" {
                       description "Drop the packet";
                     }
                     enum "sinkhole" {
                       description "Sinkhole the packet";
                     }
                   }
                 }
                 leaf notification {
                   description "Global Notification action taken for DNS Detection Methods";
                   type enumeration {
                     enum "log" {
                       description "Log Everything";
                     }
                     enum "log-detections" {
                       description "Only log malicious DNS activity";
                     }
                   }
                 }
                 container fallback-options {
                   description "Fallback options for DNS detections";
                   uses apply-advanced;
                   container notification {
                     description "Notification action taken for the packet";
                     uses apply-advanced;
                     leaf log {
                       description "Log DNS Request";
                       type empty;
                     }
                   }
                 }
               }
             }
           }
         }
       }
       container dns-filtering {
         presence "enable dns-filtering";
         uses apply-advanced;
         container traceoptions {
           description "Security intelligence trace options";
           uses dnsf-traceoptions-object;
         }
         container sinkhole {
           presence "enable sinkhole";
           description "DNS Sinkhole Configuration";
           uses apply-advanced;
           leaf ipv4-address {
             description "Sinkhole IPv4 address";
             type jt:ipv4addr;
           }
           leaf ipv6-address {
             description "Sinkhole IPv6 address";
             type jt:ipv6addr;
           }
           leaf fqdn {
             description "FQDN sent as response to MX qeries";
             type string {
               length "1 .. 80";
             }
           }
           leaf dns-resp-ttl {
             description "TTL to be used in DNS response";
             default "1800";
             units "seconds";
             type union {
               type string {
                 pattern "<.*>|$.*";
               }
               type uint32 {
                 range "0 .. 3600";
               }
             }
           }
           leaf wildcarding-level {
             description "Wildcarding level for exact match";
             default "2";
             type union {
               type string {
                 pattern "<.*>|$.*";
               }
               type uint32 {
                 range "0 .. 10";
               }
             }
           }
           leaf txt-resp-err-code {
             description "Text response error code";
             default "Refused";
             type enumeration {
               enum "Noerror" {
                 description "No error response";
               }
               enum "Refused" {
                 description "Refuse the DNS Query";
               }
             }
           }
           leaf srv-resp-err-code {
             description "Server response error code";
             default "Refused";
             type enumeration {
               enum "Noerror" {
                 description "No error response";
               }
               enum "Refused" {
                 description "Refuse the DNS Query";
               }
             }
           }
         }
       }
       container vector-routing {
         description "Configure service vector routing";
         uses apply-advanced;
         leaf authority-name {
           description "Authority name";
           type string {
             length "1 .. 63";
           }
         }
         list cipher-suites {
           key name;
           ordered-by user;
           description "Cipher suites";
           uses svr-cipher-suite-list-type;
         }
         list router {
           key name;
           ordered-by user;
           description "Router configuration";
           max-elements 1;
           junos:must "(\".. authority-name\")";
           junos:must-message "'authority-name' must be configured";
           uses svr-router-list-type;
         }
         list source-tenants {
           key name;
           ordered-by user;
           description "Configure vector routing source tenant";
           uses svr-source-tenant-list-type;
         }
         list destination-services {
           key name;
           ordered-by user;
           description "Configure vector routing destination service";
           uses svr-destination-service-list-type;
         }
         container meta-bfd {
           description "Meta-BFD configuration";
           uses svr-meta-bfd-type;
         }
         container traceoptions {
           description "Vector routing trace options";
           uses vector-routing-traceoptions;
         }
       }
     }
     container class-of-service {
       presence "enable class-of-service";
       description "Class-of-service configuration";
       uses apply-advanced;
       container application-traffic-control {
         presence "enable application-traffic-control";
         description "Application classifier configuration";
         uses apply-advanced;
         container traceoptions {
           description "Trace options for application classifier";
           uses appqos-traceoptions-type;
         }
         list rate-limiters {
           key name;
           ordered-by user;
           description "Configure application-traffic-control rate limiters";
           leaf name {
             description "Application classifier rate-limiter name";
             type string {
               length "1 .. 63";
             }
           }
           uses apply-advanced;
           leaf bandwidth-limit {
             description "Bandwidth limit";
             units "kbps";
             type union {
               type string {
                 pattern "<.*>|$.*";
               }
               type uint32 {
                 range "64 .. 10485760";
               }
             }
           }
           leaf burst-size-limit {
             description "Burst size limit (default with bandwidth-limit and no larger than 6400 * bandwidth)";
             units "bytes";
             type union {
               type string {
                 pattern "<.*>|$.*";
               }
               type uint32 {
                 range "1 .. 1342177280";
               }
             }
           }
         }
         list rule-sets {
           key name;
           ordered-by user;
           description "Configure application-traffic-control rule-sets";
           leaf name {
             description "Application classifier rule-set name";
             type string {
               length "1 .. 63";
             }
           }
           uses apply-advanced;
           list rule {
             key name;
             ordered-by user;
             description "Rule";
             uses appqos_rule_type;
           }
         }
       }
     }
   }
   grouping aamwd-traceoptions {
     description "Advanced anti-malware trace options";
     uses apply-advanced;
     leaf no-remote-trace {
       description "Disable remote tracing";
       junos:must "(\"system tracing\")";
       junos:must-message "'no-remote-trace' is valid only when [system tracing] is configured";
       type empty;
     }
     container file {
       description "Trace file information";
       leaf filename {
         description "Name of file in which to write trace information";
         type string {
           length "1 .. 1024";
           junos:posix-pattern "![/ %]";
           junos:pattern-message "Must not contain '/', % or a space";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     leaf level {
       description "Level of debugging output";
       type enumeration {
         enum "error" {
           description "Match error conditions";
         }
         enum "warning" {
           description "Match warning messages";
         }
         enum "notice" {
           description "Match conditions that should be handled specially";
         }
         enum "info" {
           description "Match informational messages";
         }
         enum "verbose" {
           description "Match verbose messages";
         }
         enum "all" {
           description "Match all levels";
         }
       }
     }
     list flag {
       key name;
       ordered-by user;
       description "Trace flags";
       leaf name {
         type enumeration {
           enum "all" {
             description "Trace everything";
           }
           enum "connection" {
             description "Trace the connection to server";
           }
           enum "content" {
             description "Trace the content buffer management";
           }
           enum "daemon" {
             description "Trace advanced-anti-malware daemon";
           }
           enum "http" {
             description "Trace http protocol operations";
           }
           enum "identification" {
             description "Trace file identification";
           }
           enum "imap" {
             description "Trace imap protocol operations";
           }
           enum "parser" {
             description "Trace protocol context parser";
           }
           enum "plugin" {
             description "Trace advanced-anti-malware plugin";
           }
           enum "policy" {
             description "Trace advanced-anti-malware policy";
           }
           enum "smb" {
             description "Trace smb protocol operations";
           }
           enum "smtp" {
             description "Trace smtp protocol operations";
           }
         }
       }
     }
   }
   grouping access-client-name-filter-object {
     description "Restrictions on client names authenticated on this server";
     uses apply-advanced;
     leaf domain-name {
       description "Domain name to match (must be part of username)";
       type string;
     }
     leaf separator {
       description "Separator character in domain name";
       type string {
         length 1;
       }
     }
     leaf count {
       description "Number of separator instances";
       default "0";
       type union {
         type string {
           pattern "<.*>|$.*";
         }
         type uint8 {
           range "0 .. 255";
         }
       }
     }
   }
   grouping access-client-object {
     leaf name {
       description "Name of entity requesting access";
       type string;
     }
     uses apply-advanced;
     leaf no-rfc2486 {
       description "RFC2486 compliance is not enforced";
       type empty;
     }
     leaf chap-secret {
       description "CHAP secret";
       type jt:unreadable;
     }
     leaf pap-password {
       description "PAP password";
       type jt:unreadable;
     }
     choice client_type {
       case case_1 {
         container ppp {
           presence "enable ppp";
           description "Configuration for Point-to-Point Protocol";
           uses apply-advanced;
           leaf framed-pool {
             description "Address pool used to assign an address for the user";
             junos:must "(\"access address-pool $$\")";
             junos:must-message "referenced address pool must be defined";
             type string {
               length "1 .. 63";
             }
           }
           leaf idle-timeout {
             description "Idle timeout before termination of session";
             default "0";
             units "seconds";
             type union {
               type string {
                 pattern "<.*>|$.*";
               }
               type uint32 {
                 range "0 .. 4294967295";
               }
             }
           }
           container ppp-options {
             presence "enable ppp-options";
             description "Point-to-Point Protocol interface-specific options";
             uses apply-advanced;
             leaf pap {
               description "Password Authentication Protocol";
               type empty;
             }
             leaf chap {
               description "Challenge Handshake Authentication Protocol";
               type empty;
             }
           }
           leaf keepalive {
             description "PPP keepalive interval";
             default "10";
             units "seconds";
             type union {
               type string {
                 pattern "<.*>|$.*";
               }
               type uint16 {
                 range "0 .. 32767";
               }
             }
           }
           leaf primary-dns {
             description "Primary DNS server name";
             type string;
           }
           leaf secondary-dns {
             description "Secondary DNS server name";
             type string;
           }
           leaf primary-wins {
             description "Primary wins server name";
             type string;
           }
           leaf secondary-wins {
             description "Secondary wins server name";
             type string;
           }
           leaf encapsulation-overhead {
             description "Encapsulation overhead for Class of Service calculation";
             type union {
               type string {
                 pattern "<.*>|$.*";
               }
               type int8 {
                 range "-63 .. 64";
               }
             }
           }
           leaf cell-overhead {
             description "ATM cell overhead for Class of Service calculation";
             type empty;
           }
           leaf interface-id {
             description "Interface identifier to look up session information";
             type string {
               length "1 .. 63";
               junos:posix-pattern "^[A-Za-z0-9][_0-9A-Za-z-]{0,62}$";
               junos:pattern-message "Must be a string beginning with a number or letter and consisting of no more than 63 total letters, numbers, dashes and underscores.";
             }
           }
           leaf framed-ip-address {
             description "Address to be configured for the user";
             type jt:ipv4prefix;
           }
           leaf keepalive-retries {
             description "PPP keepalive retries";
             default "10";
             type union {
               type string {
                 pattern "<.*>|$.*";
               }
               type uint16 {
                 range "3 .. 32767";
               }
             }
           }
         }
       }
       case case_2 {
         container l2tp {
           presence "enable l2tp";
           junos:must "(!(\".. pap-password\"))";
           junos:must-message "Cannot define PAP password for L2TP tunnel client";
           junos:must "(!(\".. chap-secret\"))";
           junos:must-message "Cannot define CHAP secret for L2TP tunnel client";
           description "Configuration for Layer 2 Tunneling Protocol";
           uses apply-advanced;
           leaf maximum-sessions {
             description "Maximum number of sessions per client";
             type union {
               type uint32;
               type string {
                 pattern "<.*>|$.*";
               }
             }
           }
           leaf maximum-sessions-per-tunnel {
             description "Maximum number of sessions per L2TP tunnel";
             default "0";
             type union {
               type uint16;
               type string {
                 pattern "<.*>|$.*";
               }
             }
           }
           leaf service-profile {
             description "Dynamic service profile(s) to be applied to this session";
             type string;
           }
           leaf interface-id {
             description "Interface identifier for PPP users missing one";
             type string {
               length "1 .. 63";
               junos:posix-pattern "^[A-Za-z0-9][_0-9A-Za-z-]{0,62}$";
               junos:pattern-message "Must be a string beginning with a number or letter and consisting of no more than 63 total letters, numbers, dashes and underscores.";
             }
           }
           leaf lcp-renegotiation {
             description "Force renegotiation of LCP options";
             type empty;
           }
           leaf local-chap {
             description "Force local CHAP challenge";
             type empty;
           }
           container override-result-code {
             description "Override result code with admin value in CDN message at LNS";
             uses apply-advanced;
             leaf session-out-of-resource {
               description "Override result code for session out-of-resource due to permanent or temporary condition with admin value in CDN message at LNS";
               type empty;
             }
           }
           leaf aaa-access-profile {
             description "AAA access profile name";
             junos:must "(\"access profile $$\")";
             junos:must-message "referenced access profile must be defined";
             type string {
               length "1 .. 63";
             }
           }
           container multilink {
             description "Multilink Point-to-Point Protocol command options";
             presence "enable multilink";
             uses multilink-object;
           }
           leaf session-limit-group {
             description "Session limit group name";
             type string;
           }
           leaf ppp-authentication {
             description "Method for authenticating client";
             type enumeration {
               enum "chap" {
                 description "Challenge Handshake Authentication Protocol";
               }
               enum "pap" {
                 description "Password Authentication Protocol";
               }
             }
           }
           leaf shared-secret {
             description "Shared secret for authenticating peer";
             type string {
               length "1 .. 64";
             }
           }
           leaf ppp-profile {
             description "User profile name";
             junos:must "(!(any \"access profile $$ client <*> l2tp\"))";
             junos:must-message "clients of referenced profile must have only PPP attributes";
             junos:must "(\"access profile $$\")";
             junos:must-message "referenced group-profile must be defined";
             type string;
           }
           leaf dynamic-profile {
             description "Dynamic profile name";
             junos:must "(\"dynamic-profiles $$\")";
             junos:must-message "referenced dynamic profile must be defined";
             type string;
           }
         }
       }
     }
     leaf group-profile {
       description "Group profile name";
       junos:must "(((!(\".. l2tp\") && \"access group-profile $$ ppp\") || (!(\".. ppp\") && \"access group-profile $$ l2tp\")))";
       junos:must-message "ppp client cannot have l2tp group-profile and vice-versa";
       junos:must "(\"access group-profile $$\")";
       junos:must-message "referenced group-profile must be defined";
       type string;
     }
     leaf user-group-profile {
       description "User group profile name";
       junos:must "(!(\".. ppp\"))";
       junos:must-message "user-group-profile must be defined only for tunnel clients";
       junos:must "(\"access group-profile $$ ppp\")";
       junos:must-message "referenced user-group-profile must have only ppp attributes";
       junos:must "(\"access group-profile $$\")";
       junos:must-message "referenced group-profile must be defined";
       type string;
     }
     container xauth {
       description "Configure xauth attributes";
       uses apply-advanced;
       leaf ip-address {
         description "Specify the ip-address for client";
         type jt:ipv4prefix;
       }
     }
     leaf-list client-group {
       ordered-by user;
       description "One or more groups to which the client belongs";
       type string;
     }
     container firewall-user {
       description "Client is configured as a firewall user";
       uses apply-advanced;
       leaf password {
         description "Password for user";
         type string {
           length "1 .. 128";
         }
       }
     }
   }
   grouping access-ldap-options {
     uses apply-advanced;
     leaf revert-interval {
       description "Time after which to revert to primary server";
       default "600";
       units "seconds";
       type union {
         type string {
           pattern "<.*>|$.*";
         }
         type uint32 {
           range "60 .. 4294967295";
         }
       }
     }
     leaf base-distinguished-name {
       description "Suffix when assembling user distinguished name (DN) or base DN under which to search for user DN";
       type string;
     }
     choice search_type {
       case case_1 {
         container assemble {
           presence "enable assemble";
           description "Derive user distinguished name from 'common-name' and 'base-distinguished-name'";
           uses apply-advanced;
           leaf common-name {
             description "Prefix in user distinguished name (for example, 'cn' or 'uid')";
             default "cn";
             type string;
           }
         }
       }
       case case_2 {
         container search {
           presence "enable search";
           description "Search for user's distinguished name";
           uses apply-advanced;
           leaf search-filter {
             description "Filter to use in search (examples: 'cn=' or 'givenName=')";
             type string;
           }
           container admin-search {
             presence "enable admin-search";
             description "Perform an administrator search to find user's distinguished name";
             uses apply-advanced;
             leaf distinguished-name {
               description "Administrator's distinguished name";
               type string;
             }
             leaf password {
               description "Administrator password";
               type jt:unreadable;
             }
           }
         }
       }
     }
     list allowed-groups {
       key name;
       ordered-by user;
       description "LDAP allowed groups configuration";
       uses ldap-allowed-groups-object;
     }
   }
   grouping access-radius-options {
     uses apply-advanced;
     leaf revert-interval {
       description "Time after which to revert to primary server";
       default "60";
       units "seconds";
       type union {
         type string {
           pattern "<.*>|$.*";
         }
         type uint32 {
           range "0 .. 604800";
         }
       }
     }
     leaf timeout-grace {
       description "The period after a RADIUS server times out before marking the server as dead";
       default "10";
       units "seconds";
       type union {
         type string {
           pattern "<.*>|$.*";
         }
         type uint32 {
           range "0 .. 30";
         }
       }
     }
     leaf request-rate {
       description "Maximum number of RADIUS requests sent per second";
       default "500";
       type union {
         type string {
           pattern "<.*>|$.*";
         }
         type uint32 {
           range "100 .. 4000";
         }
       }
     }
     leaf interim-rate {
       description "Maximum number of RADIUS requests sent per second";
       default "500";
       type union {
         type string {
           pattern "<.*>|$.*";
         }
         type uint32 {
           range "50 .. 4000";
         }
       }
     }
     leaf interim-update-tolerance {
       description "Maximum tolerance for Interim Updates to RADIUS";
       status deprecated;
       default "60";
       units "seconds";
       type union {
         type string {
           pattern "<.*>|$.*";
         }
         type uint32 {
           range "1 .. 600";
         }
       }
     }
     container unique-nas-port {
       presence "enable unique-nas-port";
       junos:must "(!(any \"access profile <*> radius options vlan-nas-port-stacked-format\"))";
       junos:must-message "unique-nas-port is not supported with vlan-nas-port-stacked-format";
       junos:must "(!(any \"access profile <*> radius options nas-port-extended-format\"))";
       junos:must-message "unique-nas-port is not supported with nas-port-extended-format";
       description "Use unique value for NAS-Port radius attribute";
       uses apply-advanced;
       leaf chassis-id {
         description "Configure chassis identifier field of NAS-Port";
         junos:must "(\".. chassis-id-width\")";
         junos:must-message "chassis-id-width must be configured";
         type union {
           type string {
             pattern "<.*>|$.*";
           }
           type uint32 {
             range "0 .. 127";
           }
         }
       }
       leaf chassis-id-width {
         description "Number of bits for the chassis identifier field of NAS-Port";
         units "bits";
         junos:must "(\".. chassis-id\")";
         junos:must-message "chassis-id must be configured";
         type union {
           type string {
             pattern "<.*>|$.*";
           }
           type uint32 {
             range "1 .. 7";
           }
         }
       }
     }
   }
   grouping address-filter-type {
     description "IP address filter";
     uses apply-advanced;
     leaf address-book {
       description "Referenced address book";
       type string;
     }
     leaf address-set {
       description "Referenced address set";
       type string {
         length "1 .. 63";
       }
     }
   }
   grouping alg-object {
     uses apply-advanced;
     container traceoptions {
       description "ALG trace options";
       uses apply-advanced;
       leaf no-remote-trace {
         description "Disable remote tracing";
         junos:must "(\"system tracing\")";
         junos:must-message "'no-remote-trace' is valid only when [system tracing] is configured";
         type empty;
       }
       container file {
         description "Trace file information";
         leaf filename {
           description "Name of file in which to write trace information";
           type string {
             length "1 .. 1024";
             junos:posix-pattern "![/ %]";
             junos:pattern-message "Must not contain '/', % or a space";
           }
         }
         leaf size {
           description "Maximum trace file size";
           type string;
         }
         leaf files {
           description "Maximum number of trace files";
           default "3";
           type union {
             type string {
               pattern "<.*>|$.*";
             }
             type uint32 {
               range "2 .. 1000";
             }
           }
         }
         choice world-readable-choice {
           leaf world-readable {
             description "Allow any user to read the log file";
             type empty;
           }
           leaf no-world-readable {
             description "Don't allow any user to read the log file";
             type empty;
           }
         }
         leaf match {
           description "Regular expression for lines to be logged";
           type jt:regular-expression;
         }
       }
       leaf level {
         description "Set level of tracing output";
         default "brief";
         type enumeration {
           enum "brief" {
             description "Brief messages";
           }
           enum "detail" {
             description "Detail messages";
           }
           enum "extensive" {
             description "Extensive messages";
           }
           enum "verbose" {
             description "Verbose messages";
           }
         }
       }
     }
     container alg-manager {
       description "Configure ALG-MANAGER";
       leaf clear-dont-frag-bit {
         description "Enable ALG clear DF(don't frag) bit in IP header";
         type empty;
       }
       container traceoptions {
         description "ALG-MANAGER trace options";
         uses apply-advanced;
         list flag {
           key name;
           ordered-by user;
           description "ALG-MANAGER trace flags";
           leaf name {
             type enumeration {
               enum "all" {
                 description "Trace everything";
               }
             }
           }
           choice level {
             case case_1 {
               leaf extensive {
                 description "Set trace verbosity level to extensive";
                 type empty;
               }
             }
           }
         }
       }
     }
     container alg-support-lib {
       description "Configure ALG-SUPPORT-LIB";
       container traceoptions {
         description "ALG-SUPPORT-LIB trace options";
         uses apply-advanced;
         list flag {
           key name;
           ordered-by user;
           description "ALG-SUPPORT-LIB trace flags";
           leaf name {
             type enumeration {
               enum "all" {
                 description "Trace everything";
               }
             }
           }
           choice level {
             case case_1 {
               leaf extensive {
                 description "Set trace verbosity level to extensive";
                 type empty;
               }
             }
           }
         }
       }
     }
     container dns {
       description "Configure DNS ALG";
       uses apply-advanced;
       leaf disable {
         description "Disable DNS ALG";
         type empty;
       }
       leaf maximum-message-length {
         description "Set maximum message length";
         default "512";
         units "bytes";
         type union {
           type string {
             pattern "<.*>|$.*";
           }
           type uint32 {
             range "512 .. 8192";
           }
         }
       }
       leaf oversize-message-drop {
         description "Drop oversized DNS packets";
         type empty;
       }
       container doctoring {
         description "Configure DNS ALG doctoring";
         uses apply-advanced;
         choice type {
           case case_1 {
             leaf none {
               description "Disable all DNS ALG Doctoring";
               type empty;
             }
           }
           case case_2 {
             leaf sanity-check {
               description "Perform only DNS ALG sanity checks";
               type empty;
             }
           }
         }
       }
       container traceoptions {
         description "DNS ALG trace options";
         uses apply-advanced;
         list flag {
           key name;
           ordered-by user;
           description "DNS ALG trace flags";
           leaf name {
             type enumeration {
               enum "all" {
                 description "Trace everything";
               }
             }
           }
           choice level {
             case case_1 {
               leaf extensive {
                 description "Set trace verbosity level to extensive";
                 type empty;
               }
             }
           }
         }
       }
     }
     container ftp {
       description "Configure FTP ALG";
       leaf disable {
         description "Disable FTP ALG";
         type empty;
       }
       leaf ftps-extension {
         description "Enable secure FTP and FTP-ssl protocols";
         type empty;
       }
       leaf line-break-extension {
         description "Enable CR+LF line termination";
         type empty;
       }
       leaf allow-mismatch-ip-address {
         description "Pass FTP packets with mismatched ip address headers and payload";
         type empty;
       }
       container traceoptions {
         description "FTP ALG trace options";
         uses apply-advanced;
         list flag {
           key name;
           ordered-by user;
           description "FTP ALG trace flags";
           leaf name {
             type enumeration {
               enum "all" {
                 description "Trace everything";
               }
             }
           }
           choice level {
             case case_1 {
               leaf extensive {
                 description "Set trace verbosity level to extensive";
                 type empty;
               }
             }
           }
         }
       }
     }
     container h323 {
       presence "enable h323";
       description "Configure H.323 ALG";
       uses apply-advanced;
       leaf disable {
         description "Disable H.323 ALG";
         type empty;
       }
       leaf endpoint-registration-timeout {
         description "Timeout for endpoints";
         default "64800";
         units "seconds";
         type union {
           type string {
             pattern "<.*>|$.*";
           }
           type uint32 {
             range "10 .. 65535";
           }
         }
       }
       leaf media-source-port-any {
         description "Permit media from any source port on the endpoint";
         type empty;
       }
       container application-screen {
         description "Configure application screens";
         uses apply-advanced;
         container unknown-message {
           description "Configure ALG action on receiving an unknown message";
           uses apply-advanced;
           leaf permit-nat-applied {
             description "Permit unknown messages on packets that are NATed";
             type empty;
           }
           leaf permit-routed {
             description "Permit unknown messages on routed packets";
             type empty;
           }
         }
         container message-flood {
           description "Configure Message flood ALG options";
           uses apply-advanced;
           container gatekeeper {
             description "Set options for gatekeeper messages";
             leaf threshold {
               description "Message flood gatekeeper threshold";
               default "1000";
               units "messages per second";
               type union {
                 type string {
                   pattern "<.*>|$.*";
                 }
                 type uint32 {
                   range "1 .. 50000";
                 }
               }
             }
           }
         }
       }
       container dscp-rewrite {
         description "DSCP code rewrite";
         uses apply-advanced;
         leaf code-point {
           description "Set dscp codepoint 6-bit string";
           type string {
             junos:posix-pattern "^([01]{6})$";
             junos:pattern-message "Must be form of xxxxxx, where x is 1 or 0";
           }
         }
       }
       container traceoptions {
         description "H.323 ALG trace options";
         uses apply-advanced;
         list flag {
           key name;
           ordered-by user;
           description "H.323 ALG trace flags";
           leaf name {
             type enumeration {
               enum "q931" {
                 description "Enable tracing for Q.931 processing";
               }
               enum "h245" {
                 description "Enable tracing for H.245 processing";
               }
               enum "ras" {
                 description "Enable tracing for RAS processing";
               }
               enum "h225-asn1" {
                 description "Enable tracing for H.225 ASN.1 processing";
               }
               enum "h245-asn1" {
                 description "Enable tracing for H.245 ASN.1 processing";
               }
               enum "ras-asn1" {
                 description "Enable tracing for RAS ASN.1 processing";
               }
               enum "chassis-cluster" {
                 description "Enable tracing for H.323 chassis cluster functions";
               }
               enum "all" {
                 description "Trace everything";
               }
             }
           }
           choice level {
             case case_1 {
               leaf terse {
                 description "Set trace verbosity level to terse";
                 type empty;
               }
             }
             case case_2 {
               leaf detail {
                 description "Set trace verbosity level to detail";
                 type empty;
               }
             }
             case case_3 {
               leaf extensive {
                 description "Set trace verbosity level to extensive";
                 type empty;
               }
             }
           }
         }
       }
     }
     container mgcp {
       presence "enable mgcp";
       description "Configure MGCP ALG";
       uses apply-advanced;
       leaf disable {
         description "Disable MGCP ALG";
         type empty;
       }
       leaf inactive-media-timeout {
         description "Set inactive media timeout";
         default "120";
         units "seconds";
         type union {
           type string {
             pattern "<.*>|$.*";
           }
           type uint32 {
             range "10 .. 2550";
           }
         }
       }
       leaf transaction-timeout {
         description "Set transaction timeout";
         default "30";
         units "seconds";
         type union {
           type string {
             pattern "<.*>|$.*";
           }
           type uint32 {
             range "3 .. 50";
           }
         }
       }
       leaf maximum-call-duration {
         description "Set maximum call duration";
         default "720";
         units "minutes";
         type union {
           type string {
             pattern "<.*>|$.*";
           }
           type uint32 {
             range "3 .. 720";
           }
         }
       }
       container application-screen {
         description "Configure application screens";
         uses apply-advanced;
         container unknown-message {
           description "Configure ALG action on receiving an unknown message";
           uses apply-advanced;
           leaf permit-nat-applied {
             description "Permit unknown messages on packets that are NATed";
             type empty;
           }
           leaf permit-routed {
             description "Permit unknown messages on routed packets";
             type empty;
           }
         }
         container message-flood {
           description "Set message flood ALG options";
           leaf threshold {
             description "Message flood threshold";
             default "100";
             units "messages per second per MG";
             type union {
               type string {
                 pattern "<.*>|$.*";
               }
               type uint32 {
                 range "2 .. 50000";
               }
             }
           }
         }
         container connection-flood {
           description "Set connection flood options";
           leaf threshold {
             description "Connection flood threshold";
             default "10";
             units "connection requests per second per MG";
             type union {
               type string {
                 pattern "<.*>|$.*";
               }
               type uint32 {
                 range "2 .. 10000";
               }
             }
           }
         }
       }
       container dscp-rewrite {
         description "DSCP code rewrite";
         uses apply-advanced;
         leaf code-point {
           description "Set dscp codepoint 6-bit string";
           type string {
             junos:posix-pattern "^([01]{6})$";
             junos:pattern-message "Must be form of xxxxxx, where x is 1 or 0";
           }
         }
       }
       container traceoptions {
         description "MGCP ALG trace options";
         uses apply-advanced;
         list flag {
           key name;
           ordered-by user;
           description "MGCP ALG trace flags";
           leaf name {
             type enumeration {
               enum "call" {
                 description "Enable tracing for MGCP call processing";
               }
               enum "decode" {
                 description "Enable tracing for MGCP decoder operations";
               }
               enum "error" {
                 description "Enable tracing for MGCP processing errors";
               }
               enum "chassis-cluster" {
                 description "Enable tracing for MGCP chassis cluster functions";
               }
               enum "nat" {
                 description "Enable tracing for MGCP Network Address Translation (NAT) processing";
               }
               enum "packet" {
                 description "Enable tracing for MGCP protocol packet processing";
               }
               enum "rm" {
                 description "Enable tracing MGCP Resource Management (Resmgr) functions";
               }
               enum "all" {
                 description "Trace everything";
               }
             }
           }
           choice level {
             case case_1 {
               leaf extensive {
                 description "Set trace verbosity level to extensive";
                 type empty;
               }
             }
           }
         }
       }
     }
     container msrpc {
       description "Configure MSRPC ALG";
       leaf disable {
         description "Disable MSRPC ALG";
         type empty;
       }
       leaf group-max-usage {
         description "Set maximum group usage percentage, default 80";
         default "80";
         type union {
           type string {
             pattern "<.*>|$.*";
           }
           type uint32 {
             range "10 .. 100";
           }
         }
       }
       leaf map-entry-timeout {
         description "Set entry timeout, default 8hour";
         default "480";
         units "minutes";
         type union {
           type string {
             pattern "<.*>|$.*";
           }
           type uint32 {
             range "5 .. 4320";
           }
         }
       }
       container traceoptions {
         description "MSRPC ALG trace options";
         uses apply-advanced;
         list flag {
           key name;
           ordered-by user;
           description "MSRPC ALG trace flags";
           leaf name {
             type enumeration {
               enum "all" {
                 description "Trace everything";
               }
             }
           }
           choice level {
             case case_1 {
               leaf extensive {
                 description "Set trace verbosity level to extensive";
                 type empty;
               }
             }
           }
         }
       }
     }
     container sunrpc {
       description "Configure SUNRPC ALG";
       leaf disable {
         description "Disable SUNRPC ALG";
         type empty;
       }
       leaf group-max-usage {
         description "Set maximum group usage percentage, default 80";
         default "80";
         type union {
           type string {
             pattern "<.*>|$.*";
           }
           type uint32 {
             range "10 .. 100";
           }
         }
       }
       leaf map-entry-timeout {
         description "Set entry timeout, default 8hour";
         default "480";
         units "minutes";
         type union {
           type string {
             pattern "<.*>|$.*";
           }
           type uint32 {
             range "5 .. 4320";
           }
         }
       }
       container traceoptions {
         description "SUNRPC ALG trace options";
         uses apply-advanced;
         list flag {
           key name;
           ordered-by user;
           description "SUNRPC ALG trace flags";
           leaf name {
             type enumeration {
               enum "all" {
                 description "Trace everything";
               }
             }
           }
           choice level {
             case case_1 {
               leaf extensive {
                 description "Set trace verbosity level to extensive";
                 type empty;
               }
             }
           }
         }
       }
     }
     container rsh {
       presence "enable rsh";
       description "Configure RSH ALG";
       uses apply-advanced;
       leaf disable {
         description "Disable RSH ALG";
         type empty;
       }
       container traceoptions {
         description "RSH ALG trace options";
         uses apply-advanced;
         list flag {
           key name;
           ordered-by user;
           description "RSH ALG trace flags";
           leaf name {
             type enumeration {
               enum "all" {
                 description "Trace everything";
               }
             }
           }
           choice level {
             case case_1 {
               leaf extensive {
                 description "Set trace verbosity level to extensive";
                 type empty;
               }
             }
           }
         }
       }
     }
     container rtsp {
       presence "enable rtsp";
       description "Configure RTSP ALG";
       leaf disable {
         description "Disable RTSP ALG";
         type empty;
       }
       container traceoptions {
         description "RTSP ALG trace options";
         uses apply-advanced;
         list flag {
           key name;
           ordered-by user;
           description "RTSP ALG trace flags";
           leaf name {
             type enumeration {
               enum "all" {
                 description "Trace everything";
               }
             }
           }
           choice level {
             case case_1 {
               leaf extensive {
                 description "Set trace verbosity level to extensive";
                 type empty;
               }
             }
           }
         }
       }
     }
     container sccp {
       presence "enable sccp";
       description "Configure SCCP ALG";
       uses apply-advanced;
       leaf disable {
         description "Disable SCCP ALG";
         type empty;
       }
       leaf inactive-media-timeout {
         description "Set inactive media timeout";
         default "120";
         units "seconds";
         type union {
           type string {
             pattern "<.*>|$.*";
           }
           type uint32 {
             range "10 .. 600";
           }
         }
       }
       container application-screen {
         description "Configure application screens";
         uses apply-advanced;
         container unknown-message {
           description "Configure ALG action on receiving an unknown message";
           uses apply-advanced;
           leaf permit-nat-applied {
             description "Permit unknown messages on packets that are NATed";
             type empty;
           }
           leaf permit-routed {
             description "Permit unknown messages on routed packets";
             type empty;
           }
         }
         container call-flood {
           description "Configure call flood thresholds";
           leaf threshold {
             description "Calls per second per client";
             default "20";
             type union {
               type string {
                 pattern "<.*>|$.*";
               }
               type uint32 {
                 range "2 .. 1000";
               }
             }
           }
         }
       }
       container dscp-rewrite {
         description "DSCP code rewrite";
         uses apply-advanced;
         leaf code-point {
           description "Set dscp codepoint 6-bit string";
           type string {
             junos:posix-pattern "^([01]{6})$";
             junos:pattern-message "Must be form of xxxxxx, where x is 1 or 0";
           }
         }
       }
       container traceoptions {
         description "SCCP ALG trace options";
         uses apply-advanced;
         list flag {
           key name;
           ordered-by user;
           description "SCCP ALG trace flags";
           leaf name {
             type enumeration {
               enum "call" {
                 description "Enable tracing SCCP call processing";
               }
               enum "cli" {
                 description "Enable tracing SCCP cli processing";
               }
               enum "decode" {
                 description "Enable tracing for SCCP decoder operations";
               }
               enum "error" {
                 description "Enable tracing for SCCP processing errors";
               }
               enum "chassis-cluster" {
                 description "Enable tracing for SCCP chassis cluster functions";
               }
               enum "init" {
                 description "Enable tracing for SCCP initialization errors";
               }
               enum "nat" {
                 description "Enable tracing for SCCP Network Address Translation (NAT) processing";
               }
               enum "rm" {
                 description "Enable tracing SCCP Resource Management (Resmgr) functions";
               }
               enum "all" {
                 description "Trace everything";
               }
             }
           }
           choice level {
             case case_1 {
               leaf extensive {
                 description "Set trace verbosity level to extensive";
                 type empty;
               }
             }
           }
         }
       }
     }
     container sip {
       presence "enable sip";
       description "Configure SIP ALG";
       uses apply-advanced;
       leaf disable {
         description "Disable SIP ALG";
         type empty;
       }
       leaf inactive-media-timeout {
         description "Set inactive media timeout";
         default "120";
         units "seconds";
         type union {
           type string {
             pattern "<.*>|$.*";
           }
           type uint16 {
             range "10 .. 2550";
           }
         }
       }
       leaf maximum-call-duration {
         description "Set maximum call duration 0 or 3..720";
         default "720";
         units "minutes";
         type union {
           type uint32;
           type string {
             pattern "<.*>|$.*";
           }
         }
       }
       leaf t1-interval {
         description "Set T1 interval";
         default "500";
         units "milliseconds";
         type union {
           type string {
             pattern "<.*>|$.*";
           }
           type uint32 {
             range "500 .. 5000";
           }
         }
       }
       leaf t4-interval {
         description "Set T4 interval";
         default "5";
         units "seconds";
         type union {
           type string {
             pattern "<.*>|$.*";
           }
           type uint32 {
             range "5 .. 10";
           }
         }
       }
       leaf c-timeout {
         description "Set C timeout";
         default "3";
         units "minutes";
         type union {
           type string {
             pattern "<.*>|$.*";
           }
           type uint32 {
             range "3 .. 10";
           }
         }
       }
       leaf disable-call-id-hiding {
         description "Disable translation of host IP in Call-ID header";
         status deprecated;
         type empty;
       }
       leaf bulk-call-mode {
         description "Enable SIP distribution session in bulk mode";
         type empty;
       }
       leaf enable-call-distribution {
         description "Enable Call-id-based SIP call distribution between SPUs";
         type empty;
       }
       leaf retain-hold-resource {
         description "Retain SDP resources during call hold";
         type empty;
       }
       container hide-via-headers {
         description "Hide via headers options";
         uses apply-advanced;
         leaf disable {
           description "Disable hide via headers function";
           type empty;
         }
       }
       list distribution-ip {
         key name;
         ordered-by user;
         description "Configure SIP distribute server IPV6 or IPV4 ip";
         leaf name {
           description "Distribution IP address";
           type jt:ipaddr;
         }
         uses apply-advanced;
         container distribute-to {
           description "Distribute sip packet";
           uses apply-advanced;
           container fpc {
             description "FPC card number";
             uses apply-advanced;
             leaf slot {
               description "FPC slot number";
               type union {
                 type string {
                   pattern "<.*>|$.*";
                 }
                 type uint32 {
                   range "0 .. 127";
                 }
               }
             }
             container pic {
               description "PIC card number";
               uses apply-advanced;
               leaf slot {
                 description "Physical Interface Card number";
                 type union {
                   type string {
                     pattern "<.*>|$.*";
                   }
                   type uint32 {
                     range "0 .. 11";
                   }
                 }
               }
             }
           }
         }
       }
       container application-screen {
         description "Configure application screens";
         uses apply-advanced;
         container unknown-message {
           description "Configure ALG action on receiving an unknown message";
           uses apply-advanced;
           leaf permit-nat-applied {
             description "Permit unknown messages on packets that are NATed";
             type empty;
           }
           leaf permit-routed {
             description "Permit unknown messages on routed packets";
             type empty;
           }
         }
         container protect {
           description "Configure Protect options";
           uses apply-advanced;
           container deny {
             presence "enable deny";
             description "Protect deny options";
             uses apply-advanced;
             choice deny-choice {
               case case_1 {
                 list destination-ip {
                   key name;
                   ordered-by user;
                   description "List of protected destination server IP";
                   leaf name {
                     description "Protected destination server IPv4 or IPv6 entry";
                     type jt:ipprefix;
                   }
                   uses apply-advanced;
                 }
               }
               case case_2 {
                 leaf all {
                   description "Enable attack protection for all servers";
                   type empty;
                 }
               }
             }
             leaf timeout {
               description "Timeout value for SIP INVITE attack table entry";
               default "5";
               units "seconds";
               type union {
                 type string {
                   pattern "<.*>|$.*";
                 }
                 type uint32 {
                   range "1 .. 3600";
                 }
               }
             }
           }
         }
       }
       container dscp-rewrite {
         description "DSCP code rewrite";
         uses apply-advanced;
         leaf code-point {
           description "Set dscp codepoint 6-bit string";
           type string {
             junos:posix-pattern "^([01]{6})$";
             junos:pattern-message "Must be form of xxxxxx, where x is 1 or 0";
           }
         }
       }
       container traceoptions {
         description "SIP ALG trace options";
         uses apply-advanced;
         list flag {
           key name;
           ordered-by user;
           description "SIP ALG trace flags";
           leaf name {
             type enumeration {
               enum "call" {
                 description "Enable tracing for SIP call processing";
               }
               enum "chassis-cluster" {
                 description "Enable tracing for SIP chassis cluster functions";
               }
               enum "nat" {
                 description "Enable tracing for SIP Network Address Translation (NAT) processing";
               }
               enum "parser" {
                 description "Enable tracing for SIP parser operations";
               }
               enum "rm" {
                 description "Enable tracing SIP Resource Management (Resmgr) functions";
               }
               enum "all" {
                 description "Trace everything";
               }
             }
           }
           choice level {
             case case_1 {
               leaf terse {
                 description "Set trace verbosity level to terse";
                 type empty;
               }
             }
             case case_2 {
               leaf detail {
                 description "Set trace verbosity level to detail";
                 type empty;
               }
             }
             case case_3 {
               leaf extensive {
                 description "Set trace verbosity level to extensive";
                 type empty;
               }
             }
           }
         }
       }
     }
     container sql {
       presence "enable sql";
       description "Configure SQL ALG";
       leaf disable {
         description "Disable SQL ALG";
         type empty;
       }
       container traceoptions {
         description "SQL ALG trace options";
         uses apply-advanced;
         list flag {
           key name;
           ordered-by user;
           description "SQL ALG trace flags";
           leaf name {
             type enumeration {
               enum "all" {
                 description "Trace everything";
               }
             }
           }
           choice level {
             case case_1 {
               leaf extensive {
                 description "Set trace verbosity level to extensive";
                 type empty;
               }
             }
           }
         }
       }
     }
     container talk {
       description "Configure Talk ALG";
       leaf disable {
         description "Disable Talk ALG";
         type empty;
       }
       container traceoptions {
         description "TALK ALG trace options";
         uses apply-advanced;
         list flag {
           key name;
           ordered-by user;
           description "TALK ALG trace flags";
           leaf name {
             type enumeration {
               enum "all" {
                 description "Trace everything";
               }
             }
           }
           choice level {
             case case_1 {
               leaf extensive {
                 description "Set trace verbosity level to extensive";
                 type empty;
               }
             }
           }
         }
       }
     }
     container tftp {
       description "Configure TFTP ALG";
       leaf disable {
         description "Disable TFTP ALG";
         type empty;
       }
       container traceoptions {
         description "TFTP ALG trace options";
         uses apply-advanced;
         list flag {
           key name;
           ordered-by user;
           description "TFTP ALG trace flags";
           leaf name {
             type enumeration {
               enum "all" {
                 description "Trace everything";
               }
             }
           }
           choice level {
             case case_1 {
               leaf extensive {
                 description "Set trace verbosity level to extensive";
                 type empty;
               }
             }
           }
         }
       }
     }
     container pptp {
       description "Configure PPTP ALG";
       leaf disable {
         description "Disable PPTP ALG";
         type empty;
       }
       container traceoptions {
         description "PPTP ALG trace options";
         uses apply-advanced;
         list flag {
           key name;
           ordered-by user;
           description "PPTP ALG trace flags";
           leaf name {
             type enumeration {
               enum "all" {
                 description "Trace everything";
               }
             }
           }
           choice level {
             case case_1 {
               leaf extensive {
                 description "Set trace verbosity level to extensive";
                 type empty;
               }
             }
           }
         }
       }
     }
     container ike-esp-nat {
       description "Configure IKE-ESP ALG with NAT";
       uses apply-advanced;
       leaf enable {
         description "Enable IKE-ESP ALG";
         type empty;
       }
       leaf esp-gate-timeout {
         description "Set ESP gate timeout";
         default "5";
         units "seconds";
         type union {
           type string {
             pattern "<.*>|$.*";
           }
           type uint32 {
             range "2 .. 30";
           }
         }
       }
       leaf esp-session-timeout {
         description "Set ESP session timeout";
         default "1800";
         units "seconds";
         type union {
           type string {
             pattern "<.*>|$.*";
           }
           type uint32 {
             range "60 .. 2400";
           }
         }
       }
       leaf state-timeout {
         description "Set ALG state timeout";
         default "14400";
         units "seconds";
         type union {
           type string {
             pattern "<.*>|$.*";
           }
           type uint32 {
             range "180 .. 86400";
           }
         }
       }
       container traceoptions {
         description "IKE-ESP ALG trace options";
         uses apply-advanced;
         list flag {
           key name;
           ordered-by user;
           description "IKE-ESP ALG trace flags";
           leaf name {
             type enumeration {
               enum "all" {
                 description "Trace everything";
               }
             }
           }
           choice level {
             case case_1 {
               leaf extensive {
                 description "Set trace verbosity level to extensive";
                 type empty;
               }
             }
           }
         }
       }
     }
     container twamp {
       presence "enable twamp";
       description "Configure TWAMP ALG";
       uses apply-advanced;
       container traceoptions {
         description "TWAMP ALG trace options";
         uses apply-advanced;
         list flag {
           key name;
           ordered-by user;
           description "TWAMP ALG trace flags";
           leaf name {
             type enumeration {
               enum "all" {
                 description "Trace everything";
               }
             }
           }
           choice level {
             case case_1 {
               leaf extensive {
                 description "Trace verbosity level to extensive";
                 type empty;
               }
             }
           }
         }
       }
     }
   }
   grouping anti-spam-feature {
     description "Anti-spam feature";
     uses apply-advanced;
     container sbl {
       description "SBL settings";
       presence "enable sbl";
       uses sbl-type;
     }
   }
   grouping anti-virus-feature {
     description "Anti-virus feature";
     uses apply-advanced;
     container mime-whitelist {
       description "Anti-virus MIME whitelist";
       status deprecated;
       uses apply-advanced;
       leaf list {
         description "MIME list";
         junos:must "(\"security utm custom-objects mime-pattern $$\")";
         junos:must-message "mime-pattern must be defined";
         type string;
       }
       leaf exception {
         description "Exception settings for MIME white list";
         junos:must "(\"security utm custom-objects mime-pattern $$\")";
         junos:must-message "mime-pattern must be defined";
         type string;
       }
     }
     leaf url-whitelist {
       description "Anti-virus URL white list";
       status deprecated;
       type string;
     }
     leaf type {
       description "Anti-virus engine type";
       status deprecated;
       type enumeration {
         enum "sophos-engine" {
           description "Anti-virus sophos-engine";
           status deprecated;
         }
         enum "avira-engine" {
           description "Anti-virus avira-engine";
           status deprecated;
         }
         enum "anti-virus-none" {
           status deprecated;
         }
       }
     }
     list profile {
       key name;
       ordered-by user;
       description "Anti-virus profile";
       leaf name {
         description "Anti-virus profile name";
         type string {
           length "1 .. 29";
         }
       }
       uses apply-advanced;
       container fallback-options {
         description "Anti-virus fallback options";
         presence "enable fallback-options";
         uses av-fallback-settings;
       }
       container notification-options {
         description "Anti-virus notification options";
         presence "enable notification-options";
         uses anti-virus-notification-options;
       }
       container mime-whitelist {
         description "Anti-virus MIME whitelist";
         uses apply-advanced;
         leaf list {
           description "MIME list";
           junos:must "(\"security utm custom-objects mime-pattern $$\")";
           junos:must-message "mime-pattern must be defined";
           type string;
         }
         leaf exception {
           description "Exception settings for MIME white list";
           junos:must "(\"security utm custom-objects mime-pattern $$\")";
           junos:must-message "mime-pattern must be defined";
           type string;
         }
       }
       leaf url-whitelist {
         description "Anti-virus URL white list";
         junos:must "(\"security utm custom-objects custom-url-category $$\")";
         junos:must-message "custom-url-category must be defined";
         type string;
       }
     }
     container traceoptions {
       description "Trace options for anti-virus feature";
       status deprecated;
       uses anti-virus-traceoptions;
     }
     container sophos-engine {
       description "Anti-virus sophos-engine";
       status deprecated;
       uses apply-advanced;
       container server {
         description "SAV and Anti-Spam first hop DNS server";
         status deprecated;
         uses apply-advanced;
         leaf ip {
           description "SAV and Anti-Spam first hop DNS server ip";
           type jt:ipaddr;
         }
         leaf routing-instance {
           description "Routing instance name";
           junos:must "(\"routing-instances $$\")";
           junos:must-message "Routing-instance must be defined";
           type string;
         }
         leaf source-address {
           description "Source ip address used to connect server";
           type jt:ipaddr;
         }
       }
       leaf sxl-timeout {
         description "Sxl sophos anti-virus engine timeout";
         status deprecated;
         units "seconds";
         type union {
           type string {
             pattern "<.*>|$.*";
           }
           type uint32 {
             range "1 .. 5";
           }
         }
       }
       leaf sxl-retry {
         description "Sxl sophos anti-virus engine query retry (number of times)";
         status deprecated;
         type union {
           type string {
             pattern "<.*>|$.*";
           }
           type uint32 {
             range "0 .. 5";
           }
         }
       }
       container pattern-update {
         description "Anti-virus sophos-engine pattern update";
         presence "enable pattern-update";
         status deprecated;
         uses anti-virus-pattern-update;
       }
       list profile {
         key name;
         ordered-by user;
         description "Anti-virus sophos-engine profile";
         status deprecated;
         leaf name {
           description "Anti-virus sophos-engine profile name";
           type string {
             length "1 .. 29";
           }
         }
         uses apply-advanced;
         container fallback-options {
           description "Anti-virus sophos-engine fallback options";
           presence "enable fallback-options";
           uses av-fallback-settings;
         }
         container scan-options {
           description "Anti-virus sophos-engine scan options";
           presence "enable scan-options";
           uses sophos-scan-options;
         }
         container trickling {
           description "Anti-virus trickling";
           presence "enable trickling";
           uses anti-virus-trickling;
         }
         container notification-options {
           description "Anti-virus notification options";
           presence "enable notification-options";
           uses anti-virus-notification-options;
         }
         container mime-whitelist {
           description "Anti-virus MIME whitelist";
           uses apply-advanced;
           leaf list {
             description "MIME list";
             junos:must "(\"security utm custom-objects mime-pattern $$\")";
             junos:must-message "mime-pattern must be defined";
             type string;
           }
           leaf exception {
             description "Exception settings for MIME white list";
             junos:must "(\"security utm custom-objects mime-pattern $$\")";
             junos:must-message "mime-pattern must be defined";
             type string;
           }
         }
         leaf url-whitelist {
           description "Anti-virus URL white list";
           junos:must "(\"security utm custom-objects custom-url-category $$\")";
           junos:must-message "custom-url-category must be defined";
           type string;
         }
       }
     }
   }
   grouping anti-virus-notification-options {
     description "Anti-virus notification options";
     uses apply-advanced;
     container virus-detection {
       presence "enable virus-detection";
       description "Virus detection notification";
       uses apply-advanced;
       leaf type {
         description "Virus detection notification type";
         type enumeration {
           enum "protocol-only" {
             description "Notification in protocol level only";
           }
           enum "message" {
             description "Notification in message";
           }
         }
       }
       choice notify-mail-sender-choice {
         leaf notify-mail-sender {
           description "Notify mail sender";
           type empty;
         }
         leaf no-notify-mail-sender {
           description "Don't notify mail sender";
           type empty;
         }
       }
       leaf custom-message {
         description "Custom message for notification";
         type string {
           length "1 .. 512";
         }
       }
       leaf custom-message-subject {
         description "Custom message subject for notification";
         type string {
           length "1 .. 255";
         }
       }
     }
     container fallback-block {
       presence "enable fallback-block";
       description "Fallback block notification";
       uses apply-advanced;
       leaf type {
         description "Fallback block notification type";
         type enumeration {
           enum "protocol-only" {
             description "Notification in protocol level only";
           }
           enum "message" {
             description "Notification in message";
           }
         }
       }
       choice notify-mail-sender-choice {
         leaf notify-mail-sender {
           description "Notify mail sender";
           type empty;
         }
         leaf no-notify-mail-sender {
           description "Don't notify mail sender";
           type empty;
         }
       }
       leaf custom-message {
         description "Custom message for notification";
         type string {
           length "1 .. 512";
         }
       }
       leaf custom-message-subject {
         description "Custom message subject for notification";
         type string {
           length "1 .. 255";
         }
       }
     }
     container fallback-non-block {
       presence "enable fallback-non-block";
       description "Fallback non block notification";
       uses apply-advanced;
       choice notify-mail-recipient-choice {
         leaf notify-mail-recipient {
           description "Notify mail recipient";
           type empty;
         }
         leaf no-notify-mail-recipient {
           description "Don't notify mail recipient";
           type empty;
         }
       }
       leaf custom-message {
         description "Custom message for notification";
         type string {
           length "1 .. 512";
         }
       }
       leaf custom-message-subject {
         description "Custom message subject for notification";
         type string {
           length "1 .. 255";
         }
       }
     }
   }
   grouping anti-virus-pattern-update {
     description "Anti-virus pattern update";
     uses apply-advanced;
     container email-notify {
       presence "enable email-notify";
       description "Virus pattern file updated notification";
       uses apply-advanced;
       leaf admin-email {
         description "Admin emails to be notified about pattern file update";
         type string {
           length "1 .. 255";
         }
       }
       leaf custom-message {
         description "Custom message for notification";
         type string {
           length "1 .. 512";
         }
       }
       leaf custom-message-subject {
         description "Custom message subject for notification";
         type string {
           length "1 .. 255";
         }
       }
     }
     leaf url {
       description "Server URL";
       type string {
         length "1 .. 256";
       }
     }
     leaf proxy-profile {
       description "Proxy profile";
       junos:must "(\"services proxy profile $$\")";
       junos:must-message "Referenced Proxy profile must be defined";
       type string {
         length "1 .. 64";
       }
     }
     leaf routing-instance {
       description "Routing instance name";
       junos:must "(\"routing-instances $$\")";
       junos:must-message "Routing-instance must be defined";
       type string;
     }
     leaf interval {
       description "Interval in minutes to check the update";
       type union {
         type string {
           pattern "<.*>|$.*";
         }
         type uint32 {
           range "10 .. 10080";
         }
       }
     }
     leaf start-time {
       description "Start time (YYYY-MM-DD.HH:MM:SS)";
       type jt:time;
     }
     leaf no-autoupdate {
       description "Don't automatically update anti-virus pattern";
       type empty;
     }
   }
   grouping anti-virus-traceoptions {
     description "Trace options for anti-virus feature";
     uses apply-advanced;
     list flag {
       key name;
       ordered-by user;
       description "Trace options for anti-virus feature flag";
       leaf name {
         description "Trace options for anti-virus feature flag name";
         type enumeration {
           enum "basic" {
             description "Trace anti-virus module generic basic information";
           }
           enum "detail" {
             description "Trace anti-virus module generic detail information";
           }
           enum "engine" {
             description "Trace scan engine information";
           }
           enum "pattern" {
             description "Trace detail information of pattern loading";
           }
           enum "updater" {
             description "Trace pattern updater process activities";
           }
           enum "manager" {
             description "Trace anti-virus manager process activities";
           }
           enum "worker" {
             description "Trace anti-virus worker process activities";
           }
           enum "sendmail" {
             description "Trace mail notifier process activities";
           }
           enum "ipc" {
             description "Trace communication events with PFE";
           }
           enum "event" {
             description "Trace communication events between RE side processes";
           }
           enum "statistics" {
             description "Trace statistics information";
           }
           enum "all" {
             description "Enable trace all anti-virus trace options";
           }
         }
       }
     }
   }
   grouping anti-virus-trickling {
     description "Anti-virus trickling";
     leaf timeout {
       description "Trickling timeout";
       type union {
         type string {
           pattern "<.*>|$.*";
         }
         type uint32 {
           range "0 .. 600";
         }
       }
     }
   }
   grouping apbr_rule_type {
     leaf name {
       description "Rule name";
       type string {
         length "1 .. 63";
       }
     }
     uses apply-advanced;
     leaf disable-midstream-routing {
       description "Disable midstream routing";
       type empty;
     }
     container match {
       presence "enable match";
       description "Specify security rule  match-criteria";
       uses apply-advanced;
       leaf-list dynamic-application {
         ordered-by user;
         type string;
       }
       leaf-list dynamic-application-group {
         ordered-by user;
         description "Specify dynamic application group name to match";
         type string;
       }
       leaf-list category {
         ordered-by user;
         description "Url category";
         type string;
       }
       leaf-list dscp {
         ordered-by user;
         description "Specify dscp value to match";
         type union {
           type string {
             pattern "<.*>|$.*";
           }
           type int32 {
             range "0 .. 63";
           }
         }
       }
     }
     container then {
       presence "enable then";
       description "Specify rule action to take when packet match criteria";
       uses apply-advanced;
       container routing-instance {
         description "Packets are directed to specified routing instance";
         leaf routing-instance-name {
           description "Name of routing instance";
           type string {
             junos:posix-pattern "!^((__.*__)|(all)|(.*[ ].*)|(\"\")|(.{129,}))$";
             junos:pattern-message "Must be a non-reserved string of 128 characters or less with no spaces.";
           }
         }
       }
       container sla-rule {
         presence "enable sla-rule";
         description "SLA Rule";
         uses apply-advanced;
         leaf sla-rule-name {
           description "SLA rule name";
           type string;
         }
       }
       leaf application-services-bypass {
         description "Bypass the application services";
         type empty;
       }
     }
   }
   grouping appfw_rule_type {
     leaf name {
       description "Rule name";
       type string {
         length "1 .. 63";
       }
     }
     uses apply-advanced;
     container match {
       presence "enable match";
       description "Specify security rule  match-criteria";
       uses apply-advanced;
       leaf-list dynamic-application {
         ordered-by user;
         type string;
       }
       leaf-list dynamic-application-group {
         ordered-by user;
         description "Specify dynamic application group name to match";
         type string;
       }
       leaf ssl-encryption {
         description "Select SSL encryption rules";
         type enumeration {
           enum "any" {
             description "Encrypted and non-encrypted rule";
           }
           enum "yes" {
             description "Encrypted rule";
           }
           enum "no" {
             description "Non-encrypted rule";
           }
         }
       }
     }
     container then {
       presence "enable then";
       description "Specify rule action to take when packet match criteria";
       uses apply-advanced;
       choice action {
         case case_1 {
           leaf permit {
             description "Permit packets";
             type empty;
           }
         }
         case case_2 {
           container deny {
             presence "enable deny";
             description "Deny packets";
             uses apply-advanced;
             leaf block-message {
               description "Redirect sessions";
               type empty;
             }
           }
         }
         case case_3 {
           container reject {
             presence "enable reject";
             description "Reject packets";
             uses apply-advanced;
             leaf block-message {
               description "Redirect sessions";
               type empty;
             }
           }
         }
       }
     }
   }
   grouping application_object {
     leaf name {
       description "Application name";
       type string {
         length "1 .. 63";
         junos:posix-pattern "^[[:alnum:]][[:alnum:]_-]*$";
         junos:pattern-message "Must be a string beginning with a number or letter and consisting of letters, numbers, dashes and underscores.";
       }
     }
     uses apply-advanced;
     leaf description {
       description "Text description of application";
       type string {
         length "1 .. 900";
         junos:posix-pattern "^[^&<>\n]+$";
         junos:pattern-message "Must be a string excluding '&', '<', '>' and '\n'";
       }
     }
     list term {
       key name;
       ordered-by user;
       description "Define individual application protocols";
       max-elements 8;
       uses term_object;
     }
     leaf application-protocol {
       description "Application protocol type";
       type enumeration {
         enum "bootp" {
           description "Bootstrap protocol";
         }
         enum "dce-rpc" {
           description "DCE RPC";
         }
         enum "dce-rpc-portmap" {
           description "DCE RPC portmap";
         }
         enum "dns" {
           description "Domain Name Service";
         }
         enum "exec" {
           description "Remote Execution Protocol";
         }
         enum "ftp" {
           description "File Transfer Protocol";
         }
         enum "ftp-data" {
           description "File Transfer Protocol Data Session";
         }
         enum "gprs-gtp-c" {
           description "GPRS Tunneling Control Plane";
         }
         enum "gprs-gtp-u" {
           description "GPRS Tunneling User Plane";
         }
         enum "gprs-gtp-v0" {
           description "GPRS Tunneling Version 0";
         }
         enum "gprs-sctp" {
           description "GPRS Stream Control Protocol";
         }
         enum "h323" {
           description "H.323";
         }
         enum "icmp" {
           description "ICMP";
         }
         enum "icmpv6" {
           description "ICMPv6";
         }
         enum "ignore" {
           description "Ignore application type";
         }
         enum "iiop" {
           description "Internet Inter-ORB Protocol";
         }
         enum "ike-esp-nat" {
           description "IKE/ESP with NAT";
         }
         enum "ip" {
           description "IP";
         }
         enum "login" {
           description "Login";
         }
         enum "mgcp-ca" {
           description "MGCP-CA";
         }
         enum "mgcp-ua" {
           description "MGCP-UA";
         }
         enum "ms-rpc" {
           description "Microsoft RPC";
         }
         enum "netbios" {
           description "NetBIOS";
         }
         enum "netshow" {
           description "NetShow";
         }
         enum "none" {
           description "None";
         }
         enum "pptp" {
           description "Point-to-Point Tunneling Protocol";
         }
         enum "q931" {
           description "Q.931";
         }
         enum "ras" {
           description "RAS";
         }
         enum "realaudio" {
           description "RealAudio";
         }
         enum "rpc" {
           description "RPC";
         }
         enum "rpc-portmap" {
           description "RPC portmap";
         }
         enum "rsh" {
           description "Remote Shell";
         }
         enum "rtsp" {
           description "Real Time Streaming Protocol";
         }
         enum "sccp" {
           description "Skinny Client Control Protocol";
         }
         enum "sip" {
           description "Session Initiation Protocol";
         }
         enum "shell" {
           description "Shell";
         }
         enum "snmp" {
           description "SNMP";
         }
         enum "sqlnet" {
           description "SQLNet";
         }
         enum "sqlnet-v2" {
           description "Oracle SQL*Net Version 2";
         }
         enum "sun-rpc" {
           description "Sun Microsystems RPC";
         }
         enum "talk" {
           description "Talk Program";
         }
         enum "tftp" {
           description "Trivial File Transfer Protocol";
         }
         enum "traceroute" {
           description "Traceroute";
         }
         enum "http" {
           description "Hypertext Transfer Protocol";
         }
         enum "winframe" {
           description "WinFrame";
         }
         enum "https" {
           description "Hypertext Transfer Protocol";
         }
         enum "imap" {
           description "Internet Mail Access Protocol";
         }
         enum "smtp" {
           description "Simple Mail Transfer Protocol";
         }
         enum "ssh" {
           description "Secure Shell Protocol";
         }
         enum "telnet" {
           description "Telnet Protocol";
         }
         enum "twamp" {
           description "Two Way Active Meaurement Protocol";
         }
         enum "pop3" {
           description "Post Office Protocol 3 Protocol";
         }
         enum "smtps" {
           description "Simple Mail Transfer Protocol Over TLS";
         }
         enum "imaps" {
           description "Internet Mail Access Protocol Over TLS";
         }
         enum "pop3s" {
           description "Post Office Protocol 3 Protocol Over TLS";
         }
       }
     }
     leaf protocol {
       description "Match IP protocol type";
       type string;
     }
     leaf source-port {
       description "Match TCP/UDP source port";
       type string;
     }
     leaf destination-port {
       description "Match TCP/UDP destination port";
       type string;
     }
     leaf ether-type {
       description "Match ether type";
       type string {
         junos:posix-pattern "^(0[Xx][0-9A-Fa-f]{4})$|^([0-9A-Fa-f]{4})$";
         junos:pattern-message "Ether-type should be in hex - (example: 0x8906)";
       }
     }
     leaf snmp-command {
       description "Match SNMP command";
       type enumeration {
         enum "get" {
           description "Get request";
         }
         enum "get-next" {
           description "Get-next request";
         }
         enum "get-response" {
           description "Get response";
         }
         enum "set" {
           description "Set request";
         }
         enum "trap" {
           description "Trap";
         }
       }
     }
     leaf icmp-type {
       description "Match ICMP message type";
       type string;
     }
     leaf icmp6-type {
       description "Match ICMP6 message type";
       type string;
     }
     leaf icmp-code {
       description "Match ICMP message code";
       type string;
     }
     leaf icmp6-code {
       description "Match ICMP6 message code";
       type string;
     }
     leaf ttl-threshold {
       description "Traceroute TTL threshold";
       type union {
         type uint8;
         type string {
           pattern "<.*>|$.*";
         }
       }
     }
     leaf rpc-program-number {
       description "Match range of RPC program numbers";
       type string {
         junos:posix-pattern "^(0|[1-9][0-9]{0,9})(-(0|[1-9][0-9]{0,9}))?$";
         junos:pattern-message "Value must be an integer or a range of integers";
       }
     }
     leaf uuid {
       description "Match universal unique identifier for DCE RPC objects";
       type string {
         junos:posix-pattern "^[[:xdigit:]]{8}-[[:xdigit:]]{4}-[[:xdigit:]]{4}-[[:xdigit:]]{4}-[[:xdigit:]]{12}$";
         junos:pattern-message "Value must be of the form xxxxxxxx-xxxx-xxxx-xxxx-xxxxxxxxxxxx";
       }
     }
     leaf inactivity-timeout {
       description "Application-specific inactivity timeout";
       units "seconds";
       type string;
     }
     leaf gate-timeout {
       description "Application-specific gate timeout";
       units "seconds";
       type union {
         type string {
           pattern "<.*>|$.*";
         }
         type uint32 {
           range "5 .. 21600";
         }
       }
     }
     leaf child-inactivity-timeout {
       description "Application-specific child session inactivity timeout";
       units "seconds";
       type union {
         type string {
           pattern "<.*>|$.*";
         }
         type uint32 {
           range "4 .. 86400";
         }
       }
     }
     choice dns-choice {
       case case_1 {
         leaf do-not-translate-AAAA-query-to-A-query {
           description "Knob to control the translation of AAAA query to A query";
           junos:must "(\".. application-protocol dns\")";
           junos:must-message "Application protocol must be DNS";
           type empty;
         }
       }
       case case_2 {
         leaf do-not-translate-A-query-to-AAAA-query {
           description "Knob to control the translation of A query to AAAA query";
           junos:must "(\".. application-protocol dns\")";
           junos:must-message "Application protocol must be DNS";
           type empty;
         }
       }
     }
   }
   grouping application_set_object {
     leaf name {
       description "Application set name";
       type string {
         length "1 .. 63";
         junos:posix-pattern "^[[:alnum:]][[:alnum:]_-]*$";
         junos:pattern-message "Must be a string beginning with a number or letter and consisting of letters, numbers, dashes and underscores.";
       }
     }
     uses apply-advanced;
     leaf description {
       description "Text description of application set";
       type string {
         length "1 .. 900";
         junos:posix-pattern "^[^&<>\n]+$";
         junos:pattern-message "Must be a string excluding '&', '<', '>' and '\n'";
       }
     }
     list application {
       key name;
       ordered-by user;
       description "Application to be included in the set";
       leaf name {
         description "Application name";
         type string {
           length "1 .. 63";
           junos:posix-pattern "^[[:alnum:]][[:alnum:]_-]*$";
           junos:pattern-message "Must be a string beginning with a number or letter and consisting of letters, numbers, dashes and underscores.";
         }
       }
       uses apply-advanced;
     }
     list application-set {
       key name;
       ordered-by user;
       description "Define an application-set";
       leaf name {
         description "Define an application-set name";
         type string {
           length "1 .. 63";
           junos:posix-pattern "^[[:alnum:]][[:alnum:]_-]*$";
           junos:pattern-message "Must be a string beginning with a number or letter and consisting of letters, numbers, dashes and underscores.";
         }
       }
       uses apply-advanced;
     }
   }
   grouping apply-advanced {
     description "Apply advanced configuration logic";
     leaf-list apply-groups {
       ordered-by user;
       description "Groups from which to inherit configuration data";
       type string;
     }
     leaf-list apply-groups-except {
       ordered-by user;
       description "Don't inherit configuration data from these groups";
       type string;
     }
     list apply-macro {
       key name;
       ordered-by user;
       description "Macro and parameters for commit script expansion";
       uses apply-macro-type;
     }
   }
   grouping apply-macro-type {
     description "Macro data for commit-script expansion";
     leaf name {
       description "Name of the macro to be expanded";
       type string;
     }
     list data {
       key name;
       uses macro-data-type;
     }
   }
   grouping appqoe-probe-params {
     description "Active probe parameters";
     uses apply-advanced;
     container data-fill {
       description "Probe Data Payload content";
       uses apply-advanced;
       leaf fill {
         description "Repetitive payload string ";
         type string {
           length "1 .. 63";
         }
       }
     }
     container data-size {
       presence "enable data-size";
       description "Probe data size";
       uses apply-advanced;
       leaf size {
         description "Data Payload size of probe packet";
         type union {
           type string {
             pattern "<.*>|$.*";
           }
           type uint32 {
             range "4 .. 256";
           }
         }
       }
     }
     container per-packet-loss-timeout {
       presence "enable per-packet-loss-timeout";
       description "Time interval between 2 consecutive SaaS probes";
       uses apply-advanced;
       leaf timeout {
         description "Interval value in milliseconds";
         default "1000";
         type union {
           type string {
             pattern "<.*>|$.*";
           }
           type uint32 {
             range "100 .. 10000";
           }
         }
       }
     }
     container probe-interval {
       presence "enable probe-interval";
       description "Time interval between 2 consecutive probes";
       uses apply-advanced;
       leaf interval {
         description "Interval value in sec";
         default "10";
         type union {
           type string {
             pattern "<.*>|$.*";
           }
           type uint32 {
             range "1 .. 60";
           }
         }
       }
     }
     container probe-count {
       presence "enable probe-count";
       description "Minimum number of samples to be collected to evaluate SLA measurement";
       uses apply-advanced;
       leaf count {
         description "Sample count";
         default "5";
         type union {
           type string {
             pattern "<.*>|$.*";
           }
           type uint32 {
             range "1 .. 1000";
           }
         }
       }
     }
     container burst-size {
       presence "enable burst-size";
       description "Number of probes out of probe count to be sent as a burst";
       uses apply-advanced;
       leaf size {
         description "Burst size";
         default "1";
         type union {
           type string {
             pattern "<.*>|$.*";
           }
           type uint32 {
             range "1 .. 100";
           }
         }
       }
     }
     container sla-export-interval {
       description "Enabled time based SLA exporting";
       uses apply-advanced;
       leaf interval {
         description "Interval (sec)";
         type union {
           type string {
             pattern "<.*>|$.*";
           }
           type uint32 {
             range "60 .. 600";
           }
         }
       }
     }
     container dscp-code-points {
       description "Mapping of code point aliases to bit strings";
       uses apply-advanced;
       leaf dscp {
         description "DSCP";
         type string;
       }
     }
     container forwarding-class {
       description "Forwarding class corresponding to the DSCP";
       uses apply-advanced;
       leaf fc-name {
         description "Forwarding class name";
         type string;
       }
     }
     container loss-priority {
       presence "enable loss-priority";
       uses apply-advanced;
       leaf priority {
         description "Packet loss priority";
         type enumeration {
           enum "low" {
             description "Low loss priority";
           }
           enum "medium-low" {
             description "Medium-low loss priority";
           }
           enum "medium-high" {
             description "Medium-high loss priority";
           }
           enum "high" {
             description "High loss priority";
           }
         }
       }
     }
   }
   grouping appqoe-probe-path {
     description "Set probe path details";
     uses apply-advanced;
     container local {
       description "Local node's info";
       presence "enable local";
       uses appqoe-node;
     }
     container remote {
       description "Remote node's info";
       presence "enable remote";
       uses appqoe-node;
     }
   }
   grouping appqoe-node {
     description "Set node info";
     uses apply-advanced;
     container ip-address {
       presence "enable ip-address";
       description "Set IP address";
       uses apply-advanced;
       leaf ip_address {
         description "IP address";
         type jt:ipaddr;
       }
     }
   }
   grouping appqoe_sla_metric_profile {
     description "Metric Name";
     uses apply-advanced;
     container delay-round-trip {
       presence "enable delay-round-trip";
       description "Maximum acceptable delay";
       uses apply-advanced;
       leaf delay-val {
         description "Delay value(micro-sec)";
         type union {
           type string {
             pattern "<.*>|$.*";
           }
           type uint32 {
             range "0 .. 60000000";
           }
         }
       }
     }
     container jitter {
       presence "enable jitter";
       description "Maximum acceptable jitter";
       uses apply-advanced;
       leaf jitter-val {
         description "Jitter value(micro-sec)";
         type union {
           type string {
             pattern "<.*>|$.*";
           }
           type uint32 {
             range "0 .. 60000000";
           }
         }
       }
     }
     container jitter-type {
       presence "enable jitter-type";
       description "Type of Jitter";
       uses apply-advanced;
       leaf type {
         description "Jitter Type";
         type enumeration {
           enum "two-way-jitter" {
             description "Two-way-jitter-type";
           }
           enum "egress-jitter" {
             description "Egress-jitter-type";
           }
           enum "ingress-jitter" {
             description "Ingress-jitter-type";
           }
         }
       }
     }
     container packet-loss {
       presence "enable packet-loss";
       description "Maximum acceptable packet-loss";
       uses apply-advanced;
       leaf loss {
         description "Packet loss percentage";
         type union {
           type string {
             pattern "<.*>|$.*";
           }
           type uint32 {
             range "1 .. 100";
           }
         }
       }
     }
     container match {
       presence "enable match";
       description "Type of SLA match";
       uses apply-advanced;
       leaf sla_match {
         type enumeration {
           enum "any-one" {
             description "Match any one strings";
           }
           enum "all" {
             description "Match all metrics";
           }
         }
       }
     }
   }
   grouping appqos-traceoptions-type {
     description "Trace options for application classifier";
     uses apply-advanced;
     leaf no-remote-trace {
       description "Disable remote tracing";
       junos:must "(\"system tracing\")";
       junos:must-message "'no-remote-trace' is valid only when [system tracing] is configured";
       type empty;
     }
     container file {
       description "Trace file information";
       leaf filename {
         description "Name of file in which to write trace information";
         type string {
           length "1 .. 1024";
           junos:posix-pattern "![/ %]";
           junos:pattern-message "Must not contain '/', % or a space";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     list flag {
       key name;
       ordered-by user;
       description "Events and other information to include in trace output";
       leaf name {
         description "Flag name to include in trace output";
         type enumeration {
           enum "all" {
             description "All events";
           }
         }
       }
     }
     leaf level {
       description "Level of debugging output";
       default "error";
       type enumeration {
         enum "error" {
           description "Match error conditions";
         }
         enum "warning" {
           description "Match warning messages";
         }
         enum "notice" {
           description "Match conditions that should be handled specially";
         }
         enum "info" {
           description "Match informational messages";
         }
         enum "verbose" {
           description "Match verbose messages";
         }
         enum "all" {
           description "Match all levels";
         }
       }
     }
   }
   grouping appqos_rule_type {
     leaf name {
       description "Rule name";
       type string {
         length "1 .. 63";
       }
     }
     uses apply-advanced;
     container match {
       description "Specify application traffic control rule match-criteria";
       uses apply-advanced;
       leaf application-any {
         description "Any applications";
         type empty;
       }
       leaf application-unknown {
         description "Uknown applcations";
         status deprecated;
         type empty;
       }
       leaf application-known {
         description "Identifiable applications";
         type empty;
       }
       leaf-list application {
         ordered-by user;
         description "Specify application name to match";
         type string {
           length "1 .. 63";
         }
       }
       leaf-list application-group {
         ordered-by user;
         description "Specify application group name to match";
         type string {
           length "1 .. 63";
         }
       }
     }
     container then {
       description "Specify rule action to take when packet match criteria";
       uses apply-advanced;
       leaf forwarding-class {
         description "Forwarding class for outgoing packets";
         type string {
           junos:posix-pattern "^.{1,64}$";
           junos:pattern-message "Must be string of 64 characters or less";
         }
       }
       leaf dscp-code-point {
         description "DSCP code point bitmap or alias";
         type string {
           junos:posix-pattern "^(([01]{6})|([a-zA-Z].{0,63}))$";
           junos:pattern-message "Not 6-bit pattern or code point alias";
         }
       }
       leaf loss-priority {
         description "Packet loss priority";
         type enumeration {
           enum "low" {
             description "Low loss priority";
           }
           enum "medium-low" {
             description "Medium-low loss priority";
           }
           enum "medium-high" {
             description "Medium-high loss priority";
           }
           enum "high" {
             description "High loss priority";
           }
         }
       }
       container rate-limit {
         description "Apply rate limiters";
         uses apply-advanced;
         leaf client-to-server {
           description "Client-to-server rate limiter";
           junos:must "(\"class-of-service application-traffic-control rate-limiters $$\")";
           junos:must-message "Rate limiter must be defined";
           type string;
         }
         leaf server-to-client {
           description "Server-to-client rate limiter";
           junos:must "(\"class-of-service application-traffic-control rate-limiters $$\")";
           junos:must-message "Rate limiter must be defined";
           type string;
         }
         leaf loss-priority-high {
           description "Set Rate limiter's action Loss-Priority to high";
           type empty;
         }
       }
       leaf log {
         description "Log the action";
         type empty;
       }
     }
   }
   grouping authentication-source-type {
     description "Configure user-identification authentication-source";
     leaf name {
       description "User-identification authentication-source name";
       type enumeration {
         enum "local-authentication-table" {
           description "Local-authentication-table, default priority is 100.";
         }
         enum "unified-access-control" {
           description "Unified-access-control, default priority is 200.";
         }
         enum "firewall-authentication" {
           description "Firewall-authentication, default priority is 150.";
         }
         enum "active-directory-authentication-table" {
           description "Active-directory-authentication-table, default priority is 125.";
         }
         enum "aruba-clearpass" {
           description "ClearPass-authentication-table, default priority is 110.";
         }
       }
     }
     uses apply-advanced;
     choice authentication-source-option {
       case case_1 {
         leaf priority {
           description "Larger number means lower priority, 0 for disable";
           type union {
             type string {
               pattern "<.*>|$.*";
             }
             type uint16 {
               range "0 .. 65535";
             }
           }
         }
       }
     }
   }
   grouping av-fallback-settings {
     description "Anti-virus fallback settings";
     uses apply-advanced;
     leaf default {
       description "Default action";
       type enumeration {
         enum "permit" {
         }
         enum "log-and-permit" {
         }
         enum "block" {
         }
       }
     }
     leaf content-size {
       description "Fallback action for over content size";
       type enumeration {
         enum "permit" {
         }
         enum "log-and-permit" {
         }
         enum "block" {
         }
       }
     }
     leaf engine-not-ready {
       description "Fallback action for engine not ready";
       type enumeration {
         enum "permit" {
         }
         enum "log-and-permit" {
         }
         enum "block" {
         }
       }
     }
     leaf timeout {
       description "Fallback action for engine scan timeout";
       type enumeration {
         enum "permit" {
         }
         enum "log-and-permit" {
         }
         enum "block" {
         }
       }
     }
     leaf out-of-resources {
       description "Fallback action for out of resources";
       type enumeration {
         enum "permit" {
         }
         enum "log-and-permit" {
         }
         enum "block" {
         }
       }
     }
     leaf too-many-requests {
       description "Fallback action for requests exceed engine limit";
       type enumeration {
         enum "permit" {
         }
         enum "log-and-permit" {
         }
         enum "block" {
         }
       }
     }
     leaf decompress-err {
       description "Fallback action for decompress error";
       type enumeration {
         enum "permit" {
         }
         enum "log-and-permit" {
         }
         enum "block" {
         }
       }
     }
   }
   grouping aws-object {
     uses apply-advanced;
     container cloudwatch {
       description "Configure AWS CloudWatch";
       uses apply-advanced;
       container metric {
         description "Configure AWS CloudWatch metric";
         uses apply-advanced;
         leaf collect-interval {
           description "Set metric collection interval";
           default "3";
           units "minutes";
           type union {
             type string {
               pattern "<.*>|$.*";
             }
             type uint32 {
               range "1 .. 60";
             }
           }
         }
         leaf namespace {
           description "Container for collected metrics";
           type string {
             length "1 .. 32";
             junos:posix-pattern "![/ %]";
             junos:pattern-message "Must not contain '/', % or a space";
           }
         }
         leaf region {
           description "Set AWS CloudWatch metric region";
           type string;
         }
       }
       container log {
         description "Configure AWS CloudWatch metric";
         uses apply-advanced;
         leaf group {
           description "Group of log streams";
           type string {
             length "1 .. 32";
             junos:posix-pattern "![/ %]";
             junos:pattern-message "Must not contain '/', % or a space";
           }
         }
         leaf region {
           description "Set AWS CloudWatch log region";
           type string;
         }
         list file {
           key name;
           description "File from which to collect log data";
           leaf name {
             description "Name of file from which to collect log data";
             type string {
               length "1 .. 64";
               junos:posix-pattern "![/ %]";
               junos:pattern-message "Must not contain '/', % or a space";
             }
           }
           uses apply-advanced;
           leaf security-hub-import {
             description "Import security events in the file to AWS Security Hub";
             type empty;
           }
           leaf collect-interval {
             description "Set log collection interval";
             default "3";
             units "minutes";
             type union {
               type string {
                 pattern "<.*>|$.*";
               }
               type uint32 {
                 range "1 .. 60";
               }
             }
           }
         }
       }
     }
   }
   grouping banner-object {
     uses apply-advanced;
     container banner {
       description "Banners that are prompted during authentication";
       uses apply-advanced;
       leaf login {
         description "The message that will be displayed before login";
         type string {
           length "1 .. 250";
         }
       }
       leaf success {
         description "The message that will be displayed on successful login";
         type string {
           length "1 .. 250";
         }
       }
       leaf fail {
         description "The message that will be displayed after failed user login";
         type string {
           length "1 .. 250";
         }
       }
     }
   }
   grouping batch-query-type {
     description "Batch query configuration";
     uses apply-advanced;
     leaf items-per-batch {
       description "Items number per batch query";
       default "200";
       type union {
         type string {
           pattern "<.*>|$.*";
         }
         type uint32 {
           range "100 .. 1000";
         }
       }
     }
     leaf query-interval {
       description "Query interval";
       default "5";
       units "seconds";
       type union {
         type string {
           pattern "<.*>|$.*";
         }
         type uint32 {
           range "1 .. 60";
         }
       }
     }
   }
   grouping category-list-type {
     description "Configure category-list object";
     leaf name {
       description "Configure name of category-list object";
       type string {
         length "1 .. 59";
         junos:posix-pattern "^[a-zA-Z_]+[a-zA-Z_0-9-]*$";
         junos:pattern-message "Must be a string beginning with a letter or underscore and consisting of letters, numbers, dashes and underscores.";
       }
     }
     uses apply-advanced;
     leaf-list value {
       ordered-by user;
       description "Configure value of category-list object";
       type string;
     }
   }
   grouping certificate-object {
     leaf name {
       description "Simple name to identify this certificate";
       type string;
     }
     uses apply-advanced;
     leaf certificate {
       description "Certificate and private key string";
       type string;
     }
   }
   grouping command-list-type {
     description "Configure command-list object";
     leaf name {
       description "Configure name of command-list object";
       type string {
         length "1 .. 29";
         junos:posix-pattern "^[a-zA-Z_]+[a-zA-Z_0-9-]*$";
         junos:pattern-message "Must be a string beginning with a letter or underscore and consisting of letters, numbers, dashes and underscores.";
       }
     }
     uses apply-advanced;
     leaf-list value {
       ordered-by user;
       description "Configure value of command-list object";
       type string {
         length "1 .. 64";
       }
     }
   }
   grouping content-filtering-feature {
     description "Content-filtering feature";
     uses apply-advanced;
     list profile {
       key name;
       ordered-by user;
       description "Content filtering profile";
       leaf name {
         description "Content-filtering feature profile name";
         type string {
           length "1 .. 29";
         }
       }
       uses apply-advanced;
       leaf permit-command {
         description "Permit command list";
         junos:must "(\"security utm custom-objects protocol-command $$\")";
         junos:must-message "protocol-command must be defined";
         type string;
       }
       leaf block-command {
         description "Block command list";
         junos:must "(\"security utm custom-objects protocol-command $$\")";
         junos:must-message "protocol-command must be defined";
         type string;
       }
       leaf block-extension {
         description "Block extension list";
         junos:must "(\"security utm custom-objects filename-extension $$\")";
         junos:must-message "filename-extension must be defined";
         type string;
       }
       container block-mime {
         presence "enable block-mime";
         description "Content-filtering feature block MIME";
         uses apply-advanced;
         leaf list {
           description "Block MIME list";
           junos:must "(\"security utm custom-objects mime-pattern $$\")";
           junos:must-message "mime-pattern must be defined";
           type string;
         }
         leaf exception {
           description "Exception of block MIME list";
           junos:must "(\"security utm custom-objects mime-pattern $$\")";
           junos:must-message "mime-pattern must be defined";
           type string;
         }
       }
       container block-content-type {
         description "Content-filtering feature block content type";
         uses apply-advanced;
         leaf activex {
           description "Block activex";
           type empty;
         }
         leaf java-applet {
           description "Block Java-applet";
           type empty;
         }
         leaf exe {
           description "Block Windows/dos exe file";
           type empty;
         }
         leaf zip {
           description "Block zip file";
           type empty;
         }
         leaf http-cookie {
           description "Block HTTP cookie";
           type empty;
         }
       }
       container notification-options {
         presence "enable notification-options";
         description "Notification options";
         uses apply-advanced;
         leaf type {
           description "Notification options type";
           type enumeration {
             enum "protocol-only" {
               description "Notification in protocol level";
             }
             enum "message" {
               description "Notification in message";
             }
           }
         }
         choice notify-mail-sender-choice {
           leaf notify-mail-sender {
             description "Notifiy mail sender";
             type empty;
           }
           leaf no-notify-mail-sender {
             description "Don't notifiy mail sender";
             type empty;
           }
         }
         leaf custom-message {
           description "Custom notification message";
           type string {
             length "1 .. 512";
           }
         }
       }
     }
   }
   grouping custom-attack-group-type {
     description "Define custom attack group";
     leaf name {
       description "Custom attack group name";
       type string;
     }
     uses apply-advanced;
     leaf attack-group-description {
       description "Attack group description in xml format";
       status deprecated;
       type string;
     }
     leaf-list group-members {
       ordered-by user;
       description "List of attacks/attack groups belonging to this group";
       type string;
     }
   }
   grouping custom-attack-type {
     description "Define custom attack";
     leaf name {
       description "Custom attack name";
       type string {
         junos:posix-pattern "^.{1,60}$";
         junos:pattern-message "Custom attack name must be a string of 60 characters or less";
       }
     }
     uses apply-advanced;
     leaf-list attack-description {
       ordered-by user;
       description "Attack description";
       type string;
     }
     leaf recommended-action {
       description "Recommended Action";
       type enumeration {
         enum "none" {
           description "No action";
         }
         enum "ignore" {
           description "No further inspection on the flow";
         }
         enum "drop-packet" {
           description "Drop the packet";
         }
         enum "drop" {
           description "Drop the packet and subsequent packets of the flow";
         }
         enum "close-client" {
           description "Reset the client side";
         }
         enum "close-server" {
           description "Reset the server side";
         }
         enum "close" {
           description "Reset both client and server";
         }
       }
     }
     leaf severity {
       description "Select the severity that matches the lethality of this attack on your network";
       type enumeration {
         enum "info" {
           description "Provide information of attack when it matches.";
         }
         enum "warning" {
           description "Issue a warning when attack matches.";
         }
         enum "minor" {
           description "The attack is a  minor one.";
         }
         enum "major" {
           description "The attack is a major one.";
         }
         enum "critical" {
           description "The attack is a critical one.";
         }
       }
     }
     container time-binding {
       description "Time binding params";
       leaf count {
         description "Number of times this attack is to be triggered";
         type union {
           type uint32;
           type string {
             pattern "<.*>|$.*";
           }
         }
       }
       leaf scope {
         description "Scope within which the count occurs";
         junos:must "((!(\".. count 0\") && !(\".. count 1\")))";
         junos:must-message "Scope should be defined if count > 1";
         type enumeration {
           enum "peer" {
             description "If the attack is between a single source and single destination";
           }
           enum "source" {
             description "If the attack is from one source and multiple destination";
           }
           enum "destination" {
             description "If the attack is from multiple sources to one destination";
           }
         }
       }
       leaf interval {
         description "Maximum time-gap between two instances of the attack. Format : MMm-SSs";
         default "01m-00s";
         junos:must "((!(\".. count 0\") && (!(\".. count 1\") && (\".. count\" && \".. scope\"))))";
         junos:must-message "To configure interval, count & scope should be set and count should be greater than or equal to 2";
         type string {
           junos:posix-pattern "^((([0-5][0-9])[m][-]([0-5][0-9])[s])|([6][0][m][-][0][0][s]))$";
           junos:pattern-message "Invalid interval format: Correct format MMm-SSs, with minutes range 00-60, seconds range 00-59";
         }
       }
     }
     container detection-filter {
       junos:must "(!(\".. time-binding\"))";
       junos:must-message "Time-binding and detection-filter will not be allowed together";
       description "Detection filter params";
       leaf count {
         description "Number of matches for this attack to be triggered. Must be greater than 0";
         type union {
           type uint32;
           type string {
             pattern "<.*>|$.*";
           }
         }
       }
       leaf scope {
         description "Scope within which the count occurs";
         type enumeration {
           enum "session" {
             description "If the attack is between a single source and single destination";
           }
           enum "source" {
             description "If the attack is from one source and multiple destination";
           }
           enum "destination" {
             description "If the attack is from multiple sources to one destination";
           }
         }
       }
       leaf interval {
         description "Time period over which count is accrued. Format : MMm-SSs. Minimum value is 1 second";
         type string {
           junos:posix-pattern "^((([0-5][0-9])[m][-]([0-5][0-9])[s])|([6][0][m][-][0][0][s]))$";
           junos:pattern-message "Invalid interval format: Correct format MMm-SSs, with minutes range 00-60, seconds range 00-59";
         }
       }
     }
     container attack-type {
       description "Type of attack";
       uses apply-advanced;
       container signature {
         junos:must "(!((\".. anomaly\" || \".. chain\")))";
         junos:must-message "Only one attack type is permitted";
         description "Signature based attack";
         uses apply-advanced;
         container protocol-binding {
           description "Protocol binding over which attack will be detected";
           uses apply-advanced;
           choice protocol {
             case case_1 {
               container tcp {
                 presence "enable tcp";
                 description "Attack is for TCP packets only";
                 uses apply-advanced;
                 list minimum-port {
                   key name;
                   ordered-by user;
                   description "Multiple sets of (single port/port ranges) can be specified";
                   uses port-range;
                 }
               }
             }
             case case_2 {
               container udp {
                 presence "enable udp";
                 description "Attack is for UDP packets only";
                 uses apply-advanced;
                 list minimum-port {
                   key name;
                   ordered-by user;
                   description "Either single port or port ranges can be specified";
                   uses port-range;
                 }
               }
             }
             case case_3 {
               container rpc {
                 presence "enable rpc";
                 description "Attack is for RPC packets only";
                 uses apply-advanced;
                 leaf program-number {
                   description "RPC Program Number";
                   type union {
                     type uint32;
                     type string {
                       pattern "<.*>|$.*";
                     }
                   }
                 }
               }
             }
             case case_4 {
               leaf icmp {
                 description "Attack is for ICMP packets only";
                 type empty;
               }
             }
             case case_5 {
               leaf icmpv6 {
                 description "Attack is for ICMPv6 packets only";
                 type empty;
               }
             }
             case case_6 {
               container ip {
                 presence "enable ip";
                 description "Attack is for all IP based packets";
                 uses apply-advanced;
                 leaf protocol-number {
                   description "Transport layer protocol number";
                   type union {
                     type string {
                       pattern "<.*>|$.*";
                     }
                     type uint32 {
                       range "0 .. 139";
                     }
                   }
                 }
               }
             }
             case case_7 {
               container ipv6 {
                 presence "enable ipv6";
                 description "Attack is for all IPv6 based packets";
                 uses apply-advanced;
                 leaf protocol-number {
                   description "Transport layer protocol number";
                   type union {
                     type string {
                       pattern "<.*>|$.*";
                     }
                     type uint32 {
                       range "0 .. 139";
                     }
                   }
                 }
               }
             }
             case case_8 {
               leaf application {
                 description "Application name";
                 type string;
               }
             }
             case case_9 {
               leaf nested-application {
                 description "Nested application name";
                 status deprecated;
                 type string;
               }
             }
           }
         }
         leaf context {
           description "Context";
           type string;
         }
         leaf pattern {
           description "Pattern is the signature of the attack you want to detect";
           junos:must "(\".. context\")";
           junos:must-message "Context must be specified";
           type string {
             length "0 .. 511";
           }
         }
         leaf pattern-pcre {
           description "Attack signature pattern in PCRE format";
           junos:must "(\".. context\")";
           junos:must-message "Context must be specified";
           type string {
             length "0 .. 511";
           }
         }
         container content {
           junos:must "(\".. context\")";
           junos:must-message "Context must be specified";
           description "Mention the match-modifire parameters to enhance pattern matching";
           leaf pattern {
             description "Specify match-modifier pattern";
             type string;
           }
           leaf pcre {
             description "PCRE expression";
             type string {
               length "0 .. 511";
             }
           }
           container depth {
             junos:must "(\".. pattern\")";
             junos:must-message "Content pattern must be specified";
             description "Maximum depth to search pattern within a packet. Depth is not relative";
             leaf depth-value {
               description "Specify the value of 'depth'";
               type union {
                 type string {
                   pattern "<.*>|$.*";
                 }
                 type uint16 {
                   range "1 .. 65535";
                 }
               }
             }
             leaf depth-variable {
               description "Specify the variable name from which 'depth' should be extracted";
               type string;
             }
           }
           container offset {
             junos:must "(\".. pattern\")";
             junos:must-message "Content pattern must be specified";
             description "Where to start searching for a pattern within a packet. Offset value is not relative";
             leaf offset-value {
               description "Specify the value of 'offset'";
               type union {
                 type string {
                   pattern "<.*>|$.*";
                 }
                 type uint16 {
                   range "0 .. 65535";
                 }
               }
             }
             leaf offset-variable {
               description "Specify the variable name from which 'offset' should be extracted";
               type string;
             }
           }
           container within {
             junos:must "(\".. pattern\")";
             junos:must-message "Content pattern must be specified";
             description "Maximum Number of bytes present between two conjugative pattern match. within is  relative";
             leaf within-value {
               description "Specify the value of 'within'";
               type union {
                 type string {
                   pattern "<.*>|$.*";
                 }
                 type uint16 {
                   range "1 .. 65535";
                 }
               }
             }
             leaf within-variable {
               description "Specify the variable name from which 'within' should be extracted";
               type string;
             }
           }
           container distance {
             junos:must "(\".. pattern\")";
             junos:must-message "Content pattern must be specified";
             description "Maximum Length to ignore before searching next pattern match. Distance is  relative";
             leaf distance-value {
               description "Specify the value of 'distance'";
               type union {
                 type string {
                   pattern "<.*>|$.*";
                 }
                 type int32 {
                   range "-65535 .. 65535";
                 }
               }
             }
             leaf distance-variable {
               description "Specify the variable name from which 'distance' should be extracted";
               type string;
             }
           }
           container byte-extract {
             junos:must "(\".. pattern\")";
             junos:must-message "Content pattern must be specified";
             description "Mention the byte-extract parameters for signature in length encoded protocols";
             leaf bytes {
               description "Specify the number of bytes to extract from packet";
               type union {
                 type string {
                   pattern "<.*>|$.*";
                 }
                 type uint32 {
                   range "1 .. 10";
                 }
               }
             }
             leaf offset {
               description "Specify the number of bytes in to payload to start processing";
               type union {
                 type int32;
                 type string {
                   pattern "<.*>|$.*";
                 }
               }
             }
             leaf var-name {
               description "Specify the name of the variable to reference in other rule options";
               type string;
             }
             leaf relative {
               description "Specify whether to use an offset relative to last pattern match or not";
               type empty;
             }
             leaf multiplier {
               description "Specify the value to be multiplied against the bytes read";
               type union {
                 type uint16;
                 type string {
                   pattern "<.*>|$.*";
                 }
               }
             }
             leaf endianness {
               description "Specify the endianness with which bytes read should be processed";
               type enumeration {
                 enum "Little" {
                   description "Process data in little endian";
                 }
                 enum "Big" {
                   description "Process data in big endian";
                 }
               }
             }
             leaf align {
               description "Specify the byte alignment";
               type enumeration {
                 enum "2-byte" {
                   description "Round the number of converted bytes to 2-byte boundary";
                 }
                 enum "4-byte" {
                   description "Round the number of converted bytes to 4-byte boundary";
                 }
               }
             }
             leaf string {
               description "Specify the data type in which string data should be parsed";
               type enumeration {
                 enum "hex" {
                   description "Process data in hexadecimal format";
                 }
                 enum "dec" {
                   description "Process data in decimal format";
                 }
                 enum "oct" {
                   description "Process data in octal format";
                 }
               }
             }
             leaf bitmask {
               description "Specify the bitmask (1-4 bytes) for AND operation in hexadecimal format";
               type string;
             }
           }
           container byte-test {
             junos:must "(\".. pattern\")";
             junos:must-message "Content pattern must be specified";
             description "Mention the byte-test parameters for signature in length encoded protocols";
             leaf bytes {
               description "Specify the number of bytes to extract from packet";
               type union {
                 type string {
                   pattern "<.*>|$.*";
                 }
                 type uint32 {
                   range "1 .. 10";
                 }
               }
             }
             container offset {
               description "Mention the offset variable name or offset value to be used";
               leaf offset-value {
                 description "Specify the number of bytes in to payload to start processing";
                 type union {
                   type int32;
                   type string {
                     pattern "<.*>|$.*";
                   }
                 }
               }
               leaf offset-variable {
                 description "Specify the name of the offset variable";
                 type string;
               }
             }
             container rvalue {
               description "Specify the rvalue to test the converted value against";
               leaf rvalue-value {
                 description "Specify the value";
                 type union {
                   type uint32;
                   type string {
                     pattern "<.*>|$.*";
                   }
                 }
               }
               leaf rvalue-variable {
                 description "Specify the variable name";
                 type string;
               }
             }
             leaf relative {
               description "Specify whether to use an offset relative to last pattern match or not";
               type empty;
             }
             leaf operator {
               description "Specify the operation to perform on extracted value";
               type enumeration {
                 enum "less-than" {
                   description "Perform operation 'less than'";
                 }
                 enum "greater-than" {
                   description "Perform operation 'greater than'";
                 }
                 enum "less-than-or-equal" {
                   description "Perform operation 'less than or equal'";
                 }
                 enum "greater-than-or-equal" {
                   description "Perform operation 'greater than or equal'";
                 }
                 enum "equal" {
                   description "Perform operation 'equal'";
                 }
                 enum "bitwise-AND" {
                   description "Perform operation 'bitwise AND'";
                 }
                 enum "bitwise-XOR" {
                   description "Perform operation 'bitwise OR'";
                 }
               }
             }
             leaf negate {
               description "Check if the operator is not true";
               type empty;
             }
             leaf endianness {
               description "Specify the endianness with which bytes read should be processed";
               type enumeration {
                 enum "Little" {
                   description "Process data in little endian";
                 }
                 enum "Big" {
                   description "Process data in big endian";
                 }
               }
             }
             leaf string {
               description "Specify the data type in which string data should be parsed";
               type enumeration {
                 enum "hex" {
                   description "Process data in hexadecimal format";
                 }
                 enum "dec" {
                   description "Process data in decimal format";
                 }
                 enum "oct" {
                   description "Process data in octal format";
                 }
               }
             }
             leaf bitmask {
               description "Specify the bitmask (1-4 bytes) for AND operation in hexadecimal format";
               type string;
             }
           }
           container byte-math {
             junos:must "(\".. pattern\")";
             junos:must-message "Content pattern must be specified";
             description "Mention the byte-math parameters for signature in length encoded protocols";
             leaf bytes {
               description "Specify the number of bytes to extract from packet";
               type union {
                 type string {
                   pattern "<.*>|$.*";
                 }
                 type uint32 {
                   range "1 .. 10";
                 }
               }
             }
             leaf offset {
               description "Specify the number of bytes in to payload to start processing";
               type union {
                 type string {
                   pattern "<.*>|$.*";
                 }
                 type uint16 {
                   range "0 .. 65535";
                 }
               }
             }
             container rvalue {
               description "Specify the value to use mathematical operation against";
               leaf rvalue-value {
                 description "Specify the value";
                 type union {
                   type uint32;
                   type string {
                     pattern "<.*>|$.*";
                   }
                 }
               }
               leaf rvalue-variable {
                 description "Specify the variable name";
                 type string;
               }
             }
             leaf relative {
               description "Specify whether to use an offset relative to last pattern match or not";
               type empty;
             }
             leaf operator {
               description "Specify the operation to perform on extracted value";
               type enumeration {
                 enum "addition" {
                   description "Perform operation 'addition'";
                 }
                 enum "subtraction" {
                   description "Perform operation 'subtraction'";
                 }
                 enum "multiplication" {
                   description "Perform operation 'multiplication'";
                 }
                 enum "division" {
                   description "Perform operation 'division'";
                 }
                 enum "right-shift" {
                   description "Perform operation 'right shift'";
                 }
                 enum "left-shift" {
                   description "Perform operation 'left shift'";
                 }
               }
             }
             leaf endianness {
               description "Specify the endianness with which bytes read should be processed";
               type enumeration {
                 enum "Little" {
                   description "Process data in little endian";
                 }
                 enum "Big" {
                   description "Process data in big endian";
                 }
               }
             }
             leaf string {
               description "Specify the data type in which string data should be parsed";
               type enumeration {
                 enum "hex" {
                   description "Process data in hexadecimal format";
                 }
                 enum "dec" {
                   description "Process data in decimal format";
                 }
                 enum "oct" {
                   description "Process data in octal format";
                 }
               }
             }
             leaf bitmask {
               description "Specify the bitmask (1-4 bytes) for AND operation in hexadecimal format";
               type string;
             }
             leaf result {
               description "Specify the variable name to which result should be stored";
               type string;
             }
           }
           container byte-jump {
             junos:must "(\".. pattern\")";
             junos:must-message "Content pattern must be specified";
             description "Mention the byte-jump parameters for signature in length encoded protocols";
             leaf bytes {
               description "Specify the number of bytes to extract from packet";
               type union {
                 type string {
                   pattern "<.*>|$.*";
                 }
                 type uint32 {
                   range "1 .. 10";
                 }
               }
             }
             container offset {
               description "Mention the offset variable name or offset value to be used";
               leaf offset-value {
                 description "Specify the number of bytes in to payload to start processing";
                 type union {
                   type string {
                     pattern "<.*>|$.*";
                   }
                   type uint16 {
                     range "0 .. 65535";
                   }
                 }
               }
               leaf offset-variable {
                 description "Specify the name of the offset variable";
                 type string;
               }
             }
             leaf relative {
               description "Specify whether to use an offset relative to last pattern match or not";
               type empty;
             }
             leaf multiplier {
               description "Specify the value to be multiplied against the bytes read";
               type union {
                 type uint16;
                 type string {
                   pattern "<.*>|$.*";
                 }
               }
             }
             leaf endianness {
               description "Specify the endianness with which bytes read should be processed";
               type enumeration {
                 enum "Little" {
                   description "Process data in little endian";
                 }
                 enum "Big" {
                   description "Process data in big endian";
                 }
               }
             }
             leaf align {
               description "Specify the endianness with which bytes read should be processed";
               type enumeration {
                 enum "4-byte" {
                   description "Round the number of converted bytes to 4-byte boundary";
                 }
               }
             }
             leaf string {
               description "Specify the data type in which string data should be parsed";
               type enumeration {
                 enum "hex" {
                   description "Process data in hexadecimal format";
                 }
                 enum "dec" {
                   description "Process data in decimal format";
                 }
                 enum "oct" {
                   description "Process data in octal format";
                 }
               }
             }
             leaf bitmask {
               description "Specify the bitmask (1-4 bytes) for AND operation in hexadecimal format";
               type string;
             }
             leaf from-beginning {
               description "Enable jump from the beginning of the payload";
               type empty;
             }
             leaf from-end {
               description "Enable jump from the end of the payload";
               type empty;
             }
             leaf post-offset {
               description "Specify the number of bytes to skip forward or backward";
               type union {
                 type string {
                   pattern "<.*>|$.*";
                 }
                 type int32 {
                   range "-65535 .. 65535";
                 }
               }
             }
           }
           container is-data-at {
             junos:must "(\".. pattern\")";
             junos:must-message "Content pattern must be specified";
             description "Mention the is-data-at parameters for signature in length encoded protocols";
             container offset {
               description "Mention the offset variable name or offset value to be used";
               leaf offset-value {
                 description "Specify the number of bytes in to payload to start processing";
                 type union {
                   type string {
                     pattern "<.*>|$.*";
                   }
                   type uint16 {
                     range "0 .. 65535";
                   }
                 }
               }
               leaf offset-variable {
                 description "Specify the name of the offset variable";
                 type string;
               }
             }
             leaf relative {
               description "Specify whether to use an offset relative to last pattern match or not";
               type empty;
             }
             leaf negate {
               description "Negates the results of the isdataat test";
               type empty;
             }
           }
         }
         container optional-parameters {
           junos:must "(\".. pattern-pcre\")";
           junos:must-message "Applicable only for pattern-pcre defined signatures";
           description "Mention the optional parameters to enhance pattern matching";
           leaf min-offset {
             description "Minimum offset in data at which pattern-match can end";
             type union {
               type uint64;
               type string {
                 pattern "<.*>|$.*";
               }
             }
           }
           leaf max-offset {
             description "Maximum offset in data at which pattern-match can end";
             type union {
               type uint64;
               type string {
                 pattern "<.*>|$.*";
               }
             }
           }
           leaf min-length {
             description "Minimum match length required to match the pattern";
             type union {
               type uint64;
               type string {
                 pattern "<.*>|$.*";
               }
             }
           }
           leaf edit-distance {
             description "Match the pattern within this edit distance";
             type union {
               type uint32;
               type string {
                 pattern "<.*>|$.*";
               }
             }
           }
           leaf hamming-distance {
             description "Match the pattern within this hamming distance";
             type union {
               type uint32;
               type string {
                 pattern "<.*>|$.*";
               }
             }
           }
         }
         leaf regexp {
           description "Regular expression used for matching repetition of patterns";
           junos:must "((\".. pattern\" || \".. pattern-pcre\"))";
           junos:must-message "A pattern or pattern-pcre must be defined ";
           type string {
             length "0 .. 511";
           }
         }
         leaf negate {
           description "Trigger the attack if condition is not met";
           junos:must "(!((\".. context normalized-stream\" || (\".. context normalized-stream256\" || (\".. context normalized-stream1k\" || \".. context normalized-stream8k\")))))";
           junos:must-message "Negation not supported for normalized-stream contexts";
           junos:must "(!((\".. context stream\" || (\".. context stream256\" || (\".. context stream1k\" || \".. context stream8k\")))))";
           junos:must-message "Negation not supported for stream contexts";
           type empty;
         }
         leaf direction {
           description "Connection direction of the attack";
           type enumeration {
             enum "client-to-server" {
               description "Client to Server";
             }
             enum "server-to-client" {
               description "Server to Client";
             }
             enum "any" {
               description "Any direction";
             }
           }
         }
         leaf shellcode {
           description "Specify shellcode flag for this attack";
           type enumeration {
             enum "intel" {
               description "Detect shellcode for intel platforms";
             }
             enum "sparc" {
               description "Detect shellcode for sparc platforms";
             }
             enum "all" {
               description "Detect shellcode for both intel and sparc platforms";
             }
             enum "no-shellcode" {
               description "Do not detect shellcode";
             }
           }
         }
         container protocol {
           description "Protocol header matches";
           uses apply-advanced;
           container ipv4 {
             description "IPv4 protocol parameters";
             uses apply-advanced;
             container tos {
               presence "enable tos";
               description "Type of Service";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 255";
                   }
                 }
               }
             }
             container ihl {
               presence "enable ihl";
               description "Header length in words";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 15";
                   }
                 }
               }
             }
             container total-length {
               presence "enable total-length";
               description "Total Length of IP datagram";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 65535";
                   }
                 }
               }
             }
             container identification {
               presence "enable identification";
               description "Fragment Identification";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 65535";
                   }
                 }
               }
             }
             container ip-flags {
               presence "enable ip-flags";
               description "IP Flag bits";
               choice rb-choice {
                 leaf rb {
                   description "Reserved bit";
                   type empty;
                 }
                 leaf no-rb {
                   description "Don't reserved bit";
                   type empty;
                 }
               }
               choice mf-choice {
                 leaf mf {
                   description "More Fragment bit";
                   type empty;
                 }
                 leaf no-mf {
                   description "Don't more Fragment bit";
                   type empty;
                 }
               }
               choice df-choice {
                 leaf df {
                   description "Don't Fragment bit";
                   type empty;
                 }
                 leaf no-df {
                   description "Don't don't Fragment bit";
                   type empty;
                 }
               }
             }
             container ttl {
               presence "enable ttl";
               description "Time to live";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 255";
                   }
                 }
               }
             }
             container protocol {
               presence "enable protocol";
               description "Transport layer protocol";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 255";
                   }
                 }
               }
             }
             container source {
               presence "enable source";
               description "Source IP-address/Hostname";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type jt:ipv4addr;
               }
             }
             container destination {
               presence "enable destination";
               description "Destination IP-address/Hostname";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type jt:ipv4addr;
               }
             }
             container checksum-validate {
               presence "enable checksum-validate";
               description "Validate checksum field against calculated checksum";
               leaf match {
                 description "Match condition";
                 junos:must "(\".. value\")";
                 junos:must-message "Missing mandatory statement: 'value'";
                 type enumeration {
                   enum "equal" {
                     description "Match when checksum field in packet is exact match";
                   }
                   enum "greater-than" {
                     description "Match when checksum field in packet is greater";
                   }
                   enum "less-than" {
                     description "Match when checksum field in packet is less";
                   }
                   enum "not-equal" {
                     description "Match when checksum field in packet is not exact match";
                   }
                 }
               }
               leaf value {
                 description "Match value";
                 default "0";
                 junos:must "(\".. match\")";
                 junos:must-message "Missing mandatory statement: 'match'";
                 type union {
                   type string {
                     pattern "<.*>|$.*";
                   }
                   type uint32 {
                     range "0 .. 65535";
                   }
                 }
               }
             }
           }
           container ipv6 {
             description "IPv6 protocol parameters";
             uses apply-advanced;
             container traffic-class {
               presence "enable traffic-class";
               description "Traffic class. Similar to TOS in IPv4";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 255";
                   }
                 }
               }
             }
             container payload-length {
               presence "enable payload-length";
               description "Length of the payload in the IPv6 datagram";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 65535";
                   }
                 }
               }
             }
             container flow-label {
               presence "enable flow-label";
               description "Flow label identification";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 1048575";
                   }
                 }
               }
             }
             container hop-limit {
               presence "enable hop-limit";
               description "Hop limit";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 255";
                   }
                 }
               }
             }
             container next-header {
               presence "enable next-header";
               description "The header following the basic IPv6 header";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 255";
                   }
                 }
               }
             }
             container source {
               presence "enable source";
               description "Source IP-address or hostname";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type jt:ipv6addr;
               }
             }
             container destination {
               presence "enable destination";
               description "Destination IP-address or hostname";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type jt:ipv6addr;
               }
             }
             container extension-header {
               description "IPv6 Extension headers";
               uses apply-advanced;
               container routing-header {
                 presence "enable routing-header";
                 description "IPv6 Routing extension header";
                 uses apply-advanced;
                 container header-type {
                   description "Routing header type";
                   uses apply-advanced;
                   leaf match {
                     description "Match condition";
                     type enumeration {
                       enum "equal" {
                         description "Match when value in packet is exact match";
                       }
                       enum "greater-than" {
                         description "Match when value in packet is greater";
                       }
                       enum "less-than" {
                         description "Match when value in packet is less";
                       }
                       enum "not-equal" {
                         description "Match when value in packet is not exact match";
                       }
                     }
                   }
                   leaf value {
                     description "Match value";
                     type union {
                       type string {
                         pattern "<.*>|$.*";
                       }
                       type uint32 {
                         range "0 .. 255";
                       }
                     }
                   }
                 }
               }
               container destination-option {
                 description "IPv6 Destination option extension header";
                 uses apply-advanced;
                 container option-type {
                   description "Destination option header type";
                   uses apply-advanced;
                   leaf match {
                     description "Match condition";
                     type enumeration {
                       enum "equal" {
                         description "Match when value in packet is exact match";
                       }
                       enum "greater-than" {
                         description "Match when value in packet is greater";
                       }
                       enum "less-than" {
                         description "Match when value in packet is less";
                       }
                       enum "not-equal" {
                         description "Match when value in packet is not exact match";
                       }
                     }
                   }
                   leaf value {
                     description "Match value";
                     type union {
                       type string {
                         pattern "<.*>|$.*";
                       }
                       type uint32 {
                         range "0 .. 255";
                       }
                     }
                   }
                 }
                 container home-address {
                   description "IPv6 Home address of the mobile node";
                   uses apply-advanced;
                   leaf match {
                     description "Match condition";
                     type enumeration {
                       enum "equal" {
                         description "Match when value in packet is exact match";
                       }
                       enum "greater-than" {
                         description "Match when value in packet is greater";
                       }
                       enum "less-than" {
                         description "Match when value in packet is less";
                       }
                       enum "not-equal" {
                         description "Match when value in packet is not exact match";
                       }
                     }
                   }
                   leaf value {
                     description "Match value";
                     type jt:ipv6addr;
                   }
                 }
               }
             }
           }
           container tcp {
             junos:must "((!(\".. udp\") && !(\".. icmp\")))";
             junos:must-message "tcp cannot be specified with udp or icmp";
             description "TCP protocol parameters";
             uses apply-advanced;
             container source-port {
               presence "enable source-port";
               description "Source port";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 65535";
                   }
                 }
               }
             }
             container destination-port {
               presence "enable destination-port";
               description "Destination port";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 65535";
                   }
                 }
               }
             }
             container sequence-number {
               presence "enable sequence-number";
               description "Sequence Number";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 4294967295";
                   }
                 }
               }
             }
             container ack-number {
               presence "enable ack-number";
               description "Acknowledgement Number";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 4294967295";
                   }
                 }
               }
             }
             container header-length {
               presence "enable header-length";
               description "Header Length in words";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 15";
                   }
                 }
               }
             }
             container reserved {
               presence "enable reserved";
               description "Three reserved bits";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 7";
                   }
                 }
               }
             }
             container window-size {
               presence "enable window-size";
               description "Window Size";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 65535";
                   }
                 }
               }
             }
             container urgent-pointer {
               presence "enable urgent-pointer";
               description "Urgent Pointer";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 65535";
                   }
                 }
               }
             }
             container tcp-flags {
               presence "enable tcp-flags";
               description "TCP header flags";
               choice r1-choice {
                 leaf r1 {
                   description "Set Reserverd bit 1";
                   type empty;
                 }
                 leaf no-r1 {
                   description "Don't set Reserverd bit 1";
                   type empty;
                 }
               }
               choice r2-choice {
                 leaf r2 {
                   description "Set Reserved bit 2";
                   type empty;
                 }
                 leaf no-r2 {
                   description "Don't set Reserved bit 2";
                   type empty;
                 }
               }
               choice urg-choice {
                 leaf urg {
                   description "Set Urgent bit";
                   type empty;
                 }
                 leaf no-urg {
                   description "Don't set Urgent bit";
                   type empty;
                 }
               }
               choice ack-choice {
                 leaf ack {
                   description "Set Acknowledge bit";
                   type empty;
                 }
                 leaf no-ack {
                   description "Don't set Acknowledge bit";
                   type empty;
                 }
               }
               choice psh-choice {
                 leaf psh {
                   description "Set Push bit";
                   type empty;
                 }
                 leaf no-psh {
                   description "Don't set Push bit";
                   type empty;
                 }
               }
               choice rst-choice {
                 leaf rst {
                   description "Set Reset bit";
                   type empty;
                 }
                 leaf no-rst {
                   description "Don't set Reset bit";
                   type empty;
                 }
               }
               choice syn-choice {
                 leaf syn {
                   description "Set SYN bit";
                   type empty;
                 }
                 leaf no-syn {
                   description "Don't set SYN bit";
                   type empty;
                 }
               }
               choice fin-choice {
                 leaf fin {
                   description "Set FINish bit";
                   type empty;
                 }
                 leaf no-fin {
                   description "Don't set FINish bit";
                   type empty;
                 }
               }
             }
             container option {
               presence "enable option";
               description "Kind";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 255";
                   }
                 }
               }
             }
             container data-length {
               presence "enable data-length";
               description "Size of IP datagram subtracted by TCP header length";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "2 .. 255";
                   }
                 }
               }
             }
             container window-scale {
               presence "enable window-scale";
               description "Window scale";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 255";
                   }
                 }
               }
             }
             container mss {
               presence "enable mss";
               description "Maximum Segment Size";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 65535";
                   }
                 }
               }
             }
             container checksum-validate {
               presence "enable checksum-validate";
               description "Validate checksum field against calculated checksum";
               leaf match {
                 description "Match condition";
                 junos:must "(\".. value\")";
                 junos:must-message "Missing mandatory statement: 'value'";
                 type enumeration {
                   enum "equal" {
                     description "Match when checksum field in packet is exact match";
                   }
                   enum "greater-than" {
                     description "Match when checksum field in packet is greater";
                   }
                   enum "less-than" {
                     description "Match when checksum field in packet is less";
                   }
                   enum "not-equal" {
                     description "Match when checksum field in packet is not exact match";
                   }
                 }
               }
               leaf value {
                 description "Match value";
                 default "0";
                 junos:must "(\".. match\")";
                 junos:must-message "Missing mandatory statement: 'match'";
                 type union {
                   type string {
                     pattern "<.*>|$.*";
                   }
                   type uint32 {
                     range "0 .. 65535";
                   }
                 }
               }
             }
           }
           container udp {
             junos:must "((!(\".. tcp\") && !(\".. icmp\")))";
             junos:must-message "udp cannot be specified with tcp or icmp";
             description "UDP protocol parameters";
             uses apply-advanced;
             container source-port {
               presence "enable source-port";
               description "Source port";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 65535";
                   }
                 }
               }
             }
             container destination-port {
               presence "enable destination-port";
               description "Destination port";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 65535";
                   }
                 }
               }
             }
             container data-length {
               presence "enable data-length";
               description "Size of IP datagram subtracted by UDP header length";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 65535";
                   }
                 }
               }
             }
             container checksum-validate {
               presence "enable checksum-validate";
               description "Validate checksum field against calculated checksum";
               leaf match {
                 description "Match condition";
                 junos:must "(\".. value\")";
                 junos:must-message "Missing mandatory statement: 'value'";
                 type enumeration {
                   enum "equal" {
                     description "Match when checksum field in packet is exact match";
                   }
                   enum "greater-than" {
                     description "Match when checksum field in packet is greater";
                   }
                   enum "less-than" {
                     description "Match when checksum field in packet is less";
                   }
                   enum "not-equal" {
                     description "Match when checksum field in packet is not exact match";
                   }
                 }
               }
               leaf value {
                 description "Match value";
                 default "0";
                 junos:must "(\".. match\")";
                 junos:must-message "Missing mandatory statement: 'match'";
                 type union {
                   type string {
                     pattern "<.*>|$.*";
                   }
                   type uint32 {
                     range "0 .. 65535";
                   }
                 }
               }
             }
           }
           container icmp {
             junos:must "((!(\".. udp\") && (!(\".. tcp\") && !(\".. icmpv6\"))))";
             junos:must-message "icmp cannot be specified with tcp or udp or icmpv6";
             description "ICMP protocol parameters";
             uses apply-advanced;
             container type {
               presence "enable type";
               description "Type";
               uses apply-advanced;
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 255";
                   }
                 }
               }
             }
             container code {
               presence "enable code";
               description "Code";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 255";
                   }
                 }
               }
             }
             container identification {
               presence "enable identification";
               description "Identifier in echo request/reply";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 65535";
                   }
                 }
               }
             }
             container sequence-number {
               presence "enable sequence-number";
               description "Sequence Number";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 65535";
                   }
                 }
               }
             }
             container data-length {
               presence "enable data-length";
               description "Size of IP datagram subtracted by ICMP header length";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 65535";
                   }
                 }
               }
             }
             container checksum-validate {
               presence "enable checksum-validate";
               description "Validate checksum field against calculated checksum";
               leaf match {
                 description "Match condition";
                 junos:must "(\".. value\")";
                 junos:must-message "Missing mandatory statement: 'value'";
                 type enumeration {
                   enum "equal" {
                     description "Match when checksum field in packet is exact match";
                   }
                   enum "greater-than" {
                     description "Match when checksum field in packet is greater";
                   }
                   enum "less-than" {
                     description "Match when checksum field in packet is less";
                   }
                   enum "not-equal" {
                     description "Match when checksum field in packet is not exact match";
                   }
                 }
               }
               leaf value {
                 description "Match value";
                 default "0";
                 junos:must "(\".. match\")";
                 junos:must-message "Missing mandatory statement: 'match'";
                 type union {
                   type string {
                     pattern "<.*>|$.*";
                   }
                   type uint32 {
                     range "0 .. 65535";
                   }
                 }
               }
             }
           }
           container icmpv6 {
             junos:must "((!(\".. udp\") && (!(\".. tcp\") && !(\".. icmp\"))))";
             junos:must-message "icmpv6 cannot be specified with tcp or udp or icmp";
             description "ICMPv6 protocol parameters";
             uses apply-advanced;
             container type {
               presence "enable type";
               description "Type";
               uses apply-advanced;
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 255";
                   }
                 }
               }
             }
             container code {
               presence "enable code";
               description "Code";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 255";
                   }
                 }
               }
             }
             container identification {
               presence "enable identification";
               description "Identifier in echo request/reply";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 65535";
                   }
                 }
               }
             }
             container sequence-number {
               presence "enable sequence-number";
               description "Sequence number";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 65535";
                   }
                 }
               }
             }
             container data-length {
               presence "enable data-length";
               description "Size of IPv6 datagram subtracted by ICMPv6 header length";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 255";
                   }
                 }
               }
             }
             container checksum-validate {
               presence "enable checksum-validate";
               description "Validate checksum field against calculated checksum";
               leaf match {
                 description "Match condition";
                 junos:must "(\".. value\")";
                 junos:must-message "Missing mandatory statement: 'value'";
                 type enumeration {
                   enum "equal" {
                     description "Match when checksum field in packet is exact match";
                   }
                   enum "greater-than" {
                     description "Match when checksum field in packet is greater";
                   }
                   enum "less-than" {
                     description "Match when checksum field in packet is less";
                   }
                   enum "not-equal" {
                     description "Match when checksum field in packet is not exact match";
                   }
                 }
               }
               leaf value {
                 description "Match value";
                 default "0";
                 junos:must "(\".. match\")";
                 junos:must-message "Missing mandatory statement: 'match'";
                 type union {
                   type string {
                     pattern "<.*>|$.*";
                   }
                   type uint32 {
                     range "0 .. 65535";
                   }
                 }
               }
             }
           }
         }
       }
       container anomaly {
         junos:must "(!((\".. signature\" || \".. chain\")))";
         junos:must-message "Only one attack type is permitted";
         description "Protocol anomaly";
         uses apply-advanced;
         leaf service {
           description "Service name";
           type string;
         }
         leaf test {
           description "Protocol anomaly condition to be checked";
           type string;
         }
         leaf direction {
           description "Direction";
           type enumeration {
             enum "client-to-server" {
               description "From Client to Server";
             }
             enum "server-to-client" {
               description "From Server to Client";
             }
             enum "any" {
               description "Any direction";
             }
           }
         }
         leaf shellcode {
           description "Specify shellcode flag for this attack";
           type enumeration {
             enum "intel" {
               description "Detect shellcode for intel platforms";
             }
             enum "sparc" {
               description "Detect shellcode for sparc platforms";
             }
             enum "all" {
               description "Detect shellcode for both intel and sparc platforms";
             }
             enum "no-shellcode" {
               description "Do not detect shellcode";
             }
           }
         }
       }
       container chain {
         junos:must "(!((\".. signature\" || \".. anomaly\")))";
         junos:must-message "Only one attack type is permitted";
         description "Chain attack";
         uses apply-advanced;
         container protocol-binding {
           description "Protocol binding over which attack will be detected";
           uses apply-advanced;
           choice protocol {
             case case_1 {
               container tcp {
                 presence "enable tcp";
                 description "Attack is for TCP packets only";
                 uses apply-advanced;
                 list minimum-port {
                   key name;
                   ordered-by user;
                   description "Multiple sets of (single port/port ranges) can be specified";
                   uses port-range;
                 }
               }
             }
             case case_2 {
               container udp {
                 presence "enable udp";
                 description "Attack is for UDP packets only";
                 uses apply-advanced;
                 list minimum-port {
                   key name;
                   ordered-by user;
                   description "Either single port or port ranges can be specified";
                   uses port-range;
                 }
               }
             }
             case case_3 {
               container rpc {
                 presence "enable rpc";
                 description "Attack is for RPC packets only";
                 uses apply-advanced;
                 leaf program-number {
                   description "RPC Program Number";
                   type union {
                     type uint32;
                     type string {
                       pattern "<.*>|$.*";
                     }
                   }
                 }
               }
             }
             case case_4 {
               leaf icmp {
                 description "Attack is for ICMP packets only";
                 type empty;
               }
             }
             case case_5 {
               leaf icmpv6 {
                 description "Attack is for ICMPv6 packets only";
                 type empty;
               }
             }
             case case_6 {
               container ip {
                 presence "enable ip";
                 description "Attack is for all IP based packets";
                 uses apply-advanced;
                 leaf protocol-number {
                   description "Transport layer protocol number";
                   type union {
                     type string {
                       pattern "<.*>|$.*";
                     }
                     type uint32 {
                       range "0 .. 139";
                     }
                   }
                 }
               }
             }
             case case_7 {
               container ipv6 {
                 presence "enable ipv6";
                 description "Attack is for all IPv6 based packets";
                 uses apply-advanced;
                 leaf protocol-number {
                   description "Transport layer protocol number";
                   type union {
                     type string {
                       pattern "<.*>|$.*";
                     }
                     type uint32 {
                       range "0 .. 139";
                     }
                   }
                 }
               }
             }
             case case_8 {
               leaf application {
                 description "Application name";
                 type string;
               }
             }
             case case_9 {
               leaf nested-application {
                 description "Nested application name";
                 status deprecated;
                 type string;
               }
             }
           }
         }
         leaf scope {
           description "Scope of the attack";
           type enumeration {
             enum "session" {
               description "Allow matches across transactions within the same session";
             }
             enum "transaction" {
               description "Allow matches in single transactions within the same session";
             }
           }
         }
         leaf order {
           description "Attacks should match in the order in which they are defined";
           type empty;
         }
         leaf reset {
           description "Repeat match should generate a new alert";
           type empty;
         }
         leaf expression {
           description "Boolean Expression(or, and, oand). Multiple expressions can be combined using parenthesis.";
           junos:must "(!(\".. order\"))";
           junos:must-message "Boolean Expression cannot be specified with order";
           type string;
         }
         list member {
           key name;
           ordered-by user;
           description "List of member attacks.";
           uses chain-member-type;
         }
       }
     }
   }
   grouping chain-member-type {
     description "Chain member";
     leaf name {
       description "Custom attack name";
       type string;
     }
     uses apply-advanced;
     container attack-type {
       presence "enable attack-type";
       description "Type of attack";
       uses apply-advanced;
       container signature {
         junos:must "(!(\".. anomaly\"))";
         junos:must-message "Only one attack type is permitted";
         description "Signature based attack";
         uses apply-advanced;
         leaf context {
           description "Context";
           type string;
         }
         leaf pattern {
           description "Pattern is the signature of the attack you want to detect";
           junos:must "(\".. context\")";
           junos:must-message "Context must be specified";
           type string {
             length "0 .. 511";
           }
         }
         leaf pattern-pcre {
           description "Attack signature pattern in PCRE format";
           junos:must "(\".. context\")";
           junos:must-message "Context must be specified";
           type string {
             length "0 .. 511";
           }
         }
         container content {
           junos:must "(\".. context\")";
           junos:must-message "Context must be specified";
           description "Mention the match-modifire parameters to enhance pattern matching";
           leaf pattern {
             description "Specify match-modifier pattern";
             type string;
           }
           leaf pcre {
             description "PCRE expression";
             type string {
               length "0 .. 511";
             }
           }
           container depth {
             junos:must "(\".. pattern\")";
             junos:must-message "Content pattern must be specified";
             description "Maximum depth to search pattern within a packet. Depth is not relative";
             leaf depth-value {
               description "Specify the value of 'depth'";
               type union {
                 type string {
                   pattern "<.*>|$.*";
                 }
                 type uint16 {
                   range "1 .. 65535";
                 }
               }
             }
             leaf depth-variable {
               description "Specify the variable name from which 'depth' should be extracted";
               type string;
             }
           }
           container offset {
             junos:must "(\".. pattern\")";
             junos:must-message "Content pattern must be specified";
             description "Where to start searching for a pattern within a packet. Offset value is not relative";
             leaf offset-value {
               description "Specify the value of 'offset'";
               type union {
                 type string {
                   pattern "<.*>|$.*";
                 }
                 type uint16 {
                   range "0 .. 65535";
                 }
               }
             }
             leaf offset-variable {
               description "Specify the variable name from which 'offset' should be extracted";
               type string;
             }
           }
           container within {
             junos:must "(\".. pattern\")";
             junos:must-message "Content pattern must be specified";
             description "Maximum Number of bytes present between two conjugative pattern match. within is  relative";
             leaf within-value {
               description "Specify the value of 'within'";
               type union {
                 type string {
                   pattern "<.*>|$.*";
                 }
                 type uint16 {
                   range "1 .. 65535";
                 }
               }
             }
             leaf within-variable {
               description "Specify the variable name from which 'within' should be extracted";
               type string;
             }
           }
           container distance {
             junos:must "(\".. pattern\")";
             junos:must-message "Content pattern must be specified";
             description "Maximum Length to ignore before searching next pattern match. Distance is  relative";
             leaf distance-value {
               description "Specify the value of 'distance'";
               type union {
                 type string {
                   pattern "<.*>|$.*";
                 }
                 type int32 {
                   range "-65535 .. 65535";
                 }
               }
             }
             leaf distance-variable {
               description "Specify the variable name from which 'distance' should be extracted";
               type string;
             }
           }
           container byte-extract {
             junos:must "(\".. pattern\")";
             junos:must-message "Content pattern must be specified";
             description "Mention the byte-extract parameters for signature in length encoded protocols";
             leaf bytes {
               description "Specify the number of bytes to extract from packet";
               type union {
                 type string {
                   pattern "<.*>|$.*";
                 }
                 type uint32 {
                   range "1 .. 10";
                 }
               }
             }
             leaf offset {
               description "Specify the number of bytes in to payload to start processing";
               type union {
                 type int32;
                 type string {
                   pattern "<.*>|$.*";
                 }
               }
             }
             leaf var-name {
               description "Specify the name of the variable to reference in other rule options";
               type string;
             }
             leaf relative {
               description "Specify whether to use an offset relative to last pattern match or not";
               type empty;
             }
             leaf multiplier {
               description "Specify the value to be multiplied against the bytes read";
               type union {
                 type uint16;
                 type string {
                   pattern "<.*>|$.*";
                 }
               }
             }
             leaf endianness {
               description "Specify the endianness with which bytes read should be processed";
               type enumeration {
                 enum "Little" {
                   description "Process data in little endian";
                 }
                 enum "Big" {
                   description "Process data in big endian";
                 }
               }
             }
             leaf align {
               description "Specify the byte alignment";
               type enumeration {
                 enum "2-byte" {
                   description "Round the number of converted bytes to 2-byte boundary";
                 }
                 enum "4-byte" {
                   description "Round the number of converted bytes to 4-byte boundary";
                 }
               }
             }
             leaf string {
               description "Specify the data type in which string data should be parsed";
               type enumeration {
                 enum "hex" {
                   description "Process data in hexadecimal format";
                 }
                 enum "dec" {
                   description "Process data in decimal format";
                 }
                 enum "oct" {
                   description "Process data in octal format";
                 }
               }
             }
             leaf bitmask {
               description "Specify the bitmask (1-4 bytes) for AND operation in hexadecimal format";
               type string;
             }
           }
           container byte-test {
             junos:must "(\".. pattern\")";
             junos:must-message "Content pattern must be specified";
             description "Mention the byte-test parameters for signature in length encoded protocols";
             leaf bytes {
               description "Specify the number of bytes to extract from packet";
               type union {
                 type string {
                   pattern "<.*>|$.*";
                 }
                 type uint32 {
                   range "1 .. 10";
                 }
               }
             }
             container offset {
               description "Mention the offset variable name or offset value to be used";
               leaf offset-value {
                 description "Specify the number of bytes in to payload to start processing";
                 type union {
                   type int32;
                   type string {
                     pattern "<.*>|$.*";
                   }
                 }
               }
               leaf offset-variable {
                 description "Specify the name of the offset variable";
                 type string;
               }
             }
             container rvalue {
               description "Specify the rvalue to test the converted value against";
               leaf rvalue-value {
                 description "Specify the value";
                 type union {
                   type uint32;
                   type string {
                     pattern "<.*>|$.*";
                   }
                 }
               }
               leaf rvalue-variable {
                 description "Specify the variable name";
                 type string;
               }
             }
             leaf relative {
               description "Specify whether to use an offset relative to last pattern match or not";
               type empty;
             }
             leaf operator {
               description "Specify the operation to perform on extracted value";
               type enumeration {
                 enum "less-than" {
                   description "Perform operation 'less than'";
                 }
                 enum "greater-than" {
                   description "Perform operation 'greater than'";
                 }
                 enum "less-than-or-equal" {
                   description "Perform operation 'less than or equal'";
                 }
                 enum "greater-than-or-equal" {
                   description "Perform operation 'greater than or equal'";
                 }
                 enum "equal" {
                   description "Perform operation 'equal'";
                 }
                 enum "bitwise-AND" {
                   description "Perform operation 'bitwise AND'";
                 }
                 enum "bitwise-XOR" {
                   description "Perform operation 'bitwise OR'";
                 }
               }
             }
             leaf negate {
               description "Check if the operator is not true";
               type empty;
             }
             leaf endianness {
               description "Specify the endianness with which bytes read should be processed";
               type enumeration {
                 enum "Little" {
                   description "Process data in little endian";
                 }
                 enum "Big" {
                   description "Process data in big endian";
                 }
               }
             }
             leaf string {
               description "Specify the data type in which string data should be parsed";
               type enumeration {
                 enum "hex" {
                   description "Process data in hexadecimal format";
                 }
                 enum "dec" {
                   description "Process data in decimal format";
                 }
                 enum "oct" {
                   description "Process data in octal format";
                 }
               }
             }
             leaf bitmask {
               description "Specify the bitmask (1-4 bytes) for AND operation in hexadecimal format";
               type string;
             }
           }
           container byte-math {
             junos:must "(\".. pattern\")";
             junos:must-message "Content pattern must be specified";
             description "Mention the byte-math parameters for signature in length encoded protocols";
             leaf bytes {
               description "Specify the number of bytes to extract from packet";
               type union {
                 type string {
                   pattern "<.*>|$.*";
                 }
                 type uint32 {
                   range "1 .. 10";
                 }
               }
             }
             leaf offset {
               description "Specify the number of bytes in to payload to start processing";
               type union {
                 type string {
                   pattern "<.*>|$.*";
                 }
                 type uint16 {
                   range "0 .. 65535";
                 }
               }
             }
             container rvalue {
               description "Specify the value to use mathematical operation against";
               leaf rvalue-value {
                 description "Specify the value";
                 type union {
                   type uint32;
                   type string {
                     pattern "<.*>|$.*";
                   }
                 }
               }
               leaf rvalue-variable {
                 description "Specify the variable name";
                 type string;
               }
             }
             leaf relative {
               description "Specify whether to use an offset relative to last pattern match or not";
               type empty;
             }
             leaf operator {
               description "Specify the operation to perform on extracted value";
               type enumeration {
                 enum "addition" {
                   description "Perform operation 'addition'";
                 }
                 enum "subtraction" {
                   description "Perform operation 'subtraction'";
                 }
                 enum "multiplication" {
                   description "Perform operation 'multiplication'";
                 }
                 enum "division" {
                   description "Perform operation 'division'";
                 }
                 enum "right-shift" {
                   description "Perform operation 'right shift'";
                 }
                 enum "left-shift" {
                   description "Perform operation 'left shift'";
                 }
               }
             }
             leaf endianness {
               description "Specify the endianness with which bytes read should be processed";
               type enumeration {
                 enum "Little" {
                   description "Process data in little endian";
                 }
                 enum "Big" {
                   description "Process data in big endian";
                 }
               }
             }
             leaf string {
               description "Specify the data type in which string data should be parsed";
               type enumeration {
                 enum "hex" {
                   description "Process data in hexadecimal format";
                 }
                 enum "dec" {
                   description "Process data in decimal format";
                 }
                 enum "oct" {
                   description "Process data in octal format";
                 }
               }
             }
             leaf bitmask {
               description "Specify the bitmask (1-4 bytes) for AND operation in hexadecimal format";
               type string;
             }
             leaf result {
               description "Specify the variable name to which result should be stored";
               type string;
             }
           }
           container byte-jump {
             junos:must "(\".. pattern\")";
             junos:must-message "Content pattern must be specified";
             description "Mention the byte-jump parameters for signature in length encoded protocols";
             leaf bytes {
               description "Specify the number of bytes to extract from packet";
               type union {
                 type string {
                   pattern "<.*>|$.*";
                 }
                 type uint32 {
                   range "1 .. 10";
                 }
               }
             }
             container offset {
               description "Mention the offset variable name or offset value to be used";
               leaf offset-value {
                 description "Specify the number of bytes in to payload to start processing";
                 type union {
                   type string {
                     pattern "<.*>|$.*";
                   }
                   type uint16 {
                     range "0 .. 65535";
                   }
                 }
               }
               leaf offset-variable {
                 description "Specify the name of the offset variable";
                 type string;
               }
             }
             leaf relative {
               description "Specify whether to use an offset relative to last pattern match or not";
               type empty;
             }
             leaf multiplier {
               description "Specify the value to be multiplied against the bytes read";
               type union {
                 type uint16;
                 type string {
                   pattern "<.*>|$.*";
                 }
               }
             }
             leaf endianness {
               description "Specify the endianness with which bytes read should be processed";
               type enumeration {
                 enum "Little" {
                   description "Process data in little endian";
                 }
                 enum "Big" {
                   description "Process data in big endian";
                 }
               }
             }
             leaf align {
               description "Specify the endianness with which bytes read should be processed";
               type enumeration {
                 enum "4-byte" {
                   description "Round the number of converted bytes to 4-byte boundary";
                 }
               }
             }
             leaf string {
               description "Specify the data type in which string data should be parsed";
               type enumeration {
                 enum "hex" {
                   description "Process data in hexadecimal format";
                 }
                 enum "dec" {
                   description "Process data in decimal format";
                 }
                 enum "oct" {
                   description "Process data in octal format";
                 }
               }
             }
             leaf bitmask {
               description "Specify the bitmask (1-4 bytes) for AND operation in hexadecimal format";
               type string;
             }
             leaf from-beginning {
               description "Enable jump from the beginning of the payload";
               type empty;
             }
             leaf from-end {
               description "Enable jump from the end of the payload";
               type empty;
             }
             leaf post-offset {
               description "Specify the number of bytes to skip forward or backward";
               type union {
                 type string {
                   pattern "<.*>|$.*";
                 }
                 type int32 {
                   range "-65535 .. 65535";
                 }
               }
             }
           }
           container is-data-at {
             junos:must "(\".. pattern\")";
             junos:must-message "Content pattern must be specified";
             description "Mention the is-data-at parameters for signature in length encoded protocols";
             container offset {
               description "Mention the offset variable name or offset value to be used";
               leaf offset-value {
                 description "Specify the number of bytes in to payload to start processing";
                 type union {
                   type string {
                     pattern "<.*>|$.*";
                   }
                   type uint16 {
                     range "0 .. 65535";
                   }
                 }
               }
               leaf offset-variable {
                 description "Specify the name of the offset variable";
                 type string;
               }
             }
             leaf relative {
               description "Specify whether to use an offset relative to last pattern match or not";
               type empty;
             }
             leaf negate {
               description "Negates the results of the isdataat test";
               type empty;
             }
           }
         }
         container optional-parameters {
           junos:must "(\".. pattern-pcre\")";
           junos:must-message "Applicable only for pattern-pcre defined signatures";
           description "Mention the optional parameters to enhance pattern matching";
           leaf min-offset {
             description "Minimum offset in data at which pattern-match can end";
             type union {
               type uint64;
               type string {
                 pattern "<.*>|$.*";
               }
             }
           }
           leaf max-offset {
             description "Maximum offset in data at which pattern-match can end";
             type union {
               type uint64;
               type string {
                 pattern "<.*>|$.*";
               }
             }
           }
           leaf min-length {
             description "Minimum match length required to match the pattern";
             type union {
               type uint64;
               type string {
                 pattern "<.*>|$.*";
               }
             }
           }
           leaf edit-distance {
             description "Match the pattern within this edit distance";
             type union {
               type uint32;
               type string {
                 pattern "<.*>|$.*";
               }
             }
           }
           leaf hamming-distance {
             description "Match the pattern within this hamming distance";
             type union {
               type uint32;
               type string {
                 pattern "<.*>|$.*";
               }
             }
           }
         }
         leaf regexp {
           description "Regular expression used for matching repetition of patterns";
           junos:must "((\".. pattern\" || \".. pattern-pcre\"))";
           junos:must-message "A pattern or pattern-pcre must be defined ";
           type string {
             length "0 .. 511";
           }
         }
         leaf negate {
           description "Trigger the attack if condition is not met";
           junos:must "(!((\".. context normalized-stream\" || (\".. context normalized-stream256\" || (\".. context normalized-stream1k\" || \".. context normalized-stream8k\")))))";
           junos:must-message "Negation not supported for normalized-stream contexts";
           junos:must "(!((\".. context stream\" || (\".. context stream256\" || (\".. context stream1k\" || \".. context stream8k\")))))";
           junos:must-message "Negation not supported for stream contexts";
           type empty;
         }
         leaf direction {
           description "Connection direction of the attack";
           type enumeration {
             enum "client-to-server" {
               description "Client to Server";
             }
             enum "server-to-client" {
               description "Server to Client";
             }
             enum "any" {
               description "Any direction";
             }
           }
         }
         leaf shellcode {
           description "Specify shellcode flag for this attack";
           type enumeration {
             enum "intel" {
               description "Detect shellcode for intel platforms";
             }
             enum "sparc" {
               description "Detect shellcode for sparc platforms";
             }
             enum "all" {
               description "Detect shellcode for both intel and sparc platforms";
             }
             enum "no-shellcode" {
               description "Do not detect shellcode";
             }
           }
         }
         container protocol {
           description "Protocol header matches";
           uses apply-advanced;
           container ipv4 {
             description "IPv4 protocol parameters";
             uses apply-advanced;
             container tos {
               presence "enable tos";
               description "Type of Service";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 255";
                   }
                 }
               }
             }
             container ihl {
               presence "enable ihl";
               description "Header length in words";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 15";
                   }
                 }
               }
             }
             container total-length {
               presence "enable total-length";
               description "Total Length of IP datagram";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 65535";
                   }
                 }
               }
             }
             container identification {
               presence "enable identification";
               description "Fragment Identification";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 65535";
                   }
                 }
               }
             }
             container ip-flags {
               presence "enable ip-flags";
               description "IP Flag bits";
               choice rb-choice {
                 leaf rb {
                   description "Reserved bit";
                   type empty;
                 }
                 leaf no-rb {
                   description "Don't reserved bit";
                   type empty;
                 }
               }
               choice mf-choice {
                 leaf mf {
                   description "More Fragment bit";
                   type empty;
                 }
                 leaf no-mf {
                   description "Don't more Fragment bit";
                   type empty;
                 }
               }
               choice df-choice {
                 leaf df {
                   description "Don't Fragment bit";
                   type empty;
                 }
                 leaf no-df {
                   description "Don't don't Fragment bit";
                   type empty;
                 }
               }
             }
             container ttl {
               presence "enable ttl";
               description "Time to live";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 255";
                   }
                 }
               }
             }
             container protocol {
               presence "enable protocol";
               description "Transport layer protocol";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 255";
                   }
                 }
               }
             }
             container source {
               presence "enable source";
               description "Source IP-address/Hostname";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type jt:ipv4addr;
               }
             }
             container destination {
               presence "enable destination";
               description "Destination IP-address/Hostname";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type jt:ipv4addr;
               }
             }
             container checksum-validate {
               presence "enable checksum-validate";
               description "Validate checksum field against calculated checksum";
               leaf match {
                 description "Match condition";
                 junos:must "(\".. value\")";
                 junos:must-message "Missing mandatory statement: 'value'";
                 type enumeration {
                   enum "equal" {
                     description "Match when checksum field in packet is exact match";
                   }
                   enum "greater-than" {
                     description "Match when checksum field in packet is greater";
                   }
                   enum "less-than" {
                     description "Match when checksum field in packet is less";
                   }
                   enum "not-equal" {
                     description "Match when checksum field in packet is not exact match";
                   }
                 }
               }
               leaf value {
                 description "Match value";
                 default "0";
                 junos:must "(\".. match\")";
                 junos:must-message "Missing mandatory statement: 'match'";
                 type union {
                   type string {
                     pattern "<.*>|$.*";
                   }
                   type uint32 {
                     range "0 .. 65535";
                   }
                 }
               }
             }
           }
           container ipv6 {
             description "IPv6 protocol parameters";
             uses apply-advanced;
             container traffic-class {
               presence "enable traffic-class";
               description "Traffic class. Similar to TOS in IPv4";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 255";
                   }
                 }
               }
             }
             container payload-length {
               presence "enable payload-length";
               description "Length of the payload in the IPv6 datagram";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 65535";
                   }
                 }
               }
             }
             container flow-label {
               presence "enable flow-label";
               description "Flow label identification";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 1048575";
                   }
                 }
               }
             }
             container hop-limit {
               presence "enable hop-limit";
               description "Hop limit";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 255";
                   }
                 }
               }
             }
             container next-header {
               presence "enable next-header";
               description "The header following the basic IPv6 header";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 255";
                   }
                 }
               }
             }
             container source {
               presence "enable source";
               description "Source IP-address or hostname";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type jt:ipv6addr;
               }
             }
             container destination {
               presence "enable destination";
               description "Destination IP-address or hostname";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type jt:ipv6addr;
               }
             }
             container extension-header {
               description "IPv6 Extension headers";
               uses apply-advanced;
               container routing-header {
                 presence "enable routing-header";
                 description "IPv6 Routing extension header";
                 uses apply-advanced;
                 container header-type {
                   description "Routing header type";
                   uses apply-advanced;
                   leaf match {
                     description "Match condition";
                     type enumeration {
                       enum "equal" {
                         description "Match when value in packet is exact match";
                       }
                       enum "greater-than" {
                         description "Match when value in packet is greater";
                       }
                       enum "less-than" {
                         description "Match when value in packet is less";
                       }
                       enum "not-equal" {
                         description "Match when value in packet is not exact match";
                       }
                     }
                   }
                   leaf value {
                     description "Match value";
                     type union {
                       type string {
                         pattern "<.*>|$.*";
                       }
                       type uint32 {
                         range "0 .. 255";
                       }
                     }
                   }
                 }
               }
               container destination-option {
                 description "IPv6 Destination option extension header";
                 uses apply-advanced;
                 container option-type {
                   description "Destination option header type";
                   uses apply-advanced;
                   leaf match {
                     description "Match condition";
                     type enumeration {
                       enum "equal" {
                         description "Match when value in packet is exact match";
                       }
                       enum "greater-than" {
                         description "Match when value in packet is greater";
                       }
                       enum "less-than" {
                         description "Match when value in packet is less";
                       }
                       enum "not-equal" {
                         description "Match when value in packet is not exact match";
                       }
                     }
                   }
                   leaf value {
                     description "Match value";
                     type union {
                       type string {
                         pattern "<.*>|$.*";
                       }
                       type uint32 {
                         range "0 .. 255";
                       }
                     }
                   }
                 }
                 container home-address {
                   description "IPv6 Home address of the mobile node";
                   uses apply-advanced;
                   leaf match {
                     description "Match condition";
                     type enumeration {
                       enum "equal" {
                         description "Match when value in packet is exact match";
                       }
                       enum "greater-than" {
                         description "Match when value in packet is greater";
                       }
                       enum "less-than" {
                         description "Match when value in packet is less";
                       }
                       enum "not-equal" {
                         description "Match when value in packet is not exact match";
                       }
                     }
                   }
                   leaf value {
                     description "Match value";
                     type jt:ipv6addr;
                   }
                 }
               }
             }
           }
           container tcp {
             junos:must "((!(\".. udp\") && !(\".. icmp\")))";
             junos:must-message "tcp cannot be specified with udp or icmp";
             description "TCP protocol parameters";
             uses apply-advanced;
             container source-port {
               presence "enable source-port";
               description "Source port";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 65535";
                   }
                 }
               }
             }
             container destination-port {
               presence "enable destination-port";
               description "Destination port";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 65535";
                   }
                 }
               }
             }
             container sequence-number {
               presence "enable sequence-number";
               description "Sequence Number";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 4294967295";
                   }
                 }
               }
             }
             container ack-number {
               presence "enable ack-number";
               description "Acknowledgement Number";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 4294967295";
                   }
                 }
               }
             }
             container header-length {
               presence "enable header-length";
               description "Header Length in words";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 15";
                   }
                 }
               }
             }
             container reserved {
               presence "enable reserved";
               description "Three reserved bits";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 7";
                   }
                 }
               }
             }
             container window-size {
               presence "enable window-size";
               description "Window Size";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 65535";
                   }
                 }
               }
             }
             container urgent-pointer {
               presence "enable urgent-pointer";
               description "Urgent Pointer";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 65535";
                   }
                 }
               }
             }
             container tcp-flags {
               presence "enable tcp-flags";
               description "TCP header flags";
               choice r1-choice {
                 leaf r1 {
                   description "Set Reserverd bit 1";
                   type empty;
                 }
                 leaf no-r1 {
                   description "Don't set Reserverd bit 1";
                   type empty;
                 }
               }
               choice r2-choice {
                 leaf r2 {
                   description "Set Reserved bit 2";
                   type empty;
                 }
                 leaf no-r2 {
                   description "Don't set Reserved bit 2";
                   type empty;
                 }
               }
               choice urg-choice {
                 leaf urg {
                   description "Set Urgent bit";
                   type empty;
                 }
                 leaf no-urg {
                   description "Don't set Urgent bit";
                   type empty;
                 }
               }
               choice ack-choice {
                 leaf ack {
                   description "Set Acknowledge bit";
                   type empty;
                 }
                 leaf no-ack {
                   description "Don't set Acknowledge bit";
                   type empty;
                 }
               }
               choice psh-choice {
                 leaf psh {
                   description "Set Push bit";
                   type empty;
                 }
                 leaf no-psh {
                   description "Don't set Push bit";
                   type empty;
                 }
               }
               choice rst-choice {
                 leaf rst {
                   description "Set Reset bit";
                   type empty;
                 }
                 leaf no-rst {
                   description "Don't set Reset bit";
                   type empty;
                 }
               }
               choice syn-choice {
                 leaf syn {
                   description "Set SYN bit";
                   type empty;
                 }
                 leaf no-syn {
                   description "Don't set SYN bit";
                   type empty;
                 }
               }
               choice fin-choice {
                 leaf fin {
                   description "Set FINish bit";
                   type empty;
                 }
                 leaf no-fin {
                   description "Don't set FINish bit";
                   type empty;
                 }
               }
             }
             container option {
               presence "enable option";
               description "Kind";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 255";
                   }
                 }
               }
             }
             container data-length {
               presence "enable data-length";
               description "Size of IP datagram subtracted by TCP header length";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "2 .. 255";
                   }
                 }
               }
             }
             container window-scale {
               presence "enable window-scale";
               description "Window scale";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 255";
                   }
                 }
               }
             }
             container mss {
               presence "enable mss";
               description "Maximum Segment Size";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 65535";
                   }
                 }
               }
             }
             container checksum-validate {
               presence "enable checksum-validate";
               description "Validate checksum field against calculated checksum";
               leaf match {
                 description "Match condition";
                 junos:must "(\".. value\")";
                 junos:must-message "Missing mandatory statement: 'value'";
                 type enumeration {
                   enum "equal" {
                     description "Match when checksum field in packet is exact match";
                   }
                   enum "greater-than" {
                     description "Match when checksum field in packet is greater";
                   }
                   enum "less-than" {
                     description "Match when checksum field in packet is less";
                   }
                   enum "not-equal" {
                     description "Match when checksum field in packet is not exact match";
                   }
                 }
               }
               leaf value {
                 description "Match value";
                 default "0";
                 junos:must "(\".. match\")";
                 junos:must-message "Missing mandatory statement: 'match'";
                 type union {
                   type string {
                     pattern "<.*>|$.*";
                   }
                   type uint32 {
                     range "0 .. 65535";
                   }
                 }
               }
             }
           }
           container udp {
             junos:must "((!(\".. tcp\") && !(\".. icmp\")))";
             junos:must-message "udp cannot be specified with tcp or icmp";
             description "UDP protocol parameters";
             uses apply-advanced;
             container source-port {
               presence "enable source-port";
               description "Source port";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 65535";
                   }
                 }
               }
             }
             container destination-port {
               presence "enable destination-port";
               description "Destination port";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 65535";
                   }
                 }
               }
             }
             container data-length {
               presence "enable data-length";
               description "Size of IP datagram subtracted by UDP header length";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 65535";
                   }
                 }
               }
             }
             container checksum-validate {
               presence "enable checksum-validate";
               description "Validate checksum field against calculated checksum";
               leaf match {
                 description "Match condition";
                 junos:must "(\".. value\")";
                 junos:must-message "Missing mandatory statement: 'value'";
                 type enumeration {
                   enum "equal" {
                     description "Match when checksum field in packet is exact match";
                   }
                   enum "greater-than" {
                     description "Match when checksum field in packet is greater";
                   }
                   enum "less-than" {
                     description "Match when checksum field in packet is less";
                   }
                   enum "not-equal" {
                     description "Match when checksum field in packet is not exact match";
                   }
                 }
               }
               leaf value {
                 description "Match value";
                 default "0";
                 junos:must "(\".. match\")";
                 junos:must-message "Missing mandatory statement: 'match'";
                 type union {
                   type string {
                     pattern "<.*>|$.*";
                   }
                   type uint32 {
                     range "0 .. 65535";
                   }
                 }
               }
             }
           }
           container icmp {
             junos:must "((!(\".. udp\") && (!(\".. tcp\") && !(\".. icmpv6\"))))";
             junos:must-message "icmp cannot be specified with tcp or udp or icmpv6";
             description "ICMP protocol parameters";
             uses apply-advanced;
             container type {
               presence "enable type";
               description "Type";
               uses apply-advanced;
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 255";
                   }
                 }
               }
             }
             container code {
               presence "enable code";
               description "Code";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 255";
                   }
                 }
               }
             }
             container identification {
               presence "enable identification";
               description "Identifier in echo request/reply";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 65535";
                   }
                 }
               }
             }
             container sequence-number {
               presence "enable sequence-number";
               description "Sequence Number";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 65535";
                   }
                 }
               }
             }
             container data-length {
               presence "enable data-length";
               description "Size of IP datagram subtracted by ICMP header length";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 65535";
                   }
                 }
               }
             }
             container checksum-validate {
               presence "enable checksum-validate";
               description "Validate checksum field against calculated checksum";
               leaf match {
                 description "Match condition";
                 junos:must "(\".. value\")";
                 junos:must-message "Missing mandatory statement: 'value'";
                 type enumeration {
                   enum "equal" {
                     description "Match when checksum field in packet is exact match";
                   }
                   enum "greater-than" {
                     description "Match when checksum field in packet is greater";
                   }
                   enum "less-than" {
                     description "Match when checksum field in packet is less";
                   }
                   enum "not-equal" {
                     description "Match when checksum field in packet is not exact match";
                   }
                 }
               }
               leaf value {
                 description "Match value";
                 default "0";
                 junos:must "(\".. match\")";
                 junos:must-message "Missing mandatory statement: 'match'";
                 type union {
                   type string {
                     pattern "<.*>|$.*";
                   }
                   type uint32 {
                     range "0 .. 65535";
                   }
                 }
               }
             }
           }
           container icmpv6 {
             junos:must "((!(\".. udp\") && (!(\".. tcp\") && !(\".. icmp\"))))";
             junos:must-message "icmpv6 cannot be specified with tcp or udp or icmp";
             description "ICMPv6 protocol parameters";
             uses apply-advanced;
             container type {
               presence "enable type";
               description "Type";
               uses apply-advanced;
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 255";
                   }
                 }
               }
             }
             container code {
               presence "enable code";
               description "Code";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 255";
                   }
                 }
               }
             }
             container identification {
               presence "enable identification";
               description "Identifier in echo request/reply";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 65535";
                   }
                 }
               }
             }
             container sequence-number {
               presence "enable sequence-number";
               description "Sequence number";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 65535";
                   }
                 }
               }
             }
             container data-length {
               presence "enable data-length";
               description "Size of IPv6 datagram subtracted by ICMPv6 header length";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 255";
                   }
                 }
               }
             }
             container checksum-validate {
               presence "enable checksum-validate";
               description "Validate checksum field against calculated checksum";
               leaf match {
                 description "Match condition";
                 junos:must "(\".. value\")";
                 junos:must-message "Missing mandatory statement: 'value'";
                 type enumeration {
                   enum "equal" {
                     description "Match when checksum field in packet is exact match";
                   }
                   enum "greater-than" {
                     description "Match when checksum field in packet is greater";
                   }
                   enum "less-than" {
                     description "Match when checksum field in packet is less";
                   }
                   enum "not-equal" {
                     description "Match when checksum field in packet is not exact match";
                   }
                 }
               }
               leaf value {
                 description "Match value";
                 default "0";
                 junos:must "(\".. match\")";
                 junos:must-message "Missing mandatory statement: 'match'";
                 type union {
                   type string {
                     pattern "<.*>|$.*";
                   }
                   type uint32 {
                     range "0 .. 65535";
                   }
                 }
               }
             }
           }
         }
       }
       container anomaly {
         junos:must "(!(\".. signature\"))";
         junos:must-message "Only one attack type is permitted";
         description "Protocol anomaly";
         uses apply-advanced;
         leaf test {
           description "Protocol anomaly condition to be checked";
           type string;
         }
         leaf direction {
           description "Direction";
           type enumeration {
             enum "client-to-server" {
               description "From Client to Server";
             }
             enum "server-to-client" {
               description "From Server to Client";
             }
             enum "any" {
               description "Any direction";
             }
           }
         }
         leaf shellcode {
           description "Specify shellcode flag for this attack";
           type enumeration {
             enum "intel" {
               description "Detect shellcode for intel platforms";
             }
             enum "sparc" {
               description "Detect shellcode for sparc platforms";
             }
             enum "all" {
               description "Detect shellcode for both intel and sparc platforms";
             }
             enum "no-shellcode" {
               description "Do not detect shellcode";
             }
           }
         }
       }
     }
   }
   grouping custom-message-type {
     description "Configure custom-message object";
     leaf name {
       description "Configure name of custom-message object";
       type string {
         length "1 .. 59";
         junos:posix-pattern "^[a-zA-Z_]+[a-zA-Z_0-9-]*$";
         junos:pattern-message "Must be a string beginning with a letter or underscore and consisting of letters, numbers, dashes and underscores.";
       }
     }
     uses apply-advanced;
     leaf type {
       description "Type of custom message";
       type enumeration {
         enum "redirect-url" {
           description "Redirect URL";
         }
         enum "user-message" {
           description "User message";
         }
         enum "custom-page" {
           description "Customer page";
         }
       }
     }
     choice contents {
       case case_1 {
         leaf content {
           description "Content of custom message";
           type string {
             length "1 .. 1024";
           }
         }
       }
       case case_2 {
         leaf custom-page-file {
           description "Name of custom page file";
           type string {
             length "1 .. 64";
           }
         }
       }
     }
   }
   grouping default-anti-spam-feature {
     description "Anti-spam feature";
     uses apply-advanced;
     leaf type {
       description "Anti-spam type";
       type enumeration {
         enum "sbl" {
           description "Anti-spam sophos sbl";
         }
         enum "anti-spam-none" {
         }
       }
     }
     leaf address-whitelist {
       description "Anti-spam whitelist";
       junos:must "(\"security utm custom-objects url-pattern $$\")";
       junos:must-message "url-pattern must be defined";
       type string;
     }
     leaf address-blacklist {
       description "Anti-spam blacklist";
       junos:must "(\"security utm custom-objects url-pattern $$\")";
       junos:must-message "url-pattern must be defined";
       type string;
     }
     container traceoptions {
       description "Trace options for anti-spam feature";
       uses anti-spam-traceoptions;
     }
     container sbl {
       description "SBL settings";
       presence "enable sbl";
       uses default-sbl-type;
     }
   }
   grouping anti-spam-traceoptions {
     description "Trace options for anti-spam  feature";
     uses apply-advanced;
     list flag {
       key name;
       ordered-by user;
       description "Trace options for anti-spam feature flag";
       leaf name {
         description "Trace options for anti-spam feature flag name";
         type enumeration {
           enum "manager" {
             description "Trace anti-spam manager information";
           }
           enum "sbl" {
             description "Trace SBL server information";
           }
           enum "all" {
             description "Enable trace all anti-spam trace options";
           }
         }
       }
     }
   }
   grouping default-anti-virus-feature {
     description "Anti-virus feature";
     uses apply-advanced;
     container mime-whitelist {
       description "Anti-virus MIME whitelist";
       uses apply-advanced;
       leaf list {
         description "MIME list";
         junos:must "(\"security utm custom-objects mime-pattern $$\")";
         junos:must-message "mime-pattern must be defined";
         type string;
       }
       leaf exception {
         description "Exception settings for MIME white list";
         junos:must "(\"security utm custom-objects mime-pattern $$\")";
         junos:must-message "mime-pattern must be defined";
         type string;
       }
     }
     leaf url-whitelist {
       description "Anti-virus URL white list";
       type string;
     }
     leaf type {
       description "Anti-virus engine type";
       default "anti-virus-none";
       type enumeration {
         enum "sophos-engine" {
           description "Anti-virus sophos-engine";
         }
         enum "avira-engine" {
           description "Anti-virus avira-engine";
         }
         enum "anti-virus-none" {
         }
       }
     }
     container forwarding-mode {
       description "Anti-virus forwarding mode";
       uses apply-advanced;
       leaf hold {
         description "Hold mode (hold file until analysis is complete, default is CDF mode)";
         type empty;
       }
       leaf inline-tap {
         description "Detect-only mode without blocking (default is off)";
         type empty;
       }
     }
     container scan-options {
       presence "enable scan-options";
       description "Anti-virus scan options";
       uses apply-advanced;
       choice pre-detection-choice {
         leaf pre-detection {
           description "Anti-virus Pre-Detection";
           type empty;
         }
         leaf no-pre-detection {
           description "Don't anti-virus Pre-Detection";
           type empty;
         }
       }
       choice uri-check-choice {
         leaf uri-check {
           description "Anti-virus uri-check";
           type empty;
         }
         leaf no-uri-check {
           description "Don't anti-virus uri-check";
           type empty;
         }
       }
       leaf content-size-limit {
         description "Content size limit";
         units "kilobytes";
         type string;
       }
       leaf timeout {
         description "Scan engine timeout";
         units "seconds";
         type union {
           type string {
             pattern "<.*>|$.*";
           }
           type uint32 {
             range "1 .. 1800";
           }
         }
       }
       leaf decompress-layer-limit {
         description "Decompress layer limit";
         type union {
           type string {
             pattern "<.*>|$.*";
           }
           type uint32 {
             range "0 .. 10";
           }
         }
       }
     }
     container trickling {
       description "Anti-virus trickling";
       presence "enable trickling";
       uses anti-virus-trickling;
     }
     container notification-options {
       description "Anti-virus notification options";
       presence "enable notification-options";
       uses anti-virus-notification-options;
     }
     container fallback-options {
       description "Anti-virus fallback options";
       presence "enable fallback-options";
       uses av-fallback-settings;
     }
     container traceoptions {
       description "Trace options for anti-virus feature";
       uses anti-virus-traceoptions;
     }
     container avira-engine {
       description "Anti-virus Avira-engine";
       uses apply-advanced;
       container pattern-update {
         description "Anti-virus avira-engine pattern update";
         presence "enable pattern-update";
         uses anti-virus-pattern-update;
       }
     }
     container sophos-engine {
       description "Anti-virus sophos-engine";
       uses apply-advanced;
       container server {
         description "SAV and Anti-Spam first hop DNS server";
         uses apply-advanced;
         leaf ip {
           description "SAV and Anti-Spam first hop DNS server ip";
           type jt:ipaddr;
         }
         leaf routing-instance {
           description "Routing instance name";
           junos:must "(\"routing-instances $$\")";
           junos:must-message "Routing-instance must be defined";
           type string;
         }
         leaf source-address {
           description "Source ip address used to connect server";
           type jt:ipaddr;
         }
       }
       leaf sxl-timeout {
         description "Sxl sophos anti-virus engine timeout";
         default "2";
         units "seconds";
         type union {
           type string {
             pattern "<.*>|$.*";
           }
           type uint32 {
             range "1 .. 5";
           }
         }
       }
       leaf sxl-retry {
         description "Sxl sophos anti-virus engine query retry (number of times)";
         default "1";
         type union {
           type string {
             pattern "<.*>|$.*";
           }
           type uint32 {
             range "0 .. 5";
           }
         }
       }
       container pattern-update {
         description "Anti-virus sophos-engine pattern update";
         presence "enable pattern-update";
         uses anti-virus-pattern-update;
       }
       container fallback-options {
         description "Anti-virus sophos-engine fallback options";
         presence "enable fallback-options";
         status deprecated;
         uses av-fallback-settings;
       }
       container scan-options {
         description "Anti-virus sophos-engine scan options";
         presence "enable scan-options";
         status deprecated;
         uses default-sophos-scan-options;
       }
       container trickling {
         description "Anti-virus trickling";
         presence "enable trickling";
         status deprecated;
         uses anti-virus-trickling;
       }
       container notification-options {
         description "Anti-virus notification options";
         presence "enable notification-options";
         status deprecated;
         uses anti-virus-notification-options;
       }
     }
   }
   grouping default-content-filtering-feature {
     description "Content-filtering feature";
     uses apply-advanced;
     leaf type {
       description "Content-filtering type";
       default "local";
       type enumeration {
         enum "local" {
           description "Content-filtering local";
         }
         enum "content-filtering-none" {
         }
       }
     }
     container traceoptions {
       description "Trace options for content-filtering feature";
       uses content-filtering-traceoptions;
     }
     leaf permit-command {
       description "Permit command list";
       status deprecated;
       junos:must "(\"security utm custom-objects protocol-command $$\")";
       junos:must-message "protocol-command must be defined";
       type string;
     }
     leaf block-command {
       description "Block command list";
       status deprecated;
       junos:must "(\"security utm custom-objects protocol-command $$\")";
       junos:must-message "protocol-command must be defined";
       type string;
     }
     leaf block-extension {
       description "Block extension list";
       status deprecated;
       junos:must "(\"security utm custom-objects filename-extension $$\")";
       junos:must-message "filename-extension must be defined";
       type string;
     }
     container block-mime {
       presence "enable block-mime";
       description "Content-filtering feature block MIME";
       status deprecated;
       uses apply-advanced;
       leaf list {
         description "Block MIME list";
         junos:must "(\"security utm custom-objects mime-pattern $$\")";
         junos:must-message "mime-pattern must be defined";
         type string;
       }
       leaf exception {
         description "Exception of block MIME list";
         junos:must "(\"security utm custom-objects mime-pattern $$\")";
         junos:must-message "mime-pattern must be defined";
         type string;
       }
     }
     container block-content-type {
       description "Content-filtering feature block content type";
       status deprecated;
       uses apply-advanced;
       leaf activex {
         description "Block activex";
         type empty;
       }
       leaf java-applet {
         description "Block Java-applet";
         type empty;
       }
       leaf exe {
         description "Block Windows/dos exe file";
         type empty;
       }
       leaf zip {
         description "Block zip file";
         type empty;
       }
       leaf http-cookie {
         description "Block HTTP cookie";
         type empty;
       }
     }
     list rule-set {
       key name;
       ordered-by user;
       description "Default Rule-set configuration";
       uses cf-rule-set;
     }
     container notification-options {
       presence "enable notification-options";
       description "Notification options";
       uses apply-advanced;
       leaf seclog {
         description "Event logging to security log";
         type empty;
       }
       leaf type {
         description "Notification options type";
         type enumeration {
           enum "protocol-only" {
             description "Notification in protocol level";
           }
           enum "message" {
             description "Notification in message";
           }
         }
       }
       choice notify-mail-sender-choice {
         leaf notify-mail-sender {
           description "Notifiy mail sender";
           type empty;
         }
         leaf no-notify-mail-sender {
           description "Don't notifiy mail sender";
           type empty;
         }
       }
       leaf custom-message {
         description "Custom notification message";
         type string {
           length "1 .. 512";
         }
       }
     }
   }
   grouping cf-rule-set {
     description "UTM CF Rule-Set object";
     leaf name {
       description "UTM CF Rule-set name";
       type string {
         length "1 .. 29";
       }
     }
     uses apply-advanced;
     list rule {
       key name;
       ordered-by user;
       description "Configure UTM CF Rules";
       uses cf-rule;
     }
   }
   grouping cf-rule {
     description "UTM CF Rule object";
     leaf name {
       description "UTM CF Rule name";
       type string {
         length "1 .. 29";
       }
     }
     uses apply-advanced;
     container match {
       description "Rule match criteria";
       uses apply-advanced;
       leaf-list applications {
         ordered-by user;
         description "List of applications to be inspected";
         type string;
       }
       leaf direction {
         description "Direction of the content to be inspected";
         type enumeration {
           enum "upload" {
             description "Uploading content";
           }
           enum "download" {
             description "Downloading content";
           }
           enum "any" {
             description "Content in any direction";
           }
         }
       }
       leaf-list file-types {
         ordered-by user;
         description "List of file-types in match critera";
         type string;
       }
     }
     container then {
       description "Rule then criteria";
       uses apply-advanced;
       leaf action {
         description "Configure action";
         type enumeration {
           enum "no-action" {
             description "No action";
           }
           enum "block" {
             description "Block and drop connection";
           }
           enum "close-client" {
             description "Close client";
           }
           enum "close-server" {
             description "Close server";
           }
           enum "close-client-and-server" {
             description "Close client and server";
           }
         }
       }
       container notification {
         description "Event logging and notification options";
         presence "enable notification";
         uses cf-notification;
       }
     }
   }
   grouping cf-notification {
     description "Event logging and notification options";
     uses apply-advanced;
     leaf seclog {
       description "Event logging to security log";
       type empty;
     }
     container endpoint {
       presence "enable endpoint";
       uses apply-advanced;
       leaf type {
         description "Endpoint notification type";
         type enumeration {
           enum "protocol-only" {
             description "Notification in protocol level";
           }
           enum "message" {
             description "Notification in message";
           }
         }
       }
       choice notify-mail-sender-choice {
         leaf notify-mail-sender {
           description "Notifiy mail sender";
           type empty;
         }
         leaf no-notify-mail-sender {
           description "Don't notifiy mail sender";
           type empty;
         }
       }
       leaf custom-message {
         description "Custom notification message";
         type string {
           length "1 .. 512";
         }
       }
     }
   }
   grouping content-filtering-traceoptions {
     description "Trace options for content-filtering feature";
     uses apply-advanced;
     list flag {
       key name;
       ordered-by user;
       description "Trace options for content-filtering feature flag";
       leaf name {
         description "Trace options for content-filtering feature flag name";
         type enumeration {
           enum "basic" {
             description "Trace content-filtering basic information";
           }
           enum "detail" {
             description "Trace content-filtering detail information";
           }
           enum "all" {
             description "Enable trace all content-filtering trace options";
           }
         }
       }
     }
   }
   grouping default-sbl-type {
     description "SBL type";
     uses apply-advanced;
     choice sbl-default-server-choice {
       leaf sbl-default-server {
         description "Default SBL server";
         type empty;
       }
       leaf no-sbl-default-server {
         description "Don't default SBL server";
         type empty;
       }
     }
     leaf spam-action {
       description "Anti-spam actions";
       default "tag-subject";
       type enumeration {
         enum "block" {
           description "Block e-mail";
         }
         enum "tag-header" {
           description "Tag header of e-mail";
         }
         enum "tag-subject" {
           description "Tag subject of e-mail";
         }
       }
     }
     leaf custom-tag-string {
       description "Custom tag string";
       type string {
         length "1 .. 512";
       }
     }
   }
   grouping default-sophos-scan-options {
     description "Anti-virus scan options";
     uses apply-advanced;
     choice uri-check-choice {
       leaf uri-check {
         description "Anti-virus uri-check";
         type empty;
       }
       leaf no-uri-check {
         description "Don't anti-virus uri-check";
         type empty;
       }
     }
     leaf content-size-limit {
       description "Content size limit";
       default "10000";
       units "kilobytes";
       type string;
     }
     leaf timeout {
       description "Scan engine timeout";
       units "seconds";
       type union {
         type string {
           pattern "<.*>|$.*";
         }
         type uint32 {
           range "1 .. 1800";
         }
       }
     }
   }
   grouping default-webfilter-feature {
     description "Web-filtering feature settings";
     uses apply-advanced;
     leaf url-whitelist {
       description "Configure custom URL for whitelist category";
       type string;
     }
     leaf url-blacklist {
       description "Configure custom URL for blacklist category";
       type string;
     }
     leaf http-reassemble {
       description "Reassemble HTTP request segments";
       type empty;
     }
     leaf http-persist {
       description "Check all HTTP request in a connection";
       type empty;
     }
     leaf type {
       description "Configure web-filtering engine type";
       default "web-filtering-none";
       type enumeration {
         enum "websense-redirect" {
         }
         enum "juniper-local" {
         }
         enum "juniper-enhanced" {
         }
         enum "web-filtering-none" {
         }
       }
     }
     container traceoptions {
       description "Trace options for web-filtering feature";
       uses web-filtering-traceoptions;
     }
     container websense-redirect {
       description "Configure web-filtering websense redirect engine";
       uses default-websense-type;
     }
     container juniper-local {
       description "Configure web-filtering juniper local engine";
       uses default-juniper-local-type;
     }
     container juniper-enhanced {
       description "Configure web-filtering juniper enhanced engine";
       uses default-juniper-enhanced-type;
     }
   }
   grouping default-juniper-enhanced-type {
     description "Juniper Enhanced";
     uses apply-advanced;
     container cache {
       presence "enable cache";
       uses apply-advanced;
       leaf timeout {
         description "Juniper enhanced cache timeout";
         default "1440";
         units "minutes";
         type union {
           type string {
             pattern "<.*>|$.*";
           }
           type uint32 {
             range "1 .. 1800";
           }
         }
       }
       leaf size {
         description "Juniper enhanced cache size";
         default "1024";
         units "kilobytes";
         type string;
       }
     }
     container server {
       description "Juniper enhanced server";
       presence "enable server";
       uses juniper-enhanced-server;
     }
     container reputation {
       presence "enable reputation";
       description "Customize reputation level";
       uses apply-advanced;
       leaf reputation-very-safe {
         description "Base-reputation-value (default 90)";
         default "90";
         type union {
           type string {
             pattern "<.*>|$.*";
           }
           type uint32 {
             range "1 .. 100";
           }
         }
       }
       leaf reputation-moderately-safe {
         description "Base-reputation-value (default 80)";
         default "80";
         type union {
           type string {
             pattern "<.*>|$.*";
           }
           type uint32 {
             range "1 .. 100";
           }
         }
       }
       leaf reputation-fairly-safe {
         description "Base-reputation-value (default 70)";
         default "70";
         type union {
           type string {
             pattern "<.*>|$.*";
           }
           type uint32 {
             range "1 .. 100";
           }
         }
       }
       leaf reputation-suspicious {
         description "Base-reputation-value (default 60)";
         default "60";
         type union {
           type string {
             pattern "<.*>|$.*";
           }
           type uint32 {
             range "1 .. 100";
           }
         }
       }
     }
     leaf query-type {
       description "Juniper enhanced query type";
       type enumeration {
         enum "url-ip" {
           description "Query category by URL and IP address";
         }
         enum "url" {
           description "Query category by URL only";
         }
       }
     }
     leaf base-filter {
       description "Juniper base filter";
       type string;
     }
     list category {
       key name;
       ordered-by user;
       description "Juniper enhanced category";
       uses juniper-enhanced-category-type;
     }
     container site-reputation-action {
       description "Juniper enhanced site reputation action";
       presence "enable site-reputation-action";
       uses juniper-enhanced-site-reputation-setting;
     }
     leaf default {
       description "Juniper enhanced profile default";
       type enumeration {
         enum "permit" {
           description "Permit action";
         }
         enum "block" {
           description "Block action";
         }
         enum "log-and-permit" {
           description "Log and permit action";
         }
         enum "quarantine" {
           description "Quarantine action";
         }
       }
     }
     leaf custom-message {
       description "Custom message";
       junos:must "(\"security utm custom-objects custom-message $$\")";
       junos:must-message "custom-message must be defined";
       type string;
     }
     container fallback-settings {
       description "Juniper enhanced fallback settings";
       presence "enable fallback-settings";
       uses web-filtering-fallback-setting;
     }
     leaf timeout {
       description "Juniper enhanced timeout";
       default "15";
       units "seconds";
       type union {
         type string {
           pattern "<.*>|$.*";
         }
         type uint32;
       }
     }
     leaf no-safe-search {
       description "Do not perform safe-search for Juniper enhanced protocol";
       type empty;
     }
   }
   grouping default-juniper-local-type {
     description "Juniper local";
     uses apply-advanced;
     leaf default {
       description "Juniper local profile default";
       type enumeration {
         enum "permit" {
           description "Permit action";
         }
         enum "block" {
           description "Block action";
         }
         enum "log-and-permit" {
           description "Log and permit action";
         }
       }
     }
     list category {
       key name;
       ordered-by user;
       description "Custom category";
       uses custom-category-type;
     }
     leaf custom-message {
       description "Custom message";
       junos:must "(\"security utm custom-objects custom-message $$\")";
       junos:must-message "custom-message must be defined";
       type string;
     }
     leaf no-safe-search {
       description "Do not perform safe-search for Juniper local protocol";
       type empty;
     }
     container fallback-settings {
       description "Juniper local fallback settings";
       presence "enable fallback-settings";
       uses web-filtering-fallback-setting;
     }
     leaf timeout {
       description "Juniper local timeout";
       default "15";
       units "seconds";
       type union {
         type string {
           pattern "<.*>|$.*";
         }
         type uint32 {
           range "1 .. 1800";
         }
       }
     }
   }
   grouping custom-category-type {
     description "Custom category type";
     leaf name {
       description "Name of custom category";
       junos:must "(\"security utm custom-objects custom-url-category $$\")";
       junos:must-message "custom-url-category must be defined";
       type string {
         length "1 .. 59";
       }
     }
     uses apply-advanced;
     leaf action {
       description "Action to perform when web traffic matches category";
       type enumeration {
         enum "permit" {
         }
         enum "log-and-permit" {
         }
         enum "block" {
         }
         enum "quarantine" {
         }
       }
     }
     leaf custom-message {
       description "Custom message";
       junos:must "(\"security utm custom-objects custom-message $$\")";
       junos:must-message "custom-message must be defined";
       type string;
     }
   }
   grouping default-websense-type {
     description "Websense redirect";
     uses apply-advanced;
     container server {
       description "Websense redirect server";
       presence "enable server";
       uses server;
     }
     list category {
       key name;
       ordered-by user;
       description "Custom category";
       uses custom-category-type;
     }
     leaf custom-message {
       description "Custom message";
       junos:must "(\"security utm custom-objects custom-message $$\")";
       junos:must-message "custom-message must be defined";
       type string;
     }
     leaf no-safe-search {
       description "Do not perform safe-search for websense redirect protocol";
       type empty;
     }
     container fallback-settings {
       description "Websense redirect fallback settings";
       presence "enable fallback-settings";
       uses web-filtering-fallback-setting;
     }
     leaf timeout {
       description "Websense redirect timeout";
       default "15";
       units "seconds";
       type union {
         type string {
           pattern "<.*>|$.*";
         }
         type uint32 {
           range "1 .. 1800";
         }
       }
     }
     leaf sockets {
       description "Websense redirect sockets number";
       default "32";
       type union {
         type string {
           pattern "<.*>|$.*";
         }
         type uint32 {
           range "1 .. 32";
         }
       }
     }
     leaf account {
       description "Websense redirect account";
       type string {
         length "1 .. 28";
       }
     }
   }
   grouping dnsf-traceoptions-object {
     description "URL filtering trace options";
     uses apply-advanced;
     leaf no-remote-trace {
       description "Disable remote tracing";
       junos:must "(\"system tracing\")";
       junos:must-message "'no-remote-trace' is valid only when [system tracing] is configured";
       type empty;
     }
     container file {
       description "Trace file information";
       leaf filename {
         description "Name of file in which to write trace information";
         type string {
           length "1 .. 1024";
           junos:posix-pattern "![/ %]";
           junos:pattern-message "Must not contain '/', % or a space";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     leaf level {
       description "Level of debugging output";
       default "error";
       type enumeration {
         enum "error" {
           description "Match error conditions";
         }
         enum "warning" {
           description "Match warning messages";
         }
         enum "notice" {
           description "Match conditions that should be handled specially";
         }
         enum "info" {
           description "Match informational messages";
         }
         enum "verbose" {
           description "Match verbose messages";
         }
         enum "all" {
           description "Match all levels";
         }
       }
     }
     list flag {
       key name;
       ordered-by user;
       description "Tracing flag parameters";
       leaf name {
         type enumeration {
           enum "normal" {
             description "Trace normal events";
           }
           enum "config" {
             description "Trace dns filtering config events";
           }
           enum "dns" {
             description "Trace url filtering DNS crawler events";
           }
           enum "timer" {
             description "Trace url filtering timer events";
           }
           enum "connect" {
             description "Trace url filtering ipc events";
           }
           enum "parse" {
             description "Trace url filtering parse events";
           }
           enum "statistics" {
             description "Trace url filtering statistics events";
           }
           enum "system" {
             description "Trace url filtering system events";
           }
           enum "operational-commands" {
             description "Trace url filtering show events";
           }
           enum "filter" {
             description "Trace url filtering filter programming events";
           }
           enum "gencfg" {
             description "Trace url filtering gencfg events";
           }
           enum "routing" {
             description "Trace url filtering route programming events";
           }
           enum "snmp" {
             description "Trace url filtering snmp events";
           }
           enum "all" {
             description "Trace everything";
           }
         }
       }
     }
   }
   grouping dynamic-attack-group-type {
     description "Define dynamic attack group";
     leaf name {
       description "Name of the dynamic attack group";
       type string;
     }
     uses apply-advanced;
     leaf attack-group-description {
       description "Filter name/value in xml format";
       status deprecated;
       type string;
     }
     container filters {
       description "Configure filters";
       uses apply-advanced;
       container direction {
         presence "enable direction";
         description "Direction of attack";
         uses apply-advanced;
         leaf expression {
           description "Boolean AND/OR to be used for values";
           default "or";
           type enumeration {
             enum "and" {
               description "AND values together (recommended if 'exclude-*' values are set)";
             }
             enum "or" {
               description "OR values together";
             }
           }
         }
         leaf-list values {
           ordered-by user;
           description "Values for direction field";
           type enumeration {
             enum "client-to-server" {
               description "Select attacks from client to server";
             }
             enum "server-to-client" {
               description "Select attacks from server to client";
             }
             enum "any" {
               description "Select attacks which can occur in either direction";
             }
             enum "exclude-client-to-server" {
               description "Filter out attacks from client to server";
             }
             enum "exclude-server-to-client" {
               description "Filter out attacks from server to client";
             }
             enum "exclude-any" {
               description "Filter out attacks which occur in either direction";
             }
           }
         }
       }
       container severity {
         presence "enable severity";
         description "Severity of attack";
         uses apply-advanced;
         leaf-list values {
           ordered-by user;
           description "Values for severity field";
           type enumeration {
             enum "info" {
               description "Provide information of attack when it matches.";
             }
             enum "warning" {
               description "Issue a warning when attack matches.";
             }
             enum "minor" {
               description "The attack is a minor one.";
             }
             enum "major" {
               description "The attack is a major one.";
             }
             enum "critical" {
               description "The attack is a critical one.";
             }
           }
         }
       }
       container type {
         presence "enable type";
         description "Type of attack";
         uses apply-advanced;
         leaf-list values {
           ordered-by user;
           description "Values for type field";
           type enumeration {
             enum "signature" {
               description "Signature based attacks";
             }
             enum "anomaly" {
               description "Protocol anomalies";
             }
           }
         }
       }
       choice recommended-choice {
         leaf recommended {
           description "Recommended flag";
           type empty;
         }
         leaf no-recommended {
           description "Don't recommended flag";
           type empty;
         }
       }
       container performance {
         presence "enable performance";
         description "Performance of attack";
         uses apply-advanced;
         leaf-list values {
           ordered-by user;
           description "Values for performance field";
           type enumeration {
             enum "unknown" {
               description "Performance level unknown";
             }
             enum "fast" {
               description "Fast performance";
             }
             enum "normal" {
               description "Normal performance";
             }
             enum "slow" {
               description "Slow performance";
             }
           }
         }
       }
       container category {
         presence "enable category";
         description "Category of attack";
         uses apply-advanced;
         leaf-list values {
           ordered-by user;
           description "Values for category field";
           type string;
         }
       }
       container service {
         presence "enable service";
         description "Service/Application of attack";
         uses apply-advanced;
         leaf-list values {
           ordered-by user;
           description "Values for service field";
           type string;
         }
       }
       container false-positives {
         presence "enable false-positives";
         description "False positive field in attack";
         uses apply-advanced;
         leaf-list values {
           ordered-by user;
           description "Values for false-positives field";
           type enumeration {
             enum "unknown" {
               description "Unknown information";
             }
             enum "rarely" {
               description "Rare false positives occurrence";
             }
             enum "occasionally" {
               description "Ocassional false positives occurrence";
             }
             enum "frequently" {
               description "Frequent false positives occurrence";
             }
           }
         }
       }
       list vendor {
         key name;
         ordered-by user;
         description "Vendor/Product the attack belongs to";
         uses vendor-object;
       }
       container file-type {
         presence "enable file-type";
         description "File type the attack is valid for";
         uses apply-advanced;
         leaf-list values {
           ordered-by user;
           description "Values for file-type field";
           type string;
         }
       }
       container vulnerability-type {
         presence "enable vulnerability-type";
         description "Vulnariability type of attack";
         uses apply-advanced;
         leaf-list values {
           ordered-by user;
           description "Values for vulnariability-type field";
           type string;
         }
       }
       choice excluded-choice {
         leaf excluded {
           description "Excluded Attacks";
           type empty;
         }
         leaf no-excluded {
           description "Don't excluded Attacks";
           type empty;
         }
       }
       container attack-prefix {
         presence "enable attack-prefix";
         description "Prefix match for attack names";
         uses apply-advanced;
         leaf-list values {
           ordered-by user;
           description "Values for attack name prefix match";
           type string;
         }
       }
       list cvss-score {
         key name;
         ordered-by user;
         description "CVSS score of Attack ";
         leaf name {
           description "Match condition of CVSS score";
           type enumeration {
             enum "greater-than" {
               description "Match when cvss score is greater";
             }
             enum "less-than" {
               description "Match when cvss score is less";
             }
           }
         }
         uses apply-advanced;
         leaf value {
           description "Match value";
           junos:must "(\".. value\")";
           junos:must-message "Missing mandatory statement: 'value'";
           type decimal64 {
             fraction-digits 9;
             range "0 .. 10";
           }
         }
       }
       list age-of-attack {
         key name;
         ordered-by user;
         description "Age of an Attack ";
         leaf name {
           description "Match condition of Age of Attack";
           type enumeration {
             enum "greater-than" {
               description "Match when Age of Attack is greater";
             }
             enum "less-than" {
               description "Match when Age of Attack is less";
             }
           }
         }
         uses apply-advanced;
         leaf value {
           description "Match value";
           junos:must "(\".. value\")";
           junos:must-message "Missing mandatory statement: 'value'";
           type union {
             type string {
               pattern "<.*>|$.*";
             }
             type uint32 {
               range "1 .. 100";
             }
           }
         }
       }
     }
   }
   grouping e2e-action-profile {
     leaf name {
       description "Name of the action profile";
       type string {
         length "1 .. 64";
       }
     }
     uses apply-advanced;
     leaf preserve-trace-order {
       description "Preserve trace order (has performance overhead)";
       type empty;
     }
     leaf record-pic-history {
       description "Record the PIC(s) in which the packet has been processed";
       type empty;
     }
     list event {
       key name;
       ordered-by user;
       uses e2e-event;
     }
     list module {
       key name;
       ordered-by user;
       uses e2e-module;
     }
   }
   grouping e2e-event {
     leaf name {
       description "Name of the event";
       type enumeration {
         enum "np-ingress" {
           description "NP ingress";
         }
         enum "np-egress" {
           description "NP egress";
         }
         enum "mac-ingress" {
           description "SRX1K/3K IOC Mac ingress";
         }
         enum "mac-egress" {
           description "SRX1K/3K IOC Mac egress";
         }
         enum "lbt" {
           description "Load-Balance-Thread";
         }
         enum "pot" {
           description "Packet-Order-Thread";
         }
         enum "jexec" {
           description "JExec";
         }
         enum "lt-enter" {
           description "LT(Logical Tunnel) enter";
         }
         enum "lt-leave" {
           description "LT(Logical Tunnel) leave";
         }
       }
     }
     uses apply-advanced;
     leaf trace {
       description "Trace action";
       type empty;
     }
     leaf count {
       description "Count action";
       type empty;
     }
     leaf packet-summary {
       description "Packet summary action";
       type empty;
     }
     leaf packet-dump {
       description "Packet dump action";
       type empty;
     }
   }
   grouping e2e-module {
     leaf name {
       description "Name of the module";
       type enumeration {
         enum "flow" {
           description "Flow module";
         }
       }
     }
     uses apply-advanced;
     list flag {
       key name;
       ordered-by user;
       description "Events and other information to include in trace output";
       leaf name {
         type enumeration {
           enum "all" {
             description "All flow trace";
           }
         }
       }
     }
   }
   grouping end-to-end-debug-filter {
     description "End to end debug packer filter settings";
     leaf name {
       description "Name of the filter";
       type string {
         length "1 .. 64";
         junos:posix-pattern "^[[:alnum:]._-]+$";
         junos:pattern-message "Must be a string of letters, numbers, dashes or underscores";
       }
     }
     uses apply-advanced;
     leaf action-profile {
       description "Actions to take with this filter";
       type string;
     }
     leaf protocol {
       description "Match IP protocol type";
       type string;
     }
     leaf source-prefix {
       description "Source IPv4/IPv6 address prefix";
       type jt:ipprefix;
     }
     leaf destination-prefix {
       description "Destination IPv4/IPv6 address prefix";
       type jt:ipprefix;
     }
     leaf source-port {
       description "Match TCP/UDP source port";
       type string;
     }
     leaf destination-port {
       description "Match TCP/UDP destination port";
       type string;
     }
     leaf interface {
       description "Logical interface";
       type union {
         type jt:interface-name;
         type string {
           pattern "<.*>|$.*";
         }
       }
     }
   }
   grouping extension-list-type {
     description "Configure extension-list object";
     leaf name {
       description "Configure name of extension-list object";
       type string {
         length "1 .. 29";
         junos:posix-pattern "^[a-zA-Z_]+[a-zA-Z_0-9-]*$";
         junos:pattern-message "Must be a string beginning with a letter or underscore and consisting of letters, numbers, dashes and underscores.";
       }
     }
     uses apply-advanced;
     leaf-list value {
       ordered-by user;
       description "Configure value of extension-list object";
       type string {
         length "1 .. 29";
       }
     }
   }
   grouping flow-filter-type {
     description "Flow filter settings";
     leaf name {
       description "Name of the filter";
       type string {
         length "1 .. 63";
         junos:posix-pattern "^[[:alnum:]._-]+$";
         junos:pattern-message "Must be a string of letters, numbers, dashes or underscores";
       }
     }
     uses apply-advanced;
     leaf protocol {
       description "Match IP protocol type";
       type string;
     }
     leaf source-prefix {
       description "Source IP address prefix";
       type jt:ipprefix;
     }
     leaf destination-prefix {
       description "Destination IP address prefix";
       type jt:ipprefix;
     }
     leaf conn-tag {
       description "Session connection tag";
       type union {
         type string {
           pattern "<.*>|$.*";
         }
         type uint32 {
           range "0 .. 4294967295";
         }
       }
     }
     leaf logical-system {
       description "Logical system";
       status deprecated;
       type string {
         length "1 .. 63";
       }
     }
     leaf source-port {
       description "Match TCP/UDP source port";
       type string;
     }
     leaf destination-port {
       description "Match TCP/UDP destination port";
       type string;
     }
     leaf interface {
       description "Source logical interface";
       type union {
         type jt:interface-name;
         type string {
           pattern "<.*>|$.*";
         }
       }
     }
   }
   grouping flow-traceoptions-object {
     description "Trace options for flow services";
     uses apply-advanced;
     leaf no-remote-trace {
       description "Disable remote tracing";
       junos:must "(\"system tracing\")";
       junos:must-message "'no-remote-trace' is valid only when [system tracing] is configured";
       type empty;
     }
     container file {
       description "Trace file information";
       leaf filename {
         description "Name of file in which to write trace information";
         type string {
           length "1 .. 1024";
           junos:posix-pattern "![/ %]";
           junos:pattern-message "Must not contain '/', % or a space";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     list flag {
       key name;
       ordered-by user;
       description "Events and other information to include in trace output";
       leaf name {
         type enumeration {
           enum "all" {
             description "All events";
           }
           enum "basic-datapath" {
             description "Basic packet flow";
           }
           enum "high-availability" {
             description "Flow high-availability information";
           }
           enum "host-traffic" {
             description "Flow host-traffic information";
           }
           enum "fragmentation" {
             description "Ip fragmentation and reassembly events";
           }
           enum "multicast" {
             description "Multicast flow information";
           }
           enum "route" {
             description "Route lookup information";
           }
           enum "session" {
             description "Session creation and deletion events";
           }
           enum "session-scan" {
             description "Session scan information";
           }
           enum "tcp-basic" {
             description "TCP packet flow";
           }
           enum "tunnel" {
             description "Tunnel information";
           }
           enum "jexec" {
             description "Junos forwarding module";
           }
         }
       }
     }
     leaf rate-limit {
       description "Limit the incoming rate of trace messages";
       default "0";
       type union {
         type string {
           pattern "<.*>|$.*";
         }
         type uint32 {
           range "0 .. 4294967295";
         }
       }
     }
     list packet-filter {
       key name;
       ordered-by user;
       description "Flow packet debug filters";
       max-elements 64;
       uses flow-filter-type;
     }
     container trace-level {
       description "FLow trace level";
       uses apply-advanced;
       choice level {
         case case_1 {
           leaf minimal {
             description "Significant messages including warning, error, criticality, alert and emergency.";
             type empty;
           }
         }
         case case_2 {
           leaf brief {
             description "Brief messages including notice, in addition to minimal messages";
             type empty;
           }
         }
         case case_3 {
           leaf detail {
             description "Detail messages including info and debug, in addition to brief messages";
             type empty;
           }
         }
       }
     }
     leaf root-override {
       description "Allow collect flow trace in root from all logical-systems and tenants";
       junos:must "((\".. file\" && \".. flag\"))";
       junos:must-message "root-override must have root trace file and flag configured";
       type empty;
     }
   }
   grouping gtp-object {
     uses apply-advanced;
     list profile {
       key name;
       description "Configure GTP Profile";
       leaf name {
         description "GTP profile name";
         type string {
           length "1 .. 23";
         }
       }
       uses apply-advanced;
       leaf min-message-length {
         description "Minimum message length, from 0 to 65535 ";
         default "0";
         type union {
           type string {
             pattern "<.*>|$.*";
           }
           type uint32 {
             range "0 .. 65535";
           }
         }
       }
       leaf max-message-length {
         description "Maximum message length, from 1 to 65535";
         default "65535";
         type union {
           type string {
             pattern "<.*>|$.*";
           }
           type uint32 {
             range "1 .. 65535";
           }
         }
       }
       leaf timeout {
         description "Tunnel idle timeout";
         default "1000";
         units "hour";
         type union {
           type string {
             pattern "<.*>|$.*";
           }
           type uint32 {
             range "1 .. 1000";
           }
         }
       }
       container rate-limit {
         description "Limit messages per second";
         presence "enable rate-limit";
         uses rate-limit-object;
       }
       container log {
         presence "enable log";
         description "GPRS tunneling protocol logs";
         uses apply-advanced;
         leaf forwarded {
           description "Log passed good packets";
           type enumeration {
             enum "basic" {
               description "Basic logs";
             }
             enum "detail" {
               description "Detailed logs";
             }
           }
         }
         leaf event {
           description "Log alarms and tunnel management events";
           type enumeration {
             enum "basic" {
               description "Basic logs";
             }
             enum "detail" {
               description "Detailed logs";
             }
           }
         }
         leaf prohibited {
           description "Log dropped packets";
           type enumeration {
             enum "basic" {
               description "Basic logs";
             }
             enum "detail" {
               description "Detailed logs";
             }
           }
         }
         list gtp-u {
           key name;
           description "Logs for gtp-u";
           leaf name {
             description "Logs for gtp-u";
             type enumeration {
               enum "all" {
                 description "All gtp-u logs";
               }
               enum "dropped" {
                 description "Dropped gtp-u logs";
               }
             }
           }
           uses apply-advanced;
         }
         container rate-limited {
           presence "enable rate-limited";
           description "Dropped for rate-limit";
           uses apply-advanced;
           choice rate-limited-attr {
             case case_1 {
               leaf basic {
                 description "Basic logs";
                 type empty;
               }
             }
             case case_2 {
               leaf detail {
                 description "Detailed logs";
                 type empty;
               }
             }
           }
         }
       }
       container remove-ie {
         presence "enable remove-ie";
         description "Remove information elements";
         uses apply-advanced;
         list version {
           key name;
           description "GTP version";
           leaf name {
             description "Version name";
             type enumeration {
               enum "v1" {
                 description "GTP v1";
               }
             }
           }
           uses apply-advanced;
           list release {
             key name;
             description "Remove information elements by release";
             leaf name {
               description "Release name";
               type enumeration {
                 enum "R6" {
                   description "Release 6";
                 }
                 enum "R7" {
                   description "Release 7";
                 }
                 enum "R8" {
                   description "Release 8";
                 }
                 enum "R9" {
                   description "Release 9";
                 }
               }
             }
             uses apply-advanced;
           }
           list number {
             key name;
             description "Remove information elements by number";
             leaf name {
               type union {
                 type string {
                   pattern "<.*>|$.*";
                 }
                 type uint32 {
                   range "1 .. 255";
                 }
               }
             }
             uses apply-advanced;
           }
         }
       }
       container path-rate-limit {
         description "Limit control messages based on IP pairs";
         uses apply-advanced;
         list message-type {
           key name;
           description "Specific group of control messages";
           leaf name {
             description "Specific group of control messages";
             type enumeration {
               enum "create-req" {
                 description "Limit packet-per-second of GTP create request";
               }
               enum "delete-req" {
                 description "Limit packet-per-second of GTP delete request";
               }
               enum "echo-req" {
                 description "Limit packet-per-minute of GTP echo request";
               }
               enum "other" {
                 description "Limit packet-per-second of all other GTP control messages";
               }
             }
           }
           uses apply-advanced;
           container drop-threshold {
             description "Set drop threshold for path rate limiting";
             uses apply-advanced;
             leaf forward {
               description "Limit messages of forward direction";
               type union {
                 type string {
                   pattern "<.*>|$.*";
                 }
                 type uint32 {
                   range "1 .. 10000";
                 }
               }
             }
             leaf reverse {
               description "Limit messages of reverse direction";
               type union {
                 type string {
                   pattern "<.*>|$.*";
                 }
                 type uint32 {
                   range "1 .. 10000";
                 }
               }
             }
           }
           container alarm-threshold {
             description "Set alarm threshold for path rate limiting";
             uses apply-advanced;
             leaf forward {
               description "Limit messages of forward direction";
               type union {
                 type string {
                   pattern "<.*>|$.*";
                 }
                 type uint32 {
                   range "1 .. 10000";
                 }
               }
             }
             leaf reverse {
               description "Limit messages of reverse direction";
               type union {
                 type string {
                   pattern "<.*>|$.*";
                 }
                 type uint32 {
                   range "1 .. 10000";
                 }
               }
             }
           }
         }
       }
       container drop {
         description "Drop certain type of messages";
         uses apply-advanced;
         list aa-create-pdp {
           key name;
           ordered-by user;
           description "Create AA pdp request/response message";
           leaf name {
             description "GTP version for message";
             type enumeration {
               enum "0" {
                 description "Version 0";
               }
             }
           }
           uses apply-advanced;
         }
         list aa-delete-pdp {
           key name;
           ordered-by user;
           description "Delete AA pdp request/response message";
           leaf name {
             description "GTP version for message";
             type enumeration {
               enum "0" {
                 description "Version 0";
               }
             }
           }
           uses apply-advanced;
         }
         list bearer-resource {
           key name;
           ordered-by user;
           description "Bearer resource command/failure message";
           leaf name {
             description "GTP version for message";
             type enumeration {
               enum "2" {
                 description "Version 2";
               }
             }
           }
           uses apply-advanced;
         }
         list change-notification {
           key name;
           ordered-by user;
           description "Change notification request/response message";
           leaf name {
             description "GTP version for message";
             type enumeration {
               enum "2" {
                 description "Version 2";
               }
             }
           }
           uses apply-advanced;
         }
         list config-transfer {
           key name;
           ordered-by user;
           description "Configuration transfer message";
           leaf name {
             description "GTP version for message";
             type enumeration {
               enum "2" {
                 description "Version 2";
               }
             }
           }
           uses apply-advanced;
         }
         list context {
           key name;
           ordered-by user;
           description "Context request/response/ack message";
           leaf name {
             description "GTP version for message";
             type enumeration {
               enum "2" {
                 description "Version 2";
               }
             }
           }
           uses apply-advanced;
         }
         list create-bearer {
           key name;
           ordered-by user;
           description "Create bearer request/response message";
           leaf name {
             description "GTP version for message";
             type enumeration {
               enum "2" {
                 description "Version 2";
               }
             }
           }
           uses apply-advanced;
         }
         list create-data-forwarding {
           key name;
           ordered-by user;
           description "Create indirect data forwarding tunnel request/response message";
           leaf name {
             description "GTP version for message";
             type enumeration {
               enum "2" {
                 description "Version 2";
               }
             }
           }
           uses apply-advanced;
         }
         list create-pdp {
           key name;
           ordered-by user;
           description "Create pdp request/response message";
           leaf name {
             description "GTP version for message";
             type enumeration {
               enum "0" {
                 description "Version 0";
               }
               enum "1" {
                 description "Version 1";
               }
               enum "all" {
                 description "All versions";
               }
             }
           }
           uses apply-advanced;
         }
         list create-session {
           key name;
           ordered-by user;
           description "Create session request/response message";
           leaf name {
             description "GTP version for message";
             type enumeration {
               enum "2" {
                 description "Version 2";
               }
             }
           }
           uses apply-advanced;
         }
         list create-tnl-forwarding {
           key name;
           ordered-by user;
           description "Create forwarding tunnel request/response message";
           leaf name {
             description "GTP version for message";
             type enumeration {
               enum "2" {
                 description "Version 2";
               }
             }
           }
           uses apply-advanced;
         }
         list cs-paging {
           key name;
           ordered-by user;
           description "CS paging indication message";
           leaf name {
             description "GTP version for message";
             type enumeration {
               enum "2" {
                 description "Version 2";
               }
             }
           }
           uses apply-advanced;
         }
         list data-record {
           key name;
           ordered-by user;
           description "Data record request/response message";
           leaf name {
             description "GTP version for message";
             type enumeration {
               enum "0" {
                 description "Version 0";
               }
               enum "1" {
                 description "Version 1";
               }
               enum "all" {
                 description "All versions";
               }
             }
           }
           uses apply-advanced;
         }
         list delete-bearer {
           key name;
           ordered-by user;
           description "Delete bearer request/response message";
           leaf name {
             description "GTP version for message";
             type enumeration {
               enum "2" {
                 description "Version 2";
               }
             }
           }
           uses apply-advanced;
         }
         list delete-command {
           key name;
           ordered-by user;
           description "Delete bearer command/failure message";
           leaf name {
             description "GTP version for message";
             type enumeration {
               enum "2" {
                 description "Version 2";
               }
             }
           }
           uses apply-advanced;
         }
         list delete-data-forwarding {
           key name;
           ordered-by user;
           description "Delete indirect data forwarding tunnel request/response message";
           leaf name {
             description "GTP version for message";
             type enumeration {
               enum "2" {
                 description "Version 2";
               }
             }
           }
           uses apply-advanced;
         }
         list delete-pdn {
           key name;
           ordered-by user;
           description "Delete PDN connection set request/response message";
           leaf name {
             description "GTP version for message";
             type enumeration {
               enum "2" {
                 description "Version 2";
               }
             }
           }
           uses apply-advanced;
         }
         list delete-pdp {
           key name;
           ordered-by user;
           description "Delete pdp request/response message";
           leaf name {
             description "GTP version for message";
             type enumeration {
               enum "0" {
                 description "Version 0";
               }
               enum "1" {
                 description "Version 1";
               }
               enum "all" {
                 description "All versions";
               }
             }
           }
           uses apply-advanced;
         }
         list delete-session {
           key name;
           ordered-by user;
           description "Delete session request/response message";
           leaf name {
             description "GTP version for message";
             type enumeration {
               enum "2" {
                 description "Version 2";
               }
             }
           }
           uses apply-advanced;
         }
         list detach {
           key name;
           ordered-by user;
           description "Detach notification/ack message";
           leaf name {
             description "GTP version for message";
             type enumeration {
               enum "2" {
                 description "Version 2";
               }
             }
           }
           uses apply-advanced;
         }
         list downlink-notification {
           key name;
           ordered-by user;
           description "Downlink data notification/ack/failure message";
           leaf name {
             description "GTP version for message";
             type enumeration {
               enum "2" {
                 description "Version 2";
               }
             }
           }
           uses apply-advanced;
         }
         list echo {
           key name;
           ordered-by user;
           description "Echo request/response message";
           leaf name {
             description "GTP version for message";
             type enumeration {
               enum "0" {
                 description "Version 0";
               }
               enum "1" {
                 description "Version 1";
               }
               enum "2" {
                 description "Version 2";
               }
               enum "all" {
                 description "All versions";
               }
             }
           }
           uses apply-advanced;
         }
         list error-indication {
           key name;
           ordered-by user;
           description "Error indication message";
           leaf name {
             description "GTP version for message";
             type enumeration {
               enum "0" {
                 description "Version 0";
               }
               enum "1" {
                 description "Version 1";
               }
               enum "all" {
                 description "All versions";
               }
             }
           }
           uses apply-advanced;
         }
         list failure-report {
           key name;
           ordered-by user;
           description "Failure report request/response message";
           leaf name {
             description "GTP version for message";
             type enumeration {
               enum "0" {
                 description "Version 0";
               }
               enum "1" {
                 description "Version 1";
               }
               enum "all" {
                 description "All versions";
               }
             }
           }
           uses apply-advanced;
         }
         list fwd-access {
           key name;
           ordered-by user;
           description "Forward access context notification/ack message";
           leaf name {
             description "GTP version for message";
             type enumeration {
               enum "2" {
                 description "Version 2";
               }
             }
           }
           uses apply-advanced;
         }
         list fwd-relocation {
           key name;
           ordered-by user;
           description "Forward relocation request/response/comp/comp-ack message";
           leaf name {
             description "GTP version for message";
             type enumeration {
               enum "1" {
                 description "Version 1";
               }
               enum "2" {
                 description "Version 2";
               }
               enum "all" {
                 description "All versions";
               }
             }
           }
           uses apply-advanced;
         }
         list fwd-srns-context {
           key name;
           ordered-by user;
           description "Forward SRNS context/context-ack message";
           leaf name {
             description "GTP version for message";
             type enumeration {
               enum "1" {
                 description "Version 1";
               }
             }
           }
           uses apply-advanced;
         }
         list g-pdu {
           key name;
           ordered-by user;
           description "G-PDU (user PDU) message/T-PDU";
           leaf name {
             description "GTP version for message";
             type enumeration {
               enum "0" {
                 description "Version 0";
               }
               enum "1" {
                 description "Version 1";
               }
               enum "all" {
                 description "All versions";
               }
             }
           }
           uses apply-advanced;
         }
         list identification {
           key name;
           ordered-by user;
           description "Identification request/response message";
           leaf name {
             description "GTP version for message";
             type enumeration {
               enum "0" {
                 description "Version 0";
               }
               enum "1" {
                 description "Version 1";
               }
               enum "2" {
                 description "Version 2";
               }
               enum "all" {
                 description "All versions";
               }
             }
           }
           uses apply-advanced;
         }
         list mbms-session-start {
           key name;
           ordered-by user;
           description "MBMS session start request/response message";
           leaf name {
             description "GTP version for message";
             type enumeration {
               enum "1" {
                 description "Version 1";
               }
               enum "2" {
                 description "Version 2";
               }
               enum "all" {
                 description "All versions";
               }
             }
           }
           uses apply-advanced;
         }
         list mbms-session-stop {
           key name;
           ordered-by user;
           description "MBMS session stop request/response message";
           leaf name {
             description "GTP version for message";
             type enumeration {
               enum "1" {
                 description "Version 1";
               }
               enum "2" {
                 description "Version 2";
               }
               enum "all" {
                 description "All versions";
               }
             }
           }
           uses apply-advanced;
         }
         list mbms-session-update {
           key name;
           ordered-by user;
           description "MBMS session update request/response message";
           leaf name {
             description "GTP version for message";
             type enumeration {
               enum "1" {
                 description "Version 1";
               }
               enum "2" {
                 description "Version 2";
               }
               enum "all" {
                 description "All versions";
               }
             }
           }
           uses apply-advanced;
         }
         list modify-bearer {
           key name;
           ordered-by user;
           description "Modify bearer request/response message";
           leaf name {
             description "GTP version for message";
             type enumeration {
               enum "2" {
                 description "Version 2";
               }
             }
           }
           uses apply-advanced;
         }
         list modify-command {
           key name;
           ordered-by user;
           description "Modify bearer command/failure message";
           leaf name {
             description "GTP version for message";
             type enumeration {
               enum "2" {
                 description "Version 2";
               }
             }
           }
           uses apply-advanced;
         }
         list node-alive {
           key name;
           ordered-by user;
           description "Node alive request/response message";
           leaf name {
             description "GTP version for message";
             type enumeration {
               enum "0" {
                 description "Version 0";
               }
               enum "1" {
                 description "Version 1";
               }
               enum "all" {
                 description "All versions";
               }
             }
           }
           uses apply-advanced;
         }
         list note-ms-present {
           key name;
           ordered-by user;
           description "Note MS GPRS present request/response message";
           leaf name {
             description "GTP version for message";
             type enumeration {
               enum "0" {
                 description "Version 0";
               }
               enum "1" {
                 description "Version 1";
               }
               enum "all" {
                 description "All versions";
               }
             }
           }
           uses apply-advanced;
         }
         list pdu-notification {
           key name;
           ordered-by user;
           description "PDU notification requst/response/reject/reject-response message";
           leaf name {
             description "GTP version for message";
             type enumeration {
               enum "0" {
                 description "Version 0";
               }
               enum "1" {
                 description "Version 1";
               }
               enum "all" {
                 description "All versions";
               }
             }
           }
           uses apply-advanced;
         }
         list ran-info {
           key name;
           ordered-by user;
           description "RAN info relay message";
           leaf name {
             description "GTP version for message";
             type enumeration {
               enum "1" {
                 description "Version 1";
               }
               enum "2" {
                 description "Version 2";
               }
               enum "all" {
                 description "All versions";
               }
             }
           }
           uses apply-advanced;
         }
         list redirection {
           key name;
           ordered-by user;
           description "Redirection request/response message";
           leaf name {
             description "GTP version for message";
             type enumeration {
               enum "0" {
                 description "Version 0";
               }
               enum "1" {
                 description "Version 1";
               }
               enum "all" {
                 description "All versions";
               }
             }
           }
           uses apply-advanced;
         }
         list release-access {
           key name;
           ordered-by user;
           description "Release access-bearer request/response message";
           leaf name {
             description "GTP version for message";
             type enumeration {
               enum "2" {
                 description "Version 2";
               }
             }
           }
           uses apply-advanced;
         }
         list relocation-cancel {
           key name;
           ordered-by user;
           description "Relocation cancel request/response message";
           leaf name {
             description "GTP version for message";
             type enumeration {
               enum "1" {
                 description "Version 1";
               }
               enum "2" {
                 description "Version 2";
               }
               enum "all" {
                 description "All versions";
               }
             }
           }
           uses apply-advanced;
         }
         list resume {
           key name;
           ordered-by user;
           description "Resume notification/ack message";
           leaf name {
             description "GTP version for message";
             type enumeration {
               enum "2" {
                 description "Version 2";
               }
             }
           }
           uses apply-advanced;
         }
         list send-route {
           key name;
           ordered-by user;
           description "Send route info request/response message";
           leaf name {
             description "GTP version for message";
             type enumeration {
               enum "0" {
                 description "Version 0";
               }
               enum "1" {
                 description "Version 1";
               }
               enum "all" {
                 description "All versions";
               }
             }
           }
           uses apply-advanced;
         }
         list sgsn-context {
           key name;
           ordered-by user;
           description "SGSN context request/response/ack message";
           leaf name {
             description "GTP version for message";
             type enumeration {
               enum "0" {
                 description "Version 0";
               }
               enum "1" {
                 description "Version 1";
               }
               enum "all" {
                 description "All versions";
               }
             }
           }
           uses apply-advanced;
         }
         list stop-paging {
           key name;
           ordered-by user;
           description "Stop paging indication message";
           leaf name {
             description "GTP version for message";
             type enumeration {
               enum "2" {
                 description "Version 2";
               }
             }
           }
           uses apply-advanced;
         }
         list supported-extension {
           key name;
           ordered-by user;
           description "Supported extension headers notification message";
           leaf name {
             description "GTP version for message";
             type enumeration {
               enum "1" {
                 description "Version 1";
               }
             }
           }
           uses apply-advanced;
         }
         list suspend {
           key name;
           ordered-by user;
           description "Suspend notification/ack message";
           leaf name {
             description "GTP version for message";
             type enumeration {
               enum "2" {
                 description "Version 2";
               }
             }
           }
           uses apply-advanced;
         }
         list trace-session {
           key name;
           ordered-by user;
           description "Trace session activation/deactivation message";
           leaf name {
             description "GTP version for message";
             type enumeration {
               enum "2" {
                 description "Version 2";
               }
             }
           }
           uses apply-advanced;
         }
         list update-bearer {
           key name;
           ordered-by user;
           description "Update bearer request/response message";
           leaf name {
             description "GTP version for message";
             type enumeration {
               enum "2" {
                 description "Version 2";
               }
             }
           }
           uses apply-advanced;
         }
         list update-pdn {
           key name;
           ordered-by user;
           description "Update PDN connection set request/response message";
           leaf name {
             description "GTP version for message";
             type enumeration {
               enum "2" {
                 description "Version 2";
               }
             }
           }
           uses apply-advanced;
         }
         list update-pdp {
           key name;
           ordered-by user;
           description "Update pdp request/response message";
           leaf name {
             description "GTP version for message";
             type enumeration {
               enum "0" {
                 description "Version 0";
               }
               enum "1" {
                 description "Version 1";
               }
               enum "all" {
                 description "All versions";
               }
             }
           }
           uses apply-advanced;
         }
         list ver-not-supported {
           key name;
           ordered-by user;
           description "Version not supported message";
           leaf name {
             description "GTP version for message";
             type enumeration {
               enum "0" {
                 description "Version 0";
               }
               enum "1" {
                 description "Version 1";
               }
               enum "2" {
                 description "Version 2";
               }
               enum "all" {
                 description "All versions";
               }
             }
           }
           uses apply-advanced;
         }
       }
       list apn {
         key name;
         description "GTP Access Point Name (APN) filter";
         leaf name {
           description "Specific APN pattern string";
           type string {
             length "1 .. 64";
             junos:posix-pattern "^[*]$|^[*][^*]{1,63}$|^[^*]{1,64}$";
             junos:pattern-message "APN pattern string length should be 1-64, support wildcard for the first character";
           }
         }
         uses apply-advanced;
         list imsi-prefix {
           key name;
           description "Specific filter prefix digits for International Mobile Subscriber Identification(IMSI)";
           leaf name {
             description "IMSI prefix should be * or 5-15 digits";
             type string {
               length "1 .. 15";
               junos:posix-pattern "^[*]$|^[0-9]{5,15}$";
               junos:pattern-message "imsi-prefix should be * or 5-15 digits";
             }
           }
           uses apply-advanced;
           container action {
             description "Configure GTP profile APN action";
             uses apply-advanced;
             choice action-c {
               case case_1 {
                 leaf pass {
                   description "Pass all selection modes for this APN";
                   type empty;
                 }
               }
               case case_2 {
                 leaf drop {
                   description "Drop all selection modes for this APN";
                   type empty;
                 }
               }
               case case_3 {
                 container selection {
                   presence "enable selection";
                   description "Allowed selection modes for this APN";
                   uses apply-advanced;
                   leaf ms {
                     description "Mobile Station selection mode";
                     type empty;
                   }
                   leaf net {
                     description "Network selection mode";
                     type empty;
                   }
                   leaf vrf {
                     description "Subscriber verified mode";
                     type empty;
                   }
                 }
               }
             }
           }
         }
       }
       leaf restart-path {
         description "Restart GTP paths";
         type enumeration {
           enum "echo" {
             description "Restart GTP paths by detecting restart number stored in the Echo messages";
           }
           enum "create" {
             description "Restart GTP paths by detecting restart number stored in the Create messages";
           }
           enum "all" {
             description "Restart GTP paths by detecting restart number stored in the Echo or Create messages";
           }
         }
       }
       leaf seq-number-validated {
         description "Validate G-PDU sequence number";
         type empty;
       }
       leaf gtp-in-gtp-denied {
         description "Deny nested GTP";
         type empty;
       }
       leaf u-tunnel-validated {
         description "Validate GTP-u tunnel";
         type empty;
       }
       leaf end-user-address-validated {
         description "Validate end user address";
         type empty;
       }
       leaf req-timeout {
         description "Request message timeout, default timeout value 5 seconds";
         units "second";
         type union {
           type string {
             pattern "<.*>|$.*";
           }
           type uint8 {
             range "1 .. 30";
           }
         }
       }
       leaf handover-on-roaming-intf {
         description "Enable tunnel setup by Handover messages on roaming interface";
         type empty;
       }
       container handover-group {
         description "SGSN handover group configuration";
         uses apply-advanced;
         leaf group-name {
           description "SGSN handover group name";
           junos:must "((\"security gprs gtp handover-group $$\" || (\"security gprs gtp ip-group $$\" || (\"security gtp handover-group $$\" || \"security gtp ip-group $$\"))))";
           junos:must-message "referenced ip-group/handover-group not found";
           type string {
             length "1 .. 23";
           }
         }
       }
       leaf listening-mode {
         description "Enable listening-mode for GTP inspection";
         type empty;
       }
       container ne-group {
         description "IP validation check for NE group configuration";
         uses apply-advanced;
         leaf group-name {
           description "GTP ip group name";
           junos:must "((\"security gprs gtp ip-group $$\" || \"security gtp ip-group $$\"))";
           junos:must-message "referenced ip-group not found";
           type string {
             length "1 .. 23";
           }
         }
       }
       container ue-group {
         description "End User IP validation check for UE group configuration";
         uses apply-advanced;
         leaf group-name {
           description "GTP ip group name";
           junos:must "((\"security gprs gtp ip-group $$\" || \"security gtp ip-group $$\"))";
           junos:must-message "referenced ip-group not found";
           type string {
             length "1 .. 23";
           }
         }
       }
       container must-ie-v1 {
         description "GTPv1 Must IE check configuration";
         uses apply-advanced;
         leaf msgie-prf-v1-name {
           description "GTPv1 message-ie profile name";
           junos:must "((\"security gprs gtp message-ie-profile-v1 $$\" || \"security gtp message-ie-profile-v1 $$\"))";
           junos:must-message "referenced message-ie-profile-v1 not found";
           type string {
             length "1 .. 23";
           }
         }
       }
       container must-ie-v2 {
         description "GTPv2 Must IE check configuration";
         uses apply-advanced;
         leaf msgie-prf-v2-name {
           description "GTPv2 message-ie profile name";
           junos:must "((\"security gprs gtp message-ie-profile-v2 $$\" || \"security gtp message-ie-profile-v2 $$\"))";
           junos:must-message "referenced message-ie-profile-v2 not found";
           type string {
             length "1 .. 23";
           }
         }
       }
       container remove-ie-v1 {
         description "GTPv1 IE Removal configuration";
         uses apply-advanced;
         leaf ieset-name {
           description "GTP ie-set name";
           junos:must "((\"security gprs gtp ie-set $$\" || \"security gtp ie-set $$\"))";
           junos:must-message "referenced ie-set not found";
           type string {
             length "1 .. 23";
           }
         }
       }
       container remove-ie-v2 {
         description "GTPv2 IE Removal configuration";
         uses apply-advanced;
         leaf ieset-name {
           description "GTP ie-set name";
           junos:must "((\"security gprs gtp ie-set $$\" || \"security gtp ie-set $$\"))";
           junos:must-message "referenced ie-set not found";
           type string {
             length "1 .. 23";
           }
         }
       }
       choice apn-control-c {
         case case_1 {
           container apn-control {
             description "GTP per APN control";
             uses apply-advanced;
             leaf apn-ctrl-name {
               description "APN control profile name";
               junos:must "((\"security gprs gtp apn-control $$\" || \"security gtp apn-control $$\"))";
               junos:must-message "referenced apn-control profile not found";
               type string {
                 length "1 .. 23";
               }
             }
           }
         }
         case case_2 {
           container apn-control-group {
             description "GTP per APN control group";
             uses apply-advanced;
             leaf apn-ctrl-grp-name {
               description "APN control group name";
               junos:must "((\"security gprs gtp apn-control-group $$\" || \"security gtp apn-control-group $$\"))";
               junos:must-message "referenced apn-control group not found";
               type string {
                 length "1 .. 23";
               }
             }
           }
         }
       }
     }
     container traceoptions {
       description "Trace options for GPRS tunneling protocol";
       uses apply-advanced;
       leaf no-remote-trace {
         description "Disable remote tracing";
         junos:must "(\"system tracing\")";
         junos:must-message "'no-remote-trace' is valid only when [system tracing] is configured";
         type empty;
       }
       container file {
         description "Trace file information";
         leaf filename {
           description "Name of file in which to write trace information";
           type string {
             length "1 .. 1024";
             junos:posix-pattern "![/ %]";
             junos:pattern-message "Must not contain '/', % or a space";
           }
         }
         leaf size {
           description "Maximum trace file size";
           type string;
         }
         leaf files {
           description "Maximum number of trace files";
           default "3";
           type union {
             type string {
               pattern "<.*>|$.*";
             }
             type uint32 {
               range "2 .. 1000";
             }
           }
         }
         choice world-readable-choice {
           leaf world-readable {
             description "Allow any user to read the log file";
             type empty;
           }
           leaf no-world-readable {
             description "Don't allow any user to read the log file";
             type empty;
           }
         }
         leaf match {
           description "Regular expression for lines to be logged";
           type jt:regular-expression;
         }
       }
       list flag {
         key name;
         ordered-by user;
         description "Tracing parameters";
         leaf name {
           type enumeration {
             enum "configuration" {
               description "Trace configuration events";
             }
             enum "flow" {
               description "Trace flow events";
             }
             enum "parser" {
               description "Trace parser events";
             }
             enum "chassis-cluster" {
               description "Trace chassis cluster events";
             }
             enum "gsn" {
               description "Trace gsn events";
             }
             enum "jmpi" {
               description "Trace jmpi events";
             }
             enum "tnl" {
               description "Trace tnl events";
             }
             enum "req" {
               description "Trace req events";
             }
             enum "path" {
               description "Trace path events";
             }
             enum "all" {
               description "Trace everything";
             }
           }
         }
       }
       container trace-level {
         description "GTP trace level";
         uses apply-advanced;
         choice level {
           case case_1 {
             leaf error {
               description "Match error conditions";
               type empty;
             }
           }
           case case_2 {
             leaf warning {
               description "Match warning messages";
               type empty;
             }
           }
           case case_3 {
             leaf notice {
               description "Match conditions that should be handled specially";
               type empty;
             }
           }
           case case_4 {
             leaf info {
               description "Match informational messages";
               type empty;
             }
           }
           case case_5 {
             leaf verbose {
               description "Match verbose messages";
               type empty;
             }
           }
         }
       }
     }
     container handover-default {
       description "Set handover default deny";
       uses apply-advanced;
       leaf deny {
         description "Handover default deny";
         type empty;
       }
     }
     list ip-group {
       key name;
       description "Set GTP IP group";
       leaf name {
         description "Set ip group name";
         type string {
           length "1 .. 23";
         }
       }
       uses apply-advanced;
       list address-book {
         key name;
         description "Set addreess book";
         leaf name {
           description "Set address book name";
           junos:must "(\"security address-book $$\")";
           junos:must-message "referenced address-book not found";
           type string {
             length "1 .. 63";
           }
         }
         uses apply-advanced;
         container address-set {
           description "Set address set";
           uses apply-advanced;
           leaf set-name {
             description "Set address set name";
             type string {
               length "1 .. 63";
             }
           }
         }
       }
     }
     list ie-set {
       key name;
       description "Set GTP IE set profile";
       max-elements 20;
       leaf name {
         description "Set GTP IE set profile name";
         type string {
           length "1 .. 23";
         }
       }
       uses apply-advanced;
       list ie {
         key name;
         description "Set IE number";
         leaf name {
           description "Set IE number";
           type union {
             type string {
               pattern "<.*>|$.*";
             }
             type uint8 {
               range "1 .. 255";
             }
           }
         }
         uses apply-advanced;
       }
     }
     list message-ie-profile-v1 {
       key name;
       description "Set GTPv1 message IE profile";
       max-elements 10;
       leaf name {
         description "Set GTPv1 message IE profile name";
         type string {
           length "1 .. 23";
         }
       }
       uses apply-advanced;
       list message {
         key name;
         description "Set message type";
         leaf name {
           description "Set message type";
           type union {
             type string {
               pattern "<.*>|$.*";
             }
             type uint8 {
               range "1 .. 255";
             }
           }
         }
         uses apply-advanced;
         list ie {
           key name;
           description "Set IE number";
           leaf name {
             description "Set IE number";
             type union {
               type string {
                 pattern "<.*>|$.*";
               }
               type uint8 {
                 range "1 .. 255";
               }
             }
           }
           uses apply-advanced;
         }
       }
     }
     list grouped-ie-profile {
       key name;
       description "Set GTP grouped IE filter profile";
       max-elements 100;
       leaf name {
         description "Set GTP grouped IE filter profile name";
         type string {
           length "1 .. 23";
         }
       }
       uses apply-advanced;
       list ie {
         key name;
         description "Set IE number";
         uses ie-filter-object;
       }
     }
     list message-ie-profile-v2 {
       key name;
       description "Set GTP message IE filter profile";
       max-elements 10;
       leaf name {
         description "Set message IE filter profile name";
         type string {
           length "1 .. 23";
         }
       }
       uses apply-advanced;
       list message {
         key name;
         description "Set message type";
         leaf name {
           description "Set message type";
           type union {
             type string {
               pattern "<.*>|$.*";
             }
             type uint8 {
               range "1 .. 255";
             }
           }
         }
         uses apply-advanced;
         list ie {
           key name;
           description "Set IE number";
           uses ie-filter-object;
         }
       }
     }
     list message-list {
       key name;
       description "Set message list";
       max-elements 10;
       leaf name {
         description "Set message list name";
         type string {
           length "1 .. 23";
         }
       }
       uses apply-advanced;
       list message {
         key name;
         description "Set message type";
         leaf name {
           description "Set message type";
           type union {
             type string {
               pattern "<.*>|$.*";
             }
             type uint8 {
               range "1 .. 255";
             }
           }
         }
         uses apply-advanced;
       }
     }
     list rate-limit {
       key name;
       description "Limiting message rate";
       leaf name {
         description "Rate limit policy name";
         type enumeration {
           enum "default" {
             description "Default rate limit policy name";
           }
         }
       }
       uses apply-advanced;
       container message {
         description "GTP limited message type";
         uses message-object;
       }
     }
     list apn-control {
       key name;
       description "GTP APN control profile";
       max-elements 1024;
       leaf name {
         description "APN control profile name";
         type string {
           length "1 .. 23";
         }
       }
       uses apply-advanced;
       container apn {
         description "APN of the APN control profile";
         uses apply-advanced;
         leaf apn-string {
           description "APN string";
           type string {
             length "1 .. 100";
           }
         }
       }
       container rate-limit {
         description "APN controlled rate-limit";
         presence "enable rate-limit";
         uses rate-limit-object;
       }
     }
     list apn-control-group {
       key name;
       description "GTP APN control profile group";
       max-elements 1024;
       leaf name {
         description "APN control profile group name";
         type string {
           length "1 .. 23";
         }
       }
       uses apply-advanced;
       list apn-control {
         key name;
         description "APN control profile";
         leaf name {
           description "APN control profile name";
           junos:must "((\"security gprs gtp apn-control $$\" || \"security gtp apn-control $$\"))";
           junos:must-message "referenced apn-control profile not found";
           type string {
             length "1 .. 23";
           }
         }
         uses apply-advanced;
       }
     }
   }
   grouping ha-object {
     uses apply-advanced;
     container aws {
       uses apply-advanced;
       choice service-ctrl {
         case case_1 {
           leaf eip-based {
             description "EIP";
             type empty;
           }
         }
       }
       container peer-liveliness {
         presence "enable peer-liveliness";
         description "Configure peer-liveliness probe method";
         uses apply-advanced;
         container probe-ip {
           description "Using IP for activeness probe";
           leaf destination-ip {
             description "Destination IPv4 address for activeness probe";
             type jt:ipv4addr;
           }
           leaf source-ip {
             description "Source IPV4 address for activeness probe";
             type jt:ipv4addr;
           }
           leaf routing-instance {
             description "Routing instance name";
             junos:must "(\"routing-instances  $$\")";
             junos:must-message "Routing-instances must be defined";
             type string;
           }
         }
       }
     }
   }
   grouping icap-profile-object {
     leaf name {
       description "ICAP service profile name";
       type string {
         length "1 .. 63";
         junos:posix-pattern "^[[:alnum:]][[:alnum:]_-]*$";
         junos:pattern-message "Must be a string beginning with a number or letter and consisting of letters, numbers, dashes and underscores.";
       }
     }
     uses apply-advanced;
     list server {
       key name;
       ordered-by user;
       description "Configure service redirection server";
       max-elements 16;
       uses icap-redir-server;
     }
     container http {
       description "ICAP methods switch";
       uses http-redirect-object;
     }
     container fallback-option {
       description "Failure event actions";
       uses icap-redirect-fallback;
     }
     leaf timeout {
       description "Server response timeout in milliseconds";
       default "500";
       type union {
         type string {
           pattern "<.*>|$.*";
         }
         type uint16 {
           range "100 .. 50000";
         }
       }
     }
   }
   grouping http-redirect-object {
     uses apply-advanced;
     leaf redirect-request {
       description "Enable redirect service on HTTP request";
       type empty;
     }
     leaf redirect-response {
       description "Enable redirect service on HTTP response";
       type empty;
     }
   }
   grouping icap-redir-server {
     leaf name {
       description "Server name";
       type string {
         length "1 .. 63";
         junos:posix-pattern "^[[:alnum:]][[:alnum:]_-]*$";
         junos:pattern-message "Must be a string beginning with a number or letter and consisting of letters, numbers, dashes and underscores.";
       }
     }
     uses apply-advanced;
     container authorization {
       description "User authentication";
       uses apply-advanced;
       leaf authorization-type {
         description "Authentication type. 'Basic' by default";
         type string {
           length "1 .. 127";
         }
       }
       container credentials {
         description "Credentials text";
         choice credentials-choice {
           case case_1 {
             leaf ascii {
               description "ASCII string";
               type string {
                 length "1 .. 511";
               }
             }
           }
           case case_2 {
             leaf base64 {
               description "Base64 string";
               type string {
                 length "1 .. 511";
               }
             }
           }
         }
       }
     }
     leaf host {
       description "Host name/IP address";
       type string {
         length "1 .. 255";
       }
     }
     leaf port {
       description "Server listening port";
       default "1344";
       type union {
         type string {
           pattern "<.*>|$.*";
         }
         type uint16 {
           range "1025 .. 65535";
         }
       }
     }
     leaf reqmod-uri {
       description "REQMOD option resource identifier";
       type string {
         length "0 .. 1023";
       }
     }
     leaf respmod-uri {
       description "RESPMOD option resource identifier";
       type string {
         length "0 .. 1023";
       }
     }
     container routing-instance {
       description "Routing instance";
       leaf ri-name {
         description "Routing instance name";
         junos:must "(\"routing-instances $$ instance-type virtual-router\")";
         junos:must-message "Virtual router must be defined under [routing-instances]";
         junos:must "(\"routing-instances $$\")";
         junos:must-message "Routing-instance must be defined";
         type string {
           length "1 .. 127";
           junos:posix-pattern "!^((__.*__)|(all)|(.*[ ].*)|(\"\")|(.{129,}))$";
           junos:pattern-message "Must be a non-reserved string of 128 characters or less with no spaces.";
         }
       }
     }
     leaf sockets {
       description "Number of connections to create";
       default "8";
       type union {
         type string {
           pattern "<.*>|$.*";
         }
         type uint8 {
           range "1 .. 64";
         }
       }
     }
     leaf tls-profile {
       description "TLS profile";
       junos:must "(\"services ssl initiation profile $$\")";
       junos:must-message "Referenced SSL initiation profile is not defined";
       type string {
         length "1 .. 63";
       }
     }
   }
   grouping icap-redirect-fallback {
     uses apply-advanced;
     leaf timeout {
       description "Request timeout action";
       default "permit";
       type enumeration {
         enum "permit" {
           description "Direct permit action";
         }
         enum "log-permit" {
           description "Log then permit action";
         }
         enum "block" {
           description "Block action";
         }
       }
     }
     leaf connectivity {
       description "Connection-related failure action";
       default "permit";
       type enumeration {
         enum "permit" {
           description "Direct permit action";
         }
         enum "log-permit" {
           description "Log then permit action";
         }
         enum "block" {
           description "Block action";
         }
       }
     }
     leaf default-action {
       description "Default failure action";
       default "permit";
       type enumeration {
         enum "permit" {
           description "Direct permit action";
         }
         enum "log-permit" {
           description "Log then permit action";
         }
         enum "block" {
           description "Block action";
         }
       }
     }
   }
   grouping icap-redirect-traceoptions {
     description "ICAP redirect traceoptions";
     uses apply-advanced;
     leaf no-remote-trace {
       description "Disable remote tracing";
       junos:must "(\"system tracing\")";
       junos:must-message "'no-remote-trace' is valid only when [system tracing] is configured";
       type empty;
     }
     container file {
       description "Trace file information";
       leaf filename {
         description "Name of file in which to write trace information";
         type string {
           length "1 .. 1024";
           junos:posix-pattern "![/ %]";
           junos:pattern-message "Must not contain '/', % or a space";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     list flag {
       key name;
       ordered-by user;
       description "Trace flags";
       leaf name {
         type enumeration {
           enum "all" {
             description "Trace everything";
           }
           enum "icap-redirect-re" {
             description "Trace events on RE side";
           }
           enum "icap-redirect-control" {
             description "Trace events on PFE-ukernel side";
           }
           enum "icap-redirect-connection" {
             description "Trace ICAP server connection events";
           }
           enum "icap-redirect-protocol" {
             description "Trace redirect packet events";
           }
         }
       }
     }
   }
   grouping identity-management-connection-type {
     description "Identity management connection";
     uses apply-advanced;
     leaf connect-method {
       description "Method of connection";
       type enumeration {
         enum "https" {
           description "HTTPS connection";
         }
         enum "http" {
           description "HTTP connection";
         }
       }
     }
     leaf port {
       description "Server port";
       default "443";
       type union {
         type string {
           pattern "<.*>|$.*";
         }
         type uint32 {
           range "1 .. 65535";
         }
       }
     }
     container primary {
       description "Primary server";
       uses identity-server-connection-type;
     }
     container secondary {
       description "Secondary server";
       uses identity-server-connection-type;
     }
     leaf token-api {
       description "API of acquiring token for OAuth2 authentication";
       type string {
         length "1 .. 128";
       }
     }
     leaf query-api {
       description "Query API";
       type string {
         length "4 .. 128";
       }
     }
   }
   grouping identity-server-connection-type {
     description "Connection parameters per server";
     uses apply-advanced;
     leaf address {
       description "Server address";
       type jt:ipaddr;
     }
     leaf ca-certificate {
       description "Ca-certificate file name";
       type string {
         length "1 .. 256";
       }
     }
     leaf client-id {
       description "Client ID for OAuth2 grant";
       type string {
         length "1 .. 64";
       }
     }
     leaf client-secret {
       description "Client secret for OAuth2 grant";
       type string {
         length "1 .. 128";
       }
     }
     leaf source {
       description "Client address";
       type jt:ipaddr;
     }
     leaf interface {
       description "Interface name";
       type union {
         type jt:interface-name;
         type string {
           pattern "<.*>|$.*";
         }
       }
     }
     leaf routing-instance {
       description "Routing instance name";
       junos:must "(\"routing-instances $$\")";
       junos:must-message "Routing-instance must be defined";
       type string;
     }
   }
   grouping idp-policy-type {
     leaf name {
       description "IDP policy name";
       type string;
     }
     container rulebase-ips {
       description "IPS rulebase";
       uses apply-advanced;
       list rule {
         key name;
         ordered-by user;
         description "Configure IPS rule";
         leaf name {
           description "Rule name";
           type string;
         }
         uses apply-advanced;
         leaf description {
           description "Rule description";
           type string;
         }
         container match {
           description "Rule match criteria";
           uses apply-advanced;
           leaf from-zone {
             description "Match from zone";
             default "any";
             junos:must "((\".. from-zone any\" || \"security zones security-zone $$\"))";
             junos:must-message "from-zone should be 'any' or configured under [security zones security-zone]";
             type string;
           }
           choice source {
             case case_1 {
               leaf-list source-address {
                 ordered-by user;
                 description "Match source address";
                 type string;
               }
             }
             case case_2 {
               leaf-list source-except {
                 ordered-by user;
                 description "Don't match source address";
                 type string;
               }
             }
             case case_3 {
               leaf-list source-prefix {
                 ordered-by user;
                 description "Match source address";
                 type jt:ipv4prefix;
               }
             }
             case case_4 {
               leaf-list source-prefix-except {
                 ordered-by user;
                 description "Don't match source address";
                 type jt:ipv4prefix;
               }
             }
           }
           leaf to-zone {
             description "Match to zone";
             default "any";
             junos:must "((\".. to-zone any\" || \"security zones security-zone $$\"))";
             junos:must-message "to-zone should be 'any' or configured under [security zones security-zone]";
             type string;
           }
           choice destination {
             case case_1 {
               leaf-list destination-address {
                 ordered-by user;
                 description "Match destination address";
                 type string;
               }
             }
             case case_2 {
               leaf-list destination-except {
                 ordered-by user;
                 description "Don't match destination address";
                 type string;
               }
             }
             case case_3 {
               leaf-list destination-prefix {
                 ordered-by user;
                 description "Match destination address";
                 type jt:ipv4prefix;
               }
             }
             case case_4 {
               leaf-list destination-prefix-except {
                 ordered-by user;
                 description "Don't match destination address";
                 type jt:ipv4prefix;
               }
             }
           }
           leaf application {
             description "Specify application or application-set name to match";
             type string;
           }
           container attacks {
             description "Match attack objects";
             uses apply-advanced;
             leaf-list custom-attacks {
               ordered-by user;
               description "Custom attacks";
               type string;
             }
             leaf-list custom-attack-groups {
               ordered-by user;
               description "Custom attack groups";
               type string;
             }
             leaf-list dynamic-attack-groups {
               ordered-by user;
               description "Dynamic attack groups";
               type string;
             }
             leaf-list predefined-attacks {
               ordered-by user;
               description "Predefined attacks";
               type string;
             }
             leaf-list predefined-attack-groups {
               ordered-by user;
               description "Predefined attack groups";
               type string;
             }
           }
         }
         container then {
           uses apply-advanced;
           container action {
             choice action {
               case case_1 {
                 leaf no-action {
                   description "No action";
                   type empty;
                 }
               }
               case case_2 {
                 leaf ignore-connection {
                   description "Ignore";
                   type empty;
                 }
               }
               case case_3 {
                 container mark-diffserv {
                   description "Mark differentiated services codepoint (DSCP)";
                   uses apply-advanced;
                   leaf codepoint {
                     description "Codepoint value";
                     type union {
                       type string {
                         pattern "<.*>|$.*";
                       }
                       type uint32 {
                         range "0 .. 63";
                       }
                     }
                   }
                 }
               }
               case case_4 {
                 container class-of-service {
                   description "Classification of traffic based on class-of-service";
                   uses apply-advanced;
                   leaf forwarding-class {
                     description "Forwarding class for outgoing packets";
                     type string {
                       junos:posix-pattern "^.{1,64}$";
                       junos:pattern-message "Must be string of 64 characters or less";
                     }
                   }
                   leaf dscp-code-point {
                     description "Differentiated services code point value";
                     type union {
                       type string {
                         pattern "<.*>|$.*";
                       }
                       type uint32 {
                         range "0 .. 63";
                       }
                     }
                   }
                 }
               }
               case case_5 {
                 leaf drop-packet {
                   description "Drop packet";
                   type empty;
                 }
               }
               case case_6 {
                 leaf drop-connection {
                   description "Drop connection";
                   type empty;
                 }
               }
               case case_7 {
                 leaf close-client {
                   description "Close client";
                   type empty;
                 }
               }
               case case_8 {
                 leaf close-server {
                   description "Close server";
                   type empty;
                 }
               }
               case case_9 {
                 leaf close-client-and-server {
                   description "Close client and server";
                   type empty;
                 }
               }
               case case_10 {
                 leaf recommended {
                   description "Recommended";
                   junos:must "(\".. .. .. match attacks\")";
                   junos:must-message "attacks must also be configured.";
                   type empty;
                 }
               }
             }
           }
           container ip-action {
             uses apply-advanced;
             choice ip-action {
               case case_1 {
                 leaf ip-notify {
                   description "Notify about future traffic";
                   type empty;
                 }
               }
               case case_2 {
                 leaf ip-close {
                   description "Close future connections";
                   type empty;
                 }
               }
               case case_3 {
                 leaf ip-block {
                   description "Block future connections";
                   type empty;
                 }
               }
             }
             leaf target {
               type enumeration {
                 enum "service" {
                   description "Match source, destination, dst-port and protocol";
                 }
                 enum "source-zone-address" {
                   description "Match source-zone and source-address";
                 }
                 enum "source-address" {
                   description "Match source";
                 }
                 enum "destination-address" {
                   description "Match destination";
                 }
                 enum "zone-service" {
                   description "Match source-zone, destination, dst-port, protocol";
                 }
                 enum "source-zone" {
                   description "Match source-zone";
                 }
               }
             }
             leaf log {
               description "Log IP action taken";
               type empty;
             }
             leaf log-create {
               description "Log IP action creation";
               type empty;
             }
             leaf timeout {
               description "Number of seconds IP action should remain effective";
               type union {
                 type string {
                   pattern "<.*>|$.*";
                 }
                 type uint32 {
                   range "0 .. 64800";
                 }
               }
             }
             leaf refresh-timeout {
               description "Refresh timeout when future connections match installed ip-action filter";
               junos:must "(\".. timeout\")";
               junos:must-message "timeout must be specified";
               type empty;
             }
           }
           container notification {
             presence "enable notification";
             description "Configure notification/logging options";
             uses apply-advanced;
             container log-attacks {
               presence "enable log-attacks";
               description "Enable attack logging";
               uses apply-advanced;
               leaf alert {
                 description "Set alert flag in attack log";
                 type empty;
               }
             }
             container packet-log {
               presence "enable packet-log";
               uses apply-advanced;
               leaf pre-attack {
                 description "No of packets to capture before attack";
                 default "1";
                 type union {
                   type string {
                     pattern "<.*>|$.*";
                   }
                   type uint32 {
                     range "1 .. 255";
                   }
                 }
               }
               leaf post-attack {
                 description "No of packets to capture after attack";
                 type union {
                   type string {
                     pattern "<.*>|$.*";
                   }
                   type uint32 {
                     range "0 .. 255";
                   }
                 }
               }
               leaf post-attack-timeout {
                 description "Timeout (seconds) after attack before stopping packet capture";
                 default "5";
                 type union {
                   type string {
                     pattern "<.*>|$.*";
                   }
                   type uint32 {
                     range "0 .. 1800";
                   }
                 }
               }
             }
           }
           leaf severity {
             description "Set rule severity level";
             type enumeration {
               enum "info" {
               }
               enum "warning" {
               }
               enum "minor" {
               }
               enum "major" {
               }
               enum "critical" {
               }
             }
           }
           container application-services {
             description "Enable application services for this rule";
             container security-intelligence {
               description "Generate security intellegence feeds";
               leaf add-attacker-ip-to-feed {
                 description "Specify the desired feed-name";
                 type string {
                   length "1 .. 64";
                 }
               }
               leaf add-target-ip-to-feed {
                 description "Specify the desired feed-name";
                 type string {
                   length "1 .. 64";
                 }
               }
             }
           }
         }
         leaf terminal {
           description "Set/Unset terminal flag";
           type empty;
         }
       }
     }
     container rulebase-exempt {
       description "Exempt rulebase";
       uses apply-advanced;
       list rule {
         key name;
         ordered-by user;
         description "Configure exempt rule";
         leaf name {
           description "Rule name";
           type string;
         }
         uses apply-advanced;
         leaf description {
           description "Rule description";
           type string;
         }
         container match {
           description "Rule match criteria";
           uses apply-advanced;
           leaf from-zone {
             description "Match from zone";
             default "any";
             junos:must "((\".. from-zone any\" || \"security zones security-zone $$\"))";
             junos:must-message "from-zone should be 'any' or configured under [security zones security-zone]";
             type string;
           }
           choice source {
             case case_1 {
               leaf-list source-address {
                 ordered-by user;
                 description "Match source address";
                 type string;
               }
             }
             case case_2 {
               leaf-list source-except {
                 ordered-by user;
                 description "Don't match source address";
                 type string;
               }
             }
             case case_3 {
               leaf-list source-prefix {
                 ordered-by user;
                 description "Match source address";
                 type jt:ipv4prefix;
               }
             }
             case case_4 {
               leaf-list source-prefix-except {
                 ordered-by user;
                 description "Don't match source address";
                 type jt:ipv4prefix;
               }
             }
           }
           leaf to-zone {
             description "Match to zone";
             default "any";
             junos:must "((\".. to-zone any\" || \"security zones security-zone $$\"))";
             junos:must-message "to-zone should be 'any' or configured under [security zones security-zone]";
             type string;
           }
           choice destination {
             case case_1 {
               leaf-list destination-address {
                 ordered-by user;
                 description "Match destination address";
                 type string;
               }
             }
             case case_2 {
               leaf-list destination-except {
                 ordered-by user;
                 description "Don't match destination address";
                 type string;
               }
             }
             case case_3 {
               leaf-list destination-prefix {
                 ordered-by user;
                 description "Match destination address";
                 type jt:ipv4prefix;
               }
             }
             case case_4 {
               leaf-list destination-prefix-except {
                 ordered-by user;
                 description "Don't match destination address";
                 type jt:ipv4prefix;
               }
             }
           }
           container attacks {
             description "Match attack objects";
             uses apply-advanced;
             leaf-list custom-attacks {
               ordered-by user;
               description "Custom attacks";
               type string;
             }
             leaf-list custom-attack-groups {
               ordered-by user;
               description "Custom attack groups";
               type string;
             }
             leaf-list dynamic-attack-groups {
               ordered-by user;
               description "Dynamic attack groups";
               type string;
             }
             leaf-list predefined-attacks {
               ordered-by user;
               description "Predefined attacks";
               type string;
             }
             leaf-list predefined-attack-groups {
               ordered-by user;
               description "Predefined attack groups";
               type string;
             }
           }
         }
       }
     }
   }
   grouping idpd-traceoptions-type {
     description "Trace options for idpd";
     uses apply-advanced;
     leaf no-remote-trace {
       description "Disable remote tracing";
       junos:must "(\"system tracing\")";
       junos:must-message "'no-remote-trace' is valid only when [system tracing] is configured";
       type empty;
     }
     container file {
       description "Trace file information";
       leaf filename {
         description "Name of file in which to write trace information";
         type string {
           length "1 .. 1024";
           junos:posix-pattern "![/ %]";
           junos:pattern-message "Must not contain '/', % or a space";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     list flag {
       key name;
       ordered-by user;
       description "Events and other information to include in trace output";
       leaf name {
         description "Flag name to include in trace output";
         type enumeration {
           enum "all" {
             description "All events";
           }
         }
       }
     }
     leaf level {
       description "Level of debugging output";
       default "error";
       type enumeration {
         enum "error" {
           description "Match error conditions";
         }
         enum "warning" {
           description "Match warning messages";
         }
         enum "notice" {
           description "Match conditions that should be handled specially";
         }
         enum "info" {
           description "Match informational messages";
         }
         enum "verbose" {
           description "Match verbose messages";
         }
         enum "all" {
           description "Match all levels";
         }
       }
     }
   }
   grouping ids-option-type {
     description "Configure screen object";
     leaf name {
       description "Screen object name";
       type string {
         length "1 .. 64";
       }
     }
     uses apply-advanced;
     leaf description {
       description "Text description of screen";
       type string {
         length "1 .. 900";
         junos:posix-pattern "^[^&<>\n]+$";
         junos:pattern-message "Must be a string excluding '&', '<', '>' and '\n'";
       }
     }
     leaf alarm-without-drop {
       description "Do not drop packet, only generate alarm";
       type empty;
     }
     leaf match-direction {
       description "Match direction";
       type enumeration {
         enum "input" {
           description "Match on input to interface";
         }
         enum "output" {
           description "Match on output from interface";
         }
         enum "input-output" {
           description "Match on input to or output from interface";
         }
       }
     }
     container aggregation {
       presence "enable aggregation";
       description "Configure the source and Destination prefix for a ids-option";
       uses apply-advanced;
       leaf source-prefix-mask {
         description "Source IPV4 prefix";
         type union {
           type string {
             pattern "<.*>|$.*";
           }
           type uint32 {
             range "1 .. 32";
           }
         }
       }
       leaf destination-prefix-mask {
         description "Destination IPV4 prefix";
         type union {
           type string {
             pattern "<.*>|$.*";
           }
           type uint32 {
             range "1 .. 32";
           }
         }
       }
       leaf source-prefix-v6-mask {
         description "Source IPV6 prefix";
         type union {
           type string {
             pattern "<.*>|$.*";
           }
           type uint32 {
             range "1 .. 128";
           }
         }
       }
       leaf destination-prefix-v6-mask {
         description "Destination IPV6 prefix";
         type union {
           type string {
             pattern "<.*>|$.*";
           }
           type uint32 {
             range "1 .. 128";
           }
         }
       }
     }
     container icmp {
       description "Configure ICMP ids options";
       uses apply-advanced;
       container ip-sweep {
         presence "enable ip-sweep";
         description "Configure ip sweep ids option";
         leaf threshold {
           description "Threshold";
           default "5000";
           units "microseconds in which 10 ICMP packets are detected";
           type union {
             type string {
               pattern "<.*>|$.*";
             }
             type uint32 {
               range "1000 .. 1000000";
             }
           }
         }
       }
       leaf fragment {
         description "Enable ICMP fragment ids option";
         type empty;
       }
       leaf large {
         description "Enable large ICMP packet (size > 1024) ids option";
         type empty;
       }
       container flood {
         presence "enable flood";
         description "Configure icmp flood ids option";
         leaf threshold {
           description "Threshold";
           default "1000";
           units "ICMP packets per second";
           type union {
             type string {
               pattern "<.*>|$.*";
             }
             type uint32;
           }
         }
       }
       leaf ping-death {
         description "Enable ping of death ids option";
         type empty;
       }
       leaf icmpv6-malformed {
         description "Enable icmpv6 malformed ids option";
         type empty;
       }
     }
     container ip {
       description "Configure IP layer ids options";
       uses apply-advanced;
       leaf bad-option {
         description "Enable ip with bad option ids option";
         type empty;
       }
       leaf record-route-option {
         description "Enable ip with record route option ids option";
         type empty;
       }
       leaf timestamp-option {
         description "Enable ip with timestamp option ids option";
         type empty;
       }
       leaf security-option {
         description "Enable ip with security option ids option";
         type empty;
       }
       leaf stream-option {
         description "Enable ip with stream option ids option";
         type empty;
       }
       leaf spoofing {
         description "Enable IP address spoofing ids option";
         type empty;
       }
       leaf source-route-option {
         description "Enable ip source route ids option";
         type empty;
       }
       leaf loose-source-route-option {
         description "Enable ip with loose source route ids option";
         type empty;
       }
       leaf strict-source-route-option {
         description "Enable ip with strict source route ids option";
         type empty;
       }
       leaf unknown-protocol {
         description "Enable ip unknown protocol ids option";
         type empty;
       }
       leaf block-frag {
         description "Enable ip fragment blocking ids option";
         type empty;
       }
       leaf tear-drop {
         description "Enable tear drop ids option";
         type empty;
       }
       container ipv6-extension-header {
         description "Configure ipv6 extension header ids option";
         uses apply-advanced;
         container hop-by-hop-header {
           presence "enable hop-by-hop-header";
           description "Enable ipv6 hop by hop option header ids option";
           uses apply-advanced;
           leaf jumbo-payload-option {
             description "Enable jumbo payload option ids option";
             type empty;
           }
           leaf router-alert-option {
             description "Enable router alert option ids option";
             type empty;
           }
           leaf quick-start-option {
             description "Enable quick start option ids option";
             type empty;
           }
           leaf CALIPSO-option {
             description "Enable Common Architecture Label ipv6 Security Option ids option";
             type empty;
           }
           leaf SMF-DPD-option {
             description "Enable Simplified Multicast Forwarding ipv6 Duplicate Packet Detection option ids option";
             type empty;
           }
           leaf RPL-option {
             description "Enable Routing Protocol for Low-power and Lossy networks option ids option";
             type empty;
           }
           list user-defined-option-type {
             key name;
             ordered-by user;
             description "User-defined option type range";
             max-elements 256;
             leaf name {
               description "User-defined option type low value";
               type union {
                 type string {
                   pattern "<.*>|$.*";
                 }
                 type uint32 {
                   range "1 .. 255";
                 }
               }
             }
             container to {
               description "Upper limit of option type range";
               uses apply-advanced;
               leaf type-high {
                 description "User-defined option type high value";
                 type union {
                   type string {
                     pattern "<.*>|$.*";
                   }
                   type uint32 {
                     range "1 .. 255";
                   }
                 }
               }
             }
           }
         }
         leaf routing-header {
           description "Enable ipv6 routing header ids option";
           type empty;
         }
         leaf fragment-header {
           description "Enable ipv6 fragment header ids option";
           type empty;
         }
         leaf ESP-header {
           description "Enable ipv6 Encapsulating Security Payload header ids option";
           type empty;
         }
         leaf AH-header {
           description "Enable ipv6 Authentication Header ids option";
           type empty;
         }
         leaf no-next-header {
           description "Enable ipv6 no next header ids option";
           type empty;
         }
         container destination-header {
           presence "enable destination-header";
           description "Enable ipv6 destination option header ids option";
           uses apply-advanced;
           leaf tunnel-encapsulation-limit-option {
             description "Enable tunnel encapsulation limit option ids option";
             type empty;
           }
           leaf home-address-option {
             description "Enable home address option ids option";
             type empty;
           }
           leaf ILNP-nonce-option {
             description "Enable Identifier-Locator Network Protocol Nonce option ids option";
             type empty;
           }
           leaf line-identification-option {
             description "Enable line identification option ids option";
             type empty;
           }
           list user-defined-option-type {
             key name;
             ordered-by user;
             description "User-defined option type range";
             max-elements 256;
             leaf name {
               description "User-defined option type low value";
               type union {
                 type string {
                   pattern "<.*>|$.*";
                 }
                 type uint32 {
                   range "1 .. 255";
                 }
               }
             }
             container to {
               description "Upper limit of option type range";
               uses apply-advanced;
               leaf type-high {
                 description "User-defined option type high value";
                 type union {
                   type string {
                     pattern "<.*>|$.*";
                   }
                   type uint32 {
                     range "1 .. 255";
                   }
                 }
               }
             }
           }
         }
         leaf shim6-header {
           description "Enable ipv6 shim header ids option";
           type empty;
         }
         leaf mobility-header {
           description "Enable ipv6 mobility header ids option";
           type empty;
         }
         leaf HIP-header {
           description "Enable ipv6 Host Identify Protocol header ids option";
           type empty;
         }
         list user-defined-header-type {
           key name;
           ordered-by user;
           description "User-defined header type range";
           max-elements 256;
           leaf name {
             description "User-defined header type low value";
             type union {
               type string {
                 pattern "<.*>|$.*";
               }
               type uint32 {
                 range "0 .. 255";
               }
             }
           }
           container to {
             description "Upper limit of header type range";
             uses apply-advanced;
             leaf type-high {
               description "User-defined header type high value";
               type union {
                 type string {
                   pattern "<.*>|$.*";
                 }
                 type uint32 {
                   range "0 .. 255";
                 }
               }
             }
           }
         }
       }
       leaf ipv6-extension-header-limit {
         description "Enable ipv6 extension header limit ids option";
         type union {
           type string {
             pattern "<.*>|$.*";
           }
           type uint32 {
             range "0 .. 32";
           }
         }
       }
       leaf ipv6-malformed-header {
         description "Enable ipv6 malformed header ids option";
         type empty;
       }
       container tunnel {
         description "Configure IP tunnel ids options";
         uses apply-advanced;
         leaf bad-inner-header {
           description "Enable IP tunnel bad inner header ids option";
           type empty;
         }
         container gre {
           description "Configure IP tunnel GRE ids option";
           uses apply-advanced;
           leaf gre-6in4 {
             description "Enable IP tunnel GRE 6in4 ids option";
             type empty;
           }
           leaf gre-4in6 {
             description "Enable IP tunnel GRE 4in6 ids option";
             type empty;
           }
           leaf gre-6in6 {
             description "Enable IP tunnel GRE 6in6 ids option";
             type empty;
           }
           leaf gre-4in4 {
             description "Enable IP tunnel GRE 4in4 ids option";
             type empty;
           }
         }
         container ip-in-udp {
           description "Configure IP tunnel IPinUDP ids option";
           uses apply-advanced;
           leaf teredo {
             description "Enable IP tunnel IPinUDP Teredo ids option";
             type empty;
           }
         }
         container ipip {
           description "Configure IP tunnel IPIP ids option";
           uses apply-advanced;
           leaf ipip-6to4relay {
             description "Enable IP tunnel IPIP 6to4 Relay ids option";
             type empty;
           }
           leaf ipip-6in4 {
             description "Enable IP tunnel IPIP 6in4 ids option";
             type empty;
           }
           leaf ipip-4in6 {
             description "Enable IP tunnel IPIP 4in6 ids option";
             type empty;
           }
           leaf ipip-4in4 {
             description "Enable IP tunnel IPIP 4in4 ids option";
             type empty;
           }
           leaf ipip-6in6 {
             description "Enable IP tunnel IPIP 6in6 ids option";
             type empty;
           }
           leaf ipip-6over4 {
             description "Enable IP tunnel IPIP 6over4 ids option";
             type empty;
           }
           leaf isatap {
             description "Enable IP tunnel IPIP ISATAP ids option";
             type empty;
           }
           leaf dslite {
             description "Enable IP tunnel IPIP DS-Lite ids option";
             type empty;
           }
         }
       }
     }
     container tcp {
       description "Configure TCP Layer ids options";
       uses apply-advanced;
       leaf syn-fin {
         description "Enable SYN and FIN bits set attack ids option";
         type empty;
       }
       leaf fin-no-ack {
         description "Enable Fin bit with no ACK bit ids option";
         type empty;
       }
       leaf tcp-no-flag {
         description "Enable TCP packet without flag ids option";
         type empty;
       }
       leaf syn-frag {
         description "Enable SYN fragment ids option";
         type empty;
       }
       leaf syn-defense {
         description "Enable tcp syn-defense";
         type empty;
       }
       container port-scan {
         presence "enable port-scan";
         description "Configure TCP port scan ids option";
         leaf threshold {
           description "Threshold";
           default "5000";
           units "microseconds in which 10 attack packets are detected";
           type union {
             type string {
               pattern "<.*>|$.*";
             }
             type uint32 {
               range "1000 .. 1000000";
             }
           }
         }
       }
       container syn-ack-ack-proxy {
         presence "enable syn-ack-ack-proxy";
         description "Configure syn-ack-ack proxy ids option";
         leaf threshold {
           description "Threshold";
           default "512";
           units "un-authenticated connections";
           type union {
             type string {
               pattern "<.*>|$.*";
             }
             type uint32 {
               range "1 .. 250000";
             }
           }
         }
       }
       container syn-flood {
         presence "enable syn-flood";
         description "Configure SYN flood ids option";
         uses apply-advanced;
         leaf alarm-threshold {
           description "Alarm threshold";
           default "512";
           units "requests per second";
           type union {
             type string {
               pattern "<.*>|$.*";
             }
             type uint32;
           }
         }
         leaf attack-threshold {
           description "Attack threshold";
           default "200";
           units "proxied requests per second";
           type union {
             type string {
               pattern "<.*>|$.*";
             }
             type uint32;
           }
         }
         leaf source-threshold {
           description "Source threshold";
           default "4000";
           units "SYN pps";
           type union {
             type string {
               pattern "<.*>|$.*";
             }
             type uint32;
           }
         }
         leaf destination-threshold {
           description "Destination threshold";
           default "4000";
           units "SYN pps";
           type union {
             type string {
               pattern "<.*>|$.*";
             }
             type uint32;
           }
         }
         leaf queue-size {
           description "Queue size";
           status deprecated;
           default "1024";
           units "proxied requests in queue";
           type union {
             type string {
               pattern "<.*>|$.*";
             }
             type uint32 {
               range "200 .. 20000";
             }
           }
         }
         leaf timeout {
           description "SYN flood ager timeout";
           default "20";
           units "seconds";
           type union {
             type string {
               pattern "<.*>|$.*";
             }
             type uint32 {
               range "1 .. 50";
             }
           }
         }
         list white-list {
           key name;
           description "Set of IP addresses that will not trigger a screen";
           max-elements 2;
           leaf name {
             description "White-list name";
             type string {
               length "1 .. 32";
               junos:posix-pattern "^[[:alnum:]][[:alnum:]_-]*$";
               junos:pattern-message "Must be a string beginning with a number or letter and consisting of letters, numbers, dashes and underscores.";
             }
           }
           uses apply-advanced;
           leaf-list source-address {
             ordered-by user;
             description "Source address";
             type jt:ipprefix;
             max-elements 32;
           }
           leaf-list destination-address {
             ordered-by user;
             description "Destination address";
             type jt:ipprefix;
             max-elements 32;
           }
         }
       }
       leaf land {
         description "Enable land attack ids option";
         type empty;
       }
       leaf winnuke {
         description "Enable winnuke attack ids option";
         type empty;
       }
       container tcp-sweep {
         presence "enable tcp-sweep";
         description "Configure TCP sweep ids option";
         leaf threshold {
           description "Threshold";
           default "5000";
           units "microseconds in which 10 TCP packets are detected";
           type union {
             type string {
               pattern "<.*>|$.*";
             }
             type uint32 {
               range "1000 .. 1000000";
             }
           }
         }
       }
     }
     container udp {
       description "Configure UDP layer ids options";
       uses apply-advanced;
       container flood {
         presence "enable flood";
         description "Configure UDP flood ids option";
         uses apply-advanced;
         leaf threshold {
           description "Threshold";
           default "1000";
           units "UDP packets per second";
           type union {
             type string {
               pattern "<.*>|$.*";
             }
             type uint32;
           }
         }
         leaf-list white-list {
           ordered-by user;
           description "Configure UDP flood white list group name";
           type string;
           max-elements 2;
         }
       }
       container udp-sweep {
         presence "enable udp-sweep";
         description "Configure UDP sweep ids option";
         leaf threshold {
           description "Threshold";
           default "5000";
           units "microseconds in which 10 UDP packets are detected";
           type union {
             type string {
               pattern "<.*>|$.*";
             }
             type uint32 {
               range "1000 .. 1000000";
             }
           }
         }
       }
       container port-scan {
         presence "enable port-scan";
         description "Configure UDP port scan ids option";
         leaf threshold {
           description "Threshold";
           default "5000";
           units "microseconds in which 10 attack packets are detected";
           type union {
             type string {
               pattern "<.*>|$.*";
             }
             type uint32 {
               range "1000 .. 1000000";
             }
           }
         }
       }
     }
     container limit-session {
       description "Limit sessions";
       uses apply-advanced;
       leaf source-ip-based {
         description "Limit sessions from the same source IP";
         type union {
           type string {
             pattern "<.*>|$.*";
           }
           type uint32;
         }
       }
       leaf destination-ip-based {
         description "Limit sessions to the same destination IP";
         type union {
           type string {
             pattern "<.*>|$.*";
           }
           type uint32;
         }
       }
       container by-source {
         presence "enable by-source";
         description "Limit sessions from the same source IP or subnet";
         uses apply-advanced;
         leaf maximum-sessions {
           description "Limit sessions on the basis of maximum concurrent sessions";
           type union {
             type string {
               pattern "<.*>|$.*";
             }
             type uint32;
           }
         }
         leaf packet-rate {
           description "Limit sessions on the basis of packet rate";
           type union {
             type string {
               pattern "<.*>|$.*";
             }
             type uint32 {
               range "1 .. 4294967295";
             }
           }
         }
         leaf session-rate {
           description "Limit sessions on the basis of session rate";
           type union {
             type string {
               pattern "<.*>|$.*";
             }
             type uint32 {
               range "1 .. 4294967295";
             }
           }
         }
         container by-protocol {
           description "Limit sessions on the basis of protocol";
           presence "enable by-protocol";
           uses by-protocol-object-type;
         }
         leaf-list whitelist {
           ordered-by user;
           description "Configure white list group name";
           type string;
           max-elements 10;
         }
       }
       container by-destination {
         presence "enable by-destination";
         description "Limit sessions to the same destination IP or subnet";
         uses apply-advanced;
         leaf maximum-sessions {
           description "Limit sessions on the basis of maximum concurrent sessions";
           type union {
             type string {
               pattern "<.*>|$.*";
             }
             type uint32;
           }
         }
         leaf packet-rate {
           description "Limit sessions on the basis of packet rate";
           type union {
             type string {
               pattern "<.*>|$.*";
             }
             type uint32 {
               range "1 .. 4294967295";
             }
           }
         }
         leaf session-rate {
           description "Limit sessions on the basis of session rate";
           type union {
             type string {
               pattern "<.*>|$.*";
             }
             type uint32 {
               range "1 .. 4294967295";
             }
           }
         }
         container by-protocol {
           description "Limit sessions on the basis of protocol";
           presence "enable by-protocol";
           uses by-protocol-object-type;
         }
         leaf-list whitelist {
           ordered-by user;
           description "Configure white list group name";
           type string;
           max-elements 10;
         }
       }
     }
   }
   grouping by-protocol-object-type {
     description "Configure limit-session on the basis of protocol";
     uses apply-advanced;
     container tcp {
       description "Configure limit-session on the basis of TCP";
       presence "enable tcp";
       uses by-protocol-object-limit-tcp-type;
     }
     container udp {
       description "Configure limit-session on the basis of UDP";
       presence "enable udp";
       uses by-protocol-object-limit-type;
     }
     container icmp {
       description "Configure limit-session on the basis of ICMP";
       presence "enable icmp";
       uses by-protocol-object-limit-type;
     }
   }
   grouping by-protocol-object-limit-tcp-type {
     description "Configure the limit-session for tcp protocol";
     uses apply-advanced;
     leaf maximum-sessions {
       description "Limit sessions on the basis of maximum concurrent sessions";
       type union {
         type string {
           pattern "<.*>|$.*";
         }
         type uint32;
       }
     }
     leaf packet-rate {
       description "Limit sessions on the basis of packet rate";
       type union {
         type string {
           pattern "<.*>|$.*";
         }
         type uint32 {
           range "1 .. 4294967295";
         }
       }
     }
     leaf session-rate {
       description "Limit sessions on the basis of session rate";
       type union {
         type string {
           pattern "<.*>|$.*";
         }
         type uint32 {
           range "1 .. 4294967295";
         }
       }
     }
     leaf-list whitelist {
       ordered-by user;
       description "Configure white list group name";
       type string;
       max-elements 10;
     }
     container syn-cookie {
       presence "enable syn-cookie";
       description "Configure syn-cookie parameters";
       uses apply-advanced;
       leaf mss {
         description "TCP maximum segment size";
         type union {
           type string {
             pattern "<.*>|$.*";
           }
           type uint32 {
             range "64 .. 65535";
           }
         }
       }
       leaf threshold-rate {
         description "TCP-SYN cps rate to trigger SYN-COOKIE";
         type union {
           type string {
             pattern "<.*>|$.*";
           }
           type uint32 {
             range "1 .. 4294967295";
           }
         }
       }
       leaf threshold-num {
         description "Number of sessions to trigger SYN-COOKIE";
         type union {
           type string {
             pattern "<.*>|$.*";
           }
           type uint32;
         }
       }
     }
   }
   grouping by-protocol-object-limit-type {
     description "Configure the limit-session for each protocol";
     uses apply-advanced;
     leaf maximum-sessions {
       description "Limit sessions on the basis of maximum concurrent sessions";
       type union {
         type string {
           pattern "<.*>|$.*";
         }
         type uint32;
       }
     }
     leaf packet-rate {
       description "Limit sessions on the basis of packet rate";
       type union {
         type string {
           pattern "<.*>|$.*";
         }
         type uint32 {
           range "1 .. 4294967295";
         }
       }
     }
     leaf session-rate {
       description "Limit sessions on the basis of session rate";
       type union {
         type string {
           pattern "<.*>|$.*";
         }
         type uint32 {
           range "1 .. 4294967295";
         }
       }
     }
     leaf-list whitelist {
       ordered-by user;
       description "Configure white list group name";
       type string;
       max-elements 10;
     }
   }
   grouping ids-wlist-type {
     leaf name {
       description "White-list name";
       type string {
         length "1 .. 32";
         junos:posix-pattern "^[[:alnum:]][[:alnum:]_-]*$";
         junos:pattern-message "Must be a string beginning with a number or letter and consisting of letters, numbers, dashes and underscores.";
       }
     }
     uses apply-advanced;
     leaf-list address {
       ordered-by user;
       description "Address";
       type jt:ipprefix;
       max-elements 32;
     }
   }
   grouping ie-filter-object {
     leaf name {
       description "Set IE number";
       type union {
         type string {
           pattern "<.*>|$.*";
         }
         type uint8 {
           range "1 .. 255";
         }
       }
     }
     uses apply-advanced;
     list instance {
       key name;
       description "Set instance";
       leaf name {
         description "Set instance number";
         type union {
           type string {
             pattern "<.*>|$.*";
           }
           type uint8 {
             range "0 .. 11";
           }
         }
       }
       uses apply-advanced;
       container grouped-ie-profile {
         description "Set GTP IE filter for grouped IE";
         uses apply-advanced;
         leaf grpie-prf-name {
           description "Set grouped IE profile";
           junos:must "((\"security gprs gtp grouped-ie-profile $$\" || \"security gtp grouped-ie-profile $$\"))";
           junos:must-message "referenced grouped-ie-profile not found";
           type string {
             length "1 .. 23";
           }
         }
       }
     }
   }
   grouping ims-connection-type {
     description "Identity management connection";
     uses apply-advanced;
     leaf connect-method {
       description "Method of connection";
       type enumeration {
         enum "https" {
           description "HTTPS connection";
         }
         enum "http" {
           description "HTTP connection";
         }
       }
     }
     leaf port {
       description "Server port";
       default "443";
       type union {
         type string {
           pattern "<.*>|$.*";
         }
         type uint32 {
           range "1 .. 65535";
         }
       }
     }
     container primary {
       description "Primary server";
       uses server-connection-type;
     }
     container secondary {
       description "Secondary server";
       uses server-connection-type;
     }
     leaf token-api {
       description "API of acquiring token for OAuth2 authentication";
       type string {
         length "1 .. 128";
       }
     }
     leaf query-api {
       description "Query API";
       type string {
         length "4 .. 128";
       }
     }
   }
   grouping ims-traceoptions-type {
     description "Identity management tracing Options";
     uses apply-advanced;
     leaf no-remote-trace {
       description "Disable remote tracing";
       junos:must "(\"system tracing\")";
       junos:must-message "'no-remote-trace' is valid only when [system tracing] is configured";
       type empty;
     }
     container file {
       description "Trace file information";
       leaf filename {
         description "Name of file in which to write trace information";
         type string {
           length "1 .. 1024";
           junos:posix-pattern "![/ %]";
           junos:pattern-message "Must not contain '/', % or a space";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     leaf level {
       description "Level of debugging output";
       type enumeration {
         enum "error" {
           description "Match error conditions";
         }
         enum "warning" {
           description "Match warning messages";
         }
         enum "notice" {
           description "Match conditions that should be handled specially";
         }
         enum "info" {
           description "Match informational messages";
         }
         enum "verbose" {
           description "Match verbose messages";
         }
         enum "all" {
           description "Match all levels";
         }
       }
     }
     list flag {
       key name;
       ordered-by user;
       description "Tracing parameters";
       leaf name {
         type enumeration {
           enum "all" {
             description "Trace identity management all modules";
           }
           enum "authentication-management" {
             description "Trace advanced-query auth table management module";
           }
           enum "configuration" {
             description "Trace identity management configuration";
           }
           enum "dispatcher" {
             description "Trace dispatcher module";
           }
           enum "query" {
             description "Trace query process";
           }
           enum "jims-validator-query" {
             description "Trace jims validator query process";
           }
           enum "memory" {
             description "Trace memory";
           }
         }
       }
     }
   }
   grouping jims-validator-type {
     description "Web server from JIMS for Validate or group query request";
     uses apply-advanced;
     leaf address {
       description "IP address or hostname of web server";
       type string {
         length "1 .. 128";
       }
     }
     leaf client-id {
       description "Client ID for OAuth2 grant";
       type string {
         length "1 .. 64";
       }
     }
     leaf client-secret {
       description "Client secret for OAuth2 grant";
       type string {
         length "1 .. 128";
       }
     }
     leaf port {
       description "Web server port";
       default "591";
       type union {
         type string {
           pattern "<.*>|$.*";
         }
         type uint32 {
           range "1 .. 65535";
         }
       }
     }
   }
   grouping jsf_application_traffic_control_rule_set_type {
     description "Define service application traffic rule-set reference";
     uses apply-advanced;
     leaf rule-set {
       description "Service rule-set name";
       junos:must "(\"class-of-service application-traffic-control rule-sets $$\")";
       junos:must-message "rule-set must be defined";
       type string {
         length "1 .. 64";
       }
     }
   }
   grouping juniper-enhanced-category-type {
     description "Juniper enhanced category type";
     leaf name {
       description "Name of Juniper enhanced category";
       type string {
         length "1 .. 59";
       }
     }
     uses apply-advanced;
     leaf action {
       description "Action to perform when web traffic matches category";
       type enumeration {
         enum "permit" {
         }
         enum "log-and-permit" {
         }
         enum "block" {
         }
         enum "quarantine" {
         }
       }
     }
     leaf custom-message {
       description "Custom message";
       junos:must "(\"security utm custom-objects custom-message $$\")";
       junos:must-message "custom-message must be defined";
       type string;
     }
   }
   grouping juniper-enhanced-server {
     description "Server handling categorization requests";
     uses apply-advanced;
     leaf host {
       description "Server host IP address or string host name";
       type string;
     }
     leaf port {
       description "Server port";
       type union {
         type string {
           pattern "<.*>|$.*";
         }
         type uint16 {
           range "1 .. 65535";
         }
       }
     }
     leaf proxy-profile {
       description "Proxy profile";
       junos:must "(\"services proxy profile $$\")";
       junos:must-message "Referenced Proxy profile must be defined";
       type string {
         length "1 .. 64";
       }
     }
     leaf routing-instance {
       description "Routing instance name";
       junos:must "(\"routing-instances $$\")";
       junos:must-message "Routing-instance must be defined";
       type string;
     }
     leaf source-address {
       description "Source ip address used to connect server";
       type jt:ipaddr;
     }
   }
   grouping juniper-enhanced-site-reputation-setting {
     description "Juniper enhanced site reputation settings";
     uses apply-advanced;
     leaf very-safe {
       description "Action when site reputation is very safe";
       type enumeration {
         enum "permit" {
         }
         enum "log-and-permit" {
         }
         enum "block" {
         }
         enum "quarantine" {
         }
       }
     }
     leaf moderately-safe {
       description "Action when site reputation is moderately safe";
       type enumeration {
         enum "permit" {
         }
         enum "log-and-permit" {
         }
         enum "block" {
         }
         enum "quarantine" {
         }
       }
     }
     leaf fairly-safe {
       description "Action when site reputation is fairly safe";
       type enumeration {
         enum "permit" {
         }
         enum "log-and-permit" {
         }
         enum "block" {
         }
         enum "quarantine" {
         }
       }
     }
     leaf suspicious {
       description "Action when site reputation is suspicious";
       type enumeration {
         enum "permit" {
         }
         enum "log-and-permit" {
         }
         enum "block" {
         }
         enum "quarantine" {
         }
       }
     }
     leaf harmful {
       description "Action when site reputation is harmful";
       type enumeration {
         enum "permit" {
         }
         enum "log-and-permit" {
         }
         enum "block" {
         }
         enum "quarantine" {
         }
       }
     }
   }
   grouping juniper-routing-instance {
     description "Routing instance";
     leaf name {
       description "Routing instance name";
       type string {
         junos:posix-pattern "!^((__.*__)|(all)|(.*[ ].*)|(\"\")|(.{129,}))$";
         junos:pattern-message "Must be a non-reserved string of 128 characters or less with no spaces.";
       }
     }
     uses apply-advanced;
     leaf instance-type {
       description "Type of routing instance";
       type enumeration {
         enum "virtual-switch" {
           description "Virtual switch routing instance";
         }
         enum "layer2-control" {
           description "Layer 2 control protocols";
         }
         enum "mac-vrf" {
           description "MAC-VRF routing instance";
           junos:must "((\".. bridge-domains\" || \".. vlans\"))";
           junos:must-message "bridge-domains must be configured for mac-vrf instance";
           junos:must "(\".. service-type\")";
           junos:must-message "service-type must be configured for mac-vrf instance";
           junos:must "(\"routing-instances ${instance} protocols evpn\")";
           junos:must-message "Protocol EVPN must be configured in the mac-vrf instance";
         }
         enum "forwarding" {
           description "Forwarding instance";
         }
         enum "no-forwarding" {
           description "Nonforwarding instance";
         }
         enum "l2vpn" {
           description "Layer 2 VPN routing instance";
         }
         enum "vpls" {
           description "VPLS routing instance";
         }
         enum "virtual-router" {
           description "Virtual routing instance";
         }
         enum "l2backhaul-vpn" {
           description "L2Backhaul/L2Wholesale routing instance";
           junos:must "(\".. instance-role\")";
           junos:must-message "'instance-role' statement must be configured for l2backhaul-vpn instance";
           junos:must "(\".. no-local-switching\")";
           junos:must-message "'no-local-switching' statement must be configured for l2backhaul-vpn instance";
           junos:must "(\".. vlan-model\")";
           junos:must-message "'vlan-model' statement must be configured for l2backhaul-vpn instance";
         }
         enum "mpls-internet-multicast" {
           description "Internet Multicast over MPLS routing instance";
           junos:must "((\"protocols pim\" || \".. provider-tunnel inter-region\"))";
           junos:must-message "Protocol PIM must be configured in the master instance";
         }
         enum "evpn" {
           description "EVPN routing instance";
           junos:must "(\"routing-instances ${instance} protocols evpn\")";
           junos:must-message "Protocol EVPN must be configured in the evpn instance";
         }
         enum "mpls-forwarding" {
           description "Routing instance provides a MPLS forwarding-context";
         }
         enum "evpn-vpws" {
           description "EVPN VPWS routing instance";
           junos:must "(\"routing-instances ${instance} protocols evpn\")";
           junos:must-message "Protocol EVPN must be configured in the evpn-vpws instance";
         }
         enum "vrf" {
           description "Virtual routing forwarding instance";
         }
       }
     }
     container l2vpn-id {
       description "Layer-2 vpn-id for this instance";
       uses apply-advanced;
       leaf community {
         description "L2VPN ID community for FEC129 VPLS/VPWS with BGP auto-discovery";
         junos:must "(!(\".. .. protocols vpls neighbor\"))";
         junos:must-message "Does not support FEC129 LDP-VPLS and BGP-VPLS/FEC128-LDP-VPLS under the default mesh-group";
         junos:must "(!(\".. .. protocols vpls vpls-id\"))";
         junos:must-message "Does not support FEC129 LDP-VPLS and BGP-VPLS/FEC128-LDP-VPLS under the default mesh-group";
         junos:must "(!(\".. .. protocols vpls site\"))";
         junos:must-message "Does not support FEC129 LDP-VPLS and BGP-VPLS/FEC128-LDP-VPLS under the same instance";
         junos:must "(!(\".. .. protocols vpls site-range\"))";
         junos:must-message "site-range is not supported for FEC129 LDP VPLS";
         junos:must "(!(\".. .. protocols vpls mac-flush\"))";
         junos:must-message "mac-flush is not supported for FEC129 LDP VPLS";
         junos:must "(!(\".. .. protocols vpls label-block-size\"))";
         junos:must-message "label-block-size is not supported for FEC129 LDP VPLS";
         junos:must "(!(\".. .. protocols vpls connectivity-type\"))";
         junos:must-message "connectivity-type is not supported for FEC129 LDP VPLS";
         junos:must "(!(\".. .. protocols vpls community\"))";
         junos:must-message "community is not supported for FEC129 LDP VPLS";
         junos:must "(!(\".. .. provider-tunnel\"))";
         junos:must-message "provider-tunnel is not supported for FEC129 LDP VPLS/VPWS";
         type string {
           junos:posix-pattern "^(l2vpn-id)+:[0-9.]+:[0-9]+$";
           junos:pattern-message "Use format 'l2vpn-id:x:y' where 'x' is 2 byte AS number, or an IP address and 'y' is a number. e.g. l2vpn-id:1:100, l2vpn-id:1.2.3.4:100";
         }
       }
     }
     container routing-options {
       description "Protocol-independent routing option configuration";
       uses juniper-routing-options;
     }
     container egress-protection {
       description "Egress instance protection";
       uses apply-advanced;
       leaf protector {
         description "Enable Edge Protector functionality for this VPN";
         junos:must "(any \"protocols mpls egress-protection context-identifier <*> protector\")";
         junos:must-message "context-identifier must be type protector";
         type empty;
       }
       container context-identifier {
         description "Context identifier";
         uses apply-advanced;
         leaf context-id {
           description "IP address";
           junos:must "(\"protocols mpls egress-protection context-identifier $$ primary\")";
           junos:must-message "context-identifier must be type primary";
           junos:must "(\"protocols mpls egress-protection context-identifier $$\")";
           junos:must-message "same context-identifier must be defined in protocols mpls egress-protection";
           type jt:ipv4addr;
         }
       }
     }
     container protocols {
       junos:must "((!(\". pim\") || (\".. instance-type\" && !(\".. instance-type no-forwarding\"))))";
       junos:must-message "pim configuration is not allowed for 'instance-type no-forwarding'";
       description "Routing protocol configuration";
       uses apply-advanced;
       container bfd {
         presence "enable bfd";
         junos:must "(!(\".. .. instance-type l2vpn\"))";
         junos:must-message "bfd configuration is not allowed for 'instance-type l2vpn'";
         junos:must "(!(\".. .. instance-type vpls\"))";
         junos:must-message "bfd configuration is not allowed for 'instance-type vpls'";
         junos:must "(!(\".. .. instance-type layer2-control\"))";
         junos:must-message "bfd configuration is not allowed for 'instance-type layer2-control'";
         junos:must "(!(\".. .. instance-type virtual-switch\"))";
         junos:must-message "bfd configuration is not allowed for 'instance-type virtual-switch'";
         uses juniper-ri-protocols-bfd;
       }
       container igmp-snooping {
         description "IGMP snooping configuration";
         presence "enable igmp-snooping";
         junos:must "((\".. .. instance-type vpls\" || (\".. .. instance-type evpn\" || (\".. .. instance-type mac-vrf\" || \".. .. instance-type virtual-switch\"))))";
         junos:must-message "igmp-snooping configuration is allowed only for 'instance-type vpls/virtual-switch/evpn/mac-vrf'";
         junos:must "(!(\".. pim-snooping\"))";
         junos:must-message "igmp-snooping configuration do not co-exist with pim-snooping";
         junos:must "((\".. .. instance-type vpls\" || (\".. .. instance-type evpn\" || (\".. .. instance-type mac-vrf\" || (\".. .. instance-type virtual-switch \" && !(\".. vpls\"))))))";
         junos:must-message "igmp-snooping configuration is allowed only for 'instance-type vpls/evpn/mac-vrf or instance-type virtual-switch without vpls'";
         uses juniper-ri-protocols-igmp-snooping;
       }
       container mld-snooping {
         description "MLD snooping configuration";
         presence "enable mld-snooping";
         junos:must "((\".. .. instance-type vpls\" || (\".. .. instance-type evpn\" || \".. .. instance-type virtual-switch\")))";
         junos:must-message "mld-snooping configuration is allowed only for 'instance-type vpls/virtual-switch/evpn'";
         junos:must "((\".. .. instance-type vpls\" || (\".. .. instance-type evpn\" || (\".. .. instance-type mac-vrf\" || (\".. .. instance-type virtual-switch \" && !(\".. vpls\"))))))";
         junos:must-message "mld-snooping configuration is allowed only for 'instance-type vpls/evpn/mac-vrf or instance-type virtual-switch without vpls'";
         uses juniper-ri-protocols-mld-snooping;
       }
       container amt {
         description "AMT relay configuration";
         junos:must "(!(\".. .. instance-type no-forwarding\"))";
         junos:must-message "amt configuration is not allowed for 'instance-type no-forwarding'";
         junos:must "(!(\".. .. instance-type layer2-control\"))";
         junos:must-message "amt configuration is not allowed for 'instance-type layer2-control'";
         junos:must "(!(\".. .. instance-type virtual-switch\"))";
         junos:must-message "amt configuration is not allowed for 'instance-type virtual-switch'";
         uses juniper-protocols-amt;
       }
       container bgp {
         description "BGP options";
         junos:must "(!(\".. .. instance-type l2vpn\"))";
         junos:must-message "bgp configuration is not allowed for 'instance-type l2vpn'";
         junos:must "(!(\".. .. instance-type vpls\"))";
         junos:must-message "bgp configuration is not allowed for 'instance-type vpls'";
         junos:must "(!(\".. .. instance-type layer2-control\"))";
         junos:must-message "bgp configuration is not allowed for 'instance-type layer2-control'";
         junos:must "(!(\".. .. instance-type virtual-switch\"))";
         junos:must-message "bgp configuration is not allowed for 'instance-type virtual-switch'";
         uses juniper-protocols-bgp;
       }
       container esis {
         description "ES-IS configuration";
         junos:must "(!(\".. .. instance-type l2vpn\"))";
         junos:must-message "esis configuration is not allowed for 'instance-type l2vpn'";
         junos:must "(!(\".. .. instance-type vpls\"))";
         junos:must-message "esis configuration is not allowed for 'instance-type vpls'";
         junos:must "(!(\".. .. instance-type layer2-control\"))";
         junos:must-message "esis configuration is not allowed for 'instance-type layer2-control'";
         junos:must "(!(\".. .. instance-type virtual-switch\"))";
         junos:must-message "esis configuration is not allowed for 'instance-type virtual-switch'";
         uses juniper-protocols-esis;
       }
       container evpn {
         description "EVPN configuration";
         presence "enable evpn";
         junos:must "(!((\".. .. instance-type virtual-switch\" && \".. vpls\")))";
         junos:must-message "This configuration is not allowed for instance-type virtual-switch with 'protocols vpls' enabled";
         junos:must "(!(\".. l2vpn\"))";
         junos:must-message "This configuration is not allowed with 'protocols l2vpn'";
         junos:must "(!(\".. .. instance-type layer2-control\"))";
         junos:must-message "This configuration is not allowed for 'instance-type layer2-control'";
         uses juniper-protocols-l2vpn;
       }
       container router-discovery {
         description "ICMP router discovery options";
         junos:must "(!(\".. .. instance-type layer2-control\"))";
         junos:must-message "This configuration is not allowed for 'instance-type layer2-control'";
         junos:must "(!(\".. .. instance-type virtual-switch\"))";
         junos:must-message "This configuration is not allowed for 'instance-type virtual-switch'";
         uses juniper-protocols-router-discovery;
       }
       container isis {
         description "IS-IS configuration";
         junos:must "(!(\".. .. instance-type l2vpn\"))";
         junos:must-message "isis configuration is not allowed for 'instance-type l2vpn'";
         junos:must "(!(\".. .. instance-type vpls\"))";
         junos:must-message "isis configuration is not allowed for 'instance-type vpls'";
         junos:must "(!(\".. .. instance-type layer2-control\"))";
         junos:must-message "isis configuration is not allowed for 'instance-type layer2-control'";
         junos:must "(!(\".. .. instance-type virtual-switch\"))";
         junos:must-message "isis configuration is not allowed for 'instance-type virtual-switch'";
         uses juniper-protocols-isis;
       }
       container l2vpn {
         description "Layer 2 VPN configuration";
         junos:must "(!(\".. evpn\"))";
         junos:must-message "This configuration is not allowed with 'protocols evpn'";
         junos:must "(!(\".. vpls\"))";
         junos:must-message "This configuration is not allowed with 'protocols vpls'";
         junos:must "(!(\".. .. instance-type layer2-control\"))";
         junos:must-message "This configuration is not allowed for 'instance-type layer2-control'";
         uses juniper-protocols-l2vpn;
       }
       container vpls {
         description "VPLS configuration";
         presence "enable vpls";
         junos:must "(!(\".. .. instance-type mac-vrf\"))";
         junos:must-message "This configuration is not allowed for instance-type mac-vrf";
         junos:must "(!((\".. .. instance-type virtual-switch\" && \".. evpn\")))";
         junos:must-message "This configuration is not allowed for instance-type virtual-switch with 'protocols evpn' enabled";
         junos:must "(!(\".. l2vpn\"))";
         junos:must-message "This configuration is not allowed with 'protocols l2vpn'";
         junos:must "(!(\".. .. instance-type layer2-control\"))";
         junos:must-message "This configuration is not allowed for 'instance-type layer2-control'";
         uses juniper-protocols-l2vpn;
       }
       container ldp {
         description "LDP configuration";
         junos:must "((!(\".. ldp p2mp\") || (\".. ldp p2mp\" && !(\".. .. instance-type virtual-router\"))))";
         junos:must-message "p2mp under ldp is not allowed for 'instance-type virtual-router'";
         junos:must "((!(\".. ldp p2mp\") || (\".. ldp p2mp\" && !(\".. .. instance-type vrf\"))))";
         junos:must-message "p2mp under ldp is not allowed for 'instance-type vrf'";
         junos:must "(!(\".. .. instance-type layer2-control\"))";
         junos:must-message "ldp configuration is not allowed for 'instance-type layer2-control'";
         junos:must "(!(\".. .. instance-type virtual-switch\"))";
         junos:must-message "ldp configuration is not allowed for 'instance-type virtual-switch'";
         uses juniper-protocols-ldp;
       }
       container mpls {
         description "MPLS configuration";
         junos:must "(!(\".. .. instance-type evpn\"))";
         junos:must-message "mpls configuration is not allowed for 'instance-type evpn'";
         junos:must "(!(\".. .. instance-type mpls-internet-multicast\"))";
         junos:must-message "mpls configuration is not allowed for 'instance-type mpls-internet-multicast'";
         junos:must "(!(\".. .. instance-type layer2-control\"))";
         junos:must-message "mpls configuration is not allowed for 'instance-type layer2-control'";
         junos:must "(!(\".. .. instance-type atmvpn\"))";
         junos:must-message "mpls configuration is not allowed for 'instance-type atmvpn'";
         junos:must "(!(\".. .. instance-type l2backhaul-vpn\"))";
         junos:must-message "mpls configuration is not allowed for 'instance-type l2backhaul-vpn'";
         junos:must "(!(\".. .. instance-type virtual-switch\"))";
         junos:must-message "mpls configuration is not allowed for 'instance-type virtual-switch'";
         junos:must "(!(\".. .. instance-type vpls\"))";
         junos:must-message "mpls configuration is not allowed for 'instance-type vpls'";
         junos:must "(!(\".. .. instance-type l2vpn\"))";
         junos:must-message "mpls configuration is not allowed for 'instance-type l2vpn'";
         junos:must "(!(\".. .. instance-type no-forwarding\"))";
         junos:must-message "mpls configuration is not allowed for 'instance-type no-forwarding'";
         junos:must "(!(\".. .. instance-type forwarding\"))";
         junos:must-message "mpls configuration is not allowed for 'instance-type forwarding'";
         uses juniper-protocols-mpls;
       }
       container msdp {
         description "MSDP configuration";
         junos:must "(!(\".. .. instance-type layer2-control\"))";
         junos:must-message "msdp configuration is not allowed for 'instance-type layer2-control'";
         junos:must "(!(\".. .. instance-type virtual-switch\"))";
         junos:must-message "msdp configuration is not allowed for 'instance-type virtual-switch'";
         uses juniper-protocols-msdp;
       }
       container mvpn {
         description "BGP-MVPN configuration";
         presence "enable mvpn";
         junos:must "((!(\"system processes routing bgp rib-sharding\") || (!(\".. .. protocols bgp group\") || (!(\".. .. routing-options auto-export\") || \"system processes routing bgp rib-sharding no-l3vpn\"))))";
         junos:must-message "Auto-export of BGP learned routes will not work with sharding MVPN context";
         junos:must "((\".. pim\" || (\".. .. instance-type mpls-internet-multicast\" || (\".. .. provider-tunnel inter-as\" || \".. .. provider-tunnel inter-region\"))))";
         junos:must-message "MVPN configuration requires PIM configuration in the VRF or MPLS internet multicast instance";
         junos:must "((!(\"routing-options nonstop-routing\") || (\".. .. route-distinguisher\" || (\".. pim mvpn\" || \".. .. instance-type mpls-internet-multicast\"))))";
         junos:must-message "Nonstop routing and auto-rd mvpn instance may not be configured together";
         junos:must "(!(\".. .. instance-type layer2-control\"))";
         junos:must-message "mvpn configuration is not allowed for 'instance-type layer2-control'";
         junos:must "(!(\".. .. instance-type virtual-switch\"))";
         junos:must-message "mvpn configuration is not allowed for 'instance-type virtual-switch'";
         uses juniper-protocols-mvpn;
       }
       container ospf {
         description "OSPF configuration";
         junos:must "(!(\".. .. instance-type l2vpn\"))";
         junos:must-message "ospf configuration is not allowed for 'instance-type l2vpn'";
         junos:must "(!(\".. .. instance-type vpls\"))";
         junos:must-message "ospf configuration is not allowed for 'instance-type vpls'";
         junos:must "(!(\".. .. instance-type layer2-control\"))";
         junos:must-message "ospf configuration is not allowed for 'instance-type layer2-control'";
         junos:must "(!(\".. .. instance-type virtual-switch\"))";
         junos:must-message "ospf configuration is not allowed for 'instance-type virtual-switch'";
         uses juniper-protocols-ospf;
       }
       container ospf3 {
         description "OSPF3 configuration";
         junos:must "(!(\".. .. instance-type l2vpn\"))";
         junos:must-message "ospf configuration is not allowed for 'instance-type l2vpn'";
         junos:must "(!(\".. .. instance-type vpls\"))";
         junos:must-message "ospf configuration is not allowed for 'instance-type vpls'";
         junos:must "(!(\".. .. instance-type layer2-control\"))";
         junos:must-message "ospf configuration is not allowed for 'instance-type layer2-control'";
         junos:must "(!(\".. .. instance-type virtual-switch\"))";
         junos:must-message "ospf configuration is not allowed for 'instance-type virtual-switch'";
         uses juniper-protocols-ospf3;
       }
       container pim {
         description "PIM configuration";
         junos:must "(!(\".. .. instance-type layer2-control\"))";
         junos:must-message "pim configuration is not allowed for 'instance-type layer2-control'";
         junos:must "(!(\".. .. instance-type virtual-switch\"))";
         junos:must-message "pim configuration is not allowed for 'instance-type virtual-switch'";
         uses juniper-protocols-pim;
       }
       container ripng {
         description "RIPng options";
         junos:must "(!(\".. .. instance-type l2vpn\"))";
         junos:must-message "ripng configuration is not allowed for 'instance-type l2vpn'";
         junos:must "(!(\".. .. instance-type vpls\"))";
         junos:must-message "ripng configuration is not allowed for 'instance-type vpls'";
         junos:must "(!(\".. .. instance-type layer2-control\"))";
         junos:must-message "ripng configuration is not allowed for 'instance-type layer2-control'";
         junos:must "(!(\".. .. instance-type virtual-switch\"))";
         junos:must-message "ripng configuration is not allowed for 'instance-type virtual-switch'";
         uses juniper-protocols-ripng;
       }
       container rip {
         description "RIP options";
         junos:must "(!(\".. .. instance-type l2vpn\"))";
         junos:must-message "rip configuration is not allowed for 'instance-type l2vpn'";
         junos:must "(!(\".. .. instance-type vpls\"))";
         junos:must-message "rip configuration is not allowed for 'instance-type vpls'";
         junos:must "(!(\".. .. instance-type layer2-control\"))";
         junos:must-message "rip configuration is not allowed for 'instance-type layer2-control'";
         junos:must "(!(\".. .. instance-type virtual-switch\"))";
         junos:must-message "rip configuration is not allowed for 'instance-type virtual-switch'";
         uses juniper-protocols-rip;
       }
       container rsvp {
         description "RSVP configuration";
         junos:must "(!(\".. .. instance-type evpn\"))";
         junos:must-message "rsvp configuration is not allowed for 'instance-type evpn'";
         junos:must "(!(\".. .. instance-type mpls-internet-multicast\"))";
         junos:must-message "rsvp configuration is not allowed for 'instance-type mpls-internet-multicast'";
         junos:must "(!(\".. .. instance-type layer2-control\"))";
         junos:must-message "rsvp configuration is not allowed for 'instance-type layer2-control'";
         junos:must "(!(\".. .. instance-type atmvpn\"))";
         junos:must-message "rsvp configuration is not allowed for 'instance-type atmvpn'";
         junos:must "(!(\".. .. instance-type l2backhaul-vpn\"))";
         junos:must-message "rsvp configuration is not allowed for 'instance-type l2backhaul-vpn'";
         junos:must "(!(\".. .. instance-type virtual-switch\"))";
         junos:must-message "rsvp configuration is not allowed for 'instance-type virtual-switch'";
         junos:must "(!(\".. .. instance-type vpls\"))";
         junos:must-message "rsvp configuration is not allowed for 'instance-type vpls'";
         junos:must "(!(\".. .. instance-type l2vpn\"))";
         junos:must-message "rsvp configuration is not allowed for 'instance-type l2vpn'";
         junos:must "(!(\".. .. instance-type no-forwarding\"))";
         junos:must-message "rsvp configuration is not allowed for 'instance-type no-forwarding'";
         junos:must "(!(\".. .. instance-type forwarding\"))";
         junos:must-message "rsvp configuration is not allowed for 'instance-type forwarding'";
         uses juniper-protocols-rsvp;
       }
       container pim-snooping {
         description "PIM snooping configuration";
         presence "enable pim-snooping";
         junos:must "(!(\".. .. routing-interface\"))";
         junos:must-message "routing-interface can not be configured when pim-snooping is configured";
         junos:must "(!(\".. igmp-snooping\"))";
         junos:must-message "pim-snooping configuration can not coexist with igmp-snooping";
         junos:must "(\".. .. instance-type vpls\")";
         junos:must-message "pim-snooping configuration is allowed only for 'instance-type vpls'";
         uses juniper-protocols-pim-snooping;
       }
       container rstp {
         description "RSTP configuration";
         junos:must "((\".. .. instance-type layer2-control\" || \".. .. instance-type virtual-switch\"))";
         junos:must-message "STP protocols allowed only in layer2-control or virtual-switch instance";
         uses juniper-protocols-stp;
       }
       container mstp {
         description "MSTP configuration";
         junos:must "((\".. .. instance-type layer2-control\" || \".. .. instance-type virtual-switch\"))";
         junos:must-message "STP protocols allowed only in layer2-control or virtual-switch instance";
         uses juniper-protocols-mstp;
       }
       container vstp {
         description "VSTP configuration";
         junos:must "((\".. vstp disable\" || (!(\".. mstp\") || \".. mstp disable\")))";
         junos:must-message "MSTP is enabled in the same routing instance, VSTP not allowed";
         junos:must "((\".. .. instance-type layer2-control\" || \".. .. instance-type virtual-switch\"))";
         junos:must-message "STP protocols allowed only in layer2-control or virtual-switch instance";
         uses juniper-protocols-vstp;
       }
       container mvrp {
         description "MVRP configuration";
         junos:must "((!(\".. vstp\") || \".. vstp disable\"))";
         junos:must-message "vstp enabled, mvrp is not supported";
         junos:must "(((\".. mstp\" && !(\".. mstp disable\")) || (\".. rstp\" && !(\".. rstp disable\"))))";
         junos:must-message "rstp/mstp is not enabled, mvrp is not allowed";
         junos:must "(\".. .. instance-type virtual-switch\")";
         junos:must-message "mvrp is allowed only in virtual-switch instance";
         uses juniper-protocols-mvrp;
       }
     }
     leaf description {
       description "Text description of routing instance";
       type string {
         junos:posix-pattern "^.{1,255}$";
         junos:pattern-message "Must be a string of 255 characters or less";
       }
     }
     leaf vlan-model {
       description "Subscriber vlan-model in L2Wholesale framework";
       type enumeration {
         enum "one-to-one" {
           description "Customer VLAN model (1:1)";
         }
       }
     }
     container vtep-source-interface {
       description "Source layer-3 IFL for VXLAN";
       leaf interface-name {
         junos:must "(\"interfaces $$\")";
         junos:must-message "Interface must be defined";
         type union {
           type jt:interface-name;
           type string {
             pattern "<.*>|$.*";
           }
         }
       }
       choice family {
         case case_1 {
           container inet {
             presence "enable inet";
             description "IPv4 source";
             uses apply-advanced;
           }
         }
         case case_2 {
           container inet6 {
             presence "enable inet6";
             junos:must "((!(\"routing-instances ${instance} protocols evpn\") || \"routing-instances ${instance} protocols evpn encapsulation vxlan\"))";
             junos:must-message "encapsulation vxlan must be enabled for IPv6 underlay";
             description "IPv6 source";
             uses apply-advanced;
           }
         }
       }
     }
     container vtep-remote-interface {
       description "Remote VTEP interface";
       uses apply-advanced;
       list remote-ip {
         key name;
         ordered-by user;
         description "Remote VTEP IP address";
         leaf name {
           description "IP address";
           type jt:ipv4addr;
         }
         uses apply-advanced;
         leaf dynamic-profile {
           description "Define associate dynamic profile";
           junos:must "(\"dynamic-profiles $$\")";
           junos:must-message "Dynamic profile must be defined";
           type string;
         }
       }
       container default {
         description "To all remote vtep interface";
         uses apply-advanced;
         leaf dynamic-profile {
           description "Define associate dynamic profile";
           junos:must "(\"dynamic-profiles $$\")";
           junos:must-message "Dynamic profile must be defined";
           type string;
         }
       }
     }
     leaf-list remote-vtep-list {
       description "Configure static remote VXLAN tunnel endpoints";
       type jt:ipaddr;
       max-elements 1024;
     }
     leaf-list remote-vtep-v6-list {
       description "Configurate static ipv6 remote VXLAN tunnel endpoints";
       type jt:ipv6addr;
       max-elements 1024;
     }
     leaf instance-role {
       description "Primary role of L2Backhaul-vpn router";
       type enumeration {
         enum "access" {
           description "Role of Access/Aggregation router";
         }
         enum "nni" {
           description "Role of Provider network interfacing router";
         }
       }
     }
     choice vlan_choice {
       case case_1 {
         leaf vlan-id {
           description "IEEE 802.1q VLAN identifier for bridging domain";
           junos:must "(!(\".. instance-type mac-vrf\"))";
           junos:must-message "'vlan-id' must be configured within bridge-domains for 'instance-type mac-vrf'";
           junos:must "((\".. instance-type vpls\" || \".. instance-type evpn\"))";
           junos:must-message "'vlan-id' statement can be included only for a VPLS or EVPN";
           type string;
         }
       }
       case case_2 {
         container vlan-tags {
           presence "enable vlan-tags";
           junos:must "(\".. instance-type vpls\")";
           junos:must-message "'vlan-tags' statement can be included only for VPLS instance";
           description "IEEE 802.1q VLAN tags for bridging domain";
           leaf outer {
             description "[tpid.]vlan-id, tpid format is 0xNNNN and is optional";
             type string {
               junos:posix-pattern "^(0[Xx][0-9A-Fa-f]{4}.([0-9]{1,3}|1[0-9]{3}|2[0-9]{3}|3[0-9]{3}|40[0-8][0-9]|409[0-4]))$|^([0-9]{1,3}|1[0-9]{3}|2[0-9]{3}|3[0-9]{3}|40[0-8][0-9]|409[0-4])$";
               junos:pattern-message "vlan-id in vlan-tag (0xNNNN.vlan-id) must be 0 to 4094";
             }
           }
           leaf inner {
             description "[tpid.]vlan-id, tpid format is 0xNNNN and is optional";
             type string {
               junos:posix-pattern "^(0[Xx][0-9A-Fa-f]{4}.([0-9]{1,3}|1[0-9]{3}|2[0-9]{3}|3[0-9]{3}|40[0-8][0-9]|409[0-4]))$|^([0-9]{1,3}|1[0-9]{3}|2[0-9]{3}|3[0-9]{3}|40[0-8][0-9]|409[0-4])$";
               junos:pattern-message "vlan-id in vlan-tag (0xNNNN.vlan-id) must be 0 to 4094";
             }
           }
         }
       }
     }
     container system {
       description "System parameters";
       uses apply-advanced;
       container services {
         description "System services";
         uses apply-advanced;
         container dhcp-local-server {
           description "Dynamic Host Configuration Protocol server configuration";
           uses jdhcp-local-server-type;
         }
         container dhcp-proxy-client {
           description "Dynamic Host Configuration Protocol Proxy client configuration";
           uses jdhcp-proxy-client-type;
         }
         container static-subscribers {
           description "Static Subscriber Client configuration";
           uses jsscd-static-subscribers-type;
         }
         container remote-device-management {
           description "Remote device management configuration";
           uses apply-advanced;
           list service-device {
             key name;
             description "Service device configuraiton";
             uses service-device-object;
           }
         }
         container tcp-forwarding {
           description "TCP forwarding configuration";
           uses apply-advanced;
           list listening-port {
             key "port-number listening-address";
             ordered-by user;
             description "TCP listener configuration";
             leaf port-number {
               description "Listening port";
               type union {
                 type string {
                   pattern "<.*>|$.*";
                 }
                 type uint16 {
                   range "8000 .. 8063";
                 }
               }
             }
             leaf listening-address {
               description "Listening address";
               type jt:ipv4addr;
             }
             uses apply-advanced;
             leaf forwarding-address {
               description "Forwarding address";
               type jt:ipv4addr;
             }
             leaf forwarding-port {
               description "Forwarding port";
               type union {
                 type string {
                   pattern "<.*>|$.*";
                 }
                 type uint16 {
                   range "1 .. 65535";
                 }
               }
             }
             leaf max-connections {
               description "Maxmimum allowed connections";
               type union {
                 type string {
                   pattern "<.*>|$.*";
                 }
                 type uint16 {
                   range "1 .. 16";
                 }
               }
             }
             list allowed-source {
               key name;
               ordered-by user;
               description "Allowed source prefix";
               leaf name {
                 description "Source prefix";
                 type jt:ipv4prefix;
               }
               uses apply-advanced;
             }
           }
         }
       }
     }
     container access {
       description "Network access configuration";
       uses apply-advanced;
       container address-assignment {
         description "Address assignment configuration";
         uses address-assignment-type;
       }
       container address-protection {
         presence "enable address-protection";
         description "Initiate Duplicate Address Protection";
         uses apply-advanced;
         leaf reassign-on-match {
           description "Disconnect owning session and reassign to this session";
           type empty;
         }
       }
     }
     container access-profile {
       description "Access profile for this instance";
       leaf access-profile-name {
         description "Profile name";
         junos:must "(\"access profile $$\")";
         junos:must-message "Access-profile must be defined in the [edit access profile] hierarchy";
         type string;
       }
     }
     leaf routing-interface {
       description "Routing interface name for this routing-instance";
       junos:must "(!(\"interfaces $$-IFL family mpls\"))";
       junos:must-message "routing-interface with family mpls cannot be added to VPLS instance";
       junos:must "(!(\".. instance-type virtual-switch\"))";
       junos:must-message "routing-interface must be configured within bridge-domains for 'instance-type virtual-switch'";
       junos:must "(!(\"routing-instances ${instance} service-type vlan-bundle\"))";
       junos:must-message "routing-interface not valid for vlan-bundle service type";
       junos:must "((!(\".. vlan-id all\") && !(\".. vlan-id inner-all\")))";
       junos:must-message "routing-interface cannot be configured under routing-instance with 'vlan-id all' or 'vlan-id inner-all'";
       junos:must "((\".. vlan-id\" || \".. vlan-tags\"))";
       junos:must-message "routing-interface can be configured only under routing-instance with 'vlan-id' or 'vlan-tags'";
       type union {
         type jt:interface-unit;
         type string {
           pattern "<.*>|$.*";
         }
       }
     }
     container vxlan {
       junos:must "((\". ovsdb-managed\" || (\". multicast-group\" || (\". multicast-v6-group\" || (\". ingress-node-replication\" || (\"routing-instances ${instance} switch-options ovsdb-managed\" || \"routing-instances ${instance} protocols evpn encapsulation vxlan\"))))))";
       junos:must-message "multicast-group or multicast-v6-group or ovsdb-managed or ingress-node-replication or protocols evpn encapsulation vxlan should be enabled. ingress-node-replication must be configured when remote-vtep-list is configured";
       junos:must "((\". ovsdb-managed\" || (\"routing-instances ${instance} switch-options ovsdb-managed\" || (\". multicast-group\" || (\". multicast-v6-group\" || (\"routing-instances ${instance} remote-vtep-list\" || (\"routing-instances ${instance} remote-vtep-v6-list\" || \"routing-instances ${instance} protocols evpn encapsulation vxlan\")))))))";
       junos:must-message "One of multicast-group or multicast-v6-group or ovsdb-managed or protocols evpn encapsulation vxlan or remote-vtep-list or remote-vtep-v6-list should be enabled";
       junos:must "((\".. vlan-id\" || (\".. instance-type vpls\" || (\".. instance-type evpn\" && \".. vxlan decapsulate-accept-inner-vlan\"))))";
       junos:must-message "decapsulate-accept-inner-vlan must be configured when vlan-id is not present for evpn vxlan";
       junos:must "((\".. vlan-id\" || (\".. instance-type vpls\" || (\".. instance-type evpn\" && \".. vxlan encapsulate-inner-vlan\"))))";
       junos:must-message "encapsulate-inner-vlan must be configured when vlan-id is not present for evpn vxlan";
       junos:must "((!(\".. vlan-id all\") && !(\".. vlan-id inner-all\")))";
       junos:must-message "vxlan does not support bridge domain with 'vlan-id all' or  'vlan-id inner-all'";
       junos:must "(!(\".. instance-type mac-vrf\"))";
       junos:must-message "vxlan must be configured within bridge-domains for 'instance-type mac-vrf'";
       junos:must "(!(\".. instance-type virtual-switch\"))";
       junos:must-message "vxlan must be configured within bridge-domains for 'instance-type virtual-switch'";
       junos:must "((\".. instance-type vpls\" || \".. instance-type evpn\"))";
       junos:must-message "vxlan in routing-instance is valid only for instance-type vpls or evpn";
       junos:must "(\"routing-instances ${instance} vtep-source-interface\")";
       junos:must-message "vtep-source-interface is required for VXLAN configuration";
       description "VXLAN options";
       uses apply-advanced;
       leaf ovsdb-managed {
         description "Managed remotely via VXLAN OVSDB Controller";
         junos:must "(!((\"routing-instances ${instance} remote-vtep-list\" || \".. multicast-group\")))";
         junos:must-message "ovsdb-managed not valid with remote-vtep-list or multicast-group";
         type empty;
       }
       leaf vni {
         description "VXLAN identifier";
         type union {
           type string {
             pattern "<.*>|$.*";
           }
           type uint32 {
             range "0 .. 16777214";
           }
         }
       }
       leaf translation-vni {
         description "Translated VXLAN identifier";
         type union {
           type string {
             pattern "<.*>|$.*";
           }
           type uint32 {
             range "1 .. 16777214";
           }
         }
       }
       leaf multicast-group {
         description "Multicast group registered for VXLAN segment";
         junos:must "(!((\"routing-instances ${instance} remote-vtep-list\" || (\".. ovsdb-managed\" || (\".. multicast-v6-group\" || \"routing-instances ${instance} switch-options ovsdb-managed\")))))";
         junos:must-message "multicast-group not valid with remote-vtep-list or ovsdb-managed or multicast-v6-group";
         type jt:ipv4addr;
       }
       leaf multicast-v6-group {
         description "Multicast IPv6 group registered for VXLAN segment";
         junos:must "(!((\"routing-instances ${instance} remote-vtep-list\" || (\".. ovsdb-managed\" || (\".. multicast-group\" || \"routing-instances ${instance} switch-options ovsdb-managed\")))))";
         junos:must-message "multicast-v6-group not valid with remote-vtep-list or ovsdb-managed or multicast-group";
         type jt:ipv6addr;
       }
       leaf encapsulate-inner-vlan {
         description "Retain inner VLAN in the packet";
         junos:must "(!(\".. .. vlan-id none\"))";
         junos:must-message "encapsulate inner vlan not valid with vlan-id none ";
         type empty;
       }
       leaf decapsulate-accept-inner-vlan {
         description "Accept VXLAN packets with inner VLAN";
         junos:must "(!(\".. .. vlan-id none\"))";
         junos:must-message "accept inner vlan not valid with vlan-id none";
         type empty;
       }
       leaf unreachable-vtep-aging-timer {
         description "Unreachable VXLAN tunnel endpoint removal timer";
         units "seconds";
         type union {
           type string {
             pattern "<.*>|$.*";
           }
           type uint16 {
             range "300 .. 1800";
           }
         }
       }
       leaf ingress-node-replication {
         description "Enable ingress node replication";
         junos:must "(!(\".. .. .. .. protocols evpn assisted-replication\"))";
         junos:must-message "ingress-node-replication cannot be configured with assisted-replication";
         junos:must "((\".. ovsdb-managed\" || (\".. .. .. .. switch-options ovsdb-managed\" || (\"routing-instances ${instance} remote-vtep-list\" || (\"routing-instances ${instance} remote-vtep-v6-list\" || \"routing-instances ${instance} protocols evpn encapsulation vxlan\")))))";
         junos:must-message "Valid for ovsdb-managed instance or with remote-vtep-list or remote-vtep-v6-list or evpn vxlan";
         type empty;
       }
     }
     leaf l3-interface {
       description "L3 interface name for this routing-instance";
       junos:must "(!(\"interfaces $$-IFL family mpls\"))";
       junos:must-message "l3-interface with family mpls cannot be added to VPLS instance";
       junos:must "(!(\".. instance-type virtual-switch\"))";
       junos:must-message "l3-interface must be configured within bridge-domains for 'instance-type virtual-switch'";
       junos:must "((!(\".. vlan-id all\") && !(\".. vlan-id inner-all\")))";
       junos:must-message "l3-interface cannot be configured under routing-instance with 'vlan-id all' or 'vlan-id inner-all'";
       junos:must "((\".. vlan-id\" || \".. vlan-tags\"))";
       junos:must-message "l3-interface can be configured only under routing-instance with 'vlan-id' or 'vlan-tags'";
       type union {
         type jt:interface-unit;
         type string {
           pattern "<.*>|$.*";
         }
       }
     }
     leaf no-local-switching {
       description "Disable local switching within CE-facing interfaces";
       junos:must "((\".. instance-type vpls\" || ((\".. instance-type evpn\" && \".. protocols vpls\") || \".. instance-type l2backhaul-vpn\")))";
       junos:must-message "'no-local-switching' statement can be configured only for VPLS instances";
       type empty;
     }
     leaf no-normalization {
       description "Disable vlan id normalization for interfaces";
       type empty;
     }
     leaf qualified-bum-pruning-mode {
       description "Enable BUM pruning for VPLS instance";
       junos:must "((\".. instance-type vpls\" || (\".. instance-type evpn\" && \".. protocols vpls\")))";
       junos:must-message "'bum-pruning-mode' statement can be configured only for VPLS instances!";
       type empty;
     }
     leaf no-irb-layer-2-copy {
       description "Disable transmission of layer-2 copy of packets of irb routing-interface";
       junos:must "((\".. routing-interface\" || \".. l3-interface\"))";
       junos:must-message "routing-interface/l3-interface must be configured for this feature";
       type empty;
     }
     leaf connector-id-advertise {
       description "Advertise connector-id attribute";
       type empty;
     }
     container forwarding-options {
       description "Forwarding options configuration";
       uses juniper-forwarding-options;
     }
     container bridge-domains {
       junos:must "((\".. instance-type virtual-switch\" || \".. instance-type mac-vrf\"))";
       junos:must-message "'bridge-domains' configuration can only be used for 'instance-type virtual-switch' or 'instance-type mac-vrf'";
       junos:must "(!(\"vlans\"))";
       junos:must-message "BDs cannot be configured when VLANs are configured";
       description "Bridge domain configuration";
       uses apply-advanced;
       list domain {
         key name;
         uses juniper-bridge-domains;
       }
     }
     container switch-options {
       description "L2 options for routing-instance of type virtual-switch";
       junos:must "(\".. instance-type virtual-switch\")";
       junos:must-message "This configuration is allowed for only 'instance-type virtual-switch'";
       uses juniper-routing-instance-switch-options;
     }
     container pbb-options {
       description "Provider backbone bridging options for routing-instance";
       junos:must "(!(\".. protocols evpn\"))";
       junos:must-message "pbb-options are not supported with protocol evpn";
       junos:must "(!(\".. protocols vpls\"))";
       junos:must-message "PBB is not supported with protocol vpls";
       junos:must "(\".. instance-type virtual-switch\")";
       junos:must-message "This configuration is allowed for only 'instance-type virtual-switch'";
       uses juniper-routing-instance-pbb-options;
     }
     list service-groups {
       key name;
       description "Service group configuration for routing-instance";
       junos:must "(!(\".. protocols vpls\"))";
       junos:must-message "PBB is not supported with protocol vpls";
       junos:must "(\".. instance-type virtual-switch\")";
       junos:must-message "This configuration is allowed for only 'instance-type virtual-switch'";
       uses juniper-routing-instance-service-groups;
     }
     leaf layer3-domain-identifier {
       description "Layer3 domain identifier";
       type union {
         type string {
           pattern "<.*>|$.*";
         }
         type uint32 {
           range "2 .. 8192";
         }
       }
     }
     leaf l2-domain-id-for-l3 {
       description "Layer2 domain identifier for L3";
       type union {
         type string {
           pattern "<.*>|$.*";
         }
         type uint32 {
           range "2 .. 4095";
         }
       }
     }
     container forwarding-instance {
       junos:must "(\".. instance-type mac-vrf\")";
       junos:must-message "Forwarding instance id is applicable only for mac-vrf instances";
       description "Forwarding instance parameters for a mac-vrf instance";
       leaf identifier {
         description "Forwarding instance identifier";
         type union {
           type string {
             pattern "<.*>|$.*";
           }
           type uint32 {
             range "1 .. 99";
           }
         }
       }
     }
     leaf service-type {
       description "Sevice type";
       junos:must "(\".. instance-type mac-vrf\")";
       junos:must-message "service-type config is allowed for instance type mac-vrf only";
       type enumeration {
         enum "vlan-based" {
           description "Instance service type vlan-based";
         }
         enum "vlan-bundle" {
           description "Instance service type vlan-bundle";
         }
         enum "vlan-aware" {
           description "Instance service type vlan-aware";
         }
       }
     }
     list interface {
       key name;
       description "Interface name for this routing instance";
       leaf name {
         junos:must "((!(\"interfaces $$-IFL etree-ac-role\") || \".. .. protocols evpn evpn-etree\"))";
         junos:must-message "etree must be enabled under routing-instance";
         junos:must "(!((\"interfaces $$-IFL family bridge interface-mode\" && \".. .. instance-type evpn\")))";
         junos:must-message "access/trunk interfaces are not allowed in evpn instance";
         junos:must "((!((\"interfaces $$-IFL vlan-id-list\" || \"interfaces $$-IFL vlan-tags inner-list\")) || !((\".. .. vlan-id\" || \".. .. vlan-tags\"))))";
         junos:must-message "interface with vlan-id-list/inner-list cannot be added to routing-instance with a vlan-id/vlan-tags configured";
         junos:must "((!((\"interfaces $$-IFL family bridge interface-mode\" || \"interfaces $$-IFL family ethernet-switching\")) || (\".. .. instance-type virtual-switch\" || \".. .. instance-type mac-vrf\")))";
         junos:must-message "Interface with 'interface-mode' is allowed only in a virtual-switch or mac-vrf instance";
         junos:must "((!(\".. .. instance-type virtual-switch\") || (\"interfaces $$-IFL family bridge interface-mode\" || \"interfaces $$-IFL family ethernet-switching\")))";
         junos:must-message "Only interface with 'interface-mode' is allowed in a virtual-switch";
         junos:must "(!(\".. .. .. routing-instances bridge-domains interfaces $$\"))";
         junos:must-message "The interface cannot be defined both at routing-instance and bridge-domain level";
         junos:must "((!(\"interfaces $$-IFL vlan-id-range\") || (\".. .. instance-type vpls\" || (\".. .. instance-type evpn\" || \"security forwarding-options mode tap interface $$\"))))";
         junos:must-message "vlan-id-range is specified for this logical interface; the routing instance must be of type vpls or evpn or in Security TAP mode";
         junos:must "(((\".. .. vlan-id all\" && \"interfaces $$-IFL input-vlan-map pop\") || (\".. .. vlan-id inner-all\" || (!((\".. .. vlan-id\" || \".. .. vlan-tags\")) || (!((\"interfaces $$-IFL input-vlan-map\" || \"interfaces $$-IFL output-vlan-map\")) || (\".. .. no-normalization\" || \".. .. bridge-options no-normalization\"))))))";
         junos:must-message "interface with input/output vlan-maps cannot be added to a routing-instance with a vlan-id/vlan-tags configured";
         junos:must "((!(\"interfaces $$-IFL vlan-tags inner-range\") || ((\".. .. vlan-id all\" || \".. .. vlan-id inner-all\") || (\".. .. no-normalization\" || \".. .. bridge-options no-normalization\"))))";
         junos:must-message "vlan-tags inner-range is specified for this logical interface; 'vlan-id all' or 'vlan-id inner-all' should also be enabled";
         junos:must "(!((\"interfaces $$-IFL family ethernet-switching\" && \".. instance-type virtual-switch\")))";
         junos:must-message "Interface with family ethernet-switching is not allowed in this routing instance type";
         type string;
       }
       uses apply-advanced;
       choice mode {
         case case_1 {
           leaf any {
             description "Interface used for both unicast and multicast traffic";
             type empty;
           }
         }
         case case_2 {
           leaf unicast {
             description "Interface used for unicast traffic only";
             type empty;
           }
         }
         case case_3 {
           leaf multicast {
             description "Interface used for multicast traffic only";
             type empty;
           }
         }
       }
       leaf primary {
         description "Preferred multicast vt interface for the routing-instance";
         junos:must "(!(\".. unicast\"))";
         junos:must-message "'primary' option can not be configured for unicast interface";
         junos:must "((\".. .. instance-type vrf\" || \".. .. instance-type mpls-internet-multicast\"))";
         junos:must-message "'primary' option can only be configured for instance-type 'vrf' or 'mpls-internet-multicast'";
         type empty;
       }
       leaf protect-interface {
         description "Name of protect interface";
         junos:must "(\"interfaces $$\")";
         junos:must-message "Interface must be part of this routing instance";
         junos:must "(!(\"interfaces ${inter_name} esi\"))";
         junos:must-message "ESI can not be configured for protect interface";
         junos:must "(\"routing-instances ${instance} protocols evpn\")";
         junos:must-message "Protocol EVPN must be configured in the evpn instance";
         type union {
           type jt:interface-name;
           type string {
             pattern "<.*>|$.*";
           }
         }
       }
     }
     container route-distinguisher {
       description "Route distinguisher for this instance";
       leaf rd-type {
         description "Number in (16 bit:32 bit) or (32 bit 'L':16 bit) or (IP address:16 bit) format";
         type string {
           junos:posix-pattern "^[0-9.]+L?:[0-9]+$";
           junos:pattern-message "Use format 'x:y' where 'x' is an AS number followed by an optional 'L' (To indicate 4 byte AS), or an IP address and 'y' is a number. e.g. 123456L:100";
         }
       }
     }
     leaf-list vrf-import {
       ordered-by user;
       description "Import policy for VRF instance RIBs";
       type jt:policy-algebra;
     }
     leaf-list vrf-export {
       ordered-by user;
       description "Export policy for VRF instance RIBs";
       type jt:policy-algebra;
     }
     container vrf-target {
       description "VRF target community configuration";
       uses apply-advanced;
       leaf community {
         description "Target community to use in import and export";
         type string {
           junos:posix-pattern "^[a-z]+:[0-9.]+L?:[0-9]+$";
           junos:pattern-message "Use format 'target:x:y' where 'x' is an AS number followed by an optional 'L' (To indicate 4 byte AS), or an IP address and 'y' is a number. e.g. target:123456L:100";
         }
       }
       leaf import {
         description "Target community to use when filtering on import";
         type string {
           junos:posix-pattern "^[a-z]+:[0-9.]+L?:[0-9]+$";
           junos:pattern-message "Use format 'target:x:y' where 'x' is an AS number followed by an optional 'L' (To indicate 4 byte AS), or an IP address and 'y' is a number. e.g. target:123456L:100";
         }
       }
       leaf export {
         description "Target community to use when marking routes on export";
         type string {
           junos:posix-pattern "^[a-z]+:[0-9.]+L?:[0-9]+$";
           junos:pattern-message "Use format 'target:x:y' where 'x' is an AS number followed by an optional 'L' (To indicate 4 byte AS), or an IP address and 'y' is a number. e.g. target:123456L:100";
         }
       }
       leaf auto {
         description "Auto derive import and export target community from BGP AS & L2";
         junos:must "((\".. .. instance-type evpn\" || (\".. .. instance-type virtual-switch\" || \".. .. instance-type mac-vrf\")))";
         junos:must-message "vrf-target auto is meant only for evpn or virtual-switch instance or mac-vrf";
         type empty;
       }
     }
     leaf no-vrf-advertise {
       description "Don't advertise this instance to remote PEs";
       type empty;
     }
     leaf non-forwarding-vrf {
       description "Don't create VRF forwarding table for local or transit routes belonging to this VPN";
       junos:must "(\".. provider-tunnel inter-as\")";
       junos:must-message "Inter-AS segmented p-tunnel configuration is required";
       type empty;
     }
     container vrf-advertise-selective {
       presence "enable vrf-advertise-selective";
       junos:must "(!(\".. no-vrf-advertise\"))";
       junos:must-message "Selective vrf advertise cannot be used with no-vrf-advertise knob";
       description "Override no-vrf-advertise knob for the specified address family";
       uses apply-advanced;
       container family {
         description "Protocol family to be selectively advertised";
         uses apply-advanced;
         leaf inet-mvpn {
           description "IPv4 MVPN Address Family";
           type empty;
         }
         leaf inet6-mvpn {
           description "IPv6 MVPN Address Family";
           type empty;
         }
       }
     }
     container vrf-table-label {
       presence "enable vrf-table-label";
       description "Advertise a single VPN label for all routes in the VRF";
       leaf static {
         description "Specify label value to be used";
         type union {
           type string {
             pattern "<.*>|$.*";
           }
           type uint32 {
             range "16 .. 1048575";
           }
         }
       }
       leaf source-class-usage {
         description "Enable source class usage";
         type empty;
       }
     }
     choice vrf-propagate-ttl-or-no-vrf-propagate-ttl {
       case case_1 {
         leaf no-vrf-propagate-ttl {
           description "Disable TTL propagation from IP to MPLS (on push) and MPLS to IP (on pop)";
           type empty;
         }
       }
       case case_2 {
         leaf vrf-propagate-ttl {
           description "Enable TTL propagation from IP to MPLS (on push) and MPLS to IP (on pop)";
           type empty;
         }
       }
     }
     container provider-tunnel {
       junos:must "(!((\". inter-as\" && \". selective\")))";
       junos:must-message "Selective p-tunnel configuration not allowed on ASBR";
       junos:must "(!((\" .. non-forwarding-vrf\" && (\". rsvp-te\" || (\". pim-asm\" || (\". pim-ssm\" || \". ldp-p2mp\"))))))";
       junos:must-message "Inclusive p-tunnel configuration not allowed on ASBR with non-forwarding-vrf";
       junos:must "((!(\".. non-forwarding-vrf\") || \". inter-as\"))";
       junos:must-message "Non-forwarding VRF can only be configured with Inter-AS segmented p-tunnels";
       description "Provider tunnel configuration";
       uses apply-advanced;
       container external-controller {
         junos:must "((\".. .. protocols mvpn\" && (\".. .. instance-type vrf\" || \".. .. instance-type mpls-internet-multicast\")))";
         junos:must-message "External point-to-multipoint LSP provider can be configured only for MVPN instances";
         description "External point-to-multipoint LSP provider for flooding";
         uses apply-advanced;
         choice external-provider {
           case case_1 {
             leaf pccd {
               description "Use PCCD for external point-to-multipoint LSP computation entity";
               type empty;
             }
           }
         }
       }
       choice tunnel-type {
         case case_1 {
           container rsvp-te {
             junos:must "(!(((\".. .. instance-type evpn\" || \".. .. instance-type virtual-switch\") && \".. .. protocols evpn encapsulation vxlan\")))";
             junos:must-message "P2MP Provider Tunnels are not allowed for VxLAN encapsulation";
             junos:must "(!(((\".. .. instance-type evpn\" || \".. .. instance-type virtual-switch\") && \".. .. protocols evpn pbb-evpn-core\")))";
             junos:must-message "P2MP Provider Tunnels are not allowed for PBB-EVPN";
             junos:must "((\".. .. instance-type evpn\" || (\".. .. instance-type virtual-switch\" || (\".. .. instance-type vpls\" || (\".. .. protocols mvpn\" && (\".. .. instance-type vrf\" || \".. .. instance-type mpls-internet-multicast\"))))))";
             junos:must-message "Point-to-multipoint LSPs can be configured only for EVPN, VPLS or MVPN instances";
             junos:must "(\"protocols rsvp\")";
             junos:must-message "RSVP must be configured in the master instance";
             description "RSVP-TE point-to-multipoint LSP for flooding";
             uses apply-advanced;
             choice static-or-dynamic {
               case case_1 {
                 leaf static-lsp {
                   description "Name of point-to-multipoint LSP";
                   junos:must "(!((\".. .. .. instance-type evpn\" || \".. .. .. instance-type virtual-switch\")))";
                   junos:must-message "Static LSPs are not allowed for EVPN instances";
                   junos:must "((any \"protocols mpls label-switched-path <*> p2mp $$\" || \".. .. .. instance-type vpls\"))";
                   junos:must-message "Referenced point-to-multipoint static LSP does not exist";
                   type string {
                     junos:posix-pattern "^.{1,32}$";
                     junos:pattern-message "Must be a string of 32 characters or less";
                   }
                 }
               }
               case case_2 {
                 container label-switched-path-template {
                   description "Template for dynamic point-to-multipoint LSP parameters";
                   uses apply-advanced;
                   choice dynamic-template {
                     case case_1 {
                       leaf template-name {
                         description "Name of point-to-multipoint LSP template";
                         junos:must "((\"protocols mpls label-switched-path $$\" && (\"protocols mpls label-switched-path $$ template\" && \"protocols mpls label-switched-path $$ p2mp\")))";
                         junos:must-message "Referenced point-to-multipoint LSP template does not exist";
                         type string {
                           junos:posix-pattern "^.{1,32}$";
                           junos:pattern-message "Must be a string of 32 characters or less";
                         }
                       }
                     }
                     case case_2 {
                       leaf default-template {
                         description "Use default parameters";
                         type empty;
                       }
                     }
                   }
                 }
               }
             }
           }
         }
         case case_2 {
           container ldp-p2mp {
             presence "enable ldp-p2mp";
             junos:must "(\"protocols ldp p2mp\")";
             junos:must-message "LDP P2MP must be configured in the master instance";
             junos:must "((\".. .. instance-type evpn\" || (\".. .. instance-type virtual-switch\" || (\".. .. protocols mvpn\" && (\".. .. instance-type vrf\" || \".. .. instance-type mpls-internet-multicast\")))))";
             junos:must-message "LDP P2MP LSPs can be configured only for EVPN or MVPN instances";
             junos:must "(!(((\".. .. instance-type evpn\" || \".. .. instance-type virtual-switch\") && \".. .. protocols evpn encapsulation vxlan\")))";
             junos:must-message "P2MP Provider Tunnels are not allowed for VxLAN encapsulation";
             junos:must "(!(((\".. .. instance-type evpn\" || \".. .. instance-type virtual-switch\") && \".. .. protocols evpn pbb-evpn-core\")))";
             junos:must-message "P2MP Provider Tunnels are not allowed for PBB-EVPN";
             description "LDP point-to-multipoint LSP for flooding";
           }
         }
         case case_3 {
           container ingress-replication {
             junos:must "(((\".. .. instance-type vrf\" || \".. .. instance-type mpls-internet-multicast\") && \".. .. protocols mvpn\"))";
             junos:must-message "Ingress Replication can be configured only for MVPN instances";
             junos:must "(!(\".. .. protocols mvpn sender-based-rpf\"))";
             junos:must-message "This release does not support Sender based RPF for inclusive ingress replication provider tunnels";
             description "Ingress replication tunnel";
             uses apply-advanced;
             leaf create-new-ucast-tunnel {
               description "Create new unicast tunnel for ingress replication";
               junos:must "(\".. label-switched-path label-switched-path-template\")";
               junos:must-message "label-switched-path-template must be defined";
               type empty;
             }
             container label-switched-path {
               presence "enable label-switched-path";
               description "Point-to-point LSP unicast tunnel";
               uses apply-advanced;
               container label-switched-path-template {
                 junos:must "(\".. .. create-new-ucast-tunnel\")";
                 junos:must-message "Templates must be specified when and only when create-new-ucast-tunnel is defined";
                 description "Template for dynamic point-to-point LSP parameters";
                 uses apply-advanced;
                 choice dynamic-template {
                   case case_1 {
                     leaf template-name {
                       description "Name of point-to-point LSP template";
                       junos:must "((\"protocols mpls label-switched-path $$\" && (\"protocols mpls label-switched-path $$ template\" && !(\"protocols mpls label-switched-path $$ p2mp\"))))";
                       junos:must-message "Referenced point-to-point LSP template does not exist";
                       type string {
                         junos:posix-pattern "^.{1,32}$";
                         junos:pattern-message "Must be a string of 32 characters or less";
                       }
                     }
                   }
                   case case_2 {
                     leaf default-template {
                       description "Use default parameters";
                       type empty;
                     }
                   }
                 }
               }
             }
           }
         }
         case case_4 {
           container pim-asm {
             junos:must "(!(\".. .. protocols mvpn sender-based-rpf\"))";
             junos:must-message "this release does not support sender based RPF for PIM-SM provider tunnels";
             junos:must "(!(\"protocols pim mpls-internet-multicast\"))";
             junos:must-message "mpls-internet-multicast must not be configured";
             junos:must "(\"protocols pim\")";
             junos:must-message "PIM-SM must be configured in the master instance";
             junos:must "(\".. .. instance-type vrf\")";
             junos:must-message "PIM-SM must be configured only for vrf instances";
             description "PIM-SM provider tunnel";
             uses apply-advanced;
             leaf group-address {
               description "PIM-SM provider tunnel group address";
               type jt:ipv4addr;
             }
             container family {
               presence "enable family";
               description "PIM-SM provider tunnel address family";
               status deprecated;
               uses apply-advanced;
               container inet {
                 presence "enable inet";
                 description "IPv4 PIM-SM provider tunnel";
                 uses apply-advanced;
                 leaf group-address {
                   description "PIM-SM provider tunnel group address for IPV4";
                   type jt:ipv4addr;
                 }
                 leaf tunnel-source {
                   description "Source address for the provider space mGRE tunnel";
                   type jt:ipv4addr;
                 }
               }
               container inet6 {
                 presence "enable inet6";
                 description "IPv6 PIM-SM provider tunnel";
                 uses apply-advanced;
                 leaf group-address {
                   description "PIM-SM provider tunnel group address for IPV6";
                   type jt:ipv4addr;
                 }
                 leaf tunnel-source {
                   description "Source address for the provider space mGRE tunnel";
                   type jt:ipv4addr;
                 }
               }
             }
           }
         }
         case case_5 {
           container pim-ssm {
             junos:must "(!(\".. .. protocols mvpn sender-based-rpf\"))";
             junos:must-message "This release does not support sender based RPF for PIM-SSM provider tunnels";
             junos:must "(!(\"protocols pim mpls-internet-multicast\"))";
             junos:must-message "mpls-internet-multicast must not be configured";
             junos:must "(\"protocols pim\")";
             junos:must-message "PIM-SSM must be configured in the master instance";
             junos:must "(\".. .. protocols mvpn\")";
             junos:must-message "PIM-SSM provider tunnel can be configured only for multicast VPN instances";
             junos:must "(\".. .. instance-type vrf\")";
             junos:must-message "PIM-SM must be configured only for vrf instances";
             description "PIM-SSM provider tunnel";
             uses apply-advanced;
             leaf group-address {
               description "PIM-SSM provider tunnel group address";
               type jt:ipv4addr;
             }
             container family {
               presence "enable family";
               description "PIM-SSM provider tunnel address family";
               status deprecated;
               uses apply-advanced;
               container inet {
                 presence "enable inet";
                 description "IPv4 PIM-SSM provider tunnel";
                 uses apply-advanced;
                 leaf group-address {
                   description "PIM-SSM provider tunnel group address for IPV4";
                   type jt:ipv4addr;
                 }
                 leaf tunnel-source {
                   description "Source address for the provider space mGRE tunnel";
                   type jt:ipv4addr;
                 }
               }
               container inet6 {
                 presence "enable inet6";
                 description "IPv6 PIM-SSM provider tunnel";
                 uses apply-advanced;
                 leaf group-address {
                   description "PIM-SSM provider tunnel group address for IPV6";
                   type jt:ipv4addr;
                 }
                 leaf tunnel-source {
                   description "Source address for the provider space mGRE tunnel";
                   type jt:ipv4addr;
                 }
               }
             }
           }
         }
       }
       container inter-as {
         junos:must "(\".. .. non-forwarding-vrf\")";
         junos:must-message "Inter-as segmented tunnels can only be configured for non-forwarding-vrfs";
         junos:must "(!(\".. .. protocols mvpn sender-based-rpf\"))";
         junos:must-message "This release does not support sender based RPF for inter-as provider tunnels";
         junos:must "(\".. .. instance-type vrf\")";
         junos:must-message "Inter-as segmented tunnels can only be configured for VRF instances";
         junos:must "(\".. .. protocols mvpn\")";
         junos:must-message "Inter-as segmented tunnels can only be configured for MVPN instances";
         description "Inter-AS segmented tunnels";
         uses apply-advanced;
         choice tunnel-type {
           case case_1 {
             container ingress-replication {
               junos:must "(\". label-switched-path label-switched-path-template\")";
               junos:must-message "label-switched-path template must be configured for Inter-AS segmented tunnel";
               description "Ingress replication tunnel";
               uses apply-advanced;
               leaf create-new-ucast-tunnel {
                 description "Create new unicast tunnel for ingress replication";
                 junos:must "(\".. label-switched-path label-switched-path-template\")";
                 junos:must-message "label-switched-path-template must be defined";
                 type empty;
               }
               container label-switched-path {
                 presence "enable label-switched-path";
                 description "Point-to-point LSP unicast tunnel";
                 uses apply-advanced;
                 container label-switched-path-template {
                   junos:must "(\".. .. create-new-ucast-tunnel\")";
                   junos:must-message "Templates must be specified when and only when create-new-ucast-tunnel is defined";
                   description "Template for dynamic point-to-point LSP parameters";
                   uses apply-advanced;
                   choice dynamic-template {
                     case case_1 {
                       leaf template-name {
                         description "Name of point-to-point LSP template";
                         junos:must "((\"protocols mpls label-switched-path $$\" && (\"protocols mpls label-switched-path $$ template\" && !(\"protocols mpls label-switched-path $$ p2mp\"))))";
                         junos:must-message "Referenced point-to-point LSP template does not exist";
                         type string {
                           junos:posix-pattern "^.{1,32}$";
                           junos:pattern-message "Must be a string of 32 characters or less";
                         }
                       }
                     }
                     case case_2 {
                       leaf default-template {
                         description "Use default parameters";
                         type empty;
                       }
                     }
                   }
                 }
               }
             }
           }
           case case_2 {
             container rsvp-te {
               junos:must "(\"protocols rsvp\")";
               junos:must-message "RSVP must be configured in the master instance";
               description "RSVP-TE point-to-multipoint LSP for flooding";
               uses apply-advanced;
               choice static-or-dynamic {
                 case case_1 {
                   container label-switched-path-template {
                     description "Template for dynamic point-to-multipoint LSP parameters";
                     uses apply-advanced;
                     choice dynamic-template {
                       case case_1 {
                         leaf template-name {
                           description "Name of point-to-multipoint LSP template";
                           junos:must "((\"protocols mpls label-switched-path $$\" && (\"protocols mpls label-switched-path $$ template\" && \"protocols mpls label-switched-path $$ p2mp\")))";
                           junos:must-message "Referenced point-to-multipoint LSP template does not exist";
                           type string {
                             junos:posix-pattern "^.{1,32}$";
                             junos:pattern-message "Must be a string of 32 characters or less";
                           }
                         }
                       }
                       case case_2 {
                         leaf default-template {
                           description "Use default parameters";
                           type empty;
                         }
                       }
                     }
                   }
                 }
               }
             }
           }
           case case_3 {
             container ldp-p2mp {
               presence "enable ldp-p2mp";
               junos:must "(\"protocols ldp p2mp\")";
               junos:must-message "LDP P2MP must be configured in the master instance";
               description "LDP point-to-multipoint LSP for flooding";
             }
           }
         }
         container inter-region-segmented {
           junos:must "(!((\".. pim-ssm\" || \".. pim-asm\")))";
           junos:must-message "Inter-region-segmented cannot be set for PIM tunnel";
           description "Inter-Region Segmented LSP triggered by threshold rate and/or fan-out";
           uses apply-advanced;
           leaf threshold {
             description "Data threshold rate to trigger segmentation";
             units "kilobits";
             type union {
               type string {
                 pattern "<.*>|$.*";
               }
               type uint32 {
                 range "0 .. 1000000";
               }
             }
           }
           leaf fan-out {
             description "Number of remote Leaf-AD routes";
             type union {
               type string {
                 pattern "<.*>|$.*";
               }
               type uint32 {
                 range "1 .. 10000";
               }
             }
           }
         }
       }
       container inter-region {
         junos:must "((\".. .. instance-type vrf\" || \".. .. instance-type mpls-internet-multicast\"))";
         junos:must-message "Inter-region segmented tunnels can only be configured for VRF or Internet-multicast instances";
         junos:must "(!((\".. selective\" || (\".. pim-ssm\" || (\".. pim-asm\" || (\".. rsvp-te\" || (\".. ldp-p2mp\" || (\".. ingress-replication\" || \".. inter-as\"))))))))";
         junos:must-message "Inter-region on RBR can not be allowed with other tunnel options";
         description "Inter-region segmented tunnels";
         uses apply-advanced;
         choice segmented-or-not {
           case case_1 {
             leaf template {
               description "Use inter-region segmentation template";
               junos:must "(\"protocols mvpn inter-region-template template $$\")";
               junos:must-message "Referenced template doesn't exist";
               type string;
             }
           }
           case case_2 {
             leaf no-inter-region-segmentation {
               description "Do not participate in inter-region segmentation";
               type empty;
             }
           }
         }
       }
       container inter-region-segmented {
         junos:must "(!((\".. pim-ssm\" || \".. pim-asm\")))";
         junos:must-message "Inter-region-segmented cannot be set for PIM tunnel";
         description "Inter-Region Segmented LSP triggered by fan-out factor only";
         uses apply-advanced;
         leaf fan-out {
           description "Number of remote Leaf-AD routes";
           type union {
             type string {
               pattern "<.*>|$.*";
             }
             type uint32 {
               range "1 .. 10000";
             }
           }
         }
       }
       container selective {
         junos:must "(\".. .. protocols mvpn\")";
         junos:must-message "Selective tunnels can only be configured for MVPN instances";
         description "Selective tunnels";
         uses apply-advanced;
         leaf tunnel-limit {
           description "Maximum number of selective tunnels";
           type union {
             type string {
               pattern "<.*>|$.*";
             }
             type uint32 {
               range "0 .. 30000";
             }
           }
         }
         leaf leaf-tunnel-limit-inet {
           description "Maximum number of selective leaf tunnels for v4";
           junos:must "(\".. .. .. protocols mvpn mvpn-mode rpt-spt\")";
           junos:must-message "Selective leaf tunnel limit can only be configured for MVPN rpt-spt mode";
           type union {
             type string {
               pattern "<.*>|$.*";
             }
             type uint32 {
               range "0 .. 15000";
             }
           }
         }
         leaf leaf-tunnel-limit-inet6 {
           description "Maximum number of selective leaf tunnels for v6";
           junos:must "(\".. .. .. protocols mvpn mvpn-mode rpt-spt\")";
           junos:must-message "Selective leaf tunnel limit can only be configured for MVPN rpt-spt mode";
           type union {
             type string {
               pattern "<.*>|$.*";
             }
             type uint32 {
               range "0 .. 15000";
             }
           }
         }
         container wildcard-group-inet {
           description "IPv4 wilcard group matching any group address";
           uses apply-advanced;
           container wildcard-source {
             presence "enable wildcard-source";
             junos:must "(\".. .. .. .. protocols mvpn mvpn-mode rpt-spt\")";
             junos:must-message "MVPN instance needs to be in rpt-spt mode while configuring wildcard-source for selective provider tunnels";
             description "Use Selective-Tunnel for wildcard-source (*,G) joins";
             uses apply-advanced;
             leaf threshold-rate {
               description "Data threshold to create new tunnel";
               units "kilobits";
               type union {
                 type string {
                   pattern "<.*>|$.*";
                 }
                 type uint32 {
                   range "0 .. 1000000";
                 }
               }
             }
             choice tunnel-type {
               case case_1 {
                 container ingress-replication {
                   junos:must "(((\".. .. .. .. .. instance-type vrf\" || \".. .. .. .. .. instance-type mpls-internet-multicast\") && \".. .. .. .. .. protocols mvpn\"))";
                   junos:must-message "Ingress Replication can be configured only for MVPN instances. Sender based RPF is not supported for ingress-replication provider-tunnels";
                   description "Ingress replication tunnel";
                   uses apply-advanced;
                   leaf create-new-ucast-tunnel {
                     description "Create new unicast tunnel for ingress replication";
                     junos:must "(\".. label-switched-path label-switched-path-template\")";
                     junos:must-message "label-switched-path-template must be defined";
                     type empty;
                   }
                   container label-switched-path {
                     presence "enable label-switched-path";
                     description "Point-to-point LSP unicast tunnel";
                     uses apply-advanced;
                     container label-switched-path-template {
                       junos:must "(\".. .. create-new-ucast-tunnel\")";
                       junos:must-message "Templates must be specified when and only when create-new-ucast-tunnel is defined";
                       description "Template for dynamic point-to-point LSP parameters";
                       uses apply-advanced;
                       choice dynamic-template {
                         case case_1 {
                           leaf template-name {
                             description "Name of point-to-point LSP template";
                             junos:must "((\"protocols mpls label-switched-path $$\" && (\"protocols mpls label-switched-path $$ template\" && !(\"protocols mpls label-switched-path $$ p2mp\"))))";
                             junos:must-message "Referenced point-to-point LSP template does not exist";
                             type string {
                               junos:posix-pattern "^.{1,32}$";
                               junos:pattern-message "Must be a string of 32 characters or less";
                             }
                           }
                         }
                         case case_2 {
                           leaf default-template {
                             description "Use default parameters";
                             type empty;
                           }
                         }
                       }
                     }
                   }
                 }
               }
               case case_2 {
                 container rsvp-te {
                   junos:must "(\"protocols rsvp\")";
                   junos:must-message "RSVP must be configured in the master instance";
                   description "RSVP-TE point-to-multipoint LSP for flooding";
                   uses apply-advanced;
                   choice static-or-dynamic {
                     case case_1 {
                       leaf static-lsp {
                         description "Name of point-to-multipoint LSP";
                         junos:must "(!(\".. .. .. .. .. rsvp-te static-lsp $$\"))";
                         junos:must-message "Referenced point-to-multipoint static LSP configured for inclusive tunnel";
                         junos:must "(any \"protocols mpls label-switched-path <*> p2mp $$\")";
                         junos:must-message "Referenced point-to-multipoint static LSP does not exist";
                         type string {
                           junos:posix-pattern "^.{1,32}$";
                           junos:pattern-message "Must be a string of 32 characters or less";
                         }
                       }
                     }
                     case case_2 {
                       container label-switched-path-template {
                         description "Template for dynamic point-to-multipoint LSP parameters";
                         uses apply-advanced;
                         choice dynamic-template {
                           case case_1 {
                             leaf template-name {
                               description "Name of point-to-multipoint LSP template";
                               junos:must "((\"protocols mpls label-switched-path $$\" && (\"protocols mpls label-switched-path $$ template\" && \"protocols mpls label-switched-path $$ p2mp\")))";
                               junos:must-message "Referenced point-to-multipoint LSP template does not exist";
                               type string {
                                 junos:posix-pattern "^.{1,32}$";
                                 junos:pattern-message "Must be a string of 32 characters or less";
                               }
                             }
                           }
                           case case_2 {
                             leaf default-template {
                               description "Use default parameters";
                               type empty;
                             }
                           }
                         }
                       }
                     }
                   }
                 }
               }
               case case_3 {
                 container ldp-p2mp {
                   presence "enable ldp-p2mp";
                   junos:must "(\"protocols ldp p2mp\")";
                   junos:must-message "LDP P2MP must be configured in the master instance";
                   junos:must "((\".. .. .. .. .. protocols mvpn\" && (\".. .. .. .. .. instance-type vrf\" || \".. .. .. .. .. instance-type mpls-internet-multicast\")))";
                   junos:must-message "LDP P2MP LSPs can be configured only for MVPN instances";
                   description "LDP point-to-multipoint LSP for flooding";
                 }
               }
               case case_4 {
                 container pim-ssm {
                   junos:must "(!(\".. .. .. .. .. protocols mvpn sender-based-rpf\"))";
                   junos:must-message "This release does not support sender based RPF for PIM-SSM provider-tunnel";
                   junos:must "(\".. .. .. .. .. protocols mvpn\")";
                   junos:must-message "";
                   junos:must "(\".. .. .. .. .. instance-type vrf\")";
                   junos:must-message "PIM-SSM can be configured only for vrf instances";
                   junos:must "(\"protocols pim\")";
                   junos:must-message "PIM-SSM must be configured in the master instance";
                   description "PIM-SSM provider tunnel";
                   uses apply-advanced;
                   leaf group-range {
                     description "PIM-SSM provider tunnel group range";
                     type jt:ipv4prefix;
                   }
                 }
               }
             }
             container inter-region-segmented {
               junos:must "(!((\".. pim-ssm\" || \".. pim-asm\")))";
               junos:must-message "Inter-region-segmented cannot be set for PIM tunnel";
               description "Inter-Region Segmented LSP triggered by fan-out factor only";
               uses apply-advanced;
               leaf fan-out {
                 description "Number of remote Leaf-AD routes";
                 type union {
                   type string {
                     pattern "<.*>|$.*";
                   }
                   type uint32 {
                     range "1 .. 10000";
                   }
                 }
               }
             }
           }
         }
         container wildcard-group-inet6 {
           description "IPv6 wilcard group matching any group address";
           uses apply-advanced;
           container wildcard-source {
             presence "enable wildcard-source";
             junos:must "(\".. .. .. .. protocols mvpn mvpn-mode rpt-spt\")";
             junos:must-message "MVPN instance needs to be in rpt-spt mode while configuring wildcard-source for selective provider tunnels";
             description "Use Selective-Tunnel for wildcard-source (*,G) joins";
             uses apply-advanced;
             leaf threshold-rate {
               description "Data threshold to create new tunnel";
               units "kilobits";
               type union {
                 type string {
                   pattern "<.*>|$.*";
                 }
                 type uint32 {
                   range "0 .. 1000000";
                 }
               }
             }
             choice tunnel-type {
               case case_1 {
                 container ingress-replication {
                   junos:must "(((\".. .. .. .. .. instance-type vrf\" || \".. .. .. .. .. instance-type mpls-internet-multicast\") && \".. .. .. .. .. protocols mvpn\"))";
                   junos:must-message "Ingress Replication can be configured only for MVPN instances";
                   description "Ingress replication tunnel";
                   uses apply-advanced;
                   leaf create-new-ucast-tunnel {
                     description "Create new unicast tunnel for ingress replication";
                     junos:must "(\".. label-switched-path label-switched-path-template\")";
                     junos:must-message "label-switched-path-template must be defined";
                     type empty;
                   }
                   container label-switched-path {
                     presence "enable label-switched-path";
                     description "Point-to-point LSP unicast tunnel";
                     uses apply-advanced;
                     container label-switched-path-template {
                       junos:must "(\".. .. create-new-ucast-tunnel\")";
                       junos:must-message "Templates must be specified when and only when create-new-ucast-tunnel is defined";
                       description "Template for dynamic point-to-point LSP parameters";
                       uses apply-advanced;
                       choice dynamic-template {
                         case case_1 {
                           leaf template-name {
                             description "Name of point-to-point LSP template";
                             junos:must "((\"protocols mpls label-switched-path $$\" && (\"protocols mpls label-switched-path $$ template\" && !(\"protocols mpls label-switched-path $$ p2mp\"))))";
                             junos:must-message "Referenced point-to-point LSP template does not exist";
                             type string {
                               junos:posix-pattern "^.{1,32}$";
                               junos:pattern-message "Must be a string of 32 characters or less";
                             }
                           }
                         }
                         case case_2 {
                           leaf default-template {
                             description "Use default parameters";
                             type empty;
                           }
                         }
                       }
                     }
                   }
                 }
               }
               case case_2 {
                 container rsvp-te {
                   junos:must "(\"protocols rsvp\")";
                   junos:must-message "RSVP must be configured in the master instance";
                   description "RSVP-TE point-to-multipoint LSP for flooding";
                   uses apply-advanced;
                   choice static-or-dynamic {
                     case case_1 {
                       leaf static-lsp {
                         description "Name of point-to-multipoint LSP";
                         junos:must "(!(\".. .. .. .. .. rsvp-te static-lsp $$\"))";
                         junos:must-message "Referenced point-to-multipoint static LSP configured for inclusive tunnel";
                         junos:must "(any \"protocols mpls label-switched-path <*> p2mp $$\")";
                         junos:must-message "Referenced point-to-multipoint static LSP does not exist";
                         type string {
                           junos:posix-pattern "^.{1,32}$";
                           junos:pattern-message "Must be a string of 32 characters or less";
                         }
                       }
                     }
                     case case_2 {
                       container label-switched-path-template {
                         description "Template for dynamic point-to-multipoint LSP parameters";
                         uses apply-advanced;
                         choice dynamic-template {
                           case case_1 {
                             leaf template-name {
                               description "Name of point-to-multipoint LSP template";
                               junos:must "((\"protocols mpls label-switched-path $$\" && (\"protocols mpls label-switched-path $$ template\" && \"protocols mpls label-switched-path $$ p2mp\")))";
                               junos:must-message "Referenced point-to-multipoint LSP template does not exist";
                               type string {
                                 junos:posix-pattern "^.{1,32}$";
                                 junos:pattern-message "Must be a string of 32 characters or less";
                               }
                             }
                           }
                           case case_2 {
                             leaf default-template {
                               description "Use default parameters";
                               type empty;
                             }
                           }
                         }
                       }
                     }
                   }
                 }
               }
               case case_3 {
                 container ldp-p2mp {
                   presence "enable ldp-p2mp";
                   junos:must "(\"protocols ldp p2mp\")";
                   junos:must-message "LDP P2MP must be configured in the master instance";
                   junos:must "((\".. .. .. .. .. protocols mvpn\" && (\".. .. .. .. .. instance-type vrf\" || \".. .. .. .. .. instance-type mpls-internet-multicast\")))";
                   junos:must-message "LDP P2MP LSPs can be configured only for MVPN instances";
                   description "LDP point-to-multipoint LSP for flooding";
                 }
               }
               case case_4 {
                 container pim-ssm {
                   junos:must "(!(\".. .. .. .. .. protocols mvpn sender-based-rpf\"))";
                   junos:must-message "This release does not support sender based RPF for PIM-SSM provider-tunnel";
                   junos:must "(\".. .. .. .. .. protocols mvpn\")";
                   junos:must-message "";
                   junos:must "(\".. .. .. .. .. instance-type vrf\")";
                   junos:must-message "PIM-SSM can be configured only for vrf instances";
                   junos:must "(\"protocols pim\")";
                   junos:must-message "PIM-SSM must be configured in the master instance";
                   description "PIM-SSM provider tunnel";
                   uses apply-advanced;
                   leaf group-range {
                     description "PIM-SSM provider tunnel group range";
                     type jt:ipv4prefix;
                   }
                 }
               }
             }
             container inter-region-segmented {
               junos:must "(!((\".. pim-ssm\" || \".. pim-asm\")))";
               junos:must-message "Inter-region-segmented cannot be set for PIM tunnel";
               description "Inter-Region Segmented LSP triggered by fan-out factor only";
               uses apply-advanced;
               leaf fan-out {
                 description "Number of remote Leaf-AD routes";
                 type union {
                   type string {
                     pattern "<.*>|$.*";
                   }
                   type uint32 {
                     range "1 .. 10000";
                   }
                 }
               }
             }
           }
         }
         list group {
           key name;
           ordered-by user;
           description "IP prefix of multicast group";
           leaf name {
             description "IP prefix of group";
             type jt:ipprefix;
           }
           uses apply-advanced;
           container wildcard-source {
             presence "enable wildcard-source";
             junos:must "(\".. .. .. .. protocols mvpn mvpn-mode rpt-spt\")";
             junos:must-message "MVPN instance needs to be in rpt-spt mode while configuring wildcard-source for selective provider tunnels";
             description "Use Selective-Tunnel for wildcard-source (*,G) joins";
             uses apply-advanced;
             leaf threshold-rate {
               description "Data threshold to create new tunnel";
               units "kilobits";
               type union {
                 type string {
                   pattern "<.*>|$.*";
                 }
                 type uint32 {
                   range "0 .. 1000000";
                 }
               }
             }
             choice tunnel-type {
               case case_1 {
                 container ingress-replication {
                   junos:must "(((\".. .. .. .. .. instance-type vrf\" || \".. .. .. .. .. instance-type mpls-internet-multicast\") && \".. .. .. .. .. protocols mvpn\"))";
                   junos:must-message "Ingress Replication can be configured only for MVPN instances.";
                   description "Ingress replication tunnel";
                   uses apply-advanced;
                   leaf create-new-ucast-tunnel {
                     description "Create new unicast tunnel for ingress replication";
                     junos:must "(\".. label-switched-path label-switched-path-template\")";
                     junos:must-message "label-switched-path-template must be defined";
                     type empty;
                   }
                   container label-switched-path {
                     presence "enable label-switched-path";
                     description "Point-to-point LSP unicast tunnel";
                     uses apply-advanced;
                     container label-switched-path-template {
                       junos:must "(\".. .. create-new-ucast-tunnel\")";
                       junos:must-message "Templates must be specified when and only when create-new-ucast-tunnel is defined";
                       description "Template for dynamic point-to-point LSP parameters";
                       uses apply-advanced;
                       choice dynamic-template {
                         case case_1 {
                           leaf template-name {
                             description "Name of point-to-point LSP template";
                             junos:must "((\"protocols mpls label-switched-path $$\" && (\"protocols mpls label-switched-path $$ template\" && !(\"protocols mpls label-switched-path $$ p2mp\"))))";
                             junos:must-message "Referenced point-to-point LSP template does not exist";
                             type string {
                               junos:posix-pattern "^.{1,32}$";
                               junos:pattern-message "Must be a string of 32 characters or less";
                             }
                           }
                         }
                         case case_2 {
                           leaf default-template {
                             description "Use default parameters";
                             type empty;
                           }
                         }
                       }
                     }
                   }
                 }
               }
               case case_2 {
                 container rsvp-te {
                   junos:must "(\"protocols rsvp\")";
                   junos:must-message "RSVP must be configured in the master instance";
                   description "RSVP-TE point-to-multipoint LSP for flooding";
                   uses apply-advanced;
                   choice static-or-dynamic {
                     case case_1 {
                       leaf static-lsp {
                         description "Name of point-to-multipoint LSP";
                         junos:must "(!(\".. .. .. .. .. rsvp-te static-lsp $$\"))";
                         junos:must-message "Referenced point-to-multipoint static LSP configured for inclusive tunnel";
                         junos:must "(any \"protocols mpls label-switched-path <*> p2mp $$\")";
                         junos:must-message "Referenced point-to-multipoint static LSP does not exist";
                         type string {
                           junos:posix-pattern "^.{1,32}$";
                           junos:pattern-message "Must be a string of 32 characters or less";
                         }
                       }
                     }
                     case case_2 {
                       container label-switched-path-template {
                         description "Template for dynamic point-to-multipoint LSP parameters";
                         uses apply-advanced;
                         choice dynamic-template {
                           case case_1 {
                             leaf template-name {
                               description "Name of point-to-multipoint LSP template";
                               junos:must "((\"protocols mpls label-switched-path $$\" && (\"protocols mpls label-switched-path $$ template\" && \"protocols mpls label-switched-path $$ p2mp\")))";
                               junos:must-message "Referenced point-to-multipoint LSP template does not exist";
                               type string {
                                 junos:posix-pattern "^.{1,32}$";
                                 junos:pattern-message "Must be a string of 32 characters or less";
                               }
                             }
                           }
                           case case_2 {
                             leaf default-template {
                               description "Use default parameters";
                               type empty;
                             }
                           }
                         }
                       }
                     }
                   }
                 }
               }
               case case_3 {
                 container ldp-p2mp {
                   presence "enable ldp-p2mp";
                   junos:must "(\"protocols ldp p2mp\")";
                   junos:must-message "LDP P2MP must be configured in the master instance";
                   junos:must "((\".. .. .. .. .. protocols mvpn\" && (\".. .. .. .. .. instance-type vrf\" || \".. .. .. .. .. instance-type mpls-internet-multicast\")))";
                   junos:must-message "LDP P2MP LSPs can be configured only for MVPN instances";
                   description "LDP point-to-multipoint LSP for flooding";
                 }
               }
               case case_4 {
                 container pim-ssm {
                   junos:must "(!(\".. .. .. .. .. protocols mvpn sender-based-rpf\"))";
                   junos:must-message "This release does not support sender based RPF for PIM-SSM provider-tunnel";
                   junos:must "(\".. .. .. .. .. protocols mvpn\")";
                   junos:must-message "";
                   junos:must "(\".. .. .. .. .. instance-type vrf\")";
                   junos:must-message "PIM-SSM can be configured only for vrf instances";
                   junos:must "(\"protocols pim\")";
                   junos:must-message "PIM-SSM must be configured in the master instance";
                   description "PIM-SSM provider tunnel";
                   uses apply-advanced;
                   leaf group-range {
                     description "PIM-SSM provider tunnel group range";
                     type jt:ipv4prefix;
                   }
                 }
               }
             }
             container inter-region-segmented {
               junos:must "(!((\".. pim-ssm\" || \".. pim-asm\")))";
               junos:must-message "Inter-region-segmented cannot be set for PIM tunnel";
               description "Inter-Region Segmented LSP triggered by threshold rate and/or fan-out";
               uses apply-advanced;
               leaf threshold {
                 description "Data threshold rate to trigger segmentation";
                 units "kilobits";
                 type union {
                   type string {
                     pattern "<.*>|$.*";
                   }
                   type uint32 {
                     range "0 .. 1000000";
                   }
                 }
               }
               leaf fan-out {
                 description "Number of remote Leaf-AD routes";
                 type union {
                   type string {
                     pattern "<.*>|$.*";
                   }
                   type uint32 {
                     range "1 .. 10000";
                   }
                 }
               }
             }
           }
           list source {
             key name;
             ordered-by user;
             description "IP prefix of one or more multicast sources";
             leaf name {
               description "IP prefix of source";
               type jt:ipprefix;
             }
             uses apply-advanced;
             choice tunnel-type {
               case case_1 {
                 container ingress-replication {
                   junos:must "(((\".. .. .. .. .. instance-type vrf\" || \".. .. .. .. .. instance-type mpls-internet-multicast\") && \".. .. .. .. .. protocols mvpn\"))";
                   junos:must-message "Ingress Replication can be configured only for MVPN instances";
                   description "Ingress replication tunnel";
                   uses apply-advanced;
                   leaf create-new-ucast-tunnel {
                     description "Create new unicast tunnel for ingress replication";
                     junos:must "(\".. label-switched-path label-switched-path-template\")";
                     junos:must-message "label-switched-path-template must be defined";
                     type empty;
                   }
                   container label-switched-path {
                     presence "enable label-switched-path";
                     description "Point-to-point LSP unicast tunnel";
                     uses apply-advanced;
                     container label-switched-path-template {
                       junos:must "(\".. .. create-new-ucast-tunnel\")";
                       junos:must-message "Templates must be specified when and only when create-new-ucast-tunnel is defined";
                       description "Template for dynamic point-to-point LSP parameters";
                       uses apply-advanced;
                       choice dynamic-template {
                         case case_1 {
                           leaf template-name {
                             description "Name of point-to-point LSP template";
                             junos:must "((\"protocols mpls label-switched-path $$\" && (\"protocols mpls label-switched-path $$ template\" && !(\"protocols mpls label-switched-path $$ p2mp\"))))";
                             junos:must-message "Referenced point-to-point LSP template does not exist";
                             type string {
                               junos:posix-pattern "^.{1,32}$";
                               junos:pattern-message "Must be a string of 32 characters or less";
                             }
                           }
                         }
                         case case_2 {
                           leaf default-template {
                             description "Use default parameters";
                             type empty;
                           }
                         }
                       }
                     }
                   }
                 }
               }
               case case_2 {
                 container rsvp-te {
                   junos:must "(\"protocols rsvp\")";
                   junos:must-message "RSVP must be configured in the master instance";
                   description "RSVP-TE point-to-multipoint LSP for flooding";
                   uses apply-advanced;
                   choice static-or-dynamic {
                     case case_1 {
                       leaf static-lsp {
                         description "Name of point-to-multipoint LSP";
                         junos:must "(!(\".. .. .. .. .. rsvp-te static-lsp $$\"))";
                         junos:must-message "Referenced point-to-multipoint static LSP configured for inclusive tunnel";
                         junos:must "(any \"protocols mpls label-switched-path <*> p2mp $$\")";
                         junos:must-message "Referenced point-to-multipoint static LSP does not exist";
                         type string {
                           junos:posix-pattern "^.{1,32}$";
                           junos:pattern-message "Must be a string of 32 characters or less";
                         }
                       }
                     }
                     case case_2 {
                       container label-switched-path-template {
                         description "Template for dynamic point-to-multipoint LSP parameters";
                         uses apply-advanced;
                         choice dynamic-template {
                           case case_1 {
                             leaf template-name {
                               description "Name of point-to-multipoint LSP template";
                               junos:must "((\"protocols mpls label-switched-path $$\" && (\"protocols mpls label-switched-path $$ template\" && \"protocols mpls label-switched-path $$ p2mp\")))";
                               junos:must-message "Referenced point-to-multipoint LSP template does not exist";
                               type string {
                                 junos:posix-pattern "^.{1,32}$";
                                 junos:pattern-message "Must be a string of 32 characters or less";
                               }
                             }
                           }
                           case case_2 {
                             leaf default-template {
                               description "Use default parameters";
                               type empty;
                             }
                           }
                         }
                       }
                     }
                   }
                 }
               }
               case case_3 {
                 container pim-ssm {
                   junos:must "(!(\".. .. .. .. .. protocols mvpn sender-based-rpf\"))";
                   junos:must-message "This release does not support sender based RPF for PIM-SSM provider-tunnel";
                   junos:must "(\".. .. .. .. .. protocols mvpn\")";
                   junos:must-message "";
                   junos:must "(\".. .. .. .. .. instance-type vrf\")";
                   junos:must-message "PIM-SSM can be configured only for vrf instances";
                   junos:must "(\"protocols pim\")";
                   junos:must-message "PIM-SSM must be configured in the master instance";
                   description "PIM-SSM provider tunnel";
                   uses apply-advanced;
                   leaf group-range {
                     description "PIM-SSM provider tunnel group range";
                     type jt:ipv4prefix;
                   }
                 }
               }
               case case_4 {
                 container ldp-p2mp {
                   presence "enable ldp-p2mp";
                   junos:must "(\"protocols ldp p2mp\")";
                   junos:must-message "LDP P2MP must be configured in the master instance";
                   junos:must "((\".. .. .. .. .. protocols mvpn\" && (\".. .. .. .. .. instance-type vrf\" || \".. .. .. .. .. instance-type mpls-internet-multicast\")))";
                   junos:must-message "LDP P2MP LSPs can be configured only for MVPN instances";
                   description "LDP point-to-multipoint LSP for flooding";
                 }
               }
             }
             leaf threshold-rate {
               description "Data threshold to create new tunnel";
               units "kilobits";
               type union {
                 type string {
                   pattern "<.*>|$.*";
                 }
                 type uint32 {
                   range "0 .. 1000000";
                 }
               }
             }
             container inter-region-segmented {
               junos:must "(!((\".. pim-ssm\" || \".. pim-asm\")))";
               junos:must-message "Inter-region-segmented cannot be set for PIM tunnel";
               description "Inter-Region Segmented LSP triggered by threshold rate and/or fan-out";
               uses apply-advanced;
               leaf threshold {
                 description "Data threshold rate to trigger segmentation";
                 units "kilobits";
                 type union {
                   type string {
                     pattern "<.*>|$.*";
                   }
                   type uint32 {
                     range "0 .. 1000000";
                   }
                 }
               }
               leaf fan-out {
                 description "Number of remote Leaf-AD routes";
                 type union {
                   type string {
                     pattern "<.*>|$.*";
                   }
                   type uint32 {
                     range "1 .. 10000";
                   }
                 }
               }
             }
           }
         }
       }
       container mdt {
         junos:must "(\".. .. protocols pim mvpn\")";
         junos:must-message "Data MDT tunnels can only be configured for PIM MVPN instances";
         description "Data MDT tunnels for PIM MVPN";
         status deprecated;
         uses apply-advanced;
         container threshold {
           description "Threshold for creation of multicast tunnels";
           uses apply-advanced;
           list group {
             key name;
             ordered-by user;
             description "IP prefix of multicast group";
             leaf name {
               description "IP prefix of group";
               type jt:ipprefix;
             }
             uses apply-advanced;
             list source {
               key name;
               ordered-by user;
               description "IP prefix of one or more multicast sources ";
               leaf name {
                 description "IP prefix of source";
                 type jt:ipprefix;
               }
               uses apply-advanced;
               leaf rate {
                 description "Data threshold to create new tunnel";
                 units "kilobits";
                 type union {
                   type string {
                     pattern "<.*>|$.*";
                   }
                   type uint32 {
                     range "10 .. 1000000";
                   }
                 }
               }
             }
           }
         }
         leaf data-mdt-reuse {
           description "Allow multiple customer streams to be transmitted over one data tunnel ";
           type empty;
         }
         leaf tunnel-limit {
           description "Maximum multicast data tunnels";
           type union {
             type string {
               pattern "<.*>|$.*";
             }
             type uint32 {
               range "0 .. 8192";
             }
           }
         }
         leaf group-range {
           description "Group address range for multicast data tunnels";
           type jt:ipprefix;
         }
       }
       container family {
         presence "enable family";
         uses apply-advanced;
         container inet {
           presence "enable inet";
           junos:must "(!((\" .. .. .. non-forwarding-vrf\" && (\". rsvp-te\" || (\". pim-asm\" || (\". pim-ssm\" || \". ldp-p2mp\"))))))";
           junos:must-message "Inclusive p-tunnel configuration not allowed on ASBR with non-forwarding-vrf";
           uses apply-advanced;
           choice tunnel-type {
             case case_1 {
               container rsvp-te {
                 junos:must "((\".. .. .. .. instance-type vpls\" || (\".. .. .. .. protocols mvpn\" && (\".. .. .. .. instance-type vrf\" || \".. .. .. .. instance-type mpls-internet-multicast\"))))";
                 junos:must-message "Point-to-multipoint LSPs can be configured only for VPLS or MVPN instances";
                 junos:must "(\"protocols rsvp\")";
                 junos:must-message "RSVP must be configured in the master instance";
                 description "RSVP-TE point-to-multipoint LSP for flooding";
                 uses apply-advanced;
                 choice static-or-dynamic {
                   case case_1 {
                     leaf static-lsp {
                       description "Name of point-to-multipoint LSP";
                       junos:must "((any \"protocols mpls label-switched-path <*> p2mp $$\" || \".. .. .. instance-type vpls\"))";
                       junos:must-message "Referenced point-to-multipoint static LSP does not exist";
                       type string {
                         junos:posix-pattern "^.{1,32}$";
                         junos:pattern-message "Must be a string of 32 characters or less";
                       }
                     }
                   }
                   case case_2 {
                     container label-switched-path-template {
                       description "Template for dynamic point-to-multipoint LSP parameters";
                       uses apply-advanced;
                       choice dynamic-template {
                         case case_1 {
                           leaf template-name {
                             description "Name of point-to-multipoint LSP template";
                             junos:must "((\"protocols mpls label-switched-path $$\" && (\"protocols mpls label-switched-path $$ template\" && \"protocols mpls label-switched-path $$ p2mp\")))";
                             junos:must-message "Referenced point-to-multipoint LSP template does not exist";
                             type string {
                               junos:posix-pattern "^.{1,32}$";
                               junos:pattern-message "Must be a string of 32 characters or less";
                             }
                           }
                         }
                         case case_2 {
                           leaf default-template {
                             description "Use default parameters";
                             type empty;
                           }
                         }
                       }
                     }
                   }
                 }
               }
             }
             case case_2 {
               container ldp-p2mp {
                 presence "enable ldp-p2mp";
                 junos:must "(\"protocols ldp p2mp\")";
                 junos:must-message "LDP P2MP must be configured in the master instance";
                 junos:must "((\".. .. .. .. protocols mvpn\" && (\".. .. .. .. instance-type vrf\" || \".. .. .. .. instance-type mpls-internet-multicast\")))";
                 junos:must-message "LDP P2MP LSPs can be configured only for valid MVPN instances";
                 description "LDP point-to-multipoint LSP for flooding";
               }
             }
             case case_3 {
               container ingress-replication {
                 junos:must "(((\".. .. .. .. instance-type vrf\" || \".. .. .. .. instance-type mpls-internet-multicast\") && \".. .. .. .. protocols mvpn\"))";
                 junos:must-message "Ingress Replication can be configured only for MVPN instances";
                 junos:must "(!(\".. .. .. .. protocols mvpn sender-based-rpf\"))";
                 junos:must-message "This release does not support Sender based RPF for inclusive ingress replication provider tunnels";
                 description "Ingress replication tunnel";
                 uses apply-advanced;
                 leaf create-new-ucast-tunnel {
                   description "Create new unicast tunnel for ingress replication";
                   junos:must "(\".. label-switched-path label-switched-path-template\")";
                   junos:must-message "label-switched-path-template must be defined";
                   type empty;
                 }
                 container label-switched-path {
                   presence "enable label-switched-path";
                   description "Point-to-point LSP unicast tunnel";
                   uses apply-advanced;
                   container label-switched-path-template {
                     junos:must "(\".. .. create-new-ucast-tunnel\")";
                     junos:must-message "Templates must be specified when and only when create-new-ucast-tunnel is defined";
                     description "Template for dynamic point-to-point LSP parameters";
                     uses apply-advanced;
                     choice dynamic-template {
                       case case_1 {
                         leaf template-name {
                           description "Name of point-to-point LSP template";
                           junos:must "((\"protocols mpls label-switched-path $$\" && (\"protocols mpls label-switched-path $$ template\" && !(\"protocols mpls label-switched-path $$ p2mp\"))))";
                           junos:must-message "Referenced point-to-point LSP template does not exist";
                           type string {
                             junos:posix-pattern "^.{1,32}$";
                             junos:pattern-message "Must be a string of 32 characters or less";
                           }
                         }
                       }
                       case case_2 {
                         leaf default-template {
                           description "Use default parameters";
                           type empty;
                         }
                       }
                     }
                   }
                 }
               }
             }
             case case_4 {
               container pim-asm {
                 junos:must "(!(\".. .. .. .. protocols mvpn sender-based-rpf\"))";
                 junos:must-message "this release does not support sender based RPF for PIM-SM provider tunnels";
                 junos:must "(!(\"protocols pim mpls-internet-multicast\"))";
                 junos:must-message "mpls-internet-multicast must not be configured";
                 junos:must "(\"protocols pim\")";
                 junos:must-message "PIM-SM must be configured in the master instance";
                 junos:must "(\".. .. .. .. instance-type vrf\")";
                 junos:must-message "PIM-SM must be configured only for vrf instances";
                 description "PIM-SM provider tunnel";
                 uses apply-advanced;
                 leaf group-address {
                   description "PIM-SM provider tunnel group address";
                   type jt:ipv4addr;
                 }
                 leaf tunnel-source {
                   description "Source address for the provider space mGRE tunnel";
                   type jt:ipv4addr;
                 }
               }
             }
             case case_5 {
               container pim-ssm {
                 junos:must "(!(\".. .. .. .. protocols mvpn sender-based-rpf\"))";
                 junos:must-message "this release does not support sender based RPF for PIM-SSM provider tunnels";
                 junos:must "(!(\"protocols pim mpls-internet-multicast\"))";
                 junos:must-message "mpls-internet-multicast must not be configured";
                 junos:must "(\"protocols pim\")";
                 junos:must-message "PIM-SSM must be configured in the master instance";
                 junos:must "(\".. .. .. .. protocols mvpn\")";
                 junos:must-message "PIM-SSM provider tunnel can be configured only for multicast VPN instances";
                 junos:must "(\".. .. .. .. instance-type vrf\")";
                 junos:must-message "PIM-SM must be configured only for vrf instances";
                 description "PIM-SSM provider tunnel";
                 uses apply-advanced;
                 leaf group-address {
                   description "PIM-SSM provider tunnel group address";
                   type jt:ipv4addr;
                 }
                 leaf tunnel-source {
                   description "Source address for the provider space mGRE tunnel";
                   type jt:ipv4addr;
                 }
               }
             }
           }
           container mdt {
             junos:must "(\".. .. .. .. protocols pim mvpn\")";
             junos:must-message "Data MDT tunnels can only be configured for PIM
                   MVPN instances";
             description "IPv4 Data MDT tunnels for PIM MVPN";
             uses apply-advanced;
             container threshold {
               description "Threshold for creation of multicast tunnels";
               uses apply-advanced;
               list group {
                 key name;
                 ordered-by user;
                 description "IP prefix of multicast group";
                 leaf name {
                   description "IP prefix of group";
                   type jt:ipprefix;
                 }
                 uses apply-advanced;
                 list source {
                   key name;
                   ordered-by user;
                   description "IP prefix of one or more multicast sources ";
                   leaf name {
                     description "IP prefix of source";
                     type jt:ipprefix;
                   }
                   uses apply-advanced;
                   leaf rate {
                     description "Data threshold to create new tunnel";
                     units "kilobits";
                     type union {
                       type string {
                         pattern "<.*>|$.*";
                       }
                       type uint32 {
                         range "10 .. 1000000";
                       }
                     }
                   }
                 }
               }
             }
             leaf data-mdt-reuse {
               description "Allow multiple customer streams to be transmitted over one data tunnel ";
               type empty;
             }
             leaf tunnel-limit {
               description "Maximum multicast data tunnels";
               type union {
                 type string {
                   pattern "<.*>|$.*";
                 }
                 type uint32 {
                   range "0 .. 8192";
                 }
               }
             }
             leaf group-range {
               description "Group address range for multicast data tunnels";
               type jt:ipprefix;
             }
           }
         }
         container inet6 {
           presence "enable inet6";
           junos:must "(!((\" .. .. .. non-forwarding-vrf\" && (\". rsvp-te\" || (\". pim-asm\" || (\". pim-ssm\" || \". ldp-p2mp\"))))))";
           junos:must-message "Inclusive p-tunnel configuration not allowed on ASBR with non-forwarding-vrf";
           uses apply-advanced;
           choice tunnel-type {
             case case_1 {
               container rsvp-te {
                 junos:must "((\".. .. .. .. instance-type vpls\" || (\".. .. .. .. protocols mvpn\" && (\".. .. .. .. instance-type vrf\" || \".. .. .. .. instance-type mpls-internet-multicast\"))))";
                 junos:must-message "Point-to-multipoint LSPs can be configured only for VPLS or MVPN instances";
                 junos:must "(\"protocols rsvp\")";
                 junos:must-message "RSVP must be configured in the master instance";
                 description "RSVP-TE point-to-multipoint LSP for flooding";
                 uses apply-advanced;
                 choice static-or-dynamic {
                   case case_1 {
                     leaf static-lsp {
                       description "Name of point-to-multipoint LSP";
                       junos:must "((any \"protocols mpls label-switched-path <*> p2mp $$\" || \".. .. .. instance-type vpls\"))";
                       junos:must-message "Referenced point-to-multipoint static LSP does not exist";
                       type string {
                         junos:posix-pattern "^.{1,32}$";
                         junos:pattern-message "Must be a string of 32 characters or less";
                       }
                     }
                   }
                   case case_2 {
                     container label-switched-path-template {
                       description "Template for dynamic point-to-multipoint LSP parameters";
                       uses apply-advanced;
                       choice dynamic-template {
                         case case_1 {
                           leaf template-name {
                             description "Name of point-to-multipoint LSP template";
                             junos:must "((\"protocols mpls label-switched-path $$\" && (\"protocols mpls label-switched-path $$ template\" && \"protocols mpls label-switched-path $$ p2mp\")))";
                             junos:must-message "Referenced point-to-multipoint LSP template does not exist";
                             type string {
                               junos:posix-pattern "^.{1,32}$";
                               junos:pattern-message "Must be a string of 32 characters or less";
                             }
                           }
                         }
                         case case_2 {
                           leaf default-template {
                             description "Use default parameters";
                             type empty;
                           }
                         }
                       }
                     }
                   }
                 }
               }
             }
             case case_2 {
               container ldp-p2mp {
                 presence "enable ldp-p2mp";
                 junos:must "(\"protocols ldp p2mp\")";
                 junos:must-message "LDP P2MP must be configured in the master instance";
                 junos:must "((\".. .. .. .. protocols mvpn\" && (\".. .. .. .. instance-type vrf\" || \".. .. .. .. instance-type mpls-internet-multicast\")))";
                 junos:must-message "LDP P2MP LSPs can be configured only for valid MVPN instances";
                 description "LDP point-to-multipoint LSP for flooding";
               }
             }
             case case_3 {
               container ingress-replication {
                 junos:must "(((\".. .. .. .. instance-type vrf\" || \".. .. .. .. instance-type mpls-internet-multicast\") && \".. .. .. .. protocols mvpn\"))";
                 junos:must-message "Ingress Replication can be configured only for MVPN instances";
                 junos:must "(!(\".. .. .. .. protocols mvpn sender-based-rpf\"))";
                 junos:must-message "This release does not support Sender based RPF for inclusive ingress replication provider tunnels";
                 description "Ingress replication tunnel";
                 uses apply-advanced;
                 leaf create-new-ucast-tunnel {
                   description "Create new unicast tunnel for ingress replication";
                   junos:must "(\".. label-switched-path label-switched-path-template\")";
                   junos:must-message "label-switched-path-template must be defined";
                   type empty;
                 }
                 container label-switched-path {
                   presence "enable label-switched-path";
                   description "Point-to-point LSP unicast tunnel";
                   uses apply-advanced;
                   container label-switched-path-template {
                     junos:must "(\".. .. create-new-ucast-tunnel\")";
                     junos:must-message "Templates must be specified when and only when create-new-ucast-tunnel is defined";
                     description "Template for dynamic point-to-point LSP parameters";
                     uses apply-advanced;
                     choice dynamic-template {
                       case case_1 {
                         leaf template-name {
                           description "Name of point-to-point LSP template";
                           junos:must "((\"protocols mpls label-switched-path $$\" && (\"protocols mpls label-switched-path $$ template\" && !(\"protocols mpls label-switched-path $$ p2mp\"))))";
                           junos:must-message "Referenced point-to-point LSP template does not exist";
                           type string {
                             junos:posix-pattern "^.{1,32}$";
                             junos:pattern-message "Must be a string of 32 characters or less";
                           }
                         }
                       }
                       case case_2 {
                         leaf default-template {
                           description "Use default parameters";
                           type empty;
                         }
                       }
                     }
                   }
                 }
               }
             }
             case case_4 {
               container pim-asm {
                 junos:must "(!(\".. .. .. .. protocols mvpn sender-based-rpf\"))";
                 junos:must-message "this release does not support sender based RPF for PIM-SM provider tunnels";
                 junos:must "(!(\"protocols pim mpls-internet-multicast\"))";
                 junos:must-message "mpls-internet-multicast must not be configured";
                 junos:must "(\"protocols pim\")";
                 junos:must-message "PIM-SM must be configured in the master instance";
                 junos:must "(\".. .. .. .. instance-type vrf\")";
                 junos:must-message "PIM-SM must be configured only for vrf instances";
                 description "PIM-SM provider tunnel";
                 uses apply-advanced;
                 leaf group-address {
                   description "PIM-SM provider tunnel group address";
                   type jt:ipv4addr;
                 }
                 leaf tunnel-source {
                   description "Source address for the provider space mGRE tunnel";
                   type jt:ipv4addr;
                 }
               }
             }
             case case_5 {
               container pim-ssm {
                 junos:must "(!(\".. .. .. .. protocols mvpn sender-based-rpf\"))";
                 junos:must-message "this release does not support sender based RPF for PIM-SSM provider tunnels";
                 junos:must "(!(\"protocols pim mpls-internet-multicast\"))";
                 junos:must-message "mpls-internet-multicast must not be configured";
                 junos:must "(\"protocols pim\")";
                 junos:must-message "PIM-SSM must be configured in the master instance";
                 junos:must "(\".. .. .. .. protocols mvpn\")";
                 junos:must-message "PIM-SSM provider tunnel can be configured only for multicast VPN instances";
                 junos:must "(\".. .. .. .. instance-type vrf\")";
                 junos:must-message "PIM-SM must be configured only for vrf instances";
                 description "PIM-SSM provider tunnel";
                 uses apply-advanced;
                 leaf group-address {
                   description "PIM-SSM provider tunnel group address";
                   type jt:ipv4addr;
                 }
                 leaf tunnel-source {
                   description "Source address for the provider space mGRE tunnel";
                   type jt:ipv4addr;
                 }
               }
             }
           }
           container mdt {
             junos:must "(\".. .. .. .. protocols pim mvpn\")";
             junos:must-message "Data MDT tunnels can only be configured for PIM
                   MVPN instances";
             description "IPv6 Data MDT tunnels for PIM MVPN";
             uses apply-advanced;
             container threshold {
               description "Threshold for creation of multicast tunnels";
               uses apply-advanced;
               list group {
                 key name;
                 ordered-by user;
                 description "IP prefix of multicast group";
                 leaf name {
                   description "IP prefix of group";
                   type jt:ipprefix;
                 }
                 uses apply-advanced;
                 list source {
                   key name;
                   ordered-by user;
                   description "IP prefix of one or more multicast sources ";
                   leaf name {
                     description "IP prefix of source";
                     type jt:ipprefix;
                   }
                   uses apply-advanced;
                   leaf rate {
                     description "Data threshold to create new tunnel";
                     units "kilobits";
                     type union {
                       type string {
                         pattern "<.*>|$.*";
                       }
                       type uint32 {
                         range "10 .. 1000000";
                       }
                     }
                   }
                 }
               }
             }
             leaf data-mdt-reuse {
               description "Allow multiple customer streams to be transmitted over one data tunnel ";
               type empty;
             }
             leaf tunnel-limit {
               description "Maximum multicast data tunnels";
               type union {
                 type string {
                   pattern "<.*>|$.*";
                 }
                 type uint32 {
                   range "0 .. 8192";
                 }
               }
             }
             leaf group-range {
               description "Group address range for multicast data tunnels";
               type jt:ipprefix;
             }
           }
         }
       }
     }
     container multicast-snooping-options {
       description "Multicast snooping option configuration";
       junos:must "((\".. instance-type vpls\" || (\".. instance-type evpn\" || (\".. instance-type virtual-switch \" || \".. instance-type mac-vrf \"))))";
       junos:must-message "multicast-snooping-options configuration is allowed only for 'instance-type vpls/evpn or instance-type virtual-switch/mac-vrf'";
       uses juniper-multicast-snooping-options;
     }
     container igmp-snooping-options {
       description "IGMP snooping option configuration";
       junos:must "((\".. instance-type vpls\" || (\".. instance-type virtual-switch\" || (\".. instance-type evpn\" && \".. protocols vpls\"))))";
       junos:must-message "igmp-snooping-options configuration is allowed only for 'instance-type vpls/virtual-switch'";
       uses juniper-igmp-snooping-options;
     }
     container mld-snooping-options {
       description "MLD snooping option configuration";
       junos:must "((\".. instance-type vpls\" || (\".. instance-type virtual-switch\" || (\".. instance-type evpn\" && \".. protocols vpls\"))))";
       junos:must-message "mld-snooping-options configuration is allowed only for 'instance-type vpls or instance-type virtual-switch'";
       uses juniper-mld-snooping-options;
     }
     container vlans {
       junos:must "((\".. instance-type virtual-switch\" || \".. instance-type mac-vrf\"))";
       junos:must-message "'vlans' configuration can only be used for 'instance-type virtual-switch' or 'instance-type mac-vrf'";
       junos:must "(!(\"bridge-domains\"))";
       junos:must-message "VLANs cannot be configured when BDs are configured";
       description "VLAN configuration";
       uses apply-advanced;
       list vlan {
         key name;
         description "Virtual LAN";
         uses vlan-types;
       }
     }
   }
   grouping address-assignment-type {
     description "Address assignment configuration";
     uses apply-advanced;
     container neighbor-discovery-router-advertisement {
       description "Designated NDRA pool for this instance";
       leaf ndra-name {
         description "Designated NDRA pool name";
         junos:must "(\".. .. pool $$  family inet6\")";
         junos:must-message "designated NDRA pool must be configured and family inet6 must be set";
         type string {
           length "1 .. 63";
           junos:posix-pattern "^[A-Za-z0-9][_0-9A-Za-z-]{0,62}$";
           junos:pattern-message "Must be a string beginning with a number or letter and consisting of no more than 63 total letters, numbers, dashes and underscores.";
         }
       }
     }
     leaf high-utilization {
       description "Generate an SNMP trap when address pool use surpasses this percentage";
       type union {
         type string {
           pattern "<.*>|$.*";
         }
         type uint16 {
           range "2 .. 99";
         }
       }
     }
     leaf abated-utilization {
       description "Generate an SNMP clear trap when address pool use falls below this percentage";
       type union {
         type string {
           pattern "<.*>|$.*";
         }
         type uint16 {
           range "1 .. 98";
         }
       }
     }
     leaf high-utilization-v6 {
       description "Generate an SNMP trap when address pool use surpasses this percentage";
       type union {
         type string {
           pattern "<.*>|$.*";
         }
         type uint16 {
           range "2 .. 99";
         }
       }
     }
     leaf abated-utilization-v6 {
       description "Generate an SNMP clear trap when address pool use falls below this percentage";
       type union {
         type string {
           pattern "<.*>|$.*";
         }
         type uint16 {
           range "1 .. 98";
         }
       }
     }
     list dynamic-pool {
       key name;
       ordered-by user;
       description "Dynamic address pool";
       leaf name {
         description "Dynamic address pool name";
         type string {
           length "1 .. 63";
           junos:posix-pattern "^[A-Za-z0-9][_0-9A-Za-z-]{0,62}$";
           junos:pattern-message "Must be a string beginning with a number or letter and consisting of no more than 63 total letters, numbers, dashes and underscores.";
         }
       }
       uses apply-advanced;
       container family {
         presence "enable family";
         description "Address family";
         uses apply-advanced;
         container inet6 {
           description "IPv6";
           uses apply-advanced;
           leaf delegated-prefix-length {
             description "Delegated IPv6 network prefix length";
             type union {
               type string {
                 pattern "<.*>|$.*";
               }
               type uint32 {
                 range "1 .. 64";
               }
             }
           }
           leaf from-interface {
             description "Get prefix from interface name";
             type union {
               type jt:interface-name;
               type string {
                 pattern "<.*>|$.*";
               }
             }
           }
           list range {
             key name;
             ordered-by user;
             description "IPv6 address range";
             leaf name {
               description "Range name";
               type string {
                 length "1 .. 63";
                 junos:posix-pattern "^[A-Za-z0-9][_0-9A-Za-z-]{0,62}$";
                 junos:pattern-message "Must be a string beginning with a number or letter and consisting of no more than 63 total letters, numbers, dashes and underscores.";
               }
             }
             uses apply-advanced;
             leaf masked-low {
               description "Lower limit of ipv6 address range";
               junos:must "(\".. masked-high\")";
               junos:must-message "range upper bound must be defined";
               type jt:ipv6prefix-mandatory;
             }
             leaf masked-high {
               description "Upper limit of ipv6 address range";
               junos:must "(\".. masked-low\")";
               junos:must-message "range lower bound must be defined";
               type jt:ipv6prefix-mandatory;
             }
             leaf prefix-length {
               description "IPv6 delegated prefix length";
               junos:must "(!(any \".. .. range <*> masked-low\"))";
               junos:must-message "'prefix-length' cannot be configured with 'masked-low' in one dynamic pool";
               junos:must "(unique \".. .. range <*> prefix-length\")";
               junos:must-message "'prefix-length' cannot be configured for multiple ranges in one dynamic pool";
               junos:must "(!(\".. masked-low\"))";
               junos:must-message "prefix-length cannot be configured with 'masked-low'";
               type union {
                 type string {
                   pattern "<.*>|$.*";
                 }
                 type uint32 {
                   range "1 .. 64";
                 }
               }
             }
           }
           container dhcp-attributes {
             description "DHCP options and match criteria";
             uses dynamic-dhcp-attribute-type;
           }
         }
       }
     }
     list pool {
       key name;
       ordered-by user;
       description "Address pool";
       leaf name {
         description "Address pool name";
         junos:must "(!(\".. link $$\"))";
         junos:must-message "Link cannot be self referential";
         type string {
           length "1 .. 63";
           junos:posix-pattern "^[A-Za-z0-9][_0-9A-Za-z-]{0,62}$";
           junos:pattern-message "Must be a string beginning with a number or letter and consisting of no more than 63 total letters, numbers, dashes and underscores.";
         }
       }
       uses apply-advanced;
       leaf active-drain {
         description "Notify client of pool active drain mode";
         type empty;
       }
       leaf hold-down {
         description "Place pool in passive drain mode";
         type empty;
       }
       leaf link {
         description "Address pool link name";
         junos:must "(\".. .. pool $$\")";
         junos:must-message "Link must be to a valid pool name";
         type string {
           length "1 .. 63";
           junos:posix-pattern "^[A-Za-z0-9][_0-9A-Za-z-]{0,62}$";
           junos:pattern-message "Must be a string beginning with a number or letter and consisting of no more than 63 total letters, numbers, dashes and underscores.";
         }
       }
       container family {
         presence "enable family";
         description "Address family";
         choice family_type {
           case case_1 {
             container inet {
               presence "enable inet";
               description "IPv4";
               uses apply-advanced;
               leaf network {
                 description "Network address";
                 type jt:ipv4prefix;
               }
               list range {
                 key name;
                 ordered-by user;
                 description "Address range";
                 max-elements 1;
                 leaf name {
                   description "Range name";
                   type string {
                     length "1 .. 63";
                     junos:posix-pattern "^[A-Za-z0-9][_0-9A-Za-z-]{0,62}$";
                     junos:pattern-message "Must be a string beginning with a number or letter and consisting of no more than 63 total letters, numbers, dashes and underscores.";
                   }
                 }
                 uses apply-advanced;
                 leaf low {
                   description "Lower limit of address range";
                   type jt:ipv4addr;
                 }
                 leaf high {
                   description "Upper limit of address range";
                   type jt:ipv4addr;
                 }
               }
               container dhcp-attributes {
                 description "DHCP options and match criteria";
                 uses dhcp-attribute-type;
               }
               container xauth-attributes {
                 description "Configure xauth attributes";
                 uses apply-advanced;
                 leaf primary-dns {
                   description "Specify the primary-dns IP address";
                   type jt:ipv4prefix;
                 }
                 leaf secondary-dns {
                   description "Specify the secondary-dns IP address";
                   type jt:ipv4prefix;
                 }
                 leaf primary-wins {
                   description "Specify the primary-wins IP address";
                   type jt:ipv4prefix;
                 }
                 leaf secondary-wins {
                   description "Specify the secondary-wins IP address";
                   type jt:ipv4prefix;
                 }
               }
               list host {
                 key name;
                 ordered-by user;
                 description "Hostname for static reservations";
                 leaf name {
                   description "Hostname";
                   junos:must "((\".. hardware-address\" || \".. user-name\"))";
                   junos:must-message "either host's hardware address or identifier must be set";
                   type string {
                     length "1 .. 256";
                   }
                 }
                 uses apply-advanced;
                 leaf hardware-address {
                   description "Hardware address";
                   type jt:mac-addr;
                 }
                 leaf ip-address {
                   description "Reserved address";
                   type jt:ipv4addr;
                 }
                 choice host-identifier-type {
                   case case_1 {
                     leaf user-name {
                       description "Set subscriber user name as host identifier";
                       type empty;
                     }
                   }
                 }
               }
               list excluded-address {
                 key name;
                 ordered-by user;
                 description "Excluded Addresses";
                 max-elements 20;
                 leaf name {
                   description "Excluded address";
                   type jt:ipv4addr;
                 }
                 uses apply-advanced;
               }
               list excluded-range {
                 key name;
                 ordered-by user;
                 description "Excluded address range";
                 max-elements 20;
                 leaf name {
                   description "Range name";
                   type string {
                     length "1 .. 63";
                     junos:posix-pattern "^[A-Za-z0-9][_0-9A-Za-z-]{0,62}$";
                     junos:pattern-message "Must be a string beginning with a number or letter and consisting of no more than 63 total letters, numbers, dashes and underscores.";
                   }
                 }
                 uses apply-advanced;
                 leaf low {
                   description "Lower limit of excluded address range";
                   type jt:ipv4addr;
                 }
                 leaf high {
                   description "Upper limit of excluded address range";
                   type jt:ipv4addr;
                 }
               }
             }
           }
           case case_2 {
             container inet6 {
               presence "enable inet6";
               description "IPv6";
               uses apply-advanced;
               leaf prefix {
                 description "IPv6 network prefix";
                 type jt:ipv6prefix-mandatory;
               }
               list range {
                 key name;
                 ordered-by user;
                 description "IPv6 address range";
                 leaf name {
                   description "Range name";
                   type string {
                     length "1 .. 63";
                     junos:posix-pattern "^[A-Za-z0-9][_0-9A-Za-z-]{0,62}$";
                     junos:pattern-message "Must be a string beginning with a number or letter and consisting of no more than 63 total letters, numbers, dashes and underscores.";
                   }
                 }
                 uses apply-advanced;
                 leaf low {
                   description "Lower limit of ipv6 address range";
                   junos:must "(\".. high\")";
                   junos:must-message "range upper bound must be defined";
                   type jt:ipv6prefix-mandatory;
                 }
                 leaf high {
                   description "Upper limit of ipv6 address range";
                   junos:must "(\".. low\")";
                   junos:must-message "range lower bound must be defined";
                   type jt:ipv6prefix-mandatory;
                 }
                 leaf prefix-length {
                   description "IPv6 delegated prefix length";
                   junos:must "(!(\".. low\"))";
                   junos:must-message "range lower bound may not be defined";
                   type union {
                     type string {
                       pattern "<.*>|$.*";
                     }
                     type uint32 {
                       range "1 .. 128";
                     }
                   }
                 }
               }
               container dhcp-attributes {
                 description "DHCP options and match criteria";
                 uses dhcp-attribute-type;
               }
               container xauth-attributes {
                 description "Configure xauth ipv6 attributes";
                 uses apply-advanced;
                 leaf primary-dns-ipv6 {
                   description "Specify the primary-dns IPv6 address";
                   type jt:ipv6addr;
                 }
                 leaf secondary-dns-ipv6 {
                   description "Specify the secondary-dns IPv6 address";
                   type jt:ipv6addr;
                 }
               }
               list host {
                 key name;
                 ordered-by user;
                 description "Hostname for static reservations";
                 leaf name {
                   description "Hostname";
                   junos:must "((\".. hardware-address\" || \".. user-name\"))";
                   junos:must-message "either host's hardware address or identifier must be set";
                   type string {
                     length "1 .. 256";
                   }
                 }
                 uses apply-advanced;
                 leaf hardware-address {
                   description "Hardware address";
                   type jt:mac-addr;
                 }
                 leaf ip-address {
                   description "Reserved address";
                   type jt:ipv6addr;
                 }
                 choice host-identifier-type {
                   case case_1 {
                     leaf user-name {
                       description "Set subscriber user name as host identifier";
                       type empty;
                     }
                   }
                 }
               }
               list excluded-address {
                 key name;
                 ordered-by user;
                 description "Excluded Addresses";
                 max-elements 20;
                 leaf name {
                   description "Excluded address";
                   type jt:ipv6addr;
                 }
                 uses apply-advanced;
               }
               list excluded-range {
                 key name;
                 ordered-by user;
                 description "Excluded address range";
                 max-elements 20;
                 leaf name {
                   description "Range name";
                   type string {
                     length "1 .. 63";
                     junos:posix-pattern "^[A-Za-z0-9][_0-9A-Za-z-]{0,62}$";
                     junos:pattern-message "Must be a string beginning with a number or letter and consisting of no more than 63 total letters, numbers, dashes and underscores.";
                   }
                 }
                 uses apply-advanced;
                 leaf low {
                   description "Lower limit of excluded address range";
                   type jt:ipv6addr;
                 }
                 leaf high {
                   description "Upper limit of excluded address range";
                   type jt:ipv6addr;
                 }
               }
             }
           }
         }
       }
     }
     list location-pool {
       key name;
       ordered-by user;
       description "Location-based IP address pool";
       max-elements 10;
       leaf name {
         description "Pool name";
         type string {
           length "1 .. 64";
         }
       }
       uses apply-advanced;
       container family {
         presence "enable family";
         description "Address family";
         container inet {
           description "IPv4 location pool";
           uses apply-advanced;
           list location {
             key name;
             description "Relative location of router";
             max-elements 32;
             leaf name {
               description "Location number";
               type union {
                 type string {
                   pattern "<.*>|$.*";
                 }
                 type uint32 {
                   range "1 .. 32";
                 }
               }
             }
             uses apply-advanced;
             leaf address {
               description "IP address/destination prefix";
               type jt:ipv4prefix;
             }
           }
         }
       }
     }
     list domain-profile {
       key name;
       ordered-by user;
       description "Address domain profile";
       leaf name {
         description "Pool domain profile name";
         type string {
           length "1 .. 63";
         }
       }
       uses apply-advanced;
       container family {
         description "Network family to which this configuration belongs";
         uses apply-advanced;
         container inet {
           description "The IPv4 internet family";
           uses apply-advanced;
           leaf preferred-prefix-length {
             description "Preferred prefix length";
             type union {
               type string {
                 pattern "<.*>|$.*";
               }
               type uint32 {
                 range "8 .. 30";
               }
             }
           }
           leaf source-partition-qualifier {
             description "Prefix source qualifier appended to location for partition name";
             type string {
               length "1 .. 63";
             }
           }
           container excluded-address {
             description "Excluded addresses from allocation";
             leaf-list last-octet {
               ordered-by user;
               description "Last octet of the excluded address";
               type union {
                 type string {
                   pattern "<.*>|$.*";
                 }
                 type uint8 {
                   range "0 .. 255";
                 }
               }
             }
           }
           leaf install-discard-routes {
             description "Install discard route domain pool prefix";
             type empty;
           }
           leaf dhcp-router-host-part {
             description "DHCP host address component to be excluded and passed to DHCP";
             type union {
               type string {
                 pattern "<.*>|$.*";
               }
               type uint8 {
                 range "1 .. 8";
               }
             }
           }
           leaf protocol-attributes {
             description "Access protocol-attributes name";
             junos:must "(\"access protocol-attributes $$\")";
             junos:must-message "referenced protocol-attributes must be defined";
             type string {
               length "1 .. 63";
             }
           }
         }
       }
     }
     list address-pools {
       key name;
       ordered-by user;
       description "Address pools for subscribers";
       max-elements 10000;
       uses sm-ippool-pool;
     }
   }
   grouping dhcp-attribute-type {
     uses apply-advanced;
     container option-match {
       description "Match";
       uses apply-advanced;
       container option-82 {
         uses apply-advanced;
         list circuit-id {
           key name;
           ordered-by user;
           description "Circuit ID portion of the option 82";
           leaf name {
             type string;
           }
           leaf range {
             description "Range name";
             type string;
           }
         }
         list remote-id {
           key name;
           ordered-by user;
           description "Remote ID portion of the option 82";
           leaf name {
             type string;
           }
           leaf range {
             description "Range name";
             type string;
           }
         }
       }
     }
     leaf maximum-lease-time {
       description "Maximum lease time advertised to clients";
       units "seconds";
       type string;
     }
     leaf next-server {
       description "Next server that clients need to contact";
       type jt:ipv4addr;
     }
     leaf server-identifier {
       description "Server Identifier - IP address value";
       type jt:ipv4addr;
     }
     leaf grace-period {
       description "Grace period for leases";
       units "seconds";
       type union {
         type uint32;
         type string {
           pattern "<.*>|$.*";
         }
       }
     }
     leaf domain-name {
       description "Domain name advertised to clients";
       type string {
         junos:posix-pattern "^[[:alnum:]._-]+$";
         junos:pattern-message "Must be a string of letters, numbers, dashes or underscores";
       }
     }
     list name-server {
       key name;
       ordered-by user;
       description "Domain name servers available to the client";
       leaf name {
         description "DNS server's IPv4 address";
         type jt:ipv4addr;
       }
       uses apply-advanced;
     }
     list wins-server {
       key name;
       ordered-by user;
       description "WINS name servers";
       leaf name {
         description "WINS server's IPv4 address";
         type jt:ipv4addr;
       }
       uses apply-advanced;
     }
     list router {
       key name;
       ordered-by user;
       description "Routers advertised to clients";
       leaf name {
         description "Router's IPv4 address";
         type jt:ipv4addr;
       }
       uses apply-advanced;
     }
     leaf boot-file {
       description "Boot filename advertised to clients";
       type string;
     }
     leaf boot-server {
       description "Boot server advertised to clients";
       type string {
         junos:posix-pattern "^[[:alnum:]._-]+$";
         junos:pattern-message "Must be a string of letters, numbers, dashes or underscores";
       }
     }
     leaf tftp-server {
       description "TFTP server IP address advertised to clients";
       type jt:ipv4addr;
     }
     container sip-server {
       description "SIP servers to clients";
       uses apply-advanced;
       list name {
         key name;
         ordered-by user;
         description "SIP server domain name available to clients";
         leaf name {
           description "SIP server name";
           junos:must "(!(any \".. .. address <*>\"))";
           junos:must-message "Cannot configure sip-server by both name and address";
           type string;
         }
         uses apply-advanced;
       }
       list ip-address {
         key name;
         ordered-by user;
         description "SIP servers list of IPv4 addresses available to the client";
         leaf name {
           description "SIP server's IPv4 address";
           type jt:ipv4addr;
         }
         uses apply-advanced;
       }
     }
     leaf netbios-node-type {
       description "Type of NETBIOS node advertised to clients";
       type enumeration {
         enum "b-node" {
           description "Broadcast node";
         }
         enum "p-node" {
           description "Peer-to-peer node";
         }
         enum "m-node" {
           description "Mixed Node";
         }
         enum "h-node" {
           description "Hybrid node";
         }
       }
     }
     leaf sip-server-domain-name {
       description "SIP server domain name available to clients";
       type string {
         junos:posix-pattern "^[[:alnum:]._-]+$";
         junos:pattern-message "Must be a string of letters, numbers, dashes or underscores";
       }
     }
     list sip-server-address {
       key name;
       ordered-by user;
       description "SIP Servers list of IPv6 addresses available to the client";
       leaf name {
         description "SIP Server's IPv6 address";
         type jt:ipv6addr;
       }
       uses apply-advanced;
     }
     list dns-server {
       key name;
       ordered-by user;
       description "Domain name servers available to the client";
       leaf name {
         description "DNS server's IPv6 address";
         type jt:ipv6addr;
       }
       uses apply-advanced;
     }
     leaf propagate-settings {
       description "Interface name for propagating TCP/IP Settings to pool";
       type string;
     }
     leaf-list propagate-ppp-settings {
       ordered-by user;
       description "PPP interface name for propagating DNS/WINS settings";
       type union {
         type jt:interface-name;
         type string {
           pattern "<.*>|$.*";
         }
       }
       max-elements 8;
     }
     list option {
       key name;
       ordered-by user;
       description "DHCP option";
       leaf name {
         description "DHCP option identifier code";
         type union {
           type uint32;
           type string {
             pattern "<.*>|$.*";
           }
         }
       }
       choice option-type-choice {
         case case_1 {
           leaf flag {
             description "Boolean flag value";
             type enumeration {
               enum "true" {
                 description "True value";
               }
               enum "false" {
                 description "False value";
               }
               enum "on" {
                 description "On value";
               }
               enum "off" {
                 description "Off value";
               }
             }
           }
         }
         case case_2 {
           leaf byte {
             description "Unsigned 8-bit value";
             type union {
               type uint8;
               type string {
                 pattern "<.*>|$.*";
               }
             }
           }
         }
         case case_3 {
           leaf short {
             description "Signed 16-bit numeric value";
             type union {
               type int16;
               type string {
                 pattern "<.*>|$.*";
               }
             }
           }
         }
         case case_4 {
           leaf unsigned-short {
             description "Unsigned 16-bit numeric value";
             type union {
               type uint16;
               type string {
                 pattern "<.*>|$.*";
               }
             }
           }
         }
         case case_5 {
           leaf integer {
             description "Signed 32-bit numeric value";
             type union {
               type int32;
               type string {
                 pattern "<.*>|$.*";
               }
             }
           }
         }
         case case_6 {
           leaf unsigned-integer {
             description "Unsigned 32-bit numeric value";
             type union {
               type uint32;
               type string {
                 pattern "<.*>|$.*";
               }
             }
           }
         }
         case case_7 {
           leaf hex-string {
             description "Hexadecimal string";
             type string {
               length "1 .. 510";
               junos:posix-pattern "^[[:xdigit:]]+$";
               junos:pattern-message "Must be hexadecimal digits (0-9, a-f, A-F)";
             }
           }
         }
         case case_8 {
           leaf string {
             description "Character string value";
             type string {
               length "1 .. 254";
             }
           }
         }
         case case_9 {
           leaf ip-address {
             description "IP address value";
             type jt:ipv4addr;
           }
         }
         case case_10 {
           leaf ipv6-address {
             description "IPV6 address value";
             type jt:ipv6addr;
           }
         }
         case case_11 {
           container array {
             presence "enable array";
             description "Array of values";
             uses apply-advanced;
             choice option-type-array-choice {
               case case_1 {
                 leaf-list flag {
                   ordered-by user;
                   description "Array of boolean flag values";
                   type enumeration {
                     enum "true" {
                       description "True value";
                     }
                     enum "false" {
                       description "False value";
                     }
                     enum "on" {
                       description "On value";
                     }
                     enum "off" {
                       description "Off value";
                     }
                   }
                 }
               }
               case case_2 {
                 leaf-list byte {
                   ordered-by user;
                   description "Array of unsigned 8-bit values";
                   type union {
                     type uint8;
                     type string {
                       pattern "<.*>|$.*";
                     }
                   }
                 }
               }
               case case_3 {
                 leaf-list short {
                   ordered-by user;
                   description "Array of signed 16-bit numeric values";
                   type union {
                     type int16;
                     type string {
                       pattern "<.*>|$.*";
                     }
                   }
                 }
               }
               case case_4 {
                 leaf-list unsigned-short {
                   ordered-by user;
                   description "Array of 16-bit numeric values";
                   type union {
                     type uint16;
                     type string {
                       pattern "<.*>|$.*";
                     }
                   }
                 }
               }
               case case_5 {
                 leaf-list integer {
                   ordered-by user;
                   description "Array of signed 32-bit numeric values";
                   type union {
                     type int32;
                     type string {
                       pattern "<.*>|$.*";
                     }
                   }
                 }
               }
               case case_6 {
                 leaf-list unsigned-integer {
                   ordered-by user;
                   description "Array of unsigned 32-bit numeric values";
                   type union {
                     type uint32;
                     type string {
                       pattern "<.*>|$.*";
                     }
                   }
                 }
               }
               case case_7 {
                 leaf-list hex-string {
                   ordered-by user;
                   description "Hexadecimal string";
                   type string {
                     length "1 .. 510";
                   }
                 }
               }
               case case_8 {
                 leaf-list string {
                   ordered-by user;
                   description "Array of character string values";
                   type string {
                     length "1 .. 254";
                   }
                 }
               }
               case case_9 {
                 leaf-list ip-address {
                   ordered-by user;
                   description "Array of IP address values";
                   type jt:ipv4addr;
                 }
               }
               case case_10 {
                 leaf-list ipv6-address {
                   ordered-by user;
                   description "Array of IPv6 address values";
                   type jt:ipv6addr;
                 }
               }
             }
           }
         }
       }
     }
     leaf valid-lifetime {
       description "Valid lifetime advertised to clients";
       units "seconds";
       junos:must "(!(\".. maximum-lease-time\"))";
       junos:must-message "'valid-lifetime' statement cannot be included along with 'maximum-lease-time'";
       type string;
     }
     leaf preferred-lifetime {
       description "Preferred lifetime advertised to clients";
       units "seconds";
       junos:must "(!(\".. maximum-lease-time\"))";
       junos:must-message "'preferred-lifetime' statement cannot be included along with 'maximum-lease-time'";
       type string;
     }
     leaf t1-percentage {
       description "T1 time as percentage of preferred lifetime or max lease";
       units "percent";
       junos:must "(!(\".. t2-rebinding-time\"))";
       junos:must-message "T1 must be configured in seconds to match T2";
       junos:must "(!(\".. t1-renewal-time\"))";
       junos:must-message "T1 time in seconds already configured";
       type union {
         type string {
           pattern "<.*>|$.*";
         }
         type uint32 {
           range "0 .. 100";
         }
       }
     }
     leaf t2-percentage {
       description "T2 time as percentage of preferred lifetime or max lease";
       units "percent";
       junos:must "(!(\".. t1-renewal-time\"))";
       junos:must-message "T2 must be configured in seconds to match T1";
       junos:must "(!(\".. t2-rebinding-time\"))";
       junos:must-message "T2 time in seconds already configured";
       type union {
         type string {
           pattern "<.*>|$.*";
         }
         type uint32 {
           range "0 .. 100";
         }
       }
     }
     leaf exclude-prefix-len {
       description "Length of IPv6 prefix to be excluded from delegated prefix";
       type union {
         type string {
           pattern "<.*>|$.*";
         }
         type uint32 {
           range "1 .. 128";
         }
       }
     }
     leaf t1-renewal-time {
       description "T1 renewal time";
       units "seconds";
       junos:must "(!(\".. t2-percentage\"))";
       junos:must-message "T1 must be configured as percentage to match T2";
       junos:must "(!(\".. t1-percentage\"))";
       junos:must-message "T1 time as percentage already configured";
       type union {
         type uint32;
         type string {
           pattern "<.*>|$.*";
         }
       }
     }
     leaf t2-rebinding-time {
       description "T2 rebinding time";
       units "seconds";
       junos:must "(!(\".. t1-percentage\"))";
       junos:must-message "T2 must be configured as percentage to match T1";
       type union {
         type uint32;
         type string {
           pattern "<.*>|$.*";
         }
       }
     }
   }
   grouping dynamic-dhcp-attribute-type {
     uses apply-advanced;
     leaf maximum-lease-time {
       description "Maximum lease time advertised to clients";
       units "seconds";
       type string;
     }
     leaf valid-lifetime {
       description "Preferred lifetime";
       units "seconds";
       type string;
     }
     leaf preferred-lifetime {
       description "Preferred lifetime";
       units "seconds";
       type string;
     }
     list dns-server {
       key name;
       ordered-by user;
       description "Domain name servers available to the client";
       leaf name {
         description "DNS server's IPv6 address";
         type jt:ipv6addr;
       }
       uses apply-advanced;
     }
     leaf t1-percentage {
       description "T1 time as percentage of preferred lifetime advertised to clients";
       units "percent";
       type union {
         type string {
           pattern "<.*>|$.*";
         }
         type uint32 {
           range "0 .. 100";
         }
       }
     }
     leaf t2-percentage {
       description "T2 time as percentage of preferred lifetime advertised to clients";
       units "percent";
       type union {
         type string {
           pattern "<.*>|$.*";
         }
         type uint32 {
           range "0 .. 100";
         }
       }
     }
   }
   grouping jdhcp-local-server-type {
     uses apply-advanced;
     container traceoptions {
       description "DHCP local server trace options";
       status deprecated;
       junos:must "(!(\"forwarding-options helpers bootp\"))";
       junos:must-message "Incompatible with 'forwarding-options helpers bootp'";
       junos:must "(!(\"system services dhcp\"))";
       junos:must-message "Incompatible with 'set system services dhcp'";
       uses jdhcp-traceoptions-type;
     }
     container interface-traceoptions {
       description "DHCP local server interface trace options";
       status deprecated;
       uses jdhcp-interface-traceoptions-type;
     }
     container dhcpv6 {
       description "DHCPv6 configuration";
       uses dhcpv6-local-server-type;
     }
     list pool-match-order {
       key name;
       ordered-by user;
       description "Define order of attribute matching for pool selection";
       leaf name {
         description "Match type";
         type enumeration {
           enum "external-authority" {
             description "External authority handles address selection";
           }
           enum "ip-address-first" {
             description "IP address used first to select a pool";
           }
           enum "option-82" {
             description "Option 82 used in matching of pool";
           }
           enum "option-82-strict" {
             description "Option 82 used in strict matching of pool";
           }
         }
       }
       uses apply-advanced;
     }
     leaf duplicate-clients-on-interface {
       description "Allow duplicate clients on different interfaces in a subnet";
       status deprecated;
       type empty;
     }
     container duplicate-clients-in-subnet {
       description "Allow duplicate clients in a subnet";
       junos:must "(!(\".. duplicate-clients-on-interface\"))";
       junos:must-message "Cannot specify duplicate-clients-in-subnet with duplicate-clients-on-interface";
       uses jdhcp-duplicate-clients-in-subnet-type;
     }
     container forward-snooped-clients {
       junos:must "((!(\".. forward-only\") && (!(\".. forward-only-replies\") && !(any \".. group <*> forward-only\"))))";
       junos:must-message "forward-only and forward-only-replies cannot be configured when forward-snooped-clients is configured";
       description "Forward snooped (unicast) packets";
       choice interface-type {
         case case_1 {
           leaf configured-interfaces {
             description "Forward snooped (unicast) packets on configured interfaces";
             type empty;
           }
         }
         case case_2 {
           leaf non-configured-interfaces {
             description "Forward snooped (unicast) packets on non-configured interfaces";
             type empty;
           }
         }
         case case_3 {
           leaf all-interfaces {
             description "Forward snooped (unicast) packets on configured and non-configured interfaces";
             type empty;
           }
         }
       }
     }
     container authentication {
       description "DHCP authentication";
       junos:must "(!(\"forwarding-options helpers bootp\"))";
       junos:must-message "'authentication' statement cannot be included along with 'forwarding-options helpers bootp' statement";
       uses authentication-type;
     }
     container liveness-detection {
       description "DHCP client liveness detection processing";
       junos:must "(!(\"forwarding-options helpers bootp\"))";
       junos:must-message "'liveness-detection' statement cannot be included along with 'forwarding-options helpers bootp' statement";
       uses dhcp-liveness-detection-type;
     }
     container reconfigure {
       description "DHCP reconfigure processing";
       presence "enable reconfigure";
       junos:must "(!(\"forwarding-options helpers bootp\"))";
       junos:must-message "'reconfigure' statement cannot be included along with 'forwarding-options helpers bootp' statement";
       uses reconfigure-type;
     }
     container overrides {
       description "DHCP override processing";
       presence "enable overrides";
       junos:must "(!(\"forwarding-options helpers bootp\"))";
       junos:must-message "'overrides' statement cannot be included along with 'forwarding-options helpers bootp' statement";
       uses override-local-server-type;
     }
     container dynamic-profile {
       description "Dynamic profile to use";
       junos:must "(!(\"forwarding-options helpers bootp\"))";
       junos:must-message "'dynamic-profile' statement cannot be included along with 'forwarding-options helpers bootp' statement";
       uses dynamic-profile-type;
     }
     leaf service-profile {
       description "Dynamic profile to use for default service activation";
       type string {
         length "1 .. 128";
       }
     }
     leaf access-profile {
       description "Access profile to use for AAA services";
       junos:must "(\"access profile $$\")";
       junos:must-message "Matching access profile must be defined";
       junos:must "(!(\"forwarding-options helpers bootp\"))";
       junos:must-message "'access-profile' statement cannot be included along with 'forwarding-options helpers bootp' statement";
       type string {
         length "1 .. 128";
       }
     }
     container short-cycle-protection {
       description "Short cycle lockout configuration";
       leaf lockout-min-time {
         description "Short cycle lockout time in seconds";
         type union {
           type string {
             pattern "<.*>|$.*";
           }
           type uint32 {
             range "1 .. 86400";
           }
         }
       }
       leaf lockout-max-time {
         description "Short cycle lockout time in seconds";
         type union {
           type string {
             pattern "<.*>|$.*";
           }
           type uint32 {
             range "1 .. 86400";
           }
         }
       }
     }
     container route-suppression {
       description "Suppress access-internal and/or destination route addition";
       junos:must "(!(\".. liveness-detection method layer2-liveness-detection\"))";
       junos:must-message "Cannot specify route-suppression with liveness-detection method layer2-liveness-detection";
       junos:must "(!(\".. overrides no-arp\"))";
       junos:must-message "Cannot specify route-suppression with overrides no-arp";
       uses dhcp-route-suppression-type;
     }
     list group {
       key name;
       ordered-by user;
       description "Define a DHCP local server group";
       junos:must "(!(\"system services dhcp\"))";
       junos:must-message "Incompatible with the dhcp server configured under 'system services dhcp'";
       junos:must "(!(\"forwarding-options helpers bootp\"))";
       junos:must-message "'group' statement cannot be included along with 'forwarding-options helpers bootp' statement";
       uses dhcp-local-server-group;
     }
     list dual-stack-group {
       key name;
       description "Define a DHCP dual stack group";
       uses dhcp-local-server-dual-stack-group;
     }
     container lease-time-validation {
       presence "enable lease-time-validation";
       description "Configure lease time violation validation";
       uses apply-advanced;
       leaf lease-time-threshold {
         description "Threshold for lease time violation seconds";
         units "seconds";
         type union {
           type string {
             pattern "<.*>|$.*";
           }
           type uint32 {
             range "60 .. 2147483647";
           }
         }
       }
       container violation-action {
         description "Lease time validation violation action";
         choice violation-action-choice {
           case case_1 {
             leaf strict {
               description "Reject discover and renew";
               type empty;
             }
           }
           case case_2 {
             leaf override-lease {
               description "Override assigned lease time with threshold";
               type empty;
             }
           }
         }
       }
     }
     choice requested-ip-check {
       case case_1 {
         leaf requested-ip-network-match {
           description "Subnet to match server's address for active and giaddr for passive clients";
           default "8";
           type union {
             type string {
               pattern "<.*>|$.*";
             }
             type uint32 {
               range "0 .. 31";
             }
           }
         }
       }
       case case_2 {
         leaf requested-ip-interface-match {
           description "Use incoming-interface's subnet to check";
           type empty;
         }
       }
     }
     leaf no-snoop {
       description "Do not snoop DHCP packets";
       junos:must "(!(\"legacy-snooping\"))";
       junos:must-message "'no-snoop' statement cannot be included along with 'legacy-snooping' statement";
       type empty;
     }
     container persistent-storage {
       description "Trigger to enable flat file storage";
       leaf automatic {
         description "Trigger automatically";
         type empty;
       }
     }
     container allow-leasequery {
       description "Allow DHCP leasequery";
       presence "enable allow-leasequery";
       junos:must "(!(\".. active-leasequery\"))";
       junos:must-message "'allow-leasequery' statement cannot be configured along with 'active-leasequery'";
       uses server-leasequery-type;
     }
     container remote-id-mismatch {
       description "DHCP client remote-id mismatch";
       presence "enable remote-id-mismatch";
       junos:must "(!(\".. reauthenticate\"))";
       junos:must-message "'remote-id-mismatch' statement cannot be included with 'reauthenticate'";
       uses dhcp-remote-id-mismatch-type;
     }
     container reauthenticate {
       presence "enable reauthenticate";
       junos:must "(!(\".. remote-id-mismatch\"))";
       junos:must-message "'reauthenticate' statement cannot be included with 'remote-id-mismatch'";
       junos:must "((\".. authentication\" || \".. .. authentication\"))";
       junos:must-message "'authentication' statement must be included with 'reauthenticate'";
       description "DHCP client reauthenticate processing";
       uses apply-advanced;
       leaf lease-renewal {
         description "Reauthenticate on each renew, rebind, DISCOVER or SOLICIT";
         junos:must "(!(\".. actual-data-rate-change\"))";
         junos:must-message "'lease-renewal' statement cannot be included with 'actual-data-rate-change'";
         type empty;
       }
       leaf remote-id-mismatch {
         description "Reauthenticate on remote-id mismatch for renew, rebind and re-negotiation";
         type empty;
       }
       container actual-data-rate-change {
         description "Reauthenticate on data rate change";
         junos:must "(!(\".. lease-renewal\"))";
         junos:must-message "'actual-data-rate-change' statement cannot be included with 'lease-renewal'";
         uses actual-data-rate-change-type;
       }
     }
     container allow-bulk-leasequery {
       description "Allow DHCP bulk leasequery";
       presence "enable allow-bulk-leasequery";
       junos:must "(!(\".. active-leasequery\"))";
       junos:must-message "'allow-bulk-leasequery' statement cannot be configured along with 'active-leasequery'";
       uses server-bulk-leasequery-type;
     }
     container allow-active-leasequery {
       description "Allow DHCP active leasequery";
       presence "enable allow-active-leasequery";
       junos:must "(!(\".. active-leasequery\"))";
       junos:must-message "'allow-active-leasequery' statement cannot be configured along with 'active-leasequery'";
       uses server-active-leasequery-type;
     }
     container active-leasequery {
       description "DHCPv4 active leasequery configuration";
       presence "enable active-leasequery";
       junos:must "((!(\".. allow-active-leasequery\") && (!(\".. allow-bulk-leasequery\") && !(\".. allow-leasequery\"))))";
       junos:must-message "'active-leasequery' statement cannot be configured along with 'allow-active-leasequery','allow-bulk-leasequery','allow-leasequery'";
       uses active-leasequery-v4-type;
     }
   }
   grouping active-leasequery-v4-type {
     description "Configure active leasequery";
     uses apply-advanced;
     leaf topology-discover {
       description "Topology discovery";
       junos:must "(\".. peer-address\")";
       junos:must-message "Must configure [peer-address] to configure topology-discover";
       type empty;
     }
     list peer-address {
       key name;
       ordered-by user;
       description "Server ip address";
       leaf name {
         description "Peer ip address";
         type jt:ipaddr;
       }
       uses apply-advanced;
     }
     leaf timeout {
       description "Read/write timeout in seconds";
       default "120";
       units "seconds";
       type union {
         type string {
           pattern "<.*>|$.*";
         }
         type uint32 {
           range "10 .. 3600";
         }
       }
     }
     leaf idle-timeout {
       description "Idle timeout in seconds";
       default "60";
       units "seconds";
       type union {
         type string {
           pattern "<.*>|$.*";
         }
         type uint32 {
           range "10 .. 3600";
         }
       }
     }
   }
   grouping actual-data-rate-change-type {
     description "Reauthenticate on data rate change processing";
     uses apply-advanced;
     container actual-data-rate-upstream {
       description "Actual data rate upstream";
       presence "enable actual-data-rate-upstream";
       uses actual-data-rate-type;
     }
     container actual-data-rate-downstream {
       description "Actual data rate downstream";
       presence "enable actual-data-rate-downstream";
       uses actual-data-rate-type;
     }
   }
   grouping actual-data-rate-type {
     description "Actual data rate type processing";
     uses apply-advanced;
     leaf threshold {
       description "Threshold in kbps";
       type union {
         type uint32;
         type string {
           pattern "<.*>|$.*";
         }
       }
     }
   }
   grouping authentication-type {
     description "DHCP authentication";
     uses apply-advanced;
     leaf password {
       description "Username password to use";
       type string {
         length "1 .. 64";
       }
     }
     container username-include {
       description "Add username options";
       uses apply-advanced;
       leaf delimiter {
         description "Change delimiter/separator character";
         type string {
           length 1;
         }
       }
       leaf domain-name {
         description "Add domain name";
         type string {
           length "1 .. 64";
         }
       }
       leaf user-prefix {
         description "Add user defined prefix";
         type string {
           length "1 .. 64";
         }
       }
       leaf mac-address {
         description "Include MAC address";
         type empty;
       }
       container option-82 {
         presence "enable option-82";
         description "Include option 82";
         leaf circuit-id {
           description "Include option 82 circuit-id (sub option 1)";
           type empty;
         }
         leaf remote-id {
           description "Include option 82 remote-id (sub option 2)";
           type empty;
         }
       }
       leaf logical-system-name {
         description "Include logical system name";
         type empty;
       }
       leaf routing-instance-name {
         description "Include routing instance name";
         type empty;
       }
       container client-id {
         presence "enable client-id";
         description "Include client ID";
         leaf exclude-headers {
           description "Exclude all the headers";
           type empty;
         }
         leaf use-automatic-ascii-hex-encoding {
           description "Use automatic ascii hex username encoding";
           type empty;
         }
       }
       leaf option-60 {
         description "Include option 60";
         type empty;
       }
       leaf circuit-type {
         description "Include circuit type";
         type empty;
       }
       leaf interface-name {
         description "Include interface name";
         type empty;
       }
       leaf interface-description {
         description "Include interface description";
         type enumeration {
           enum "device" {
             description "Add the device interface description";
           }
           enum "logical" {
             description "Add the logical interface description";
           }
         }
       }
       leaf vlan-tags {
         description "Include the vlan tag(s)";
         type empty;
       }
     }
   }
   grouping dhcp-liveness-detection-type {
     description "DHCP client liveness detection processing";
     uses apply-advanced;
     container failure-action {
       description "Liveness detection failure action options";
       uses dhcp-liveness-detection-failure-action-type;
     }
     container method {
       description "Liveness detection method options";
       uses apply-advanced;
       choice method-choice {
         case case_1 {
           container bfd {
             description "Bidirectional Forwarding Detection (BFD) options";
             uses dhcp-bfd-liveness-detection-type;
           }
         }
         case case_2 {
           container layer2-liveness-detection {
             description "Address resolution options";
             junos:must "((!(\".. .. route-suppression\") && (!(\".. .. .. route-suppression\") && !(\".. .. .. .. route-suppression\"))))";
             junos:must-message "Method not allowed with route-suppression enabled";
             uses dhcp-arp-nud-liveness-detection-type;
           }
         }
       }
     }
   }
   grouping dhcp-arp-nud-liveness-detection-type {
     description "Address Resolution detection options";
     uses apply-advanced;
     leaf transmit-interval {
       description "Transmit interval for address resolution";
       default "300";
       units "seconds";
       type union {
         type string {
           pattern "<.*>|$.*";
         }
         type uint32 {
           range "300 .. 1800";
         }
       }
     }
     leaf max-consecutive-retries {
       description "Retry attempts";
       default "3";
       type union {
         type string {
           pattern "<.*>|$.*";
         }
         type uint32 {
           range "3 .. 6";
         }
       }
     }
   }
   grouping dhcp-bfd-liveness-detection-type {
     description "Bidirectional Forwarding Detection (BFD) options";
     uses apply-advanced;
     leaf version {
       description "BFD protocol version number";
       default "automatic";
       type enumeration {
         enum "0" {
           description "BFD version 0 (deprecated)";
         }
         enum "1" {
           description "BFD version 1";
         }
         enum "automatic" {
           description "Choose BFD version automatically";
         }
       }
     }
     leaf minimum-interval {
       description "Minimum transmit and receive interval";
       units "milliseconds";
       type union {
         type string {
           pattern "<.*>|$.*";
         }
         type uint32 {
           range "30000 .. 255000";
         }
       }
     }
     leaf minimum-transmit-interval {
       description "Minimum transmit interval";
       status deprecated;
       units "milliseconds";
       type union {
         type string {
           pattern "<.*>|$.*";
         }
         type uint32 {
           range "30000 .. 255000";
         }
       }
     }
     leaf minimum-receive-interval {
       description "Minimum receive interval";
       units "milliseconds";
       type union {
         type string {
           pattern "<.*>|$.*";
         }
         type uint32 {
           range "30000 .. 255000";
         }
       }
     }
     leaf multiplier {
       description "Detection time multiplier";
       default "3";
       type union {
         type string {
           pattern "<.*>|$.*";
         }
         type uint32 {
           range "1 .. 255";
         }
       }
     }
     choice adaptation-choice {
       case case_1 {
         leaf no-adaptation {
           description "Disable adaptation";
           type empty;
         }
       }
     }
     container transmit-interval {
       description "Transmit-interval options";
       uses apply-advanced;
       leaf minimum-interval {
         description "Minimum transmit interval";
         units "milliseconds";
         type union {
           type string {
             pattern "<.*>|$.*";
           }
           type uint32 {
             range "30000 .. 255000";
           }
         }
       }
       leaf threshold {
         description "High transmit interval triggering a trap";
         units "milliseconds";
         type union {
           type uint32;
           type string {
             pattern "<.*>|$.*";
           }
         }
       }
     }
     container detection-time {
       description "Detection-time options";
       uses apply-advanced;
       leaf threshold {
         description "High detection-time triggering a trap";
         units "milliseconds";
         type union {
           type uint32;
           type string {
             pattern "<.*>|$.*";
           }
         }
       }
     }
     leaf session-mode {
       description "BFD single-hop or multihop session-mode";
       default "automatic";
       type enumeration {
         enum "automatic" {
           description "Choose session-mode automatically";
         }
         enum "single-hop" {
           description "Use single-hop";
         }
         enum "multihop" {
           description "Use multihop";
         }
       }
     }
     leaf holddown-interval {
       description "Time to hold the session-UP notification to the client";
       default "0";
       units "milliseconds";
       type union {
         type string {
           pattern "<.*>|$.*";
         }
         type uint32 {
           range "0 .. 255000";
         }
       }
     }
   }
   grouping dhcp-liveness-detection-failure-action-type {
     description "Liveness detection failure action options";
     uses apply-advanced;
     choice failure-action-type {
       case case_1 {
         leaf clear-binding {
           description "Clear the client binding";
           type empty;
         }
       }
       case case_2 {
         leaf clear-binding-if-interface-up {
           description "Clear the client binding only if the incoming interface is up";
           type empty;
         }
       }
       case case_3 {
         leaf log-only {
           description "Maintain the client binding and log the failure event";
           type empty;
         }
       }
     }
   }
   grouping dhcp-local-server-dual-stack-group {
     description "DHCP dual stack groups";
     leaf name {
       description "Dual stack group name";
       type string {
         length "1 .. 64";
         junos:posix-pattern "^[A-Za-z0-9][_0-9A-Za-z-]*$";
         junos:pattern-message "Must be a non-reserved string of 64 characters or less";
       }
     }
     uses apply-advanced;
     container authentication {
       description "DHCP authentication";
       uses dual-stack-authentication-type;
     }
     leaf access-profile {
       description "Access profile to be used for jdhcpd";
       type string {
         length "1 .. 128";
       }
     }
     container dynamic-profile {
       description "Dynamic profile to use";
       uses dynamic-profile-type;
     }
     leaf service-profile {
       description "Dynamic profile to use for default service activation";
       type string {
         length "1 .. 128";
       }
     }
     leaf on-demand-address-allocation {
       description "Allocate addresses on demand";
       type empty;
     }
     container classification-key {
       description "Classification key for identifying dual stack household";
       junos:must "(\".. dynamic-profile\")";
       junos:must-message "dynamic profile configuration in dual-stack-group is must for configuring classification-type";
       uses classification-types;
     }
     leaf dual-stack-interface-client-limit {
       description "Limit the number of client allowed on an interface";
       type union {
         type string {
           pattern "<.*>|$.*";
         }
         type uint32 {
           range "1 .. 500000";
         }
       }
     }
     container protocol-master {
       description "Select family as protocol master";
       uses jdhcp-dual-stack-protocol-mstr-type;
     }
     container liveness-detection {
       description "DHCP client liveness detection processing";
       uses dhcp-liveness-detection-dualstack-type;
     }
     container reauthenticate {
       junos:must "(\".. on-demand-address-allocation\")";
       junos:must-message "'on-demand-address-allocation' statement must be included with 'reauthenticate'";
       junos:must "(\".. authentication\")";
       junos:must-message "'authentication' statement must be included with 'reauthenticate'";
       description "DHCP client reauthenticate processing";
       leaf lease-renewal {
         description "Reauthenticate on each renew, rebind, DISCOVER or SOLICIT";
         type empty;
       }
       leaf remote-id-mismatch {
         description "Reauthenticate on remote-id mismatch for renew, rebind and re-negotiation";
         type empty;
       }
     }
     container short-cycle-protection {
       description "Short cycle lockout configuration";
       leaf lockout-min-time {
         description "Short cycle lockout time in seconds";
         type union {
           type string {
             pattern "<.*>|$.*";
           }
           type uint32 {
             range "1 .. 86400";
           }
         }
       }
       leaf lockout-max-time {
         description "Short cycle lockout time in seconds";
         type union {
           type string {
             pattern "<.*>|$.*";
           }
           type uint32 {
             range "1 .. 86400";
           }
         }
       }
     }
   }
   grouping classification-types {
     description "Different mechanisms to identify a single household";
     uses apply-advanced;
     leaf mac-address {
       description "MAC address of client";
       type empty;
     }
     leaf circuit-id {
       description "Circuit-id as key";
       type empty;
     }
     leaf remote-id {
       description "Remote-id as key";
       type empty;
     }
   }
   grouping dhcp-liveness-detection-dualstack-type {
     description "DHCP client liveness detection processing";
     uses apply-advanced;
     container failure-action {
       description "Liveness detection failure action options";
       uses dhcp-liveness-detection-failure-action-type;
     }
     container method {
       description "Liveness detection method options";
       uses apply-advanced;
       choice method-choice {
         case case_1 {
           container layer2-liveness-detection {
             description "Address resolution options";
             junos:must "((!(\".. .. route-suppression\") && (!(\".. .. .. route-suppression\") && !(\".. .. .. .. route-suppression\"))))";
             junos:must-message "Method not allowed with route-suppression enabled";
             uses dhcp-arp-nud-liveness-detection-type;
           }
         }
       }
     }
   }
   grouping dhcp-local-server-group {
     description "DHCP groups";
     leaf name {
       description "Group name";
       type string {
         length "1 .. 64";
         junos:posix-pattern "^[A-Za-z0-9][_0-9A-Za-z-]*$";
         junos:pattern-message "Must be a non-reserved string of 64 characters or less";
       }
     }
     uses apply-advanced;
     container authentication {
       description "DHCP authentication";
       uses authentication-type;
     }
     container liveness-detection {
       description "DHCP client liveness detection processing";
       uses dhcp-liveness-detection-type;
     }
     container reconfigure {
       description "DHCP reconfigure processing";
       presence "enable reconfigure";
       uses reconfigure-type;
     }
     container overrides {
       description "DHCP override processing";
       presence "enable overrides";
       uses override-local-server-type;
     }
     container dynamic-profile {
       description "Dynamic profile to use";
       uses dynamic-profile-type;
     }
     leaf service-profile {
       description "Dynamic profile to use for default service activation";
       type string {
         length "1 .. 128";
       }
     }
     leaf access-profile {
       description "Access profile to use for AAA services";
       junos:must "(\"access profile $$\")";
       junos:must-message "Matching access profile must be defined";
       type string {
         length "1 .. 128";
       }
     }
     container short-cycle-protection {
       description "Short cycle lockout configuration";
       leaf lockout-min-time {
         description "Short cycle lockout time in seconds";
         type union {
           type string {
             pattern "<.*>|$.*";
           }
           type uint32 {
             range "1 .. 86400";
           }
         }
       }
       leaf lockout-max-time {
         description "Short cycle lockout time in seconds";
         type union {
           type string {
             pattern "<.*>|$.*";
           }
           type uint32 {
             range "1 .. 86400";
           }
         }
       }
     }
     container route-suppression {
       description "Suppress access-internal and/or destination route addition";
       junos:must "(!(\".. liveness-detection method layer2-liveness-detection\"))";
       junos:must-message "Cannot specify route-suppression with liveness-detection method layer2-liveness-detection";
       junos:must "((!(\".. overrides no-arp\") && !(\".. .. overrides no-arp\")))";
       junos:must-message "Cannot specify route-suppression with overrides no-arp";
       uses dhcp-route-suppression-type;
     }
     list interface {
       key name;
       description "One or more interfaces";
       leaf name {
         description "Interface name";
         type union {
           type jt:interface-name;
           type string {
             pattern "<.*>|$.*";
           }
         }
       }
       uses apply-advanced;
       leaf upto {
         description "Interface up to";
         type union {
           type jt:interface-name;
           type string {
             pattern "<.*>|$.*";
           }
         }
       }
       leaf exclude {
         description "Exclude this interface range";
         type empty;
       }
       leaf trace {
         description "Enable tracing for this interface";
         junos:must "(!(\".. exclude\"))";
         junos:must-message "Cannot specify tracing with exclude";
         type empty;
       }
       container overrides {
         description "DHCP override processing";
         junos:must "(!(\".. exclude\"))";
         junos:must-message "Cannot specify overrides with exclude";
         uses override-local-server-type;
       }
       container dynamic-profile {
         description "Dynamic profile to use";
         junos:must "(!(\".. exclude\"))";
         junos:must-message "Cannot specify overrides with exclude";
         uses dynamic-profile-type;
       }
       leaf service-profile {
         description "Dynamic profile to use for default service activation";
         type string {
           length "1 .. 128";
         }
       }
       leaf access-profile {
         description "Access profile to use for AAA services";
         junos:must "(\"access profile $$\")";
         junos:must-message "Matching access profile must be defined";
         junos:must "(!(\".. exclude\"))";
         junos:must-message "Cannot specify overrides with exclude";
         type string {
           length "1 .. 128";
         }
       }
       container short-cycle-protection {
         description "Short cycle lockout configuration";
         leaf lockout-min-time {
           description "Short cycle lockout time in seconds";
           type union {
             type string {
               pattern "<.*>|$.*";
             }
             type uint32 {
               range "1 .. 86400";
             }
           }
         }
         leaf lockout-max-time {
           description "Short cycle lockout time in seconds";
           type union {
             type string {
               pattern "<.*>|$.*";
             }
             type uint32 {
               range "1 .. 86400";
             }
           }
         }
       }
     }
     container lease-time-validation {
       presence "enable lease-time-validation";
       description "Configure lease time violation validation";
       uses apply-advanced;
       leaf lease-time-threshold {
         description "Threshold for lease time violation seconds";
         units "seconds";
         type union {
           type string {
             pattern "<.*>|$.*";
           }
           type uint32 {
             range "60 .. 2147483647";
           }
         }
       }
       container violation-action {
         description "Lease time validation violation action";
         choice violation-action-choice {
           case case_1 {
             leaf strict {
               description "Reject discover and renew";
               type empty;
             }
           }
           case case_2 {
             leaf override-lease {
               description "Override assigned lease time with threshold";
               type empty;
             }
           }
         }
       }
     }
     container remote-id-mismatch {
       description "DHCP client remote-id mismatch";
       presence "enable remote-id-mismatch";
       junos:must "(!(\".. reauthenticate\"))";
       junos:must-message "'remote-id-mismatch' statement cannot be included with 'reauthenticate'";
       uses dhcp-remote-id-mismatch-type;
     }
     container reauthenticate {
       presence "enable reauthenticate";
       junos:must "(!(\".. remote-id-mismatch\"))";
       junos:must-message "'reauthenticate' statement cannot be included with 'remote-id-mismatch'";
       junos:must "((\".. authentication\" || \".. .. authentication\"))";
       junos:must-message "'authentication' statement must be included with 'reauthenticate'";
       description "DHCP client reauthenticate processing";
       uses apply-advanced;
       leaf lease-renewal {
         description "Reauthenticate on each renew, rebind, DISCOVER or SOLICIT";
         junos:must "(!(\".. actual-data-rate-change\"))";
         junos:must-message "'lease-renewal' statement cannot be included with 'actual-data-rate-change'";
         type empty;
       }
       leaf remote-id-mismatch {
         description "Reauthenticate on remote-id mismatch for renew, rebind and re-negotiation";
         type empty;
       }
       container actual-data-rate-change {
         description "Reauthenticate on data rate change";
         junos:must "(!(\".. lease-renewal\"))";
         junos:must-message "'actual-data-rate-change' statement cannot be included with 'lease-renewal'";
         uses actual-data-rate-change-type;
       }
     }
   }
   grouping dhcp-remote-id-mismatch-type {
     description "DHCP client remote-id-mismatch processing";
     uses apply-advanced;
     leaf disconnect {
       description "Disconnect session on remote-id mismatch";
       type empty;
     }
   }
   grouping dhcp-route-suppression-type {
     uses apply-advanced;
     choice dhcp-route-suppression-choice {
       case case_1 {
         leaf access-internal {
           description "Suppress access-internal and destination route addition";
           type empty;
         }
       }
       case case_2 {
         leaf destination {
           description "Suppress destination route addition";
           type empty;
         }
       }
     }
   }
   grouping dhcpv6-local-server-type {
     uses apply-advanced;
     container authentication {
       description "DHCPv6 authentication";
       uses dhcpv6-authentication-type;
     }
     container liveness-detection {
       description "DHCPv6 client liveness detection processing";
       uses dhcpv6-liveness-detection-type;
     }
     container reconfigure {
       description "DHCPv6 reconfigure processing";
       presence "enable reconfigure";
       uses dhcpv6-reconfigure-type;
     }
     container dynamic-profile {
       description "Dynamic profile to use";
       uses dynamic-profile-type;
     }
     container forward-snooped-clients {
       junos:must "((!(\".. forward-only\") && (!(\".. forward-only-replies\") && !(any \".. group <*> forward-only\"))))";
       junos:must-message "forward-only and forward-only-replies cannot be configured when forward-snooped-clients is configured";
       description "Forward snooped (unicast) packets";
       choice interface-type {
         case case_1 {
           leaf configured-interfaces {
             description "Forward snooped (unicast) packets on configured interfaces";
             type empty;
           }
         }
         case case_2 {
           leaf non-configured-interfaces {
             description "Forward snooped (unicast) packets on non-configured interfaces";
             type empty;
           }
         }
         case case_3 {
           leaf all-interfaces {
             description "Forward snooped (unicast) packets on configured and non-configured interfaces";
             type empty;
           }
         }
       }
     }
     leaf service-profile {
       description "Dynamic profile to use for default service activation";
       type string {
         length "1 .. 128";
       }
     }
     leaf access-profile {
       description "Access profile to use for AAA services";
       junos:must "(\"access profile $$\")";
       junos:must-message "Matching access profile must be defined";
       type string {
         length "1 .. 128";
       }
     }
     container short-cycle-protection {
       description "Short cycle lockout configuration";
       leaf lockout-min-time {
         description "Short cycle lockout time in seconds";
         type union {
           type string {
             pattern "<.*>|$.*";
           }
           type uint32 {
             range "1 .. 86400";
           }
         }
       }
       leaf lockout-max-time {
         description "Short cycle lockout time in seconds";
         type union {
           type string {
             pattern "<.*>|$.*";
           }
           type uint32 {
             range "1 .. 86400";
           }
         }
       }
     }
     container overrides {
       description "DHCPv6 override processing";
       presence "enable overrides";
       uses dhcpv6-override-local-server-type;
     }
     container route-suppression {
       description "Suppress access-internal and/or access route addition";
       uses dhcpv6-route-suppression-type;
     }
     list group {
       key name;
       ordered-by user;
       description "Define a DHCPv6 local server group";
       uses dhcpv6-local-server-group;
     }
     container lease-time-validation {
       presence "enable lease-time-validation";
       description "Configure lease time violation validation";
       uses apply-advanced;
       leaf lease-time-threshold {
         description "Threshold for lease time violation seconds";
         units "seconds";
         type union {
           type string {
             pattern "<.*>|$.*";
           }
           type uint32 {
             range "60 .. 2147483647";
           }
         }
       }
       container violation-action {
         description "Lease time validation violation action";
         choice violation-action-choice {
           case case_1 {
             leaf strict {
               description "Reject solicit and renew";
               type empty;
             }
           }
           case case_2 {
             leaf override-lease {
               description "Override assigned lease time with threshold";
               type empty;
             }
           }
         }
       }
     }
     choice requested-ip-check {
       case case_1 {
         leaf requested-ip-network-match {
           description "Subnet to match server's address for active and link-address for passive clients";
           default "16";
           type union {
             type string {
               pattern "<.*>|$.*";
             }
             type uint32 {
               range "0 .. 127";
             }
           }
         }
       }
       case case_2 {
         leaf requested-ip-interface-match {
           description "Use incoming-interface's subnet to check";
           type empty;
         }
       }
     }
     leaf no-snoop {
       description "Do not snoop DHCPV6 packets";
       junos:must "(!(\"legacy-snooping\"))";
       junos:must-message "'no-snoop' statement cannot be included along with 'legacy-snooping' statement";
       type empty;
     }
     container persistent-storage {
       description "Trigger to enable flat file storage";
       leaf automatic {
         description "Trigger automatically";
         type empty;
       }
     }
     container server-duid-type {
       description "Define the DUID type to be used as the Server ID. Type supported is DUID-LL";
       uses duid-type;
     }
     container remote-id-mismatch {
       description "DHCP client remote-id mismatch";
       presence "enable remote-id-mismatch";
       junos:must "(!(\".. reauthenticate\"))";
       junos:must-message "'remote-id-mismatch' statement cannot be included with 'reauthenticate'";
       uses dhcp-remote-id-mismatch-type;
     }
     container reauthenticate {
       junos:must "(!(\".. remote-id-mismatch\"))";
       junos:must-message "'reauthenticate' statement cannot be included with 'remote-id-mismatch'";
       junos:must "((\".. authentication\" || \".. .. authentication\"))";
       junos:must-message "'authentication' statement must be included with 'reauthenticate'";
       description "DHCP client reauthenticate processing";
       leaf lease-renewal {
         description "Reauthenticate on each renew, rebind, DISCOVER or SOLICIT";
         type empty;
       }
       leaf remote-id-mismatch {
         description "Reauthenticate on remote-id mismatch for renew, rebind and re-negotiation";
         type empty;
       }
     }
     container allow-leasequery {
       description "Allow DHCPv6 leasequery";
       presence "enable allow-leasequery";
       junos:must "(!(\".. active-leasequery\"))";
       junos:must-message "'allow-leasequery' statement cannot be configured along with 'active-leasequery'";
       uses server-leasequery-type;
     }
     container allow-bulk-leasequery {
       description "Allow DHCPv6 bulk leasequery";
       presence "enable allow-bulk-leasequery";
       junos:must "(!(\".. active-leasequery\"))";
       junos:must-message "'allow-bulk-leasequery' statement cannot be configured along with 'active-leasequery'";
       uses server-bulk-leasequery-type;
     }
     container allow-active-leasequery {
       description "Allow DHCPv6 active leasequery";
       presence "enable allow-active-leasequery";
       junos:must "(!(\".. active-leasequery\"))";
       junos:must-message "'allow-active-leasequery' statement cannot be configured along with 'active-leasequery'";
       uses server-active-leasequery-type;
     }
     container duplicate-clients {
       description "Allow duplicate clients";
       uses dhcpv6-duplicate-clients-type;
     }
     container dynamic-server {
       description "DHCPv6 dynamic server configuration";
       uses dhcpv6-dynamic-server-type;
     }
     container active-leasequery {
       description "DHCPv6 active leasequery configuration";
       presence "enable active-leasequery";
       junos:must "((!(\".. allow-active-leasequery\") && (!(\".. allow-bulk-leasequery\") && !(\".. allow-leasequery\"))))";
       junos:must-message "'active-leasequery' statement cannot be configured along with 'allow-active-leasequery','allow-bulk-leasequery','allow-leasequery'";
       uses active-leasequery-v6-type;
     }
   }
   grouping active-leasequery-v6-type {
     description "Configure active leasequery";
     uses apply-advanced;
     leaf topology-discover {
       description "Topology discovery";
       junos:must "(\".. peer-address\")";
       junos:must-message "Must configure [peer-address] to configure topology-discover";
       type empty;
     }
     leaf timeout {
       description "Read/write timeout in seconds";
       default "120";
       units "seconds";
       type union {
         type string {
           pattern "<.*>|$.*";
         }
         type uint32 {
           range "10 .. 3600";
         }
       }
     }
     leaf idle-timeout {
       description "Idle timeout in seconds";
       default "60";
       units "seconds";
       type union {
         type string {
           pattern "<.*>|$.*";
         }
         type uint32 {
           range "10 .. 3600";
         }
       }
     }
     list peer-address {
       key name;
       ordered-by user;
       description "Peer ipv6 address";
       leaf name {
         description "Peer ipv6 address";
         type jt:ipv6addr;
       }
       uses apply-advanced;
     }
   }
   grouping dhcpv6-authentication-type {
     description "DHCPv6 authentication";
     uses apply-advanced;
     leaf password {
       description "Username password to use";
       type string {
         length "1 .. 64";
       }
     }
     container username-include {
       description "Add username options";
       uses apply-advanced;
       leaf delimiter {
         description "Change delimiter/separator character";
         type string {
           length 1;
         }
       }
       leaf domain-name {
         description "Add domain name";
         type string {
           length "1 .. 64";
         }
       }
       leaf user-prefix {
         description "Add user defined prefix";
         type string {
           length "1 .. 64";
         }
       }
       leaf mac-address {
         description "Include MAC address";
         type empty;
       }
       container client-id {
         presence "enable client-id";
         description "Include client ID";
         leaf exclude-headers {
           description "Exclude all the headers";
           type empty;
         }
         leaf use-automatic-ascii-hex-encoding {
           description "Use automatic ascii hex username encoding";
           type empty;
         }
       }
       container relay-agent-remote-id {
         presence "enable relay-agent-remote-id";
         description "Include the relay agent remote ID";
         uses apply-advanced;
         choice relay-agent-remote-id-choice {
           case case_1 {
             leaf enterprise-id {
               description "Only use enterprise-id portion of option-37";
               status deprecated;
               type empty;
             }
           }
           case case_2 {
             leaf remote-id {
               description "Only use remote-id portion of option-37";
               status deprecated;
               type empty;
             }
           }
         }
       }
       leaf logical-system-name {
         description "Include logical system name";
         type empty;
       }
       leaf routing-instance-name {
         description "Include routing instance name";
         type empty;
       }
       leaf relay-agent-subscriber-id {
         description "Include the relay agent subscriber ID";
         type empty;
       }
       leaf relay-agent-interface-id {
         description "Include the relay agent interface ID";
         type empty;
       }
       leaf circuit-type {
         description "Include circuit type";
         type empty;
       }
       leaf interface-name {
         description "Include interface name";
         type empty;
       }
       leaf interface-description {
         description "Include interface description";
         type enumeration {
           enum "device" {
             description "Add the device interface description";
           }
           enum "logical" {
             description "Add the logical interface description";
           }
         }
       }
       leaf vlan-tags {
         description "Include the vlan tag(s)";
         type empty;
       }
     }
   }
   grouping dhcpv6-duplicate-clients-type {
     description "Allow duplicate clients";
     choice distinguish-with {
       case case_1 {
         leaf incoming-interface {
           description "Allow duplicate clients on different underlying interfaces";
           type empty;
         }
       }
     }
   }
   grouping dhcpv6-dynamic-server-type {
     uses apply-advanced;
     container overrides {
       description "DHCPv6 override processing";
       presence "enable overrides";
       uses dhcpv6-override-dynamic-server-type;
     }
     list group {
       key name;
       ordered-by user;
       description "Define a DHCPv6 dynamic server group";
       uses dhcpv6-dynamic-server-group;
     }
   }
   grouping dhcpv6-dynamic-server-group {
     description "DHCP dynamic server groups";
     leaf name {
       description "Group name";
       type string {
         length "1 .. 64";
         junos:posix-pattern "^[A-Za-z0-9][_0-9A-Za-z-]*$";
         junos:pattern-message "Must be a non-reserved string of 64 characters or less";
       }
     }
     uses apply-advanced;
     leaf neighbor-discovery-router-advertisement {
       description "Designated NDRA pool for this group";
       type string {
         length "1 .. 64";
       }
     }
     container overrides {
       description "DHCP override processing";
       presence "enable overrides";
       uses dhcpv6-override-dynamic-server-type;
     }
     list interface {
       key name;
       description "One or more interfaces";
       leaf name {
         description "Interface name";
         junos:must "(!(any \"system services dhcp-local-server dhcpv6 group <*> interface $$\"))";
         junos:must-message "DHCP dynamic server and dhcp local server cannot be started on the same interface";
         type union {
           type jt:interface-name;
           type string {
             pattern "<.*>|$.*";
           }
         }
       }
       uses apply-advanced;
       container overrides {
         description "DHCP override processing";
         uses dhcpv6-override-dynamic-server-type;
       }
     }
   }
   grouping dhcpv6-liveness-detection-type {
     description "DHCPv6 client liveness detection processing";
     uses apply-advanced;
     container failure-action {
       description "Liveness detection failure action options";
       uses dhcp-liveness-detection-failure-action-type;
     }
     container method {
       description "Liveness detection method options";
       uses apply-advanced;
       choice method-choice {
         case case_1 {
           container bfd {
             description "Bidirectional Forwarding Detection (BFD) options";
             uses dhcp-bfd-liveness-detection-type;
           }
         }
         case case_2 {
           container layer2-liveness-detection {
             description "Neighbor discovery options";
             uses dhcp-arp-nud-liveness-detection-type;
           }
         }
       }
     }
   }
   grouping dhcpv6-local-server-group {
     description "DHCP groups";
     leaf name {
       description "Group name";
       type string {
         length "1 .. 64";
         junos:posix-pattern "^[A-Za-z0-9][_0-9A-Za-z-]*$";
         junos:pattern-message "Must be a non-reserved string of 64 characters or less";
       }
     }
     uses apply-advanced;
     container authentication {
       description "DHCP authentication";
       uses dhcpv6-authentication-type;
     }
     container liveness-detection {
       description "DHCPv6 client liveness detection processing";
       uses dhcpv6-liveness-detection-type;
     }
     container reconfigure {
       description "DHCPv6 reconfigure processing";
       presence "enable reconfigure";
       uses dhcpv6-reconfigure-type;
     }
     container dynamic-profile {
       description "Dynamic profile to use";
       uses dynamic-profile-type;
     }
     leaf service-profile {
       description "Dynamic profile to use for default service activation";
       type string {
         length "1 .. 128";
       }
     }
     leaf access-profile {
       description "Access profile to use for AAA services";
       junos:must "(\"access profile $$\")";
       junos:must-message "Matching access profile must be defined";
       type string {
         length "1 .. 128";
       }
     }
     container short-cycle-protection {
       description "Short cycle lockout configuration";
       leaf lockout-min-time {
         description "Short cycle lockout time in seconds";
         type union {
           type string {
             pattern "<.*>|$.*";
           }
           type uint32 {
             range "1 .. 86400";
           }
         }
       }
       leaf lockout-max-time {
         description "Short cycle lockout time in seconds";
         type union {
           type string {
             pattern "<.*>|$.*";
           }
           type uint32 {
             range "1 .. 86400";
           }
         }
       }
     }
     container overrides {
       description "DHCP override processing";
       presence "enable overrides";
       uses dhcpv6-override-local-server-type;
     }
     container route-suppression {
       description "Suppress access-internal and/or access route addition";
       uses dhcpv6-route-suppression-type;
     }
     list interface {
       key name;
       description "One or more interfaces";
       leaf name {
         description "Interface name";
         type union {
           type jt:interface-name;
           type string {
             pattern "<.*>|$.*";
           }
         }
       }
       uses apply-advanced;
       leaf upto {
         description "Interface up to";
         type union {
           type jt:interface-name;
           type string {
             pattern "<.*>|$.*";
           }
         }
       }
       leaf exclude {
         description "Exclude this interface range";
         type empty;
       }
       leaf trace {
         description "Enable tracing for this interface";
         junos:must "(!(\".. exclude\"))";
         junos:must-message "Cannot specify tracing with exclude";
         type empty;
       }
       container overrides {
         description "DHCP override processing";
         junos:must "(!(\".. exclude\"))";
         junos:must-message "Cannot specify overrides with exclude";
         uses dhcpv6-override-local-server-type;
       }
       container dynamic-profile {
         description "Dynamic profile to use";
         junos:must "(!(\".. exclude\"))";
         junos:must-message "Cannot specify overrides with exclude";
         uses dynamic-profile-type;
       }
       leaf service-profile {
         description "Dynamic profile to use for default service activation";
         type string {
           length "1 .. 128";
         }
       }
       leaf access-profile {
         description "Access profile to use for AAA services";
         junos:must "(\"access profile $$\")";
         junos:must-message "Matching access profile must be defined";
         junos:must "(!(\".. exclude\"))";
         junos:must-message "Cannot specify overrides with exclude";
         type string {
           length "1 .. 128";
         }
       }
       container short-cycle-protection {
         description "Short cycle lockout configuration";
         leaf lockout-min-time {
           description "Short cycle lockout time in seconds";
           type union {
             type string {
               pattern "<.*>|$.*";
             }
             type uint32 {
               range "1 .. 86400";
             }
           }
         }
         leaf lockout-max-time {
           description "Short cycle lockout time in seconds";
           type union {
             type string {
               pattern "<.*>|$.*";
             }
             type uint32 {
               range "1 .. 86400";
             }
           }
         }
       }
     }
     container lease-time-validation {
       presence "enable lease-time-validation";
       description "Configure lease time violation validation";
       uses apply-advanced;
       leaf lease-time-threshold {
         description "Threshold for lease time violation seconds";
         units "seconds";
         type union {
           type string {
             pattern "<.*>|$.*";
           }
           type uint32 {
             range "60 .. 2147483647";
           }
         }
       }
       container violation-action {
         description "Lease time validation violation action";
         choice violation-action-choice {
           case case_1 {
             leaf strict {
               description "Reject solicit and renew";
               type empty;
             }
           }
           case case_2 {
             leaf override-lease {
               description "Override assigned lease time with threshold";
               type empty;
             }
           }
         }
       }
     }
     container remote-id-mismatch {
       description "DHCP client remote-id mismatch";
       presence "enable remote-id-mismatch";
       junos:must "(!(\".. reauthenticate\"))";
       junos:must-message "'remote-id-mismatch' statement cannot be included with 'reauthenticate'";
       uses dhcp-remote-id-mismatch-type;
     }
     container reauthenticate {
       junos:must "(!(\".. remote-id-mismatch\"))";
       junos:must-message "'reauthenticate' statement cannot be included with 'remote-id-mismatch'";
       junos:must "((\".. authentication\" || \".. .. authentication\"))";
       junos:must-message "'authentication' statement must be included with 'reauthenticate'";
       description "DHCP client reauthenticate processing";
       leaf lease-renewal {
         description "Reauthenticate on each renew, rebind, DISCOVER or SOLICIT";
         type empty;
       }
       leaf remote-id-mismatch {
         description "Reauthenticate on remote-id mismatch for renew, rebind and re-negotiation";
         type empty;
       }
     }
   }
   grouping dhcpv6-override-dynamic-server-type {
     description "DHCP override processing";
     uses apply-advanced;
     leaf interface-client-limit {
       description "Limit the number of clients allowed on an interface";
       type union {
         type string {
           pattern "<.*>|$.*";
         }
         type uint32 {
           range "1 .. 500000";
         }
       }
     }
     leaf rapid-commit {
       description "Enable rapid commit processing";
       type empty;
     }
     container process-inform {
       presence "enable process-inform";
       description "Process INFORMATION request PDUs";
       uses apply-advanced;
       leaf pool {
         description "Pool name for family inet6";
         type string {
           length "1 .. 64";
         }
       }
     }
     leaf delegated-pool {
       description "Delegated pool name for inet6";
       type string {
         length "1 .. 64";
       }
     }
     leaf ia-na-pool {
       description "IA_NA pool name for inet6";
       type string {
         length "1 .. 64";
       }
     }
   }
   grouping dhcpv6-override-local-server-type {
     description "DHCP override processing";
     uses apply-advanced;
     leaf interface-client-limit {
       description "Limit the number of clients allowed on an interface";
       type union {
         type string {
           pattern "<.*>|$.*";
         }
         type uint32 {
           range "1 .. 500000";
         }
       }
     }
     leaf rapid-commit {
       description "Enable rapid commit processing";
       type empty;
     }
     container client-negotiation-match {
       description "Use secondary match criteria for SOLICIT PDU";
       choice match-with {
         case case_1 {
           leaf incoming-interface {
             description "Use incoming interface";
             type empty;
           }
         }
       }
     }
     container process-inform {
       presence "enable process-inform";
       description "Process INFORMATION request PDUs";
       uses apply-advanced;
       leaf pool {
         description "Pool name for family inet6";
         type string {
           length "1 .. 64";
         }
       }
     }
     container delay-advertise {
       description "Filter options for dhcp-server";
       presence "enable delay-advertise";
       uses dhcpv6-filter-option;
     }
     leaf delegated-pool {
       description "Delegated pool name for inet6";
       type string {
         length "1 .. 64";
       }
     }
     leaf multi-address-embedded-option-response {
       description "If the client requests multiple addresses place the options in each address";
       type empty;
     }
     leaf always-process-option-request-option {
       description "Always process option even after address allocation failure";
       type empty;
     }
     leaf delete-binding-on-renegotiation {
       description "Delete binding on renegotiation";
       type empty;
     }
     leaf top-level-status-code {
       description "A top level status code option rather than encapsulated in IA for NoAddrsAvail in Advertise PDUs";
       type empty;
     }
     leaf always-add-option-dns-server {
       description "Add option-23, DNS recursive name server in Advertise and Reply";
       type empty;
     }
     leaf asymmetric-lease-time {
       description "Use a reduced lease time for the client. In seconds";
       units "seconds";
       type union {
         type string {
           pattern "<.*>|$.*";
         }
         type uint32 {
           range "600 .. 86400";
         }
       }
     }
     leaf asymmetric-prefix-lease-time {
       description "Use a reduced prefix lease time for the client. In seconds";
       units "seconds";
       type union {
         type string {
           pattern "<.*>|$.*";
         }
         type uint32 {
           range "600 .. 86400";
         }
       }
     }
     leaf protocol-attributes {
       description "DHCPv6 attributes to use as defined under access protocol-attributes";
       type string {
         length "1 .. 64";
       }
     }
     leaf dual-stack {
       description "Dual stack group to use";
       type string {
         length "1 .. 64";
       }
     }
   }
   grouping dhcpv6-filter-option {
     description "Generic DHCPv6 filter processing";
     uses apply-advanced;
     leaf delay-time {
       description "Time delay between solicit and advertise";
       default "3";
       units "seconds";
       type union {
         type string {
           pattern "<.*>|$.*";
         }
         type uint32 {
           range "1 .. 30";
         }
       }
     }
     container based-on {
       description "Option number";
       uses apply-advanced;
       container option-18 {
         presence "enable option-18";
         description "Option 18";
         uses apply-advanced;
         container equals {
           description "Generic option equals";
           uses server-v6-option-ascii-hex;
         }
         container not-equals {
           description "Generic option not equals";
           uses server-v6-option-ascii-hex;
         }
         container starts-with {
           description "Generic option starts-with";
           uses server-v6-option-ascii-hex;
         }
       }
       container option-37 {
         presence "enable option-37";
         description "Option 37";
         uses apply-advanced;
         container equals {
           description "Generic option equals";
           uses server-v6-option-ascii-hex;
         }
         container not-equals {
           description "Generic option not equals";
           uses server-v6-option-ascii-hex;
         }
         container starts-with {
           description "Generic option starts-with";
           uses server-v6-option-ascii-hex;
         }
       }
       container option-15 {
         presence "enable option-15";
         description "Option 15";
         uses apply-advanced;
         container equals {
           description "Generic option equals";
           uses server-v6-option-ascii-hex;
         }
         container not-equals {
           description "Generic option not equals";
           uses server-v6-option-ascii-hex;
         }
         container starts-with {
           description "Generic option starts-with";
           uses server-v6-option-ascii-hex;
         }
       }
       container option-16 {
         presence "enable option-16";
         description "Option 16";
         uses apply-advanced;
         container equals {
           description "Generic option equals";
           uses server-v6-option-ascii-hex;
         }
         container not-equals {
           description "Generic option not equals";
           uses server-v6-option-ascii-hex;
         }
         container starts-with {
           description "Generic option starts-with";
           uses server-v6-option-ascii-hex;
         }
       }
     }
   }
   grouping dhcpv6-reconfigure-type {
     description "DHCPv6 reconfigure processing";
     uses apply-advanced;
     leaf strict {
       description "Only allow packets containing Reconfigure Accept Option";
       type empty;
     }
     leaf clear-on-abort {
       description "Delete client on reconfiguration abort";
       type empty;
     }
     leaf attempts {
       description "Number of reconfigure attempts before aborting";
       type union {
         type string {
           pattern "<.*>|$.*";
         }
         type uint32 {
           range "1 .. 10";
         }
       }
     }
     leaf timeout {
       description "Initial timeout value for retry";
       type union {
         type string {
           pattern "<.*>|$.*";
         }
         type uint32 {
           range "1 .. 10";
         }
       }
     }
     leaf token {
       description "Reconfigure token";
       type string {
         length "1 .. 244";
       }
     }
     container trigger {
       description "DHCP reconfigure trigger";
       uses reconfigure-trigger-type;
     }
     leaf support-option-pd-exclude {
       description "Request prefix exclude option in reconfigure message";
       type empty;
     }
   }
   grouping dhcpv6-route-suppression-type {
     description "Suppress access-internal and/or access route addition";
     leaf access {
       description "Suppress access route addition";
       type empty;
     }
     leaf access-internal {
       description "Suppress access-internal route addition";
       type empty;
     }
   }
   grouping dual-stack-authentication-type {
     description "DHCP dual stack authentication";
     uses apply-advanced;
     leaf password {
       description "Username password to use";
       type string {
         length "1 .. 64";
       }
     }
     container username-include {
       description "Add username options";
       uses apply-advanced;
       leaf delimiter {
         description "Change delimiter/separator character";
         type string {
           length 1;
         }
       }
       leaf domain-name {
         description "Add domain name";
         type string {
           length "1 .. 64";
         }
       }
       leaf user-prefix {
         description "Add user defined prefix";
         type string {
           length "1 .. 64";
         }
       }
       leaf mac-address {
         description "Include MAC address";
         type empty;
       }
       container client-id {
         presence "enable client-id";
         description "Include client ID";
         leaf exclude-headers {
           description "Exclude all the headers";
           type empty;
         }
         leaf use-automatic-ascii-hex-encoding {
           description "Use automatic ascii hex username encoding";
           type empty;
         }
       }
       leaf relay-agent-remote-id {
         description "Include the relay agent remote ID";
         type empty;
       }
       leaf logical-system-name {
         description "Include logical system name";
         type empty;
       }
       leaf routing-instance-name {
         description "Include routing instance name";
         type empty;
       }
       leaf relay-agent-interface-id {
         description "Include the relay agent interface ID";
         type empty;
       }
       leaf interface-name {
         description "Include interface name";
         type empty;
       }
       leaf interface-description {
         description "Include interface description";
         type enumeration {
           enum "device" {
             description "Add the device interface description";
           }
           enum "logical" {
             description "Add the logical interface description";
           }
         }
       }
       leaf circuit-type {
         description "Include circuit type";
         type empty;
       }
       leaf vlan-tags {
         description "Include the vlan tag(s)";
         type empty;
       }
     }
   }
   grouping duid-type {
     uses apply-advanced;
     leaf duid_ll {
       description "Link Layer Address based DUID ";
       type empty;
     }
   }
   grouping dynamic-profile-type {
     description "Dynamic profile to use";
     uses apply-advanced;
     leaf dynamic-profile {
       description "Dynamic profile to use";
       junos:must "(\"dynamic-profiles $$\")";
       junos:must-message "Dynamic profile must be defined";
       type string {
         length "1 .. 80";
       }
     }
     choice dynamic-profile-type-choice {
       case case_1 {
         leaf use-primary {
           description "Dynamic profile to use on the primary interface";
           junos:must "(\"dynamic-profiles $$\")";
           junos:must-message "Dynamic profile must be defined";
           type string {
             length "1 .. 80";
           }
         }
       }
       case case_2 {
         container aggregate-clients {
           presence "enable aggregate-clients";
           description "Aggregate client profiles";
           uses apply-advanced;
           choice aggregate-type {
             case case_1 {
               leaf merge {
                 description "Merge the client dynamic profiles";
                 type empty;
               }
             }
             case case_2 {
               leaf replace {
                 description "Replace client dynamic profiles";
                 type empty;
               }
             }
           }
         }
       }
     }
   }
   grouping jdhcp-dual-stack-protocol-mstr-type {
     description "Select family as protocol master";
     choice addr-fam {
       case case_1 {
         leaf inet {
           description "INET family has protocol master behavior";
           type empty;
         }
       }
       case case_2 {
         leaf inet6 {
           description "INET6 family has protocol master behavior";
           type empty;
         }
       }
     }
   }
   grouping jdhcp-duplicate-clients-in-subnet-type {
     description "Allow duplicate clients in a subnet";
     choice distinguish-with {
       case case_1 {
         leaf incoming-interface {
           description "Allow duplicate clients on different interfaces in a subnet";
           type empty;
         }
       }
       case case_2 {
         leaf option-82 {
           description "Allow duplicate clients using different option-82 options in a subnet";
           type empty;
         }
       }
     }
   }
   grouping jdhcp-interface-traceoptions-type {
     description "Interface trace options for DHCP";
     uses apply-advanced;
     leaf no-remote-trace {
       description "Disable remote tracing";
       junos:must "(\"system tracing\")";
       junos:must-message "'no-remote-trace' is valid only when [system tracing] is configured";
       type empty;
     }
     container file {
       description "Trace file information";
       leaf filename {
         description "Name of file in which to write trace information";
         type string {
           length "1 .. 1024";
           junos:posix-pattern "![/ %]";
           junos:pattern-message "Must not contain '/', % or a space";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     list flag {
       key name;
       ordered-by user;
       description "Interface trace categories";
       leaf name {
         type enumeration {
           enum "state" {
             description "State-transition operations";
           }
           enum "packet" {
             description "Packet-decoding operations";
           }
           enum "flow" {
             description "Flow-decoding operations";
           }
           enum "packet-option" {
             description "DHCP option-decoding operations";
           }
           enum "dhcpv6-state" {
             description "State-transition operations for dhcpv6";
           }
           enum "dhcpv6-packet" {
             description "Packet-decoding operations for dhcpv6";
           }
           enum "dhcpv6-packet-option" {
             description "DHCP option-decoding operations for dhcpv6";
           }
           enum "all" {
             description "All operations";
           }
         }
       }
     }
   }
   grouping jdhcp-proxy-client-type {
     uses apply-advanced;
     list dhcpv4-profiles {
       key name;
       ordered-by user;
       description "DHCPv4 proxy client profile configuration";
       uses dhcpv4-profile;
     }
     list dhcpv6-profiles {
       key name;
       ordered-by user;
       description "DHCPv6 proxy client profile configuration";
       uses dhcpv6-profile;
     }
     container traceoptions {
       description "DHCP proxy-client trace options";
       uses jdhcp-traceoptions-type;
     }
   }
   grouping dhcpv4-profile {
     description "DHCPv4 proxy client configuration";
     leaf name {
       description "DHCP proxy client profile name";
       type string {
         length "1 .. 63";
       }
     }
     uses apply-advanced;
     leaf pool-name {
       description "This pool name will be sent to sever in subnet-name-suboption(3) of subnet allocation option(220). It is optional. It shall be sent only if configured.";
       type string {
         length "1 .. 63";
       }
     }
     leaf lease-time {
       description "Default least time requested in seconds. If DHCP client does not get the lease time from DHCP server, it will use this default lease time as the lease time. By default, the value of lease-time is zero";
       type union {
         type string {
           pattern "<.*>|$.*";
         }
         type uint16 {
           range "60 .. 1000";
         }
       }
     }
     leaf retransmission-attempt {
       description "Number of attempts to retransmit the DHCP client protocol message";
       default "4";
       type union {
         type string {
           pattern "<.*>|$.*";
         }
         type uint16 {
           range "0 .. 1000";
         }
       }
     }
     leaf retransmission-interval {
       description "Number of seconds between successive retransmissions of DHCP client protocols messages";
       default "4";
       type union {
         type string {
           pattern "<.*>|$.*";
         }
         type uint16 {
           range "4 .. 64";
         }
       }
     }
     leaf dead-server-retry-interval {
       description "Number of seconds before reconnecting to a server which was marked as down in previous attempts";
       default "300";
       type union {
         type string {
           pattern "<.*>|$.*";
         }
         type uint16 {
           range "300 .. 3600";
         }
       }
     }
     leaf dhcp-server-selection-algorithm {
       description "DHCP server selection algorithm to be used";
       default "round-robin";
       type enumeration {
         enum "highest-priority-server" {
           description "System will try the highest priority server first";
         }
         enum "round-robin" {
           description "System will use round-robin method to select the server";
         }
       }
     }
     leaf dead-server-successive-retry-attempt {
       description "Number of successive retry attempts before declaring an unresponsive server as dead";
       default "10";
       type union {
         type string {
           pattern "<.*>|$.*";
         }
         type uint16 {
           range "5 .. 1000";
         }
       }
     }
     leaf bind-interface {
       description "Primary IPv4 address of bind-interface is source of DHCP packets";
       junos:must "(\"interfaces $$-IFL family inet address\")";
       junos:must-message "Family inet address should be configured on this interface";
       type union {
         type jt:interface-unit;
         type string {
           pattern "<.*>|$.*";
         }
       }
     }
     list servers {
       key name;
       ordered-by user;
       description "DHCP server";
       max-elements 5;
       leaf name {
         description "DHCP server IPv4 address";
         type jt:ipv4addr;
       }
       uses apply-advanced;
       leaf priority {
         description "Server priority";
         default "3";
         type union {
           type string {
             pattern "<.*>|$.*";
           }
           type uint8 {
             range "1 .. 5";
           }
         }
       }
     }
   }
   grouping dhcpv6-profile {
     description "DHCPv6 proxy client configuration";
     leaf name {
       description "DHCP proxy client profile name";
       type string {
         length "1 .. 63";
       }
     }
     uses apply-advanced;
     leaf pool-name {
       description "This pool name will be sent to sever in subnet-name-suboption(3) of subnet allocation option(220). It is optional. It shall be sent only if configured.";
       type string {
         length "1 .. 63";
       }
     }
     leaf lease-time {
       description "Default least time requested in seconds. If DHCP client does not get the lease time from DHCP server, it will use this default lease time as the lease time. By default, the value of lease-time is zero";
       type union {
         type string {
           pattern "<.*>|$.*";
         }
         type uint16 {
           range "60 .. 1000";
         }
       }
     }
     leaf retransmission-attempt {
       description "Number of attempts to retransmit the DHCP client protocol message";
       default "4";
       type union {
         type string {
           pattern "<.*>|$.*";
         }
         type uint16 {
           range "0 .. 1000";
         }
       }
     }
     leaf retransmission-interval {
       description "Number of seconds between successive retransmissions of DHCP client protocols messages";
       default "4";
       type union {
         type string {
           pattern "<.*>|$.*";
         }
         type uint16 {
           range "4 .. 64";
         }
       }
     }
     leaf bind-interface {
       description "Source interface of DHCP control packets";
       junos:must "(\"interfaces $$-IFL family inet6 address\")";
       junos:must-message "Family inet6 address should be configured on this interface";
       type union {
         type jt:interface-unit;
         type string {
           pattern "<.*>|$.*";
         }
       }
     }
   }
   grouping jdhcp-traceoptions-type {
     description "Trace options for DHCP";
     uses apply-advanced;
     leaf no-remote-trace {
       description "Disable remote tracing";
       junos:must "(\"system tracing\")";
       junos:must-message "'no-remote-trace' is valid only when [system tracing] is configured";
       type empty;
     }
     container file {
       description "Trace file information";
       leaf filename {
         description "Name of file in which to write trace information";
         type string {
           length "1 .. 1024";
           junos:posix-pattern "![/ %]";
           junos:pattern-message "Must not contain '/', % or a space";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     list flag {
       key name;
       ordered-by user;
       description "DHCP operations to include in debugging trace";
       leaf name {
         type enumeration {
           enum "state" {
             description "State-transition operations";
           }
           enum "packet" {
             description "Packet-decoding operations";
           }
           enum "flow" {
             description "Flow-decoding operations";
           }
           enum "packet-option" {
             description "DHCP option-decoding operations";
           }
           enum "dhcpv6-state" {
             description "State-transition operations for dhcpv6";
           }
           enum "dhcpv6-packet" {
             description "Packet-decoding operations for dhcpv6";
           }
           enum "dhcpv6-packet-option" {
             description "DHCP option-decoding operations for dhcpv6";
           }
           enum "all" {
             description "All operations";
           }
           enum "database" {
             description "Database operations";
           }
           enum "persistent" {
             description "Persitent file operations";
           }
           enum "lockout-db" {
             description "Lockout database operations";
           }
           enum "interface" {
             description "Interface operations";
           }
           enum "rtsock" {
             description "Routing socket operations";
           }
           enum "flow-notify" {
             description "Flow notification operations";
           }
           enum "io" {
             description "I/O operations";
           }
           enum "ha" {
             description "High Availability-related operations";
           }
           enum "ui" {
             description "User Interface operations";
           }
           enum "general" {
             description "Miscellaneous operations";
           }
           enum "fwd" {
             description "Firewall process operations";
           }
           enum "rpd" {
             description "Routing Protocol process operations";
           }
           enum "auth" {
             description "Authentication operations";
           }
           enum "profile" {
             description "Profile operations";
           }
           enum "session-db" {
             description "Session database operations";
           }
           enum "performance" {
             description "Performance measurement operations";
           }
           enum "statistics" {
             description "Baseline statistics operations";
           }
           enum "dhcpv6-io" {
             description "I/O operations for dhcpv6";
           }
           enum "dhcpv6-rpd" {
             description "Routing Protocol process operations for dhcpv6";
           }
           enum "dhcpv6-session-db" {
             description "Session database operations for dhcpv6";
           }
           enum "dhcpv6-general" {
             description "Miscellaneous operations for dhcpv6";
           }
           enum "liveness-detection" {
             description "Liveness detection operations";
           }
           enum "security-persistence" {
             description "Liveness detection operations";
           }
           enum "mclag" {
             description "Multichassis LAG";
           }
           enum "ra-guard" {
             description "DHCP RA guard option for dhcpv6";
           }
           enum "era" {
             description "DHCP ERA logging option dhcp";
           }
         }
       }
     }
   }
   grouping jsscd-static-subscribers-type {
     uses apply-advanced;
     container access-profile {
       description "Access profile reference";
       uses jsscd-access-profile-type;
     }
     container dynamic-profile {
       description "Dynamic profile reference";
       uses jsscd-dynamic-profile-type;
     }
     container service-profile {
       description "Dynamic profile to use for default service activation";
       uses jsscd-service-profile-type;
     }
     container authentication {
       description "Static Subscriber Client authentication";
       uses jsscd-authentication-type;
     }
     list group {
       key name;
       ordered-by user;
       description "Static Subscriber Client group configuration";
       uses jsscd-group-type;
     }
     leaf auto-login {
       description "Auto login the operator logged-out static subscribers";
       type empty;
     }
     leaf baseline-stats {
       description "Baseline the statistics for static subscribers";
       type empty;
     }
     list interface {
       key name;
       description "One or more interfaces";
       leaf name {
         description "Interface name";
         junos:must "((\".. subscriber-ip-address\" || \".. subscriber-ipv6-address\"))";
         junos:must-message "subscriber ip or ipv6 address must be configured";
         type union {
           type jt:interface-unit;
           type string {
             pattern "<.*>|$.*";
           }
         }
       }
       uses apply-advanced;
       container subscriber-ip-address {
         description "Assigned IP address to report externally";
         uses apply-advanced;
         leaf address {
           description "IPv4 address";
           type jt:ipv4addr;
         }
       }
       container subscriber-ipv6-address {
         description "Assigned IPv6 address to report externally";
         uses apply-advanced;
         leaf address {
           description "IPv6 Address or Prefix";
           type jt:ipv6prefix;
         }
       }
     }
   }
   grouping jsscd-access-profile-type {
     description "Access profile for static subscribers";
     uses apply-advanced;
     leaf access-profile-name {
       description "Profile name";
       junos:must "(\"access profile $$\")";
       junos:must-message "referenced access profile must be defined";
       type string;
     }
   }
   grouping jsscd-authentication-type {
     description "Static Subscriber Client authentication";
     uses apply-advanced;
     leaf password {
       description "Username password to use";
       type jt:unreadable;
     }
     container username-include {
       description "Add username options";
       uses apply-advanced;
       leaf delimiter {
         description "Change delimiter/separator character";
         type string {
           length 1;
         }
       }
       leaf domain-name {
         description "Add domain name";
         type string {
           length "1 .. 64";
         }
       }
       leaf user-prefix {
         description "Add user defined prefix";
         type string {
           length "1 .. 64";
         }
       }
       leaf interface {
         description "Include interface name";
         type empty;
       }
       leaf logical-system-name {
         description "Include logical system name";
         type empty;
       }
       leaf routing-instance-name {
         description "Include routing instance name";
         type empty;
       }
       leaf vlan-tags {
         description "Include vlan tag(s)";
         type empty;
       }
     }
   }
   grouping jsscd-dynamic-profile-type {
     description "Dynamic profile to use";
     uses apply-advanced;
     leaf dynamic-profile-name {
       description "Dynamic profile to use";
       junos:must "(\"dynamic-profiles $$\")";
       junos:must-message "Dynamic profile must be defined";
       type string {
         length "1 .. 80";
       }
     }
     container aggregate-clients {
       presence "enable aggregate-clients";
       description "Aggregate client profiles";
       uses apply-advanced;
       choice aggregate-type {
         case case_1 {
           leaf merge {
             description "Merge the client dynamic profiles";
             type empty;
           }
         }
         case case_2 {
           leaf replace {
             description "Replace client dynamic profiles";
             type empty;
           }
         }
       }
     }
   }
   grouping jsscd-group-type {
     leaf name {
       description "Group name";
       type string {
         length "1 .. 64";
         junos:posix-pattern "^[A-Za-z0-9][_0-9A-Za-z-]*$";
         junos:pattern-message "Must be a non-reserved string of 64 characters or less";
       }
     }
     uses apply-advanced;
     container service-profile {
       description "Dynamic profile to use for default service activation";
       uses jsscd-service-profile-type;
     }
     container access-profile {
       description "Access profile reference";
       uses jsscd-access-profile-type;
     }
     container dynamic-profile {
       description "Dynamic profile reference";
       uses jsscd-dynamic-profile-type;
     }
     container authentication {
       description "Static Subscriber Client authentication";
       uses jsscd-authentication-type;
     }
     list interface {
       key name;
       description "One or more interfaces";
       leaf name {
         description "Interface name";
         type union {
           type jt:interface-unit;
           type string {
             pattern "<.*>|$.*";
           }
         }
       }
       leaf upto {
         description "Interface up to";
         type union {
           type jt:interface-unit;
           type string {
             pattern "<.*>|$.*";
           }
         }
       }
       leaf exclude {
         description "Exclude this interface range";
         type empty;
       }
     }
     leaf auto-login {
       description "Auto login the operator logged-out static subscribers";
       type empty;
     }
   }
   grouping jsscd-service-profile-type {
     description "Service profile for static subscribers";
     uses apply-advanced;
     leaf service-profile-name {
       description "Service profile name";
       junos:must "(\"dynamic-profiles $$\")";
       junos:must-message "referenced service profile must be defined";
       type string {
         length "1 .. 80";
       }
     }
   }
   grouping juniper-bridge-domains {
     description "Bridge domains";
     leaf name {
       description "Bridge domain name";
       type string {
         junos:posix-pattern "!^((__.*__)|(.{129,})|(.*[+].*))$";
         junos:pattern-message "Must be a non-reserved string of 128 characters or less";
       }
     }
     uses apply-advanced;
     leaf description {
       description "Text description of bridge domain";
       type string {
         junos:posix-pattern "^.{1,255}$";
         junos:pattern-message "Must be a string of 255 characters or less";
       }
     }
     leaf domain-type {
       description "Type of bridge domain";
       type enumeration {
         enum "bridge" {
           description "Forwarding instance";
         }
       }
     }
     choice vlan_choice {
       case case_1 {
         leaf vlan-id {
           description "IEEE 802.1q VLAN identifier for bridging domain";
           type string;
         }
       }
       case case_2 {
         container vlan-tags {
           presence "enable vlan-tags";
           description "IEEE 802.1q VLAN tags for bridging domain";
           leaf outer {
             description "[tpid.]vlan-id, tpid format is 0xNNNN and is optional";
             type string {
               junos:posix-pattern "^(0[Xx][0-9A-Fa-f]{4}.([0-9]{1,3}|1[0-9]{3}|2[0-9]{3}|3[0-9]{3}|40[0-8][0-9]|409[0-4]))$|^([0-9]{1,3}|1[0-9]{3}|2[0-9]{3}|3[0-9]{3}|40[0-8][0-9]|409[0-4])$";
               junos:pattern-message "vlan-id in vlan-tag (0xNNNN.vlan-id) must be 0 to 4094";
             }
           }
           leaf inner {
             description "[tpid.]vlan-id, tpid format is 0xNNNN and is optional";
             type string {
               junos:posix-pattern "^(0[Xx][0-9A-Fa-f]{4}.([0-9]{1,3}|1[0-9]{3}|2[0-9]{3}|3[0-9]{3}|40[0-8][0-9]|409[0-4]))$|^([0-9]{1,3}|1[0-9]{3}|2[0-9]{3}|3[0-9]{3}|40[0-8][0-9]|409[0-4])$";
               junos:pattern-message "vlan-id in vlan-tag (0xNNNN.vlan-id) must be 0 to 4094";
             }
           }
         }
       }
       case case_3 {
         leaf-list vlan-id-list {
           description "Create bridge-domain for each of the vlan-id specified in the vlan-id-list";
           junos:must "(!(\" .. .. .. pbb-options\"))";
           junos:must-message "vlan-id-list is not supported for i-comp routing-instance";
           junos:must "((!(\".. isolated-vlan\") && !(\".. community-vlans\")))";
           junos:must-message "PVLAN related configuration cannot be specified with vlan-id-list";
           junos:must "(!(\" .. vxlan\"))";
           junos:must-message "vxlan can not be specified under vlan-id-list";
           junos:must "(!(\" .. multicast-snooping-options\"))";
           junos:must-message "multicast-snooping-options can not be specified under vlan-id-list";
           junos:must "(!(\" .. protocols\"))";
           junos:must-message "protocols can not be specified under vlan-id-list";
           junos:must "(!(\" .. no-local-switching\"))";
           junos:must-message "no-local-switching can not be specified under vlan-id-list";
           junos:must "(!(\" .. domain-type\"))";
           junos:must-message "domain-type can not be specified  under vlan-id-list";
           junos:must "(!(\".. interface\"))";
           junos:must-message "interface can not be specified under vlan-id-list";
           junos:must "(!(any \".. bridge-options interface <*> static-mac\"))";
           junos:must-message "static mac can not be specified under vlan-id-list";
           type jt:vlan-range;
         }
       }
     }
     leaf-list isid-list {
       ordered-by user;
       description "Create bridge-domain for isid (Valid isid:256..16777214)";
       junos:must "(\".. vlan-id\")";
       junos:must-message "isid-list can be configured only under container with 'vlan-id'";
       junos:must "(!(\" .. .. .. pbb-options\"))";
       junos:must-message "isid-list and pbb-options can not co-exist for same routing-instance";
       junos:must "(!(\" .. vxlan\"))";
       junos:must-message "vxlan can not be specified under isid-list";
       junos:must "(!(\".. vlan-id inner-all\"))";
       junos:must-message "vlan-id inner-all can not be specified with isid-list";
       junos:must "(!(\" .. vlan-id none\"))";
       junos:must-message "vlan-id none  can not be specified with isid-list";
       junos:must "(!(\" .. vlan-id all\"))";
       junos:must-message "vlan-id all  can not be specified with isid-list";
       type string;
     }
     leaf vlan-id-scope-local {
       description "Enable the scope of vlan-id local to avoid transmitting vlan tagged packets";
       junos:must "(\".. .. .. protocols evpn\")";
       junos:must-message "scope-local can be configured only when routing-instance protocol type is evpn";
       junos:must "(\".. isid-list\")";
       junos:must-message "scope-local can be configured only when bridge-domain has isid-list configured";
       junos:must "(\".. vlan-id\")";
       junos:must-message "scope-local can be configured only under container with 'vlan-id'";
       type empty;
     }
     leaf service-id {
       description "Service id required if bridge-domain is of type MC-AE and vlan-id all or vlan-id none or vlan-tags";
       type union {
         type string {
           pattern "<.*>|$.*";
         }
         type uint32 {
           range "1 .. 65535";
         }
       }
     }
     leaf domain-id {
       description "Domain-id for auto derived Route Target";
       junos:must "(\"routing-instances ${instance} protocols evpn\")";
       junos:must-message "domain-id is allowed for EVPN instances only";
       type union {
         type string {
           pattern "<.*>|$.*";
         }
         type uint32 {
           range "1 .. 15";
         }
       }
     }
     leaf no-local-switching {
       description "Disable local switching within CE-facing interfaces";
       type empty;
     }
     leaf mcae-mac-synchronize {
       description "Enable IRB MAC synchronization in this bridge domain";
       type empty;
     }
     leaf mcae-mac-flush {
       description "Enable MCAE MAC flush in a/s mode for a bridge domain on MCAE link up";
       type empty;
     }
     leaf no-irb-layer-2-copy {
       description "Disable transmission of layer-2 copy of packets of irb routing-interface";
       junos:must "(\".. routing-interface\")";
       junos:must-message "routing-interface must be configured to configure this feature";
       type empty;
     }
     leaf enable-mac-move-action {
       description "Enable blocking action due to mac-move in this Bridge Domain";
       type empty;
     }
     list interface {
       key name;
       ordered-by user;
       description "Interface name for this bridge domain";
       leaf name {
         junos:must "(!(\"interfaces $$-IFL encapsulation ethernet\"))";
         junos:must-message "encapsulation ethernet is not allowed on l2 interface";
         junos:must "((!(\"interfaces $$-IFL etree-ac-role\") || \"routing-instances ${instance} protocols evpn evpn-etree\"))";
         junos:must-message "etree must be enabled under routing-instance";
         junos:must "((!(\"interfaces $$-IFL family\") || \"interfaces $$-IFL family bridge\"))";
         junos:must-message "only family bridge can be configured on this interface";
         junos:must "((!((\"interfaces $$-IFL vlan-id-list\" || \"interfaces $$-IFL vlan-tags inner-list\")) || !((\".. .. vlan-id\" || \".. .. vlan-tags\"))))";
         junos:must-message "interface with vlan-id-list/inner-list cannot be added to bridge-domain with a vlan-id/vlan-tags configured";
         junos:must "(!(\"irb\"))";
         junos:must-message "IRB interface is not supported as interface in bridge-domain";
         junos:must "(!(\"interfaces $$-IFL family bridge interface-mode\"))";
         junos:must-message "Interface with 'interface-mode' is not allowed in a bridge-domain";
         junos:must "(!(\".. .. .. interfaces $$\"))";
         junos:must-message "This interface is already defined at the routing-instance level";
         junos:must "(((!(\"interfaces $$-IFL vlan-id-range\") || \".. .. vlan-id all\") || (\".. .. no-normalization\" || \".. .. bridge-options no-normalization\")))";
         junos:must-message "vlan-id-range is specified for this logical interface; 'vlan-id all' should also be enabled";
         junos:must "(((\".. .. vlan-id all\" && \"interfaces $$-IFL input-vlan-map pop\") || (\".. .. vlan-id inner-all\" || (!((\".. .. vlan-id\" || \".. .. vlan-tags\")) || (!((\"interfaces $$-IFL input-vlan-map\" || \"interfaces $$-IFL output-vlan-map\")) || (\".. .. no-normalization\" || \".. .. bridge-options no-normalization\"))))))";
         junos:must-message "interface with input/output vlan-maps cannot be added to a routing-instance with a vlan-id/vlan-tags configured";
         junos:must "((!(\"interfaces $$-IFL vlan-tags inner-range\") || ((\".. .. vlan-id all\" || \".. .. vlan-id inner-all\") || (\".. .. no-normalization\" || \".. .. bridge-options no-normalization\"))))";
         junos:must-message "vlan-tags inner-range is specified for this logical interface; 'vlan-id all' or 'vlan-id inner-all' should also be enabled";
         type string;
       }
       uses apply-advanced;
       leaf protect-interface {
         description "Name of protect interface";
         junos:must "(\"interfaces $$\")";
         junos:must-message "Interface must be part of this routing instance";
         junos:must "(!(\"interfaces ${inter_name} esi\"))";
         junos:must-message "ESI can not be configured for protect interface";
         junos:must "(\"routing-instances ${instance} protocols evpn\")";
         junos:must-message "Protocol EVPN must be configured in the evpn instance";
         type union {
           type jt:interface-name;
           type string {
             pattern "<.*>|$.*";
           }
         }
       }
     }
     leaf routing-interface {
       description "Routing interface name for this bridge-domain";
       junos:must "(!((\".. .. .. protocols evpn mclag\" && !(\".. no-arp-suppression\"))))";
       junos:must-message "no-arp-suppression needs to be configured, when evpn is configured with mclag.";
       junos:must "(!((\".. mcae-mac-synchronize\" && \"interfaces $$-IFL mac\")))";
       junos:must-message "irb-ifl mac and bridge mcae-mac-synchronize cannot coexist";
       junos:must "((!(\"interfaces $$-IFL virtual-gateway-esi\") || \"routing-instances ${instance} protocols evpn encapsulation vxlan\"))";
       junos:must-message "irb-ifl with virtual-gateway-esi only for instance with encapsulation type vxlan";
       junos:must "(!(any \".. interface <ps*>\"))";
       junos:must-message "IRB cannot be added to bridge-domain with PS interface";
       junos:must "((!(\"interfaces $$-IFL family mpls\") || !((\"routing-instances ${instance} instance-type virtual-switch\" && (\"routing-instances ${instance} protocols vpls\" && \"routing-instances ${instance} route-distinguisher\")))))";
       junos:must-message "routing-interface with family mpls cannot be added to virtual-switch with protocol VPLS";
       junos:must "((!(\".. vlan-tags\") || !(\"interfaces $$-IFL family mpls\")))";
       junos:must-message "routing-interface with family mpls cannot be added to bridge-domain with 'vlan-tags'";
       junos:must "(!(\"routing-instances ${instance} service-type vlan-bundle\"))";
       junos:must-message "routing-interface not valid for vlan-bundle service type";
       junos:must "((!(\".. vlan-id all\") && !(\".. vlan-id inner-all\")))";
       junos:must-message "routing-interface cannot be configured under bridge-domain with 'vlan-id all' or 'vlan-id inner-all'";
       junos:must "((\".. vlan-id\" || \".. vlan-tags\"))";
       junos:must-message "routing-interface can be configured only under bridge-domain with 'vlan-id' or 'vlan-tags'";
       type union {
         type jt:interface-unit;
         type string {
           pattern "<.*>|$.*";
         }
       }
     }
     container forwarding-options {
       description "Forwarding options configuration";
       uses juniper-bridge-forwarding-options;
     }
     container bridge-options {
       description "Bridge domain configuration";
       uses juniper-protocols-bd;
     }
     container protocols {
       presence "enable protocols";
       uses apply-advanced;
       container igmp-snooping {
         description "IGMP snooping configuration";
         presence "enable igmp-snooping";
         uses juniper-bd-protocols-igmp-snooping;
       }
       container mld-snooping {
         description "MLD snooping configuration";
         presence "enable mld-snooping";
         uses juniper-bd-protocols-mld-snooping;
       }
     }
     container vxlan {
       junos:must "((\". ovsdb-managed\" || (\". multicast-group\" || (\". multicast-v6-group\" || (\"routing-instances ${instance} protocols evpn encapsulation vxlan\" || (\". ingress-node-replication\" || \".. .. .. switch-options ovsdb-managed\"))))))";
       junos:must-message "multicast-group or ovsdb-managed or ingress-node-replication or protocols evpn encapsulation vxlan should be enabled";
       junos:must "((\". ovsdb-managed\" || (\".. .. .. switch-options ovsdb-managed\" || (\"routing-instances ${instance} protocols evpn encapsulation vxlan\" || (\". multicast-group\" || (\". multicast-v6-group\" || (\"routing-instances ${instance} remote-vtep-list\" || (\"routing-instances ${instance} remote-vtep-v6-list\" || (\".. .. .. switch-options remote-vtep-v6-list\" || \".. .. .. switch-options remote-vtep-list\")))))))))";
       junos:must-message "One of multicast-group or ovsdb-managed or protocols evpn encapsulation vxlan or remote-vtep-list should be enabled. ingress-node-replication must be configured when remote-vtep-list is configured";
       junos:must "((!(\".. vlan-id all\") && !(\".. vlan-id inner-all\")))";
       junos:must-message "vxlan does not support bridge domain with 'vlan-id all' or 'vlan-id inner-all'";
       junos:must "((\"routing-instances ${instance} vtep-source-interface\" || \".. .. .. switch-options vtep-source-interface\"))";
       junos:must-message "vtep-source-interface is required for VXLAN configuration";
       description "VXLAN options";
       uses apply-advanced;
       leaf ovsdb-managed {
         description "Bridge-domain is managed remotely via VXLAN OVSDB Controller";
         junos:must "(!(\"routing-instances ${instance} protocols evpn encapsulation vxlan\"))";
         junos:must-message "Not valid with protocols evpn encapsulation vxlan";
         junos:must "(!((\"routing-instances ${instance} remote-vtep-list\" || (\".. .. .. .. switch-options remote-vtep-list\" || \".. multicast-group\"))))";
         junos:must-message "ovsdb-managed not valid with remote-vtep-list or multicast-group";
         type empty;
       }
       leaf vni {
         description "VXLAN identifier";
         type union {
           type string {
             pattern "<.*>|$.*";
           }
           type uint32 {
             range "0 .. 16777214";
           }
         }
       }
       leaf translation-vni {
         description "Translated VXLAN identifier";
         type union {
           type string {
             pattern "<.*>|$.*";
           }
           type uint32 {
             range "1 .. 16777214";
           }
         }
       }
       leaf multicast-group {
         description "Multicast group registered for VXLAN segment";
         junos:must "(!(\"routing-instances ${instance} protocols evpn encapsulation vxlan\"))";
         junos:must-message "Not valid with protocols evpn encapsulation vxlan";
         junos:must "(!((\"routing-instances ${instance} remote-vtep-list\" || (\".. .. .. .. switch-options remote-vtep-list\" || (\".. ovsdb-managed\" || (\".. .. .. .. switch-options ovsdb-managed\" || (\"routing-instances ${instance} switch-options ovsdb-managed\" || \".. multicast-v6-group\")))))))";
         junos:must-message "multicast-group not valid with remote-vtep-list or ovsdb-managed";
         type jt:ipv4addr;
       }
       leaf encapsulate-inner-vlan {
         description "Retain inner VLAN in the packet";
         junos:must "(!(\".. .. vlan-id none\"))";
         junos:must-message "encapsulate inner vlan not valid with vlan-id none";
         type empty;
       }
       leaf decapsulate-accept-inner-vlan {
         description "Accept VXLAN packets with inner VLAN";
         junos:must "(!(\".. .. vlan-id none\"))";
         junos:must-message "accept inner vlan not valid with vlan-id none";
         type empty;
       }
       leaf unreachable-vtep-aging-timer {
         description "Unreachable VXLAN tunnel endpoint removal timer";
         units "seconds";
         type union {
           type string {
             pattern "<.*>|$.*";
           }
           type uint16 {
             range "300 .. 1800";
           }
         }
       }
       leaf ingress-node-replication {
         description "Enable ingress node replication";
         junos:must "(!(\".. .. .. .. protocols evpn assisted-replication\"))";
         junos:must-message "ingress-node-replication cannot be configured with assisted-replication";
         junos:must "((\".. ovsdb-managed\" || (\".. .. .. .. switch-options ovsdb-managed\" || (\"routing-instances ${instance} protocols evpn encapsulation vxlan\" || (\"routing-instances ${instance} remote-vtep-list\" || (\"routing-instances ${instance} remote-vtep-v6-list\" || (\".. .. .. .. switch-options remote-vtep-v6-list\" || \".. .. .. .. switch-options remote-vtep-list\")))))))";
         junos:must-message "Valid for ovsdb-managed instance or with remote-vtep-list or remote-vtep-v6-list or evpn vxlan";
         type empty;
       }
       leaf-list static-remote-vtep-list {
         description "Configure bridge domain specific static remote VXLAN tunnel endpoints";
         type jt:ipaddr;
         max-elements 1024;
       }
     }
     leaf isolated-vlan {
       description "Isolated VLAN ID for private vlan bridge domain";
       type union {
         type string {
           pattern "<.*>|$.*";
         }
         type uint32 {
           range "1 .. 4094";
         }
       }
     }
     leaf-list community-vlans {
       description "List of Community VLANs for private vlan bridge domain";
       type jt:vlan-range;
     }
     container proxy-mac {
       junos:must "((\".. .. .. instance-type virtual-switch\" || \".. .. .. instance-type mac-vrf\"))";
       junos:must-message "Applicable to instance-type evpn or mac-vrf only";
       description "Proxy MAC settings";
       uses apply-advanced;
       leaf irb {
         description "Reply with virtual-gateway MAC or IRB MAC";
         junos:must "(!(\".. .. no-arp-suppression\"))";
         junos:must-message "Proxy MAC is not supported with no-arp-suppression";
         junos:must "((\".. .. routing-interface\" && !(\".. proxy-mac-address\")))";
         junos:must-message "Proxy MAC in IRB mode should have routing-interface configured";
         type empty;
       }
       leaf proxy-mac-address {
         description "Reply with configured MAC for all requests";
         junos:must "(!(\".. .. no-arp-suppression\"))";
         junos:must-message "Proxy MAC is not supported with no-arp-suppression";
         junos:must "((!(\".. .. routing-interface\") && !(\".. irb\")))";
         junos:must-message "Proxy MAC with specified MAC should not have routing-interface configured";
         type jt:mac-unicast;
       }
     }
     container multicast-snooping-options {
       description "Multicast snooping option configuration";
       uses juniper-multicast-snooping-options;
     }
   }
   grouping juniper-bd-protocols-igmp-snooping {
     description "IGMP snooping options";
     uses apply-advanced;
     container traceoptions {
       description "Trace options for IGMP Snooping";
       uses apply-advanced;
       container file {
         description "Trace file options";
         leaf filename {
           description "Name of file in which to write trace information";
           type string {
             length "1 .. 1024";
             junos:posix-pattern "![/ %]";
             junos:pattern-message "Must not contain '/', % or a space";
           }
         }
         leaf replace {
           description "Replace trace file rather than appending to it";
           status deprecated;
           type empty;
         }
         leaf size {
           description "Maximum trace file size";
           type string;
         }
         leaf files {
           description "Maximum number of trace files";
           default "10";
           type union {
             type string {
               pattern "<.*>|$.*";
             }
             type uint32 {
               range "2 .. 1000";
             }
           }
         }
         leaf no-stamp {
           description "Do not timestamp trace file";
           status deprecated;
           type empty;
         }
         choice world-readable-choice {
           leaf world-readable {
             description "Allow any user to read the log file";
             type empty;
           }
           leaf no-world-readable {
             description "Don't allow any user to read the log file";
             type empty;
           }
         }
       }
       list flag {
         key name;
         ordered-by user;
         description "Tracing parameters";
         leaf name {
           type enumeration {
             enum "packets" {
               description "Trace all IGMP packets";
             }
             enum "query" {
               description "Trace IGMP membership query messages";
             }
             enum "report" {
               description "Trace membership report messages";
             }
             enum "leave" {
               description "Trace leave group messages (IGMPv2 only)";
             }
             enum "group" {
               description "Trace group operations";
             }
             enum "client-notification" {
               description "Trace notifications";
             }
             enum "host-notification" {
               description "Trace host notifications";
             }
             enum "route" {
               description "Trace routing information";
             }
             enum "normal" {
               description "Trace normal events";
             }
             enum "general" {
               description "Trace general events";
             }
             enum "state" {
               description "Trace state transitions";
             }
             enum "policy" {
               description "Trace policy processing";
             }
             enum "task" {
               description "Trace routing protocol task processing";
             }
             enum "timer" {
               description "Trace routing protocol timer processing";
             }
             enum "all" {
               description "Trace everything";
             }
           }
         }
         leaf send {
           description "Trace transmitted packets";
           type empty;
         }
         leaf receive {
           description "Trace received packets";
           type empty;
         }
         leaf detail {
           description "Trace detailed information";
           type empty;
         }
         leaf disable {
           description "Disable this trace flag";
           type empty;
         }
       }
     }
     leaf query-interval {
       description "When to send host query messages";
       default "125";
       units "seconds";
       type union {
         type string {
           pattern "<.*>|$.*";
         }
         type uint32 {
           range "1 .. 1024";
         }
       }
     }
     container l2-querier {
       description "Enable L2 querier mode";
       uses apply-advanced;
       leaf source-address {
         description "Source IP address to use for L2 querier";
         type jt:ipv4addr;
       }
     }
     leaf query-response-interval {
       description "How long to wait for a host query response";
       default "10";
       units "seconds";
       type string {
         junos:posix-pattern "^[0-9]{1,4}(.[0-9])?$";
         junos:pattern-message "Up to 1 digit to right of decimal point";
       }
     }
     leaf query-last-member-interval {
       description "When to send group query messages";
       default "1";
       units "seconds";
       type string {
         junos:posix-pattern "^[0-9]{1,4}(.[0-9])?$";
         junos:pattern-message "Up to 1 digit to right of decimal point";
       }
     }
     leaf robust-count {
       description "Expected packet loss on a subnet";
       default "2";
       type union {
         type string {
           pattern "<.*>|$.*";
         }
         type uint32 {
           range "2 .. 10";
         }
       }
     }
     leaf learn-pim-router {
       description "Learn PIM router interfaces from PIM hellos";
       type empty;
     }
     leaf immediate-leave {
       description "Enable immediate group leave on interfaces";
       type empty;
     }
     leaf evpn-ssm-reports-only {
       description "Accept and process only <s,g> reports of SSM groups";
       type empty;
     }
     container proxy {
       presence "enable proxy";
       description "Enable proxy mode";
       uses apply-advanced;
       leaf source-address {
         description "Source IP address to use for proxy";
         junos:must "(!(\".. .. .. .. vlan-id all\"))";
         junos:must-message "With qualified-learning source-address should be configured under Vlan options";
         type jt:ipv4addr;
       }
       leaf irb {
         description "Proxy IGMP reports to IRB";
         type empty;
       }
     }
     list interface {
       key name;
       ordered-by user;
       description "Interface options for IGMP";
       leaf name {
         description "Interface name";
         junos:must "(!(\"interfaces $$-IFL vlan-tags inner-range\"))";
         junos:must-message "interface with vlan-tags inner-range should be specified in a learning-domain only";
         junos:must "(!(\"interfaces $$-IFL vlan-id-range\"))";
         junos:must-message "interface with vlan-id-range should be specified in a learning-domain only";
         junos:must "(((\".. .. .. .. interface $$\" || \".. .. .. .. .. .. interface $$\") || (!(\".. .. .. .. .. .. .. .. routing-instances\") && (\"interfaces $$-IFL family bridge interface-mode\" && !(any \"routing-instances <*> interface $$\")))))";
         junos:must-message "interface options can be specified for the interfaces in the routing-instance";
         junos:must "(!(\".. .. .. .. vlan-id all\"))";
         junos:must-message "When 'vlan-id all' is configured, interface should be configured only under vlan";
         type union {
           type jt:interface-name;
           type string {
             pattern "<.*>|$.*";
           }
         }
       }
       uses apply-advanced;
       leaf multicast-router-interface {
         description "Enabling multicast-router-interface on the interface";
         type empty;
       }
       leaf immediate-leave {
         description "Enable immediate group leave on interfaces";
         type empty;
       }
       leaf host-only-interface {
         description "Enable interfaces to be treated as host-side interfaces";
         junos:must "(!(\".. multicast-router-interface\"))";
         junos:must-message "interface cannot be both host-only and multicast-router";
         type empty;
       }
       leaf group-limit {
         description "Maximum number of (source,group) per interface";
         type union {
           type string {
             pattern "<.*>|$.*";
           }
           type uint16 {
             range "1 .. 65535";
           }
         }
       }
       container static {
         description "Static group or source membership";
         uses apply-advanced;
         list group {
           key name;
           ordered-by user;
           description "IP multicast group address";
           leaf name {
             description "IP multicast group address";
             type jt:ipv4addr;
           }
           uses apply-advanced;
           list source {
             key name;
             ordered-by user;
             description "IP multicast source address";
             leaf name {
               description "Source address of IP multicast data";
               type jt:ipv4addr;
             }
             uses apply-advanced;
           }
         }
       }
     }
     list pseudowire-remote-address {
       key name;
       ordered-by user;
       description "Pseudowire interface options for IGMP";
       junos:must "((\" .. .. .. igmp-snooping-options snoop-pseudowires\" || \" .. .. .. .. igmp-snooping-options snoop-pseudowires\"))";
       junos:must-message "Configure pseudowire-remote-address only with snoop-pseudowires instance config";
       leaf name {
         description "Pseudowire endpoint address";
         junos:must "(!(\".. .. .. .. vlan-id all\"))";
         junos:must-message "When 'vlan-id all' is configured, pseudowire-remote-address should be configured only under vlan";
         type jt:ipv4addr;
       }
       uses apply-advanced;
       leaf multicast-router-interface {
         description "Enabling multicast-router-interface on the interface";
         type empty;
       }
       leaf immediate-leave {
         description "Enable immediate group leave on interfaces";
         type empty;
       }
     }
     list vlan {
       key name;
       ordered-by user;
       description "Vlan options";
       leaf name {
         description "VLAN name";
         type string {
           length "1 .. 64";
         }
       }
       uses apply-advanced;
       leaf query-interval {
         description "When to send host query messages";
         units "seconds";
         type union {
           type string {
             pattern "<.*>|$.*";
           }
           type uint32 {
             range "1 .. 1024";
           }
         }
       }
       leaf query-response-interval {
         description "How long to wait for a host query response";
         units "seconds";
         type string {
           junos:posix-pattern "^[0-9]{1,4}(.[0-9])?$";
           junos:pattern-message "Up to 1 digit to right of decimal point";
         }
       }
       leaf query-last-member-interval {
         description "When to send group query messages";
         units "seconds";
         type string {
           junos:posix-pattern "^[0-9]{1,4}(.[0-9])?$";
           junos:pattern-message "Up to 1 digit to right of decimal point";
         }
       }
       leaf robust-count {
         description "Expected packet loss on a subnet";
         type union {
           type string {
             pattern "<.*>|$.*";
           }
           type uint32 {
             range "2 .. 10";
           }
         }
       }
       leaf immediate-leave {
         description "Enable immediate group leave on interfaces";
         type empty;
       }
       container proxy {
         presence "enable proxy";
         description "Enable proxy mode";
         uses apply-advanced;
         leaf source-address {
           description "Source IP address to use for proxy";
           junos:must "((!(\".. .. .. .. .. vlans ${vlan} vlan-id all\") && !(\".. .. .. .. .. vlans ${vlan} vlan-id inner-all\")))";
           junos:must-message "With qualified-learning source-address should be configured under Vlan options";
           type jt:ipv4addr;
         }
       }
       leaf evpn-ssm-reports-only {
         description "Accept and process only <s,g> reports of SSM groups";
         type empty;
       }
       list interface {
         key name;
         ordered-by user;
         description "Interface options for IGMP";
         leaf name {
           description "Interface name";
           junos:must "(!(\"interfaces $$-IFL vlan-tags inner-range\"))";
           junos:must-message "interface with vlan-tags inner-range should be specified in a learning-domain only";
           junos:must "(!(\"interfaces $$-IFL vlan-id-range\"))";
           junos:must-message "interface with vlan-id-range should be specified in a learning-domain only";
           junos:must "((!(\".. .. .. .. .. vlans ${vlan} vlan-id all\") && !(\".. .. .. .. .. vlans ${vlan} vlan-id inner-all\")))";
           junos:must-message "When 'vlan-id all' or 'vlan-id inner-all' is configured, interface should be configured only under vlan";
           type union {
             type jt:interface-name;
             type string {
               pattern "<.*>|$.*";
             }
           }
         }
         uses apply-advanced;
         leaf multicast-router-interface {
           description "Enabling multicast-router-interface on the interface";
           type empty;
         }
         leaf immediate-leave {
           description "Enable immediate group leave on interfaces";
           type empty;
         }
         leaf host-only-interface {
           description "Enable interfaces to be treated as host-side interfaces";
           junos:must "(!(\".. multicast-router-interface\"))";
           junos:must-message "interface cannot be both host-only and multicast-router";
           type empty;
         }
         leaf group-limit {
           description "Maximum number of (source,group) per interface";
           type union {
             type string {
               pattern "<.*>|$.*";
             }
             type uint16 {
               range "1 .. 65535";
             }
           }
         }
         container static {
           description "Static group or source membership";
           uses apply-advanced;
           list group {
             key name;
             ordered-by user;
             description "IP multicast group address";
             leaf name {
               description "IP multicast group address";
               type jt:ipv4addr;
             }
             uses apply-advanced;
             list source {
               key name;
               ordered-by user;
               description "IP multicast source address";
               leaf name {
                 description "Source address of IP multicast data";
                 type jt:ipv4addr;
               }
               uses apply-advanced;
             }
           }
         }
       }
       list pseudowire-remote-address {
         key name;
         ordered-by user;
         description "Pseudowire interface options for IGMP";
         junos:must "((\" .. .. .. igmp-snooping-options snoop-pseudowires\" || \" .. .. .. .. igmp-snooping-options snoop-pseudowires\"))";
         junos:must-message "Configure pseudowire-remote-address only with snoop-pseudowires instance config";
         leaf name {
           description "Pseudowire endpoint address";
           type jt:ipv4addr;
         }
         uses apply-advanced;
         leaf multicast-router-interface {
           description "Enabling multicast-router-interface on the interface";
           type empty;
         }
         leaf immediate-leave {
           description "Enable immediate group leave on interfaces";
           type empty;
         }
       }
       list qualified-vlan {
         key name;
         ordered-by user;
         description "VLAN options for qualified-learning";
         leaf name {
           description "VLAN ID of the learning-domain";
           junos:must "(\".. .. .. .. .. vlans ${vlan} vlan-id all\")";
           junos:must-message "vlan specific configuration is allowed with qualified-learning only";
           type union {
             type string {
               pattern "<.*>|$.*";
             }
             type uint32 {
               range "0 .. 1023";
             }
           }
         }
         uses apply-advanced;
         leaf query-interval {
           description "When to send host query messages";
           units "seconds";
           type union {
             type string {
               pattern "<.*>|$.*";
             }
             type uint32 {
               range "1 .. 1024";
             }
           }
         }
         leaf query-response-interval {
           description "How long to wait for a host query response";
           units "seconds";
           type string {
             junos:posix-pattern "^[0-9]{1,4}(.[0-9])?$";
             junos:pattern-message "Up to 1 digit to right of decimal point";
           }
         }
         leaf query-last-member-interval {
           description "When to send group query messages";
           units "seconds";
           type string {
             junos:posix-pattern "^[0-9]{1,4}(.[0-9])?$";
             junos:pattern-message "Up to 1 digit to right of decimal point";
           }
         }
         leaf robust-count {
           description "Expected packet loss on a subnet";
           type union {
             type string {
               pattern "<.*>|$.*";
             }
             type uint32 {
               range "2 .. 10";
             }
           }
         }
         leaf immediate-leave {
           description "Enable immediate group leave on interfaces";
           type empty;
         }
         container proxy {
           presence "enable proxy";
           description "Enable proxy mode";
           uses apply-advanced;
           leaf source-address {
             description "Source IP address to use for proxy";
             type jt:ipv4addr;
           }
         }
         leaf evpn-ssm-reports-only {
           description "Accept and process only <s,g> reports of SSM groups";
           type empty;
         }
         list interface {
           key name;
           ordered-by user;
           description "Interface options for IGMP";
           leaf name {
             description "Interface name";
             junos:must "(\".. .. .. .. .. .. vlans ${vlan} interface $$\")";
             junos:must-message "interface options can be specified for the interfaces in the routing-instance";
             type union {
               type jt:interface-name;
               type string {
                 pattern "<.*>|$.*";
               }
             }
           }
           uses apply-advanced;
           leaf multicast-router-interface {
             description "Enabling multicast-router-interface on the interface";
             type empty;
           }
           leaf immediate-leave {
             description "Enable immediate group leave on interfaces";
             type empty;
           }
           leaf host-only-interface {
             description "Enable interfaces to be treated as host-side interfaces";
             junos:must "(!(\".. multicast-router-interface\"))";
             junos:must-message "interface cannot be both host-only and multicast-router";
             type empty;
           }
           leaf group-limit {
             description "Maximum number of (source,group) per interface";
             type union {
               type string {
                 pattern "<.*>|$.*";
               }
               type uint16 {
                 range "1 .. 65535";
               }
             }
           }
           container static {
             description "Static group or source membership";
             uses apply-advanced;
             list group {
               key name;
               ordered-by user;
               description "IP multicast group address";
               leaf name {
                 description "IP multicast group address";
                 type jt:ipv4addr;
               }
               uses apply-advanced;
               list source {
                 key name;
                 ordered-by user;
                 description "IP multicast source address";
                 leaf name {
                   description "Source address of IP multicast data";
                   type jt:ipv4addr;
                 }
                 uses apply-advanced;
               }
             }
           }
         }
         list pseudowire-remote-address {
           key name;
           ordered-by user;
           description "Pseudowire interface options for IGMP";
           junos:must "((\" .. .. .. igmp-snooping-options snoop-pseudowires\" || \" .. .. .. .. igmp-snooping-options snoop-pseudowires\"))";
           junos:must-message "Configure pseudowire-remote-address only with snoop-pseudowires instance config";
           leaf name {
             description "Pseudowire endpoint address";
             type jt:ipv4addr;
           }
           uses apply-advanced;
           leaf multicast-router-interface {
             description "Enabling multicast-router-interface on the interface";
             type empty;
           }
           leaf immediate-leave {
             description "Enable immediate group leave on interfaces";
             type empty;
           }
         }
       }
     }
   }
   grouping juniper-bd-protocols-mld-snooping {
     description "MLD snooping options";
     uses apply-advanced;
     container traceoptions {
       description "Trace options for MLD Snooping";
       uses apply-advanced;
       container file {
         description "Trace file options";
         leaf filename {
           description "Name of file in which to write trace information";
           type string {
             length "1 .. 1024";
             junos:posix-pattern "![/ %]";
             junos:pattern-message "Must not contain '/', % or a space";
           }
         }
         leaf replace {
           description "Replace trace file rather than appending to it";
           status deprecated;
           type empty;
         }
         leaf size {
           description "Maximum trace file size";
           type string;
         }
         leaf files {
           description "Maximum number of trace files";
           default "10";
           type union {
             type string {
               pattern "<.*>|$.*";
             }
             type uint32 {
               range "2 .. 1000";
             }
           }
         }
         leaf no-stamp {
           description "Do not timestamp trace file";
           status deprecated;
           type empty;
         }
         choice world-readable-choice {
           leaf world-readable {
             description "Allow any user to read the log file";
             type empty;
           }
           leaf no-world-readable {
             description "Don't allow any user to read the log file";
             type empty;
           }
         }
       }
       list flag {
         key name;
         ordered-by user;
         description "Tracing parameters";
         leaf name {
           type enumeration {
             enum "packets" {
               description "Trace all MLD packets";
             }
             enum "query" {
               description "Trace MLD membership query messages";
             }
             enum "report" {
               description "Trace membership report messages";
             }
             enum "leave" {
               description "Trace leave group messages (MLDv2 only)";
             }
             enum "group" {
               description "Trace group operations";
             }
             enum "client-notification" {
               description "Trace notifications";
             }
             enum "host-notification" {
               description "Trace host notifications";
             }
             enum "route" {
               description "Trace routing information";
             }
             enum "normal" {
               description "Trace normal events";
             }
             enum "general" {
               description "Trace general events";
             }
             enum "state" {
               description "Trace state transitions";
             }
             enum "policy" {
               description "Trace policy processing";
             }
             enum "task" {
               description "Trace routing protocol task processing";
             }
             enum "timer" {
               description "Trace routing protocol timer processing";
             }
             enum "all" {
               description "Trace everything";
             }
           }
         }
         leaf send {
           description "Trace transmitted packets";
           type empty;
         }
         leaf receive {
           description "Trace received packets";
           type empty;
         }
         leaf detail {
           description "Trace detailed information";
           type empty;
         }
         leaf disable {
           description "Disable this trace flag";
           type empty;
         }
       }
     }
     leaf query-interval {
       description "When to send host query messages";
       default "125";
       units "seconds";
       type union {
         type string {
           pattern "<.*>|$.*";
         }
         type uint32 {
           range "1 .. 1024";
         }
       }
     }
     container l2-querier {
       description "Enable L2 querier mode";
       uses apply-advanced;
       leaf source-address {
         description "Source IP address to use for L2 querier";
         type jt:ipv6addr;
       }
     }
     leaf query-response-interval {
       description "How long to wait for a host query response";
       default "10";
       units "seconds";
       type string {
         junos:posix-pattern "^[0-9]{1,4}(.[0-9])?$";
         junos:pattern-message "Up to 1 digit to right of decimal point";
       }
     }
     leaf query-last-member-interval {
       description "When to send group query messages";
       default "1";
       units "seconds";
       type string {
         junos:posix-pattern "^[0-9]{1,4}(.[0-9])?$";
         junos:pattern-message "Up to 1 digit to right of decimal point";
       }
     }
     leaf robust-count {
       description "Expected packet loss on a subnet";
       default "2";
       type union {
         type string {
           pattern "<.*>|$.*";
         }
         type uint32 {
           range "2 .. 10";
         }
       }
     }
     leaf immediate-leave {
       description "Enable immediate group leave on interfaces";
       type empty;
     }
     leaf evpn-ssm-reports-only {
       description "Accept and process only <s,g> reports of SSM groups";
       type empty;
     }
     container proxy {
       presence "enable proxy";
       description "Enable proxy mode";
       uses apply-advanced;
       leaf source-address {
         description "Source IP address to use for proxy";
         junos:must "(!(\".. .. .. .. vlan-id all\"))";
         junos:must-message "With qualified-learning source-address should be configured under Vlan options";
         type jt:ipv6addr;
       }
       leaf irb {
         description "Proxy IGMP reports to IRB";
         type empty;
       }
     }
     list interface {
       key name;
       ordered-by user;
       description "Interface options for MLD";
       leaf name {
         description "Interface name";
         junos:must "(!(\"interfaces $$-IFL vlan-tags inner-range\"))";
         junos:must-message "interface with vlan-tags inner-range should be specified in a learning-domain only";
         junos:must "(!(\"interfaces $$-IFL vlan-id-range\"))";
         junos:must-message "interface with vlan-id-range should be specified in a learning-domain only";
         junos:must "(((\".. .. .. .. interface $$\" || \".. .. .. .. .. .. interface $$\") || (!(\".. .. .. .. .. .. .. .. routing-instances\") && (\"interfaces $$-IFL family bridge interface-mode\" && !(any \"routing-instances <*> interface $$\")))))";
         junos:must-message "interface options can be specified for the interfaces in the routing-instance";
         junos:must "(!(\".. .. .. .. vlan-id all\"))";
         junos:must-message "When 'vlan-id all' is configured, interface should be configured only under vlan";
         type union {
           type jt:interface-name;
           type string {
             pattern "<.*>|$.*";
           }
         }
       }
       uses apply-advanced;
       leaf multicast-router-interface {
         description "Enabling multicast-router-interface on the interface";
         type empty;
       }
       leaf immediate-leave {
         description "Enable immediate group leave on interfaces";
         type empty;
       }
       leaf host-only-interface {
         description "Enable interfaces to be treated as host-side interfaces";
         junos:must "(!(\".. multicast-router-interface\"))";
         junos:must-message "interface cannot be both host-only and multicast-router";
         type empty;
       }
       leaf group-limit {
         description "Maximum number of (source,group) per interface";
         type union {
           type string {
             pattern "<.*>|$.*";
           }
           type uint16 {
             range "1 .. 65535";
           }
         }
       }
       container static {
         description "Static group or source membership";
         uses apply-advanced;
         list group {
           key name;
           ordered-by user;
           description "IP multicast group address";
           leaf name {
             description "IP multicast group address";
             type jt:ipv6addr;
           }
           uses apply-advanced;
           list source {
             key name;
             ordered-by user;
             description "IP multicast source address";
             leaf name {
               description "Source address of IP multicast data";
               type jt:ipv6addr;
             }
             uses apply-advanced;
           }
         }
       }
     }
     list pseudowire-remote-address {
       key name;
       ordered-by user;
       description "Pseudowire interface options for MLD";
       junos:must "((\" .. .. .. mld-snooping-options snoop-pseudowires\" || \" .. .. .. .. mld-snooping-options snoop-pseudowires\"))";
       junos:must-message "Configure pseudowire-remote-address only with snoop-pseudowires instance config";
       leaf name {
         description "Pseudowire endpoint address";
         junos:must "(!(\".. .. .. .. vlan-id all\"))";
         junos:must-message "When 'vlan-id all' is configured, pseudowire-remote-address should be configured only under vlan";
         type jt:ipv4addr;
       }
       uses apply-advanced;
       leaf multicast-router-interface {
         description "Enabling multicast-router-interface on the interface";
         type empty;
       }
       leaf immediate-leave {
         description "Enable immediate group leave on interfaces";
         type empty;
       }
     }
     list vlan {
       key name;
       ordered-by user;
       description "Vlan options";
       leaf name {
         description "Vlan of the bridge-domain";
         type string {
           length "1 .. 64";
         }
       }
       uses apply-advanced;
       leaf query-interval {
         description "When to send host query messages";
         units "seconds";
         type union {
           type string {
             pattern "<.*>|$.*";
           }
           type uint32 {
             range "1 .. 1024";
           }
         }
       }
       leaf query-response-interval {
         description "How long to wait for a host query response";
         units "seconds";
         type string {
           junos:posix-pattern "^[0-9]{1,4}(.[0-9])?$";
           junos:pattern-message "Up to 1 digit to right of decimal point";
         }
       }
       leaf query-last-member-interval {
         description "When to send group query messages";
         units "seconds";
         type string {
           junos:posix-pattern "^[0-9]{1,4}(.[0-9])?$";
           junos:pattern-message "Up to 1 digit to right of decimal point";
         }
       }
       leaf robust-count {
         description "Expected packet loss on a subnet";
         type union {
           type string {
             pattern "<.*>|$.*";
           }
           type uint32 {
             range "2 .. 10";
           }
         }
       }
       leaf immediate-leave {
         description "Enable immediate group leave on interfaces";
         type empty;
       }
       container proxy {
         presence "enable proxy";
         description "Enable proxy mode";
         uses apply-advanced;
         leaf source-address {
           description "Source IP address to use for proxy";
           junos:must "((!(\".. .. .. .. .. vlans ${vlan} vlan-id all\") && !(\".. .. .. .. .. vlans ${vlan} vlan-id inner-all\")))";
           junos:must-message "With qualified-learning source-address should be configured under Vlan options";
           type jt:ipv6addr;
         }
       }
       leaf evpn-ssm-reports-only {
         description "Accept and process only <s,g> reports of SSM groups";
         type empty;
       }
       list interface {
         key name;
         ordered-by user;
         description "Interface options for MLD";
         leaf name {
           description "Interface name";
           junos:must "(!(\"interfaces $$-IFL vlan-tags inner-range\"))";
           junos:must-message "interface with vlan-tags inner-range should be specified in a learning-domain only";
           junos:must "(!(\"interfaces $$-IFL vlan-id-range\"))";
           junos:must-message "interface with vlan-id-range should be specified in a learning-domain only";
           junos:must "((!(\".. .. .. .. .. vlans ${vlan} vlan-id all\") && !(\".. .. .. .. .. vlans ${vlan} vlan-id inner-all\")))";
           junos:must-message "When 'vlan-id all' or 'vlan-id inner-all' is configured, interface should be configured only under vlan";
           type union {
             type jt:interface-name;
             type string {
               pattern "<.*>|$.*";
             }
           }
         }
         uses apply-advanced;
         leaf multicast-router-interface {
           description "Enabling multicast-router-interface on the interface";
           type empty;
         }
         leaf immediate-leave {
           description "Enable immediate group leave on interfaces";
           type empty;
         }
         leaf host-only-interface {
           description "Enable interfaces to be treated as host-side interfaces";
           junos:must "(!(\".. multicast-router-interface\"))";
           junos:must-message "interface cannot be both host-only and multicast-router";
           type empty;
         }
         leaf group-limit {
           description "Maximum number of (source,group) per interface";
           type union {
             type string {
               pattern "<.*>|$.*";
             }
             type uint16 {
               range "1 .. 65535";
             }
           }
         }
         container static {
           description "Static group or source membership";
           uses apply-advanced;
           list group {
             key name;
             ordered-by user;
             description "IP multicast group address";
             leaf name {
               description "IP multicast group address";
               type jt:ipv6addr;
             }
             uses apply-advanced;
             list source {
               key name;
               ordered-by user;
               description "IP multicast source address";
               leaf name {
                 description "Source address of IP multicast data";
                 type jt:ipv6addr;
               }
               uses apply-advanced;
             }
           }
         }
       }
       list pseudowire-remote-address {
         key name;
         ordered-by user;
         description "Pseudowire interface options for MLD";
         junos:must "((\" .. .. .. mld-snooping-options snoop-pseudowires\" || \" .. .. .. .. mld-snooping-options snoop-pseudowires\"))";
         junos:must-message "Configure pseudowire-remote-address only with snoop-pseudowires instance config";
         leaf name {
           description "Pseudowire endpoint address";
           type jt:ipv4addr;
         }
         uses apply-advanced;
         leaf multicast-router-interface {
           description "Enabling multicast-router-interface on the interface";
           type empty;
         }
         leaf immediate-leave {
           description "Enable immediate group leave on interfaces";
           type empty;
         }
       }
       list qualified-vlan {
         key name;
         ordered-by user;
         description "VLAN options for qualified-learning";
         leaf name {
           description "VLAN ID of the learning-domain";
           junos:must "(\".. .. .. .. .. vlans ${vlan} vlan-id all\")";
           junos:must-message "vlan specific configuration is allowed with qualified-learning only";
           type union {
             type string {
               pattern "<.*>|$.*";
             }
             type uint32 {
               range "0 .. 1023";
             }
           }
         }
         uses apply-advanced;
         leaf query-interval {
           description "When to send host query messages";
           units "seconds";
           type union {
             type string {
               pattern "<.*>|$.*";
             }
             type uint32 {
               range "1 .. 1024";
             }
           }
         }
         leaf query-response-interval {
           description "How long to wait for a host query response";
           units "seconds";
           type string {
             junos:posix-pattern "^[0-9]{1,4}(.[0-9])?$";
             junos:pattern-message "Up to 1 digit to right of decimal point";
           }
         }
         leaf query-last-member-interval {
           description "When to send group query messages";
           units "seconds";
           type string {
             junos:posix-pattern "^[0-9]{1,4}(.[0-9])?$";
             junos:pattern-message "Up to 1 digit to right of decimal point";
           }
         }
         leaf robust-count {
           description "Expected packet loss on a subnet";
           type union {
             type string {
               pattern "<.*>|$.*";
             }
             type uint32 {
               range "2 .. 10";
             }
           }
         }
         leaf immediate-leave {
           description "Enable immediate group leave on interfaces";
           type empty;
         }
         container proxy {
           presence "enable proxy";
           description "Enable proxy mode";
           uses apply-advanced;
           leaf source-address {
             description "Source IP address to use for proxy";
             type jt:ipv6addr;
           }
         }
         leaf evpn-ssm-reports-only {
           description "Accept and process only <s,g> reports of SSM groups";
           type empty;
         }
         list interface {
           key name;
           ordered-by user;
           description "Interface options for MLD";
           leaf name {
             description "Interface name";
             junos:must "(\".. .. .. .. .. .. vlans ${vlan} interface $$\")";
             junos:must-message "interface options can be specified for the interfaces in the routing-instance";
             type union {
               type jt:interface-name;
               type string {
                 pattern "<.*>|$.*";
               }
             }
           }
           uses apply-advanced;
           leaf multicast-router-interface {
             description "Enabling multicast-router-interface on the interface";
             type empty;
           }
           leaf immediate-leave {
             description "Enable immediate group leave on interfaces";
             type empty;
           }
           leaf host-only-interface {
             description "Enable interfaces to be treated as host-side interfaces";
             junos:must "(!(\".. multicast-router-interface\"))";
             junos:must-message "interface cannot be both host-only and multicast-router";
             type empty;
           }
           leaf group-limit {
             description "Maximum number of (source,group) per interface";
             type union {
               type string {
                 pattern "<.*>|$.*";
               }
               type uint16 {
                 range "1 .. 65535";
               }
             }
           }
           container static {
             description "Static group or source membership";
             uses apply-advanced;
             list group {
               key name;
               ordered-by user;
               description "IP multicast group address";
               leaf name {
                 description "IP multicast group address";
                 type jt:ipv6addr;
               }
               uses apply-advanced;
               list source {
                 key name;
                 ordered-by user;
                 description "IP multicast source address";
                 leaf name {
                   description "Source address of IP multicast data";
                   type jt:ipv6addr;
                 }
                 uses apply-advanced;
               }
             }
           }
         }
         list pseudowire-remote-address {
           key name;
           ordered-by user;
           description "Pseudowire interface options for MLD";
           junos:must "((\" .. .. .. mld-snooping-options snoop-pseudowires\" || \" .. .. .. .. mld-snooping-options snoop-pseudowires\"))";
           junos:must-message "Configure pseudowire-remote-address only with snoop-pseudowires instance config";
           leaf name {
             description "Pseudowire endpoint address";
             type jt:ipv4addr;
           }
           uses apply-advanced;
           leaf multicast-router-interface {
             description "Enabling multicast-router-interface on the interface";
             type empty;
           }
           leaf immediate-leave {
             description "Enable immediate group leave on interfaces";
             type empty;
           }
         }
       }
     }
   }
   grouping juniper-bridge-forwarding-options {
     uses apply-advanced;
     container filter {
       description "Filtering for bridge forwarding table";
       uses apply-advanced;
       leaf input {
         description "Name of input filter to apply for forwarded packets";
         type string;
       }
       leaf output {
         description "Name of output filter to apply for forwarded packets";
         type string;
       }
     }
     container flood {
       description "Filtering for bridge flood table";
       uses apply-advanced;
       leaf input {
         description "Name of input filter to apply for bridge flood packets";
         type string;
       }
     }
     container dhcp-relay {
       description "Dynamic Host Configuration Protocol relay configuration";
       status deprecated;
       uses jdhcp-relay-type;
     }
     container dhcp-security {
       description "Dynamic ARP Inspection configuration";
       presence "enable dhcp-security";
       uses jdhcp-security-type;
     }
   }
   grouping jdhcp-relay-type {
     description "Dynamic Host Configuration Protocol relay configuration";
     uses apply-advanced;
     container traceoptions {
       description "DHCP relay trace options";
       status deprecated;
       junos:must "(!(\"forwarding-options helpers bootp\"))";
       junos:must-message "Incompatible with 'forwarding-options helpers bootp'";
       junos:must "(!(\"system services dhcp\"))";
       junos:must-message "Incompatible with 'set system services dhcp'";
       uses jdhcp-traceoptions-type;
     }
     container persistent-storage {
       description "Trigger to enable flat file storage";
       leaf automatic {
         description "Trigger automatically";
         type empty;
       }
     }
     leaf duplicate-clients-on-interface {
       description "Allow duplicate clients on different interfaces in a subnet";
       status deprecated;
       type empty;
     }
     container duplicate-clients-in-subnet {
       description "Allow duplicate clients in a subnet";
       junos:must "(!(\".. duplicate-clients-on-interface\"))";
       junos:must-message "Cannot specify duplicate-clients-in-subnet with duplicate-clients-on-interface";
       uses jdhcp-duplicate-clients-in-subnet-type;
     }
     container interface-traceoptions {
       description "DHCP relay interface trace options";
       status deprecated;
       uses jdhcp-interface-traceoptions-type;
     }
     container dhcpv6 {
       description "DHCPv6 configuration";
       uses dhcpv6-relay-type;
     }
     leaf arp-inspection {
       description "Enable Dynamic ARP Inspection";
       type empty;
     }
     container forward-snooped-clients {
       junos:must "((!(\".. forward-only\") && (!(\".. forward-only-replies\") && !(any \".. group <*> forward-only\"))))";
       junos:must-message "forward-only and forward-only-replies cannot be configured when forward-snooped-clients is configured";
       description "Forward snooped (unicast) packets";
       choice interface-type {
         case case_1 {
           leaf configured-interfaces {
             description "Forward snooped (unicast) packets on configured interfaces";
             type empty;
           }
         }
         case case_2 {
           leaf non-configured-interfaces {
             description "Forward snooped (unicast) packets on non-configured interfaces";
             type empty;
           }
         }
         case case_3 {
           leaf all-interfaces {
             description "Forward snooped (unicast) packets on configured and non-configured interfaces";
             type empty;
           }
         }
       }
     }
     container authentication {
       description "DHCP authentication";
       junos:must "(!(\"forwarding-options helpers bootp\"))";
       junos:must-message "'authentication' statement cannot be included along with 'forwarding-options helpers bootp' statement";
       uses authentication-type;
     }
     container liveness-detection {
       description "DHCP client liveness detection processing";
       junos:must "(!(\"forwarding-options helpers bootp\"))";
       junos:must-message "'liveness-detection' statement cannot be included along with 'forwarding-options helpers bootp' statement";
       uses dhcp-liveness-detection-type;
     }
     container dynamic-profile {
       description "Dynamic profile to use";
       junos:must "(!(\"forwarding-options helpers bootp\"))";
       junos:must-message "'dynamic-profile' statement cannot be included along with 'forwarding-options helpers bootp' statement";
       uses dynamic-profile-type;
     }
     leaf service-profile {
       description "Dynamic profile to use for default service activation";
       type string {
         length "1 .. 128";
       }
     }
     leaf access-profile {
       description "Access profile to use for AAA services";
       junos:must "(\"access profile $$\")";
       junos:must-message "Matching access profile must be defined";
       junos:must "(!(\"forwarding-options helpers bootp\"))";
       junos:must-message "'access-profile' statement cannot be included along with 'forwarding-options helpers bootp' statement";
       type string {
         length "1 .. 128";
       }
     }
     container short-cycle-protection {
       description "Short cycle lockout configuration";
       leaf lockout-min-time {
         description "Short cycle lockout time in seconds";
         type union {
           type string {
             pattern "<.*>|$.*";
           }
           type uint32 {
             range "1 .. 86400";
           }
         }
       }
       leaf lockout-max-time {
         description "Short cycle lockout time in seconds";
         type union {
           type string {
             pattern "<.*>|$.*";
           }
           type uint32 {
             range "1 .. 86400";
           }
         }
       }
     }
     container overrides {
       description "DHCP override processing";
       presence "enable overrides";
       junos:must "(!(\"forwarding-options helpers bootp\"))";
       junos:must-message "'overrides' statement cannot be included along with 'forwarding-options helpers bootp' statement";
       uses override-type;
     }
     container relay-option {
       description "DHCP option processing";
       presence "enable relay-option";
       junos:must "((!(\".. relay-option-60\") && !(any \".. group <*> relay-option-60\")))";
       junos:must-message "Cannot specify relay-option-60 with relay-option";
       uses dhcp-generic-v4-option;
     }
     container server-match {
       description "Server match processing";
       uses apply-advanced;
       container default-action {
         description "Server match default action";
         presence "enable default-action";
         uses server-match-action-choice;
       }
       list address {
         key name;
         ordered-by user;
         description "Server address";
         leaf name {
           description "Server address for matching";
           type jt:ipv4prefix;
         }
         uses apply-advanced;
         choice server-match-action-choice {
           case case_1 {
             leaf forward-only {
               description "Forward without subscriber services when a match is made";
               type empty;
             }
           }
           case case_2 {
             leaf create-relay-entry {
               description "Create relay entry and allow subscriber services";
               type empty;
             }
           }
         }
       }
     }
     container relay-option-60 {
       description "DHCP option-60 processing";
       presence "enable relay-option-60";
       status deprecated;
       junos:must "(!(\"forwarding-options helpers bootp\"))";
       junos:must-message "'relay-option-60' statement cannot be included along with 'forwarding-options helpers bootp' statement";
       junos:must "((!(\".. relay-option\") && !(any \".. group <*> relay-option\")))";
       junos:must-message "Cannot specify relay-option with relay-option-60 ";
       uses relay-option-60-type-top;
     }
     container relay-option-82 {
       description "DHCP option-82 processing";
       presence "enable relay-option-82";
       junos:must "(!(\"forwarding-options helpers bootp\"))";
       junos:must-message "'relay-option-82' statement cannot be included along with 'forwarding-options helpers bootp' statement";
       uses relay-option-82-type;
     }
     container forward-only {
       description "Forward DHCP packets without creating binding";
       presence "enable forward-only";
       junos:must "(!(\"forwarding-options helpers bootp\"))";
       junos:must-message "'forward-only' statement cannot be included along with 'forwarding-options helpers bootp' statement";
       uses forward-only-to-rc-type;
     }
     leaf description {
       description "Text description of servers";
       type string;
     }
     leaf maximum-hop-count {
       description "Maximum number of hops per packet";
       type union {
         type string {
           pattern "<.*>|$.*";
         }
         type uint32 {
           range "1 .. 16";
         }
       }
     }
     leaf minimum-wait-time {
       description "Minimum number of seconds before requests are forwarded";
       type union {
         type string {
           pattern "<.*>|$.*";
         }
         type uint32 {
           range "0 .. 30000";
         }
       }
     }
     leaf client-response-ttl {
       description "IP time-to-live value to set in responses to client";
       type union {
         type string {
           pattern "<.*>|$.*";
         }
         type uint32 {
           range "1 .. 255";
         }
       }
     }
     leaf source-ip-change {
       description "Use address of egress interface as source ip";
       type empty;
     }
     leaf forward-only-replies {
       description "Forward-only replies from server to appropriate logical-system:routing-instance based on options";
       type empty;
     }
     container server-group {
       description "Define a DHCP server group";
       junos:must "(!(\"forwarding-options helpers bootp\"))";
       junos:must-message "'server-group' statement cannot be included along with 'forwarding-options helpers bootp' statement";
       uses server-group-type;
     }
     container active-server-group {
       description "Name of DHCP server group";
       uses dhcpv4-gbl-active-sg-type;
     }
     container route-suppression {
       description "Suppress access-internal and/or destination route addition";
       junos:must "(!(\".. liveness-detection method layer2-liveness-detection\"))";
       junos:must-message "Cannot specify route-suppression with liveness-detection method layer2-liveness-detection";
       junos:must "(!(\".. overrides no-arp\"))";
       junos:must-message "Cannot specify route-suppression with overrides no-arp";
       uses dhcp-route-suppression-type;
     }
     list group {
       key name;
       ordered-by user;
       description "Define a DHCP group";
       junos:must "(!(\"forwarding-options helpers bootp\"))";
       junos:must-message "'group' statement cannot be included along with 'forwarding-options helpers bootp' statement";
       uses dhcp-group;
     }
     list dual-stack-group {
       key name;
       description "Define a DHCP dual stack group";
       uses dhcp-dual-stack-group;
     }
     leaf no-snoop {
       description "Do not snoop DHCP packets";
       junos:must "(!(\"legacy-snooping\"))";
       junos:must-message "'no-snoop' statement cannot be included along with 'legacy-snooping' statement";
       type empty;
     }
     leaf server-response-time {
       description "Number of seconds in a period of activity between the last server response and an unaswered request";
       default "0";
       type union {
         type uint32;
         type string {
           pattern "<.*>|$.*";
         }
       }
     }
     container lease-time-validation {
       presence "enable lease-time-validation";
       description "Configure lease time violation validation";
       uses apply-advanced;
       leaf lease-time-threshold {
         description "Threshold for lease time violation in seconds";
         units "seconds";
         type union {
           type string {
             pattern "<.*>|$.*";
           }
           type uint32 {
             range "60 .. 2147483647";
           }
         }
       }
       container violation-action {
         description "Lease time validation violation action";
         leaf drop {
           description "Drop dhcpv4 offer and ack packets";
           type empty;
         }
       }
     }
     container leasequery {
       description "DHCP leasequery configuration";
       presence "enable leasequery";
       junos:must "(\".. overrides always-write-option-82\")";
       junos:must-message "Must configure [overrides always-write-option-82] to overwrite circuit-id";
       junos:must "((\".. relay-option-82 circuit-id\" && (!(\".. relay-option-82 circuit-id use-interface-description\") && !(\".. relay-option-82 circuit-id require-interface-description\"))))";
       junos:must-message "Must configure [relay-option-82 circuit-id] without description to insert circuit-id";
       uses relay-leasequery-type;
     }
     container bulk-leasequery {
       description "DHCP bulk leasequery configuration";
       presence "enable bulk-leasequery";
       uses relay-bulk-leasequery-v4-type;
     }
     container active-leasequery {
       description "DHCPv4 active leasequery configuration";
       presence "enable active-leasequery";
       junos:must "(\".. bulk-leasequery\")";
       junos:must-message "Must configure bulk-leasequery";
       uses active-leasequery-v4-type;
     }
     container remote-id-mismatch {
       description "DHCP client remote-id mismatch";
       presence "enable remote-id-mismatch";
       uses dhcp-remote-id-mismatch-type;
     }
   }
   grouping dhcp-dual-stack-group {
     description "DHCP dual stack groups";
     leaf name {
       description "Dual stack group name";
       type string {
         length "1 .. 64";
         junos:posix-pattern "^[A-Za-z0-9][_0-9A-Za-z-]*$";
         junos:pattern-message "Must be a non-reserved string of 64 characters or less";
       }
     }
     uses apply-advanced;
     container authentication {
       description "DHCP authentication";
       uses dual-stack-authentication-type;
     }
     leaf service-profile {
       description "Dynamic profile to use for default service activation";
       type string {
         length "1 .. 128";
       }
     }
     leaf access-profile {
       description "Access profile to be used for jdhcpd";
       type string {
         length "1 .. 128";
       }
     }
     container dynamic-profile {
       description "Dynamic profile to use";
       uses dynamic-profile-type;
     }
     container liveness-detection {
       description "DHCP client liveness detection processing";
       uses dhcp-liveness-detection-dualstack-type;
     }
     container relay-agent-interface-id {
       description "Interface-id option processing";
       presence "enable relay-agent-interface-id";
       uses v6-relay-option-interface-id-type;
     }
     container relay-agent-remote-id {
       description "Remote-id option processing";
       presence "enable relay-agent-remote-id";
       uses v6-relay-option-remote-id-type;
     }
     container classification-key {
       description "Classification key for identifying dual stack household";
       junos:must "(\".. dynamic-profile\")";
       junos:must-message "dynamic profile configuration in dual-stack-group is must for configuring classification-type";
       uses classification-types;
     }
     leaf dual-stack-interface-client-limit {
       description "Limit the number of client allowed on an interface";
       type union {
         type string {
           pattern "<.*>|$.*";
         }
         type uint32 {
           range "1 .. 500000";
         }
       }
     }
     container protocol-master {
       description "Select family as protocol master";
       uses jdhcp-dual-stack-protocol-mstr-type;
     }
     container short-cycle-protection {
       description "Short cycle lockout configuration";
       leaf lockout-min-time {
         description "Short cycle lockout time in seconds";
         type union {
           type string {
             pattern "<.*>|$.*";
           }
           type uint32 {
             range "1 .. 86400";
           }
         }
       }
       leaf lockout-max-time {
         description "Short cycle lockout time in seconds";
         type union {
           type string {
             pattern "<.*>|$.*";
           }
           type uint32 {
             range "1 .. 86400";
           }
         }
       }
     }
   }
   grouping dhcp-generic-v4-option {
     description "Generic DHCP options processing";
     uses apply-advanced;
     leaf option-number {
       description "Option number";
       status deprecated;
       type enumeration {
         enum "60" {
           description "Option 60";
           status deprecated;
         }
         enum "77" {
           description "Option 77";
           status deprecated;
         }
       }
     }
     container equals {
       description "Generic option equals";
       status deprecated;
       uses relay-v4-option-ascii-hex;
     }
     container default-action {
       description "Generic option default action";
       status deprecated;
       uses dhcp-v4-option-default-action;
     }
     container starts-with {
       description "Generic option starts with";
       status deprecated;
       uses relay-v4-option-ascii-hex;
     }
     container option-60 {
       description "Add option 60 processing";
       presence "enable option-60";
       junos:must "(!(\"option-number\"))";
       junos:must-message "Cannot specify option-60  with option-number";
       uses dhcp-generic-v4-option-type;
     }
     container option-77 {
       description "Add option 77 processing";
       presence "enable option-77";
       junos:must "(!(\"option-number\"))";
       junos:must-message "Cannot specify option-77  with option-number";
       uses dhcp-generic-v4-option-type;
     }
     list option-order {
       key name;
       ordered-by user;
       description "Options precedence order";
       junos:must "(!(\"option-number\"))";
       junos:must-message "Cannot specify option-order  with option-number";
       leaf name {
         description "Option number";
         type enumeration {
           enum "60" {
             description "Option 60";
           }
           enum "77" {
             description "Option 77";
           }
         }
       }
       uses apply-advanced;
     }
   }
   grouping dhcp-generic-v4-option-type {
     uses apply-advanced;
     container equals {
       description "Generic option equals";
       uses relay-v4-option-ascii-hex;
     }
     container default-action {
       description "Generic option default action";
       uses dhcp-v4-option-default-action;
     }
     container starts-with {
       description "Generic option starts with";
       uses relay-v4-option-ascii-hex;
     }
   }
   grouping dhcp-group {
     description "DHCP groups";
     leaf name {
       description "Group name";
       type string {
         length "1 .. 64";
         junos:posix-pattern "^[A-Za-z0-9][_0-9A-Za-z-]*$";
         junos:pattern-message "Must be a non-reserved string of 64 characters or less";
       }
     }
     uses apply-advanced;
     container active-server-group {
       description "Name of DHCP server group";
       uses dhcpv4-gp-active-sg-type;
     }
     container authentication {
       description "DHCP authentication";
       uses authentication-type;
     }
     container liveness-detection {
       description "DHCP client liveness detection processing";
       uses dhcp-liveness-detection-type;
     }
     container dynamic-profile {
       description "Dynamic profile to use";
       uses dynamic-profile-type;
     }
     leaf service-profile {
       description "Dynamic profile to use for default service activation";
       type string {
         length "1 .. 128";
       }
     }
     leaf access-profile {
       description "Access profile to use for AAA services";
       junos:must "(\"access profile $$\")";
       junos:must-message "Matching access profile must be defined";
       type string {
         length "1 .. 128";
       }
     }
     container overrides {
       description "DHCP override processing";
       presence "enable overrides";
       uses override-type;
     }
     container short-cycle-protection {
       description "Short cycle lockout configuration";
       leaf lockout-min-time {
         description "Short cycle lockout time in seconds";
         type union {
           type string {
             pattern "<.*>|$.*";
           }
           type uint32 {
             range "1 .. 86400";
           }
         }
       }
       leaf lockout-max-time {
         description "Short cycle lockout time in seconds";
         type union {
           type string {
             pattern "<.*>|$.*";
           }
           type uint32 {
             range "1 .. 86400";
           }
         }
       }
     }
     container server-match {
       description "Server match processing";
       uses apply-advanced;
       container default-action {
         description "Server match default action";
         presence "enable default-action";
         uses server-match-action-choice;
       }
       list address {
         key name;
         ordered-by user;
         description "Server address";
         leaf name {
           description "Server address for matching";
           type jt:ipv4prefix;
         }
         uses apply-advanced;
         choice server-match-action-choice {
           case case_1 {
             leaf forward-only {
               description "Forward without subscriber services when a match is made";
               type empty;
             }
           }
           case case_2 {
             leaf create-relay-entry {
               description "Create relay entry and allow subscriber services";
               type empty;
             }
           }
         }
       }
     }
     container relay-option {
       description "DHCP option processing";
       presence "enable relay-option";
       junos:must "((!(\".. relay-option-60\") && !(\".. .. relay-option-60\")))";
       junos:must-message "Cannot specify relay-option-60 with relay-option";
       uses dhcp-generic-v4-option;
     }
     container relay-option-60 {
       description "DHCP option-60 processing";
       presence "enable relay-option-60";
       status deprecated;
       junos:must "((!(\".. relay-option\") && !(\".. .. relay-option\")))";
       junos:must-message "Cannot specify relay-option with relay-option-60";
       uses relay-option-60-type-group;
     }
     container relay-option-82 {
       description "DHCP option-82 processing";
       presence "enable relay-option-82";
       uses relay-option-82-type;
     }
     container forward-only {
       description "Forward DHCP packets without creating binding";
       presence "enable forward-only";
       uses forward-only-to-rc-type;
     }
     container route-suppression {
       description "Suppress access-internal and/or destination route addition";
       junos:must "(!(\".. liveness-detection method layer2-liveness-detection\"))";
       junos:must-message "Cannot specify route-suppression with liveness-detection method layer2-liveness-detection";
       junos:must "((!(\".. overrides no-arp\") && !(\".. .. overrides no-arp\")))";
       junos:must-message "Cannot specify route-suppression with overrides no-arp";
       uses dhcp-route-suppression-type;
     }
     leaf description {
       description "Text description of servers";
       type string;
     }
     leaf maximum-hop-count {
       description "Maximum number of hops per packet";
       type union {
         type string {
           pattern "<.*>|$.*";
         }
         type uint32 {
           range "1 .. 16";
         }
       }
     }
     leaf minimum-wait-time {
       description "Minimum number of seconds before requests are forwarded";
       type union {
         type string {
           pattern "<.*>|$.*";
         }
         type uint32 {
           range "0 .. 30000";
         }
       }
     }
     leaf client-response-ttl {
       description "IP time-to-live value to set in responses to client";
       type union {
         type string {
           pattern "<.*>|$.*";
         }
         type uint32 {
           range "1 .. 255";
         }
       }
     }
     leaf source-ip-change {
       description "Use address of egress interface as source ip";
       type empty;
     }
     list interface {
       key name;
       description "One or more interfaces";
       leaf name {
         description "Interface name";
         type union {
           type jt:interface-name;
           type string {
             pattern "<.*>|$.*";
           }
         }
       }
       uses apply-advanced;
       leaf upto {
         description "Interface up to";
         type union {
           type jt:interface-name;
           type string {
             pattern "<.*>|$.*";
           }
         }
       }
       leaf exclude {
         description "Exclude this interface range";
         type empty;
       }
       leaf trace {
         description "Enable tracing for this interface";
         junos:must "(!(\".. exclude\"))";
         junos:must-message "Cannot specify tracing with exclude";
         type empty;
       }
       container overrides {
         description "DHCP override processing";
         junos:must "(!(\".. exclude\"))";
         junos:must-message "Cannot specify overrides with exclude";
         uses override-type;
       }
       container dynamic-profile {
         description "Dynamic profile to use";
         junos:must "(!(\".. exclude\"))";
         junos:must-message "Cannot specify overrides with exclude";
         uses dynamic-profile-type;
       }
       leaf service-profile {
         description "Dynamic profile to use for default service activation";
         type string {
           length "1 .. 128";
         }
       }
       leaf access-profile {
         description "Access profile to use for AAA services";
         junos:must "(\"access profile $$\")";
         junos:must-message "Matching access profile must be defined";
         junos:must "(!(\".. exclude\"))";
         junos:must-message "Cannot specify overrides with exclude";
         type string {
           length "1 .. 128";
         }
       }
       container short-cycle-protection {
         description "Short cycle lockout configuration";
         leaf lockout-min-time {
           description "Short cycle lockout time in seconds";
           type union {
             type string {
               pattern "<.*>|$.*";
             }
             type uint32 {
               range "1 .. 86400";
             }
           }
         }
         leaf lockout-max-time {
           description "Short cycle lockout time in seconds";
           type union {
             type string {
               pattern "<.*>|$.*";
             }
             type uint32 {
               range "1 .. 86400";
             }
           }
         }
       }
     }
     container remote-id-mismatch {
       description "DHCP client remote-id mismatch";
       presence "enable remote-id-mismatch";
       uses dhcp-remote-id-mismatch-type;
     }
     container lease-time-validation {
       presence "enable lease-time-validation";
       description "Configure lease time violation validation";
       uses apply-advanced;
       leaf lease-time-threshold {
         description "Threshold for lease time violation in seconds";
         units "seconds";
         type union {
           type string {
             pattern "<.*>|$.*";
           }
           type uint32 {
             range "60 .. 2147483647";
           }
         }
       }
       container violation-action {
         description "Lease time validation violation action";
         leaf drop {
           description "Drop dhcpv4 offer and ack packets";
           type empty;
         }
       }
     }
   }
   grouping dhcp-v4-option-default-action {
     description "Default action";
     uses apply-advanced;
     choice server-group-choice {
       case case_1 {
         leaf relay-server-group {
           description "Name of DHCP relay server group when match is made";
           junos:must "((\".. .. .. .. .. .. server-group $$\" || (\".. .. .. .. .. server-group $$\" || (\".. .. .. .. server-group $$\" || \".. .. .. server-group $$\"))))";
           junos:must-message "Referenced group must be defined under [edit forwarding dhcp-relay server-group]";
           type string {
             length "1 .. 64";
           }
         }
       }
       case case_2 {
         leaf local-server-group {
           description "Name of DHCP local server group when match is made";
           junos:must "((\".. .. .. .. .. .. .. .. system services dhcp-local-server group $$\" || (\".. .. .. .. .. .. .. system services dhcp-local-server group $$\" || (\".. .. .. .. .. .. system services dhcp-local-server group $$\" || \".. .. .. .. .. system services dhcp-local-server group $$\"))))";
           junos:must-message "Referenced group must be defined under [edit system services dhcp-local-server group]";
           type string {
             length "1 .. 64";
           }
         }
       }
       case case_3 {
         leaf drop {
           description "Discard when a match is made";
           type empty;
         }
       }
       case case_4 {
         leaf forward-only {
           description "Forward without subscriber services when a match is made";
           type empty;
         }
       }
     }
   }
   grouping dhcpv4-gbl-active-sg-type {
     leaf active-server-group {
       description "Name of DHCP server group";
       junos:must "(\".. .. server-group $$\")";
       junos:must-message "Referenced group must be defined under [edit forwarding-options dhcp-relay server-group]";
       type string {
         length "1 .. 64";
       }
     }
     leaf allow-server-change {
       description "Accept DHCP-ACK from any server in this group";
       type empty;
     }
   }
   grouping dhcpv4-gp-active-sg-type {
     leaf active-server-group {
       description "Name of DHCP server group";
       junos:must "(\".. .. .. server-group $$\")";
       junos:must-message "Referenced group must be defined under [edit forwarding-options dhcp-relay server-group]";
       type string {
         length "1 .. 64";
       }
     }
     leaf allow-server-change {
       description "Accept DHCP-ACK from any server in this group";
       type empty;
     }
   }
   grouping dhcpv6-relay-type {
     description "DHCPv6 relay configuration";
     uses apply-advanced;
     container authentication {
       description "DHCPv6 authentication";
       uses dhcpv6-authentication-type;
     }
     container persistent-storage {
       description "Trigger to enable flat file storage";
       leaf automatic {
         description "Trigger automatically";
         type empty;
       }
     }
     container liveness-detection {
       description "DHCPv6 client liveness detection processing";
       uses dhcpv6-liveness-detection-type;
     }
     container dynamic-profile {
       description "Dynamic profile to use";
       uses dynamic-profile-type;
     }
     leaf service-profile {
       description "Dynamic profile to use for default service activation";
       type string {
         length "1 .. 128";
       }
     }
     leaf access-profile {
       description "Access profile to use for AAA services";
       junos:must "(\"access profile $$\")";
       junos:must-message "Matching access profile must be defined";
       type string {
         length "1 .. 128";
       }
     }
     container short-cycle-protection {
       description "Short cycle lockout configuration";
       leaf lockout-min-time {
         description "Short cycle lockout time in seconds";
         type union {
           type string {
             pattern "<.*>|$.*";
           }
           type uint32 {
             range "1 .. 86400";
           }
         }
       }
       leaf lockout-max-time {
         description "Short cycle lockout time in seconds";
         type union {
           type string {
             pattern "<.*>|$.*";
           }
           type uint32 {
             range "1 .. 86400";
           }
         }
       }
     }
     container overrides {
       description "DHCPv6 override processing";
       presence "enable overrides";
       uses dhcpv6-override-relay-type;
     }
     container relay-option {
       description "DHCPv6 option processing";
       presence "enable relay-option";
       uses dhcp-generic-v6-option;
     }
     leaf exclude-relay-agent-identifier {
       description "Exclude relay agent identifier from packets to server";
       type empty;
     }
     container server-match {
       description "Server match processing";
       uses apply-advanced;
       container default-action {
         description "Server match default action";
         uses server-match-action-choice;
       }
       container duid {
         description "Match duid processing";
         uses apply-advanced;
         container equals {
           description "Duid equals";
           uses server-match-v6-ascii-hex;
         }
         container starts-with {
           description "Duid starts with";
           uses server-match-v6-ascii-hex;
         }
       }
       list address {
         key name;
         ordered-by user;
         description "Server ipv6 address";
         leaf name {
           description "Server ipv6 address for matching";
           type jt:ipv6prefix;
         }
         uses apply-advanced;
         choice server-match-action-choice {
           case case_1 {
             leaf forward-only {
               description "Forward without subscriber services when a match is made";
               type empty;
             }
           }
           case case_2 {
             leaf create-relay-entry {
               description "Create relay entry and allow subscriber services";
               type empty;
             }
           }
         }
       }
     }
     leaf relay-agent-option-79 {
       description "Add the client MAC address to the Relay Forward header.";
       type empty;
     }
     container vendor-specific-information {
       description "DHCPv6 option 17 vendor-specific processing";
       uses jdhcp-vendor-specific-type;
     }
     container forward-only {
       description "Forward DHCPv6 packets without creating binding";
       presence "enable forward-only";
       uses forward-only-to-rc-type;
     }
     leaf forward-only-replies {
       description "Forward-only replies from server to appropriate logical-system:routing-instance based on options";
       type empty;
     }
     container forward-snooped-clients {
       junos:must "((!(\".. forward-only\") && (!(\".. forward-only-replies\") && !(any \".. group <*> forward-only\"))))";
       junos:must-message "forward-only and forward-only-replies cannot be configured when forward-snooped-clients is configured";
       description "Forward snooped (unicast) packets";
       choice interface-type {
         case case_1 {
           leaf configured-interfaces {
             description "Forward snooped (unicast) packets on configured interfaces";
             type empty;
           }
         }
         case case_2 {
           leaf non-configured-interfaces {
             description "Forward snooped (unicast) packets on non-configured interfaces";
             type empty;
           }
         }
         case case_3 {
           leaf all-interfaces {
             description "Forward snooped (unicast) packets on configured and non-configured interfaces";
             type empty;
           }
         }
       }
     }
     container route-suppression {
       description "Suppress access-internal and/or access route addition";
       uses dhcpv6-route-suppression-type;
     }
     list group {
       key name;
       ordered-by user;
       description "Define a DHCPv6 relay group";
       uses dhcpv6-relay-group;
     }
     container relay-agent-interface-id {
       description "DHCPv6 interface-id option processing";
       presence "enable relay-agent-interface-id";
       uses v6-relay-option-interface-id-type;
     }
     container relay-agent-remote-id {
       description "DHCPv6 remote-id option processing";
       presence "enable relay-agent-remote-id";
       uses v6-relay-option-remote-id-type;
     }
     container server-group {
       description "Define a DHCPv6 server group";
       uses v6-server-group-type;
     }
     container active-server-group {
       description "Name of DHCPv6 server group";
       uses dhcpv6-gbl-active-sg-type;
     }
     leaf server-response-time {
       description "Number of seconds in a period of activity between the last server response and an unaswered request";
       default "0";
       type union {
         type uint32;
         type string {
           pattern "<.*>|$.*";
         }
       }
     }
     container lease-time-validation {
       presence "enable lease-time-validation";
       description "Configure lease time violation validation";
       uses apply-advanced;
       leaf lease-time-threshold {
         description "Threshold for lease time violation in seconds";
         units "seconds";
         type union {
           type string {
             pattern "<.*>|$.*";
           }
           type uint32 {
             range "60 .. 2147483647";
           }
         }
       }
       container violation-action {
         description "Lease time validation violation action";
         leaf drop {
           description "Drop dhcpv6 advertise and reply packets";
           type empty;
         }
       }
     }
     leaf no-snoop {
       description "Do not snoop DHCPV6 packets";
       junos:must "(!(\"legacy-snooping\"))";
       junos:must-message "'no-snoop' statement cannot be included along with 'legacy-snooping' statement";
       type empty;
     }
     container leasequery {
       description "DHCPv6 leasequery configuration";
       presence "enable leasequery";
       junos:must "(\".. relay-agent-interface-id\")";
       junos:must-message "Must configure [relay-agent-interface-id] to insert interface-id";
       uses relay-leasequery-type;
     }
     container bulk-leasequery {
       description "DHCPv6 bulk leasequery configuration";
       presence "enable bulk-leasequery";
       junos:must "(\".. relay-agent-interface-id\")";
       junos:must-message "Must configure [relay-agent-interface-id] to insert interface-id";
       uses relay-bulk-leasequery-v6-type;
     }
     container active-leasequery {
       description "DHCPv6 active leasequery configuration";
       presence "enable active-leasequery";
       junos:must "(\".. bulk-leasequery\")";
       junos:must-message "Must configure bulk-leasequery";
       uses active-leasequery-v6-type;
     }
     container remote-id-mismatch {
       description "DHCP client remote-id mismatch";
       presence "enable remote-id-mismatch";
       uses dhcp-remote-id-mismatch-type;
     }
     container duplicate-clients {
       description "Allow duplicate clients";
       uses dhcpv6-duplicate-clients-type;
     }
   }
   grouping dhcp-generic-v6-option {
     description "Generic DHCPv6 options processing";
     uses apply-advanced;
     leaf option-number {
       description "Option number";
       status deprecated;
       type enumeration {
         enum "15" {
           description "Option 15";
           status deprecated;
         }
         enum "16" {
           description "Option 16";
           status deprecated;
         }
       }
     }
     container equals {
       description "Generic option equals";
       status deprecated;
       uses relay-v6-option-ascii-hex;
     }
     container default-action {
       description "Generic option default action";
       status deprecated;
       uses dhcp-v6-option-default-action;
     }
     container starts-with {
       description "Generic option starts with";
       status deprecated;
       uses relay-v6-option-ascii-hex;
     }
     container option-15 {
       description "Add option 15 processing";
       presence "enable option-15";
       junos:must "(!(\"option-number\"))";
       junos:must-message "Cannot specify option-15  with option-number";
       uses dhcp-generic-v6-option-type;
     }
     container option-16 {
       description "Add option 16 processing";
       presence "enable option-16";
       junos:must "(!(\"option-number\"))";
       junos:must-message "Cannot specify option-16  with option-number";
       uses dhcp-generic-v6-option-type;
     }
     list option-order {
       key name;
       ordered-by user;
       description "Options precedence order";
       junos:must "(!(\"option-number\"))";
       junos:must-message "Cannot specify option-order  with option-number";
       leaf name {
         description "Option number";
         type enumeration {
           enum "15" {
             description "Option 15";
           }
           enum "16" {
             description "Option 16";
           }
         }
       }
       uses apply-advanced;
     }
   }
   grouping dhcp-generic-v6-option-type {
     uses apply-advanced;
     container equals {
       description "Generic option equals";
       uses relay-v6-option-ascii-hex;
     }
     container default-action {
       description "Generic option default action";
       uses dhcp-v6-option-default-action;
     }
     container starts-with {
       description "Generic option starts with";
       uses relay-v6-option-ascii-hex;
     }
   }
   grouping dhcp-v6-option-default-action {
     description "Default action";
     uses apply-advanced;
     choice server-group-choice {
       case case_1 {
         leaf relay-server-group {
           description "Name of DHCP relay server group when match is made";
           junos:must "((\".. .. .. .. .. .. server-group $$\" || (\".. .. .. .. .. server-group $$\" || (\".. .. .. .. server-group $$\" || \".. .. .. server-group $$\"))))";
           junos:must-message "Referenced group must be defined under [edit forwarding options dhcp-relay dhcpv6 server-group]";
           type string {
             length "1 .. 64";
           }
         }
       }
       case case_2 {
         leaf drop {
           description "Discard when a match is made";
           type empty;
         }
       }
       case case_3 {
         leaf forward-only {
           description "Forward without subscriber services when a match is made";
           type empty;
         }
       }
     }
   }
   grouping dhcpv6-gbl-active-sg-type {
     uses apply-advanced;
     leaf active-server-group {
       description "Name of DHCPv6 server group";
       junos:must "(\".. .. server-group $$\")";
       junos:must-message "Referenced group must be defined under [edit forwarding-options dhcp-relay dhcpv6 server-group]";
       type string {
         length "1 .. 64";
       }
     }
   }
   grouping dhcpv6-override-relay-type {
     description "DHCPv6 relay override processing";
     uses apply-advanced;
     choice allow-snooped-clients-choice {
       leaf allow-snooped-clients {
         description "Allow client creation from snooped PDUs";
         type empty;
       }
       leaf no-allow-snooped-clients {
         description "Don't allow client creation from snooped PDUs";
         type empty;
       }
     }
     leaf delay-authentication {
       description "Delay subscriber authentication in DHCP protocol processing until request packet";
       type empty;
     }
     leaf interface-client-limit {
       description "Limit the number of clients allowed on an interface";
       type union {
         type string {
           pattern "<.*>|$.*";
         }
         type uint32 {
           range "1 .. 500000";
         }
       }
     }
     leaf dual-stack {
       description "Dual stack group to use.";
       type string {
         length "1 .. 64";
       }
     }
     leaf no-bind-on-request {
       description "Do not bind if stray DHCPv6 RENEW, REBIND is received";
       type empty;
     }
     container client-negotiation-match {
       description "Use secondary match criteria for SOLICIT PDU";
       choice match-with {
         case case_1 {
           leaf incoming-interface {
             description "Use incoming interface";
             type empty;
           }
         }
       }
     }
     leaf send-release-on-delete {
       description "Always send RELEASE to the server when a binding is deleted";
       type empty;
     }
     leaf always-process-option-request-option {
       description "Always process option even after address allocation failure";
       type empty;
     }
     leaf relay-source {
       description "Interface for relay source";
       type union {
         type jt:interface-name;
         type string {
           pattern "<.*>|$.*";
         }
       }
     }
     leaf delete-binding-on-renegotiation {
       description "Delete binding on renegotiation";
       type empty;
     }
     leaf asymmetric-lease-time {
       description "Use a reduced lease time for the client. In seconds";
       units "seconds";
       type union {
         type string {
           pattern "<.*>|$.*";
         }
         type uint32 {
           range "600 .. 86400";
         }
       }
     }
     leaf asymmetric-prefix-lease-time {
       description "Use a reduced prefix lease time for the client. In seconds";
       units "seconds";
       type union {
         type string {
           pattern "<.*>|$.*";
         }
         type uint32 {
           range "600 .. 86400";
         }
       }
     }
   }
   grouping dhcpv6-relay-group {
     description "DHCPv6 groups";
     leaf name {
       description "Group name";
       type string {
         length "1 .. 64";
         junos:posix-pattern "^[A-Za-z0-9][_0-9A-Za-z-]*$";
         junos:pattern-message "Must be a non-reserved string of 64 characters or less";
       }
     }
     uses apply-advanced;
     container active-server-group {
       description "Name of DHCPv6 server group";
       uses dhcpv6-gp-active-sg-type;
     }
     list dual-stack-group {
       key name;
       description "Define a DHCP dual stack group";
       uses dhcp-dual-stack-group;
     }
     container authentication {
       description "DHCPv6 authentication";
       uses dhcpv6-authentication-type;
     }
     container liveness-detection {
       description "DHCPv6 client liveness detection processing";
       uses dhcpv6-liveness-detection-type;
     }
     container dynamic-profile {
       description "Dynamic profile to use";
       uses dynamic-profile-type;
     }
     leaf service-profile {
       description "Dynamic profile to use for default service activation";
       type string {
         length "1 .. 128";
       }
     }
     leaf access-profile {
       description "Access profile to use for AAA services";
       junos:must "(\"access profile $$\")";
       junos:must-message "Matching access profile must be defined";
       type string {
         length "1 .. 128";
       }
     }
     container short-cycle-protection {
       description "Short cycle lockout configuration";
       leaf lockout-min-time {
         description "Short cycle lockout time in seconds";
         type union {
           type string {
             pattern "<.*>|$.*";
           }
           type uint32 {
             range "1 .. 86400";
           }
         }
       }
       leaf lockout-max-time {
         description "Short cycle lockout time in seconds";
         type union {
           type string {
             pattern "<.*>|$.*";
           }
           type uint32 {
             range "1 .. 86400";
           }
         }
       }
     }
     container overrides {
       description "DHCPv6 override processing";
       presence "enable overrides";
       uses dhcpv6-override-relay-type;
     }
     container relay-option {
       description "DHCPv6 option processing";
       presence "enable relay-option";
       uses dhcp-generic-v6-option;
     }
     container vendor-specific-information {
       description "DHCPv6 option 17 vendor-specific processing";
       uses jdhcp-vendor-specific-type;
     }
     container forward-only {
       description "Forward DHCPv6 packets without creating binding";
       presence "enable forward-only";
       uses forward-only-to-rc-type;
     }
     container relay-agent-interface-id {
       description "DHCPv6 interface-id option processing";
       presence "enable relay-agent-interface-id";
       uses v6-relay-option-interface-id-type;
     }
     container relay-agent-remote-id {
       description "DHCPv6 remote-id option processing";
       presence "enable relay-agent-remote-id";
       uses v6-relay-option-remote-id-type;
     }
     container route-suppression {
       description "Suppress access-internal and/or access route addition";
       uses dhcpv6-route-suppression-type;
     }
     leaf relay-agent-option-79 {
       description "Add the client MAC address to the Relay Forward header.";
       type empty;
     }
     list interface {
       key name;
       description "One or more interfaces";
       leaf name {
         description "Interface name";
         junos:must "((unique \"forwarding-options dhcp-relay dhcpv6 group <*> interface $$\" && !(any \"system services dhcp-local-server dhcpv6 group <*> interface $$\")))";
         junos:must-message "Interface used in other relay or server group";
         type union {
           type jt:interface-name;
           type string {
             pattern "<.*>|$.*";
           }
         }
       }
       uses apply-advanced;
       leaf upto {
         description "Interface up to";
         junos:must "(!(\".. .. interface $$\"))";
         junos:must-message "Range end point must not equal start";
         type union {
           type jt:interface-name;
           type string {
             pattern "<.*>|$.*";
           }
         }
       }
       leaf exclude {
         description "Exclude this interface range";
         type empty;
       }
       leaf trace {
         description "Enable tracing for this interface";
         junos:must "(!(\".. exclude\"))";
         junos:must-message "Cannot specify tracing with exclude";
         type empty;
       }
       container overrides {
         description "DHCPv6 override processing";
         junos:must "(!(\".. exclude\"))";
         junos:must-message "Cannot specify overrides with exclude";
         uses dhcpv6-override-relay-type;
       }
       container dynamic-profile {
         description "Dynamic profile to use";
         junos:must "(!(\".. exclude\"))";
         junos:must-message "Cannot specify dynamic-profile with exclude";
         uses dynamic-profile-type;
       }
       leaf service-profile {
         description "Dynamic profile to use for default service activation";
         type string {
           length "1 .. 128";
         }
       }
       leaf access-profile {
         description "Access profile to use for AAA services";
         junos:must "(\"access profile $$\")";
         junos:must-message "Matching access profile must be defined";
         junos:must "(!(\".. exclude\"))";
         junos:must-message "Cannot specify overrides with exclude";
         type string {
           length "1 .. 128";
         }
       }
       container short-cycle-protection {
         description "Short cycle lockout configuration";
         leaf lockout-min-time {
           description "Short cycle lockout time in seconds";
           type union {
             type string {
               pattern "<.*>|$.*";
             }
             type uint32 {
               range "1 .. 86400";
             }
           }
         }
         leaf lockout-max-time {
           description "Short cycle lockout time in seconds";
           type union {
             type string {
               pattern "<.*>|$.*";
             }
             type uint32 {
               range "1 .. 86400";
             }
           }
         }
       }
     }
     container lease-time-validation {
       presence "enable lease-time-validation";
       description "Configure lease time violation validation";
       uses apply-advanced;
       leaf lease-time-threshold {
         description "Threshold for lease time violation in seconds";
         units "seconds";
         type union {
           type string {
             pattern "<.*>|$.*";
           }
           type uint32 {
             range "60 .. 2147483647";
           }
         }
       }
       container violation-action {
         description "Lease time validation violation action";
         leaf drop {
           description "Drop dhcpv6 advertise and reply packets";
           type empty;
         }
       }
     }
     container remote-id-mismatch {
       description "DHCP client remote-id mismatch";
       presence "enable remote-id-mismatch";
       uses dhcp-remote-id-mismatch-type;
     }
     container server-match {
       description "Server match processing";
       uses apply-advanced;
       container default-action {
         description "Server match default action";
         uses server-match-action-choice;
       }
       container duid {
         description "Match duid processing";
         uses apply-advanced;
         container equals {
           description "Duid equals";
           uses server-match-v6-ascii-hex;
         }
         container starts-with {
           description "Duid starts with";
           uses server-match-v6-ascii-hex;
         }
       }
       list address {
         key name;
         ordered-by user;
         description "Server ipv6 address";
         leaf name {
           description "Server ipv6 address for matching";
           type jt:ipv6prefix;
         }
         uses apply-advanced;
         choice server-match-action-choice {
           case case_1 {
             leaf forward-only {
               description "Forward without subscriber services when a match is made";
               type empty;
             }
           }
           case case_2 {
             leaf create-relay-entry {
               description "Create relay entry and allow subscriber services";
               type empty;
             }
           }
         }
       }
     }
   }
   grouping dhcpv6-gp-active-sg-type {
     uses apply-advanced;
     leaf active-server-group {
       description "Name of DHCPv6 server group";
       junos:must "(\".. .. .. server-group $$\")";
       junos:must-message "Referenced group must be defined under [edit forwarding-options dhcp-relay dhcpv6 server-group]";
       type string {
         length "1 .. 64";
       }
     }
   }
   grouping forward-only-to-rc-type {
     description "Forward DHCP packets without creating binding";
     uses apply-advanced;
     leaf logical-system {
       default "current";
       type string;
     }
     leaf routing-instance {
       default "current";
       type string;
     }
   }
   grouping jdhcp-security-type {
     description "DHCP access security configuration";
     uses apply-advanced;
     leaf no-dhcp-snooping {
       description "Disable dhcp snooping";
       junos:must "(!(\"switch-options no-arp-trap \"))";
       junos:must-message "Cannot enable ARP inspection with no-arp-trap";
       type empty;
     }
     leaf arp-inspection {
       description "Enable dynamic ARP inspection";
       type empty;
     }
     leaf ip-source-guard {
       description "Enable IP source guard";
       junos:must "(!(any \".. group <*> overrides untrusted\"))";
       junos:must-message "Ip-source-guard and dhcp-security overrides untrusted cannot be configured together";
       type empty;
     }
     leaf no-dhcpv6-snooping {
       description "Disable DHCPv6 snooping";
       type empty;
     }
     leaf neighbor-discovery-inspection {
       description "Enable neighbor discovery inspection";
       type empty;
     }
     leaf ipv6-source-guard {
       description "Enable IPv6 source guard";
       junos:must "(!(any \".. group <*> overrides untrusted\"))";
       junos:must-message "Ipv6-source-guard and dhcp-security overrides untrusted cannot be configured together";
       type empty;
     }
     leaf light-weight-dhcpv6-relay {
       description "Enable light weight dhcpv6 relay";
       type empty;
     }
     list group {
       key name;
       ordered-by user;
       description "Define a DHCP security group for overriding defaults";
       uses ds-group;
     }
     container option-82 {
       description "DHCP option-82 processing for snooped packets";
       presence "enable option-82";
       uses security-option-82-type;
     }
     container dhcpv6-options {
       description "DHCPv6 option processing for snooped packets";
       presence "enable dhcpv6-options";
       uses security-dhcpv6-options-type;
     }
   }
   grouping ds-group {
     description "DHCP security groups";
     leaf name {
       description "Group name";
       type string {
         length "1 .. 64";
         junos:posix-pattern "^[A-Za-z0-9][_0-9A-Za-z-]*$";
         junos:pattern-message "Must be a non-reserved string of 64 characters or less";
       }
     }
     uses apply-advanced;
     container overrides {
       description "DHCP override processing";
       presence "enable overrides";
       uses ds-override-type;
     }
     list interface {
       key name;
       description "One or more interfaces";
       leaf name {
         description "Interface name";
         type union {
           type jt:interface-name;
           type string {
             pattern "<.*>|$.*";
           }
         }
       }
       uses apply-advanced;
       list static-ip {
         key name;
         ordered-by user;
         description "Static IP address configuration";
         uses ip-mac-static;
       }
       list static-ipv6 {
         key name;
         ordered-by user;
         description "Static IPv6 address configuration";
         uses ipv6-mac-static;
       }
     }
   }
   grouping ds-override-type {
     description "Dynamic ARP Inspection override processing";
     uses apply-advanced;
     leaf trusted {
       description "Make this trusted group of interfaces";
       junos:must "(!(\".. untrusted\"))";
       junos:must-message "Trusted and untrusted cannot be configured together";
       type empty;
     }
     leaf untrusted {
       description "Make this untrusted group of interfaces";
       junos:must "(!(\".. trusted\"))";
       junos:must-message "Trusted and untrusted cannot be configured together";
       type empty;
     }
     leaf no-option82 {
       description "Make this group of interfaces not to add option82";
       type empty;
     }
     leaf no-option37 {
       description "Make this group of interfaces not to add option37";
       type empty;
     }
     leaf no-option18 {
       description "Make this group of interfaces not to add option18";
       type empty;
     }
     leaf no-option16 {
       description "Make this group of interfaces not to add option16";
       type empty;
     }
     leaf no-option79 {
       description "Make this group of interfaces not to add option79";
       type empty;
     }
     leaf no-dhcpv6-options {
       description "Make this group of interfaces not to add any DHCPv6 options";
       type empty;
     }
   }
   grouping ip-mac-static {
     leaf name {
       description "IP address";
       type jt:ipaddr;
     }
     leaf mac {
       description "MAC address";
       type jt:mac-addr;
     }
   }
   grouping ipv6-mac-static {
     leaf name {
       description "IP address";
       type jt:ipv6addr;
     }
     leaf mac {
       description "MAC address";
       type jt:mac-addr;
     }
   }
   grouping jdhcp-vendor-specific-type {
     description "Add vendor-specific option processing";
     uses apply-advanced;
     leaf host-name {
       description "Add router host name";
       type empty;
     }
     leaf location {
       description "Add location information expressed as interface name format";
       type empty;
     }
   }
   grouping juniper-forwarding-options {
     uses apply-advanced;
     list storm-control-profiles {
       key name;
       description "Storm control profile for this instance";
       leaf name {
         description "Storm control profile name";
         junos:must "(\"forwarding-options storm-control-profiles $$ all\")";
         junos:must-message "Only aggregate profiles supported";
         type string {
           length "1 .. 127";
         }
       }
       uses apply-advanced;
       container all {
         presence "enable all";
         description "For all BUM traffic";
         uses apply-advanced;
         choice bandwidth {
           case case_1 {
             leaf bandwidth-percentage {
               description "Percentage of link bandwidth";
               type union {
                 type string {
                   pattern "<.*>|$.*";
                 }
                 type uint32 {
                   range "1 .. 100";
                 }
               }
             }
           }
           case case_2 {
             leaf bandwidth-level {
               description "Link bandwidth";
               units "kbps";
               type union {
                 type string {
                   pattern "<.*>|$.*";
                 }
                 type uint32;
               }
             }
           }
         }
         leaf burst-size {
           description "Burst size";
           units "bytes";
           type union {
             type string {
               pattern "<.*>|$.*";
             }
             type uint32;
           }
         }
         leaf no-broadcast {
           description "Disable broadcast storm control";
           type empty;
         }
         leaf no-unknown-unicast {
           description "Disable unknown unicast storm control";
           type empty;
         }
         choice no-multicast-choices {
           case case_1 {
             leaf no-multicast {
               description "Disable multicast storm control";
               type empty;
             }
           }
           case case_2 {
             leaf no-registered-multicast {
               description "Disable registered multicast storm control";
               type empty;
             }
           }
           case case_3 {
             leaf no-unregistered-multicast {
               description "Disable unregistered multicast storm control";
               type empty;
             }
           }
         }
       }
       leaf action-shutdown {
         description "Disable port for excessive storm control errors";
         type empty;
       }
     }
     container tunnels {
       presence "enable tunnels";
       description "Tunnel port profile";
       uses apply-advanced;
       container udp {
         presence "enable udp";
         uses apply-advanced;
         container payload-port-profile {
           presence "enable payload-port-profile";
           description "Tunnel payload port profile udp, only 1 can exist";
           uses apply-advanced;
           leaf profile-name {
             description "Payload port profile name";
             type string;
           }
           leaf inet {
             description "Tunnel port profile udp inet port";
             type union {
               type string {
                 pattern "<.*>|$.*";
               }
               type uint32 {
                 range "1 .. 65535";
               }
             }
           }
           leaf inet6 {
             description "Tunnel port profile udp inet6 port";
             type union {
               type string {
                 pattern "<.*>|$.*";
               }
               type uint32 {
                 range "1 .. 65535";
               }
             }
           }
           leaf mpls {
             description "Tunnel port profile udp mpls port";
             type union {
               type string {
                 pattern "<.*>|$.*";
               }
               type uint32 {
                 range "1 .. 65535";
               }
             }
           }
           leaf iso {
             description "Tunnel port profile udp iso port";
             type union {
               type string {
                 pattern "<.*>|$.*";
               }
               type uint32 {
                 range "1 .. 65535";
               }
             }
           }
         }
       }
     }
     list mirror-profile {
       key name;
       description "Mirror profile of mirror instance";
       uses mirror-profile-attributes;
     }
     choice sampling-or-packet-capture {
       case case_1 {
         container sampling {
           description "Statistical traffic sampling options";
           uses juniper-sampling-options;
         }
       }
       case case_2 {
         container packet-capture {
           description "Packet capture options";
           uses juniper-packet-capture-options;
         }
       }
     }
     list monitoring {
       key name;
       description "Configure lawful interception of traffic";
       uses juniper-monitoring-options;
     }
     list accounting {
       key name;
       description "Configure accounting of traffic";
       uses juniper-packet-accounting-options;
     }
     list analyzer {
       key name;
       description "Analyzer options";
       max-elements 64;
       uses smpl-analyzer-type;
     }
     container port-mirroring {
       description "Configure port mirroring of traffic";
       uses juniper-port-mirror-options;
     }
     container pfe-sensor {
       description "Enable sensor for pfe resources";
       uses apply-advanced;
       container npu-memory {
         description "Gather npu memory information";
         uses apply-advanced;
         container resource-list {
           description "List of resources monitored for pfe sensors";
           uses apply-advanced;
           leaf l3-next-hop {
             description "Fetch l3 next hop information";
             type empty;
           }
           leaf host-ipv4 {
             description "Fetch host ipv4 information";
             type empty;
           }
           leaf host-ipv6 {
             description "Fetch host ipv6 information";
             type empty;
           }
           leaf lpm-table-ipv4 {
             description "Fetch lpm table ipv4 information";
             type empty;
           }
           leaf lpm-table-ipv6-64 {
             description "Fetch lpm table ipv6 information for /64 prefix routes";
             type empty;
           }
           leaf lpm-table-ipv6-128 {
             description "Fetch lpm table ipv6 information for /128 prefix routes";
             type empty;
           }
           leaf egress-l3-interface {
             description "Fetch egress l3 interface information";
             type empty;
           }
           leaf vport {
             description "Fetch vport information";
             type empty;
           }
           leaf mpls-swap-table {
             description "Fetch mpls swap table information";
             type empty;
           }
           leaf mpls-ingress-table {
             description "Fetch mpls ingress table information";
             type empty;
           }
           leaf tunnel-table {
             description "Fetch mpls/Ip tunnel table information";
             type empty;
           }
           leaf vfp {
             description "Fetch vlan filter information";
             type empty;
           }
           leaf ifp {
             description "Fetch ingress filter information";
             type empty;
           }
           leaf efp {
             description "Fetch egress filter information";
             type empty;
           }
           leaf ecmp-group-table {
             description "Fetch ecmp group table information";
             type empty;
           }
           leaf ecmp-member-table {
             description "Fetch ecmp member table information";
             type empty;
           }
         }
       }
     }
     container evpn-vxlan {
       description "EVPN VXLAN configurations";
       uses apply-advanced;
       leaf shared-tunnels {
         description "Create VTEP tunnels to EVPN PE";
         type empty;
       }
       container reroute-address {
         description "Reroute IP address for vxlan encapsulation";
         choice family {
           case case_1 {
             container inet {
               presence "enable inet";
               description "IPv4 address family";
               uses apply-advanced;
               leaf address {
                 description "Reroute address for IPV4 FRR";
                 type jt:ipv4addr;
               }
             }
           }
           case case_2 {
             container inet6 {
               presence "enable inet6";
               description "IPv6 address family";
               uses apply-advanced;
               leaf address {
                 description "Reroute address for IPV6 FRR";
                 type jt:ipv6addr;
               }
             }
           }
         }
       }
     }
     container multicast-replication {
       description "Set mode of multicast replication";
       uses apply-advanced;
       leaf ingress {
         description "Complete ingress replication";
         junos:must "(\"chassis network-services enhanced-ip\")";
         junos:must-message "Enhanced IP must be configured for using multicast-replication features";
         type empty;
       }
       leaf local-latency-fairness {
         description "Complete parallel replication";
         junos:must "(\"chassis network-services enhanced-ip\")";
         junos:must-message "Enhanced IP must be configured for using multicast-replication features";
         type empty;
       }
       container evpn {
         description "EVPN IRB multicast related options";
         uses apply-advanced;
         leaf irb {
           type enumeration {
             enum "local-only" {
               description "Multicast forward in local-only mode";
             }
             enum "local-remote" {
               description "Multicast forward in local-remote mode";
             }
             enum "oism" {
               description "Optimized inter subnet multicast mode";
             }
           }
         }
         leaf smet-nexthop-limit {
           description "Flood traffic to all egress when count goes above limit";
           type union {
             type string {
               pattern "<.*>|$.*";
             }
             type uint32 {
               range "10000 .. 40000";
             }
           }
         }
       }
     }
     container load-balance {
       description "Configure load-balancing attributes on the forwarding path";
       uses apply-advanced;
       leaf ecmp-local-bias {
         description "Apply locality bias for ecmp nexthops";
         type empty;
       }
       container indexed-load-balance {
         presence "enable indexed-load-balance";
         description "Use indexed permuted next hop lists for unilist and aggregate next hops";
         uses apply-advanced;
       }
       container per-flow {
         uses apply-advanced;
         leaf hash-seed {
           description "Enable per flow seed value on packet forwarding engine";
           type empty;
         }
       }
       container per-prefix {
         presence "enable per-prefix";
         uses apply-advanced;
         leaf hash-seed {
           description "Specifies per-router input value for per-prefix load-balancing hash function";
           default "0";
           type union {
             type string {
               pattern "<.*>|$.*";
             }
             type uint16 {
               range "0 .. 65534";
             }
           }
         }
       }
     }
     container hash-key {
       description "Select data used in the hash key";
       uses junos_hash_key;
     }
     container local-bias {
       presence "enable local-bias";
       description "Turn on local bias functionality";
       uses apply-advanced;
       leaf disable {
         description "Disable local-bias";
         type empty;
       }
     }
     container enhanced-hash-key {
       description "Select data used in the hash key for Enhanced IP Forwarding Engines";
       uses apply-advanced;
       leaf use-trunk-max-links {
         description "Use 8 links in trunk programming instead of actual links";
         type empty;
       }
       leaf ecmp-resilient-hash {
         description "Set resilient hashing for ECMP";
         junos:must "(!(\".. ecmp-dlb\"))";
         junos:must-message "RH and DLB cannot be configured together";
         type empty;
       }
       container lag-dlb {
         presence "enable lag-dlb";
         description "Setting dynamic load balancing options for LAG";
         uses apply-advanced;
         container ether-type {
           presence "enable ether-type";
           description "Setting ether type for LAG DLB";
           uses apply-advanced;
           leaf ipv4 {
             description "Ether type is ipv4";
             type empty;
           }
           leaf ipv6 {
             description "Ether type is ipv6";
             type empty;
           }
           leaf mpls {
             description "Ether type is mpls";
             type empty;
           }
         }
       }
       container fabric-load-balance {
         presence "enable fabric-load-balance";
         description "Set load balancing options for VC-Fabric forwarding";
         status deprecated;
         uses apply-advanced;
         choice mode {
           case case_1 {
             container flowlet {
               presence "enable flowlet";
               description "Inactivity-based flowlet link assignment (default)";
               status deprecated;
               uses apply-advanced;
               leaf inactivity-interval {
                 description "Minimum inactivity interval for flowlet detection";
                 status deprecated;
                 type enumeration {
                   enum "16us" {
                     description "16 microseconds (default)";
                     status deprecated;
                   }
                   enum "64us" {
                     description "64 microseconds";
                     status deprecated;
                   }
                   enum "512us" {
                     description "512 microseconds";
                     status deprecated;
                   }
                   enum "32ms" {
                     description "32 milliseconds";
                     status deprecated;
                   }
                 }
               }
             }
           }
           case case_2 {
             leaf per-packet {
               description "Per-packet optimal spraying";
               status deprecated;
               type empty;
             }
           }
         }
       }
       container ecmp-dlb {
         junos:must "(!(\".. ecmp-resilient-hash\"))";
         junos:must-message "RH and DLB cannot be configured together";
         description "Set load balancing options for VC-Fabric forwarding";
         uses apply-advanced;
         choice mode {
           case case_1 {
             leaf assigned-flow {
               description "Flow-based fixed link assignment";
               type empty;
             }
           }
           case case_2 {
             container flowlet {
               presence "enable flowlet";
               description "Inactivity-based flowlet link assignment (default)";
               uses apply-advanced;
               leaf inactivity-interval {
                 description "Minimum inactivity interval in micro-seconds for flowlet detection";
                 default "256";
                 type union {
                   type string {
                     pattern "<.*>|$.*";
                   }
                   type uint32;
                 }
               }
             }
           }
           case case_3 {
             leaf per-packet {
               description "Per-packet optimal spraying";
               type empty;
             }
           }
         }
         container ether-type {
           presence "enable ether-type";
           description "Ether type";
           uses apply-advanced;
           leaf ipv4 {
             description "Set DLB for ipv4";
             type empty;
           }
           leaf ipv6 {
             description "Set DLB for ipv6";
             type empty;
           }
           leaf mpls {
             description "Set DLB for mpls";
             type empty;
           }
         }
       }
       container hash-mode {
         description "Hashing mode";
         uses apply-advanced;
         choice instance {
           case case_1 {
             leaf layer2-header {
               description "Only layer2 header fields are considered for hashing";
               type empty;
             }
           }
           case case_2 {
             leaf layer2-payload {
               description "Only layer2 payload fields are considered for hashing";
               type empty;
             }
           }
           case case_3 {
             leaf gtp-header-offset {
               description "Gtp header first byte offset";
               type union {
                 type uint8;
                 type string {
                   pattern "<.*>|$.*";
                 }
               }
             }
           }
         }
       }
       container hash-parameters {
         description "Set traffic hashing parameters";
         uses apply-advanced;
         container ecmp {
           description "Configure hashing parameters for ECMP Traffic";
           uses apply-advanced;
           leaf offset {
             description "Set hashing offset for ECMP Traffic";
             type union {
               type string {
                 pattern "<.*>|$.*";
               }
               type uint32 {
                 range "0 .. 199";
               }
             }
           }
           container preprocess {
             description "Enable/Disable the preprocess parameter for ECMP traffic";
             uses apply-advanced;
             choice instance {
               case case_1 {
                 leaf enable {
                   description "Enable preprocess for ECMP";
                   type empty;
                 }
               }
               case case_2 {
                 leaf disable {
                   description "Disable preprocess for ECMP";
                   type empty;
                 }
               }
             }
           }
           container function {
             description "Configure hash functions for ECMP traffic";
             uses apply-advanced;
             choice instance {
               case case_1 {
                 leaf crc16-bisync {
                   description "Use CRC16-BISYNC function for ECMP traffic rcvd on xe";
                   type empty;
                 }
               }
               case case_2 {
                 leaf crc16-ccitt {
                   description "Use CRC16-CCITT function for ECMP traffic rcvd on xe";
                   type empty;
                 }
               }
               case case_3 {
                 leaf crc32-hi {
                   description "Use CRC32-HI function for ECMP traffic rcvd on xe";
                   type empty;
                 }
               }
               case case_4 {
                 leaf crc32-lo {
                   description "Use CRC32-LO function for ECMP traffic rcvd on xe";
                   type empty;
                 }
               }
             }
           }
         }
         container lag {
           description "Configure hashing parameters for LAG Traffic";
           uses apply-advanced;
           leaf offset {
             description "Set hashing offset for LAG Traffic";
             type union {
               type string {
                 pattern "<.*>|$.*";
               }
               type uint32 {
                 range "0 .. 199";
               }
             }
           }
           container preprocess {
             description "Enable/Disable the preprocess parameter for LAG traffic";
             uses apply-advanced;
             choice instance {
               case case_1 {
                 leaf enable {
                   description "Enable preprocess for LAG";
                   type empty;
                 }
               }
               case case_2 {
                 leaf disable {
                   description "Disable preprocess for LAG";
                   type empty;
                 }
               }
             }
           }
           container function {
             description "Configure hash functions for LAG traffic";
             uses apply-advanced;
             choice instance {
               case case_1 {
                 leaf crc16-bisync {
                   description "Use CRC16-BISYNC function for LAG traffic rcvd on xe";
                   type empty;
                 }
               }
               case case_2 {
                 leaf crc16-ccitt {
                   description "Use CRC16-CCITT function for LAG traffic rcvd on xe";
                   type empty;
                 }
               }
               case case_3 {
                 leaf crc32-hi {
                   description "Use CRC32-HI function for LAG traffic rcvd on xe";
                   type empty;
                 }
               }
               case case_4 {
                 leaf crc32-lo {
                   description "Use CRC32-LO function for LAG traffic rcvd on xe";
                   type empty;
                 }
               }
             }
           }
         }
       }
       container hash-seed {
         presence "enable hash-seed";
         description "Hash seed";
         uses apply-advanced;
         leaf seed-value {
           description "Hash seed value";
           type union {
             type string {
               pattern "<.*>|$.*";
             }
             type uint32 {
               range "0 .. 4294967295";
             }
           }
         }
       }
       container resilient-hash-seed {
         presence "enable resilient-hash-seed";
         description "Resilient hash seed";
         uses apply-advanced;
         leaf resilient-seed-value {
           description "Hash seed value for resilient ECMP and LAG";
           type union {
             type string {
               pattern "<.*>|$.*";
             }
             type uint32 {
               range "0 .. 4294967295";
             }
           }
         }
       }
       container mpls {
         description "Configure mpls fields";
         uses apply-advanced;
         leaf no-incoming-port {
           description "Exclude incoming port from the hash key";
           type empty;
         }
         leaf no-incoming-device {
           description "Exclude incoming device from the hash key";
           type empty;
         }
       }
       container layer2 {
         description "Configure layer2 fields";
         uses apply-advanced;
         leaf no-incoming-port {
           description "Exclude incoming port from the hash key";
           type empty;
         }
         leaf no-incoming-device {
           description "Exclude incoming device from the hash key";
           type empty;
         }
         leaf no-source-mac-address {
           description "Exclude source MAC address from the hash key";
           type empty;
         }
         leaf source-mac-address {
           description "Include source MAC address from the hash key";
           type empty;
         }
         leaf no-destination-mac-address {
           description "Exclude destination MAC address from the hash key";
           type empty;
         }
         leaf destination-mac-address {
           description "Include destination MAC address from the hash key";
           type empty;
         }
         leaf no-ether-type {
           description "Exclude ether type from the hash key";
           type empty;
         }
         leaf vlan-id {
           description "Include incoming vlan-id in hash key";
           type empty;
         }
         leaf no-vlan-id {
           description "Not include vlan-id in hash key";
           type empty;
         }
         leaf inner-vlan-id {
           description "Include incoming inner-vlan-id in hash key";
           type empty;
         }
       }
       container inet {
         description "Configure inet4 fields";
         uses apply-advanced;
         leaf no-incoming-port {
           description "Exclude incoming port from the hash key";
           type empty;
         }
         leaf no-incoming-device {
           description "Exclude incoming device from the hash key";
           type empty;
         }
         leaf no-l4-source-port {
           description "Exclude l4 source port from the hash key";
           type empty;
         }
         leaf no-l4-destination-port {
           description "Exclude l4 dest port from the hash key";
           type empty;
         }
         leaf no-protocol {
           description "Exclude protocol from the hash key";
           type empty;
         }
         leaf no-ipv4-source-address {
           description "Exclude IPv4 source address";
           type empty;
         }
         leaf no-ipv4-destination-address {
           description "Exclude IPv4 destination address";
           type empty;
         }
         leaf vlan-id {
           description "Include incoming vlan-id in hash key";
           type empty;
         }
       }
       container inet6 {
         description "Configure inet6 fields";
         uses apply-advanced;
         leaf no-incoming-port {
           description "Exclude incoming port from the hash key";
           type empty;
         }
         leaf no-incoming-device {
           description "Exclude incoming device from the hash key";
           type empty;
         }
         leaf no-l4-source-port {
           description "Exclude l4 source port from the hash key";
           type empty;
         }
         leaf no-l4-destination-port {
           description "Exclude l4 dest port from the hash key";
           type empty;
         }
         leaf ipv6-flow-label {
           description "Include IPv6 flow label";
           type empty;
         }
         leaf no-next-header {
           description "Exclude next header from the hash key";
           type empty;
         }
         leaf no-ipv6-source-address {
           description "Exclude IPv6 source address";
           type empty;
         }
         leaf no-ipv6-destination-address {
           description "Exclude IPv6 destination address";
           type empty;
         }
         leaf vlan-id {
           description "Include vlan-id in hash key";
           type empty;
         }
       }
       leaf no-mpls {
         description "Disable mpls in hash key";
         type empty;
       }
       container gre {
         description "Configure for GRE ";
         uses apply-advanced;
         leaf key {
           description "Include key in hash key";
           type empty;
         }
         leaf protocol {
           description "Include protocol in hash key";
           type empty;
         }
       }
       leaf vxlan-vnid {
         description "Enable vxlan-vnid";
         type empty;
       }
       container symmetric-hash {
         description "Enable symmetric hash for load-balancing";
         uses apply-advanced;
         leaf inet {
           description "Enable symmetric hash on ipv4 flows";
           type empty;
         }
         leaf inet6 {
           description "Enable symmetric hash on ipv6 flows";
           type empty;
         }
       }
       container services-loadbalancing {
         description "Select key to load balance across service PICs";
         uses apply-advanced;
         container family {
           description "Protocol family";
           container inet {
             description "IPv4 protocol family";
             uses apply-advanced;
             container layer-3-services {
               description "Include Layer 3 (IP) data in the hash key";
               uses apply-advanced;
               leaf source-address {
                 description "Include IP source address in the hash key";
                 type empty;
               }
               leaf destination-address {
                 description "Include IP destination address in the hash key";
                 type empty;
               }
               leaf incoming-interface-index {
                 description "Include incoming interface index in the hash key";
                 type empty;
               }
             }
           }
           container inet6 {
             description "IPv6 protocol family";
             uses apply-advanced;
             container layer-3-services {
               description "Include Layer 3 (IP) data in the hash key";
               uses apply-advanced;
               leaf source-address {
                 description "Include IP source address in the hash key";
                 type empty;
               }
               leaf destination-address {
                 description "Include IP destination address in the hash key";
                 type empty;
               }
               leaf incoming-interface-index {
                 description "Include incoming interface index in the hash key";
                 type empty;
               }
               leaf src-prefix-len {
                 description "Enhanced hash key inet6 source prefix length";
                 default "127";
                 units "bits";
                 type union {
                   type string {
                     pattern "<.*>|$.*";
                   }
                   type uint32 {
                     range "56 .. 127";
                   }
                 }
               }
             }
           }
         }
       }
       container source-destination-only-loadbalancing {
         description "Configure key for source/destination-ip-only load balancing";
         uses apply-advanced;
         container family {
           description "Protocol family";
           container inet {
             description "IPv4 protocol family";
             uses apply-advanced;
             leaf prefix-length {
               description "Source/Destination Only Load-Balancing inet prefix length";
               default "32";
               units "bits";
               type union {
                 type string {
                   pattern "<.*>|$.*";
                 }
                 type uint32 {
                   range "1 .. 32";
                 }
               }
             }
           }
           container inet6 {
             description "IPv6 protocol family";
             uses apply-advanced;
             leaf prefix-length {
               description "Source/Destination Only Load-Balancing inet6 prefix length";
               default "128";
               units "bits";
               type union {
                 type string {
                   pattern "<.*>|$.*";
                 }
                 type uint32 {
                   range "1 .. 128";
                 }
               }
             }
           }
         }
       }
       container family {
         description "Protocol family";
         container any {
           description "Applicable to all protocol families";
           uses apply-advanced;
           leaf incoming-interface-index {
             description "Include incoming interface index in the hash key";
             type empty;
           }
           leaf no-tunnel-payload {
             description "Omit tunnel payload in the hash key";
             type empty;
           }
         }
         container inet {
           description "IPv4 protocol family";
           uses apply-advanced;
           leaf incoming-interface-index {
             description "Include incoming interface index in the hash key";
             type empty;
           }
           leaf no-destination-port {
             description "Omit IP destination port in the hash key";
             type empty;
           }
           leaf no-source-port {
             description "Omit IP source port in the hash key";
             type empty;
           }
           leaf type-of-service {
             description "Include TOS byte in the hash key";
             type empty;
           }
           leaf gtp-tunnel-endpoint-identifier {
             description "Include TEID in the hash key for GTP-U packets";
             type empty;
           }
           leaf l2tp-tunnel-session-identifier {
             description "Include TID SID in the hash key for L2TP packets";
             type empty;
           }
           leaf session-id {
             description "Include session ID in the enhanced hash key";
             type empty;
           }
         }
         container inet6 {
           description "IPv6 protocol family";
           uses apply-advanced;
           leaf incoming-interface-index {
             description "Include incoming interface index in the hash key";
             type empty;
           }
           leaf traffic-class {
             description "Include Traffic Class byte in the hash key";
             type empty;
           }
           leaf no-destination-port {
             description "Omit IP destination port in the hash key";
             type empty;
           }
           leaf no-source-port {
             description "Omit IP source port in the hash key";
             type empty;
           }
           leaf gtp-tunnel-endpoint-identifier {
             description "Include TEID in the hash key for GTP-U packets";
             type empty;
           }
           leaf session-id {
             description "Include session ID in the enhanced hash key";
             type empty;
           }
           leaf no-flow-label {
             description "Omit Flow label in the hash key";
             type empty;
           }
           leaf type-of-service {
             description "Include TOS byte in the hash key";
             status deprecated;
             type empty;
           }
         }
         container mpls {
           description "MPLS protocol family";
           uses apply-advanced;
           leaf label-1-exp {
             description "Include EXP of first MPLS label from the hash key";
             type empty;
           }
           leaf incoming-interface-index {
             description "Include incoming interface index in the hash key";
             type empty;
           }
           choice pseudowire_option {
             case case_1 {
               leaf no-ether-pseudowire {
                 description "Omit IP payload over ethernet PW from the hash-key";
                 type empty;
               }
             }
             case case_2 {
               container ether-pseudowire {
                 description "Load-balance IP over ethernet PW";
                 leaf zero-control-word {
                   description "Parse zero control word in packet header";
                   type empty;
                 }
               }
             }
           }
           leaf no-labels {
             description "Exclude all MPLS labels from hash key";
             type empty;
           }
           leaf no-payload {
             description "Omit MPLS payload data from the hash key";
             type empty;
           }
         }
         container multiservice {
           description "Multiservice protocol (bridged/CCC/VPLS) family";
           uses apply-advanced;
           leaf incoming-interface-index {
             description "Include incoming interface index in hash key";
             type empty;
           }
           leaf outer-priority {
             description "Include Outer 802.1 Priority bits in the hash key";
             type empty;
           }
           leaf no-payload {
             description "Omit payload data from the hash key";
             type empty;
           }
           leaf no-mac-addresses {
             description "Omit source and destination MAC addresses from the hash key";
             type empty;
           }
         }
       }
       container hash-function {
         description "Configure hash functions";
         uses apply-advanced;
         choice instance {
           case case_1 {
             leaf CRC16-CCITT {
               description "16-bit CRC16 using CCITT polynomial";
               type empty;
             }
           }
           case case_2 {
             leaf CRC16 {
               description "16-bit CRC16 calculated using the BISYNC polynomial";
               type empty;
             }
           }
           case case_3 {
             leaf CRC16XOR1 {
               description "Upper 8 bits BISYNC CRC16 and 8 bit XOR1";
               type empty;
             }
           }
           case case_4 {
             leaf CRC16XOR2 {
               description "Upper 8 bit BISYNC CRC16 and 8 bit XOR2";
               type empty;
             }
           }
           case case_5 {
             leaf CRC16XOR4 {
               description "Upper 8 bit BISYNC CRC16 and 8 bit XOR4";
               type empty;
             }
           }
           case case_6 {
             leaf CRC16XOR8 {
               description "Upper 8 bit BISYNC CRC16 and 8 bit XOR8";
               type empty;
             }
           }
           case case_7 {
             leaf CRC32HI {
               description "16 LSBs of computed CRC32";
               type empty;
             }
           }
           case case_8 {
             leaf CRC32LO {
               description "16 MSBs of computed CRC32";
               type empty;
             }
           }
           case case_9 {
             container xor {
               presence "enable xor";
               description "XOR based hashing";
               uses apply-advanced;
               leaf no-L3-L4-headers {
                 description "Exclude source IP, dest IP, source L4 port, dest L4 port addresses from hashing";
                 type empty;
               }
               leaf no-L4-ports {
                 description "Exclude source L4 port and dest L4 port addresses from hashing";
                 type empty;
               }
               leaf mac-addresses {
                 description "Include source and destination MAC addresses in IPv4/IPv6 packet hashing";
                 type empty;
               }
               leaf no-mpls-hash {
                 description "Exclude MPLS information from hashing";
                 type empty;
               }
               leaf no-ipv4-source-address {
                 description "Exclude source IPv4 address from hashing";
                 type empty;
               }
               leaf no-ipv4-destination-address {
                 description "Exclude dest IPv4 address from hashing";
                 type empty;
               }
               leaf no-ipv6-source-address {
                 description "Exclude source IPv6 address from hashing";
                 type empty;
               }
               leaf no-ipv6-destination-address {
                 description "Exclude dest IPv6 address from hashing";
                 type empty;
               }
               leaf no-ip6-flow-label {
                 description "Exclude IPv6 flow label from hashing";
                 type empty;
               }
               leaf en-ip-over-mpls {
                 description "Enable parsing of IP in MPLS packets";
                 type empty;
               }
               leaf no-mpls-label0 {
                 description "Exclude MPLS Label 0 from hashing";
                 type empty;
               }
               leaf no-mpls-label1 {
                 description "Exclude MPLS Label 1 from hashing";
                 type empty;
               }
               leaf no-source-mac-address {
                 description "Exclude source MAC address from hashing";
                 type empty;
               }
               leaf no-destination-mac-address {
                 description "Exclude dest MAC address from hashing";
                 type empty;
               }
               leaf no-l4-source-port {
                 description "Exclude l4 source port from the hash key";
                 type empty;
               }
               leaf no-l4-destination-port {
                 description "Exclude l4 dest port from the hash key";
                 type empty;
               }
             }
           }
           case case_10 {
             leaf ingress-port {
               description "Ingress port based hashing";
               type empty;
             }
           }
           case case_11 {
             container crc6 {
               presence "enable crc6";
               description "CRC6 based hashing";
               uses apply-advanced;
               leaf crc6-seed {
                 description "CRC6 seed value";
                 type union {
                   type string {
                     pattern "<.*>|$.*";
                   }
                   type uint32 {
                     range "0 .. 63";
                   }
                 }
               }
               leaf en-ip-over-mpls {
                 description "Enable parsing of IP in MPLS packets";
                 type empty;
               }
               leaf no-source-mac-address {
                 description "Exclude source MAC address from hashing";
                 type empty;
               }
               leaf no-destination-mac-address {
                 description "Exclude dest MAC address from hashing";
                 type empty;
               }
               leaf no-mpls-label0 {
                 description "Exclude MPLS Label 0 from hashing";
                 type empty;
               }
               leaf no-mpls-label1 {
                 description "Exclude MPLS Label 1 from hashing";
                 type empty;
               }
               leaf no-l4-source-port {
                 description "Exclude l4 source port from the hash key";
                 type empty;
               }
               leaf no-l4-destination-port {
                 description "Exclude l4 dest port from the hash key";
                 type empty;
               }
               leaf no-ip-source-address {
                 description "Exclude source IPv4/IPv6 address from hashing";
                 type empty;
               }
               leaf no-ip-destination-address {
                 description "Exclude dest IPv4/IPv6 address from hashing";
                 type empty;
               }
               leaf no-ip6-flow-label {
                 description "Exclude IPv6 flow label from hashing";
                 type empty;
               }
             }
           }
           case case_12 {
             container crc16 {
               presence "enable crc16";
               description "CRC16 based hashing";
               uses apply-advanced;
               leaf crc16-seed {
                 description "CRC16 seed value";
                 type union {
                   type string {
                     pattern "<.*>|$.*";
                   }
                   type uint32 {
                     range "0 .. 65535";
                   }
                 }
               }
               leaf en-ip-over-mpls {
                 description "Enable parsing of IP in MPLS packets";
                 type empty;
               }
               leaf no-source-mac-address {
                 description "Exclude source MAC address from hashing";
                 type empty;
               }
               leaf no-destination-mac-address {
                 description "Exclude dest MAC address from hashing";
                 type empty;
               }
               leaf no-mpls-label0 {
                 description "Exclude MPLS Label 0 from hashing";
                 type empty;
               }
               leaf no-mpls-label1 {
                 description "Exclude MPLS Label 1 from hashing";
                 type empty;
               }
               leaf no-l4-source-port {
                 description "Exclude l4 source port from the hash key";
                 type empty;
               }
               leaf no-l4-destination-port {
                 description "Exclude l4 dest port from the hash key";
                 type empty;
               }
               leaf no-ip-source-address {
                 description "Exclude source IPv4/IPv6 address from hashing";
                 type empty;
               }
               leaf no-ip-destination-address {
                 description "Exclude dest IPv4/IPv6 address from hashing";
                 type empty;
               }
               leaf no-ip6-flow-label {
                 description "Exclude IPv6 flow label from hashing";
                 type empty;
               }
             }
           }
         }
       }
       container vxlan {
         description "Vxlan traffic";
         uses apply-advanced;
         leaf no-inner-payload {
           description "To enable load-balancing on Vxlan traffic based on outer IP/UDP header";
           type empty;
         }
       }
       list conditional-match {
         key name;
         ordered-by user;
         description "Configures a conditional match";
         leaf name {
           description "Name identifier";
           type string;
         }
         uses apply-advanced;
         container offset1 {
           presence "enable offset1";
           description "Configure offset 1";
           uses apply-advanced;
           leaf base-offset1 {
             description "Configure base-offset";
             type enumeration {
               enum "start-of-L2Header" {
                 description "Offset will be extracted from start of L2 header";
               }
               enum "start-of-L3-OuterHeader" {
                 description "Offset will be extracted from start of outer L3 header";
               }
               enum "start-of-L3-InnerHeader" {
                 description "Offset will be extracted from start of inner L3 header";
               }
               enum "start-of-L4-Header" {
                 description "Offset will be extracted from start of L4 header";
               }
             }
           }
           leaf offset1-value {
             description "Offset of the data to be extracted from the base offset. Only even number";
             type union {
               type string {
                 pattern "<.*>|$.*";
               }
               type uint8 {
                 range "0 .. 126";
               }
             }
           }
           leaf matchdata1 {
             description "Data to be matched";
             type string {
               length 4;
               junos:posix-pattern "^[[:xdigit:]]+$";
               junos:pattern-message "Must be hexadecimal digits (0-9, a-f, A-F)";
             }
           }
           leaf matchdata1-mask {
             description "Matchdata mask";
             type string {
               length 4;
               junos:posix-pattern "^[[:xdigit:]]+$";
               junos:pattern-message "Must be hexadecimal digits (0-9, a-f, A-F)";
             }
           }
         }
         container offset2 {
           presence "enable offset2";
           description "Configure offset 2";
           uses apply-advanced;
           leaf base-offset2 {
             description "Configure base-offset";
             type enumeration {
               enum "start-of-L2Header" {
                 description "Offset will be extracted from start of L2 header";
               }
               enum "start-of-L3-OuterHeader" {
                 description "Offset will be extracted from start of outer L3 header";
               }
               enum "start-of-L3-InnerHeader" {
                 description "Offset will be extracted from start of inner L3 header";
               }
               enum "start-of-L4-Header" {
                 description "Offset will be extracted from start of L4 header";
               }
             }
           }
           leaf offset2-value {
             description "Offset of the data to be extracted from the base offset. Only even number";
             type union {
               type string {
                 pattern "<.*>|$.*";
               }
               type uint8 {
                 range "0 .. 126";
               }
             }
           }
           leaf matchdata2 {
             description "Data to be matched";
             type string {
               length 4;
               junos:posix-pattern "^[[:xdigit:]]+$";
               junos:pattern-message "Must be hexadecimal digits (0-9, a-f, A-F)";
             }
           }
           leaf matchdata2-mask {
             description "Matchdata mask";
             type string {
               length 4;
               junos:posix-pattern "^[[:xdigit:]]+$";
               junos:pattern-message "Must be hexadecimal digits (0-9, a-f, A-F)";
             }
           }
         }
         container offset3 {
           presence "enable offset3";
           description "Configure offset 3";
           uses apply-advanced;
           leaf base-offset3 {
             description "Configure base-offset";
             type enumeration {
               enum "start-of-L2Header" {
                 description "Offset will be extracted from start of L2 header";
               }
               enum "start-of-L3-OuterHeader" {
                 description "Offset will be extracted from start of outer L3 header";
               }
               enum "start-of-L3-InnerHeader" {
                 description "Offset will be extracted from start of inner L3 header";
               }
               enum "start-of-L4-Header" {
                 description "Offset will be extracted from start of L4 header";
               }
             }
           }
           leaf offset3-value {
             description "Offset of the data to be extracted from the base offset. Only even number";
             type union {
               type string {
                 pattern "<.*>|$.*";
               }
               type uint8 {
                 range "0 .. 126";
               }
             }
           }
           leaf matchdata3 {
             description "Data to be matched";
             type string {
               length 4;
               junos:posix-pattern "^[[:xdigit:]]+$";
               junos:pattern-message "Must be hexadecimal digits (0-9, a-f, A-F)";
             }
           }
           leaf matchdata3-mask {
             description "Matchdata mask";
             type string {
               length 4;
               junos:posix-pattern "^[[:xdigit:]]+$";
               junos:pattern-message "Must be hexadecimal digits (0-9, a-f, A-F)";
             }
           }
         }
         container offset4 {
           presence "enable offset4";
           description "Configure offset 4";
           uses apply-advanced;
           leaf base-offset4 {
             description "Configure base-offset";
             type enumeration {
               enum "start-of-L2Header" {
                 description "Offset will be extracted from start of L2 header";
               }
               enum "start-of-L3-OuterHeader" {
                 description "Offset will be extracted from start of outer L3 header";
               }
               enum "start-of-L3-InnerHeader" {
                 description "Offset will be extracted from start of inner L3 header";
               }
               enum "start-of-L4-Header" {
                 description "Offset will be extracted from start of L4 header";
               }
             }
           }
           leaf offset4-value {
             description "Offset of the data to be extracted from the base offset. Only even number";
             type union {
               type string {
                 pattern "<.*>|$.*";
               }
               type uint8 {
                 range "0 .. 126";
               }
             }
           }
           leaf matchdata4 {
             description "Data to be matched";
             type string {
               length 4;
               junos:posix-pattern "^[[:xdigit:]]+$";
               junos:pattern-message "Must be hexadecimal digits (0-9, a-f, A-F)";
             }
           }
           leaf matchdata4-mask {
             description "Matchdata mask";
             type string {
               length 4;
               junos:posix-pattern "^[[:xdigit:]]+$";
               junos:pattern-message "Must be hexadecimal digits (0-9, a-f, A-F)";
             }
           }
         }
       }
       list flex-hashing {
         key name;
         ordered-by user;
         description "Set flex hashing";
         leaf name {
           description "Name identifier";
           type string;
         }
         uses apply-advanced;
         container ethtype {
           presence "enable ethtype";
           description "Configure ether-type of packet";
           uses apply-advanced;
           container inet {
             description "Enable flex-hashing on ipv4";
             uses apply-advanced;
             leaf interface {
               description "Incoming interface name. This is optional parameter";
               type union {
                 type jt:interface-name;
                 type string {
                   pattern "<.*>|$.*";
                 }
               }
             }
             leaf conditional-match {
               description "Conditional match to be matched in the packet";
               type string;
             }
             container hash-offset {
               description "Configure the offsets for hashing";
               uses apply-advanced;
               container offset1 {
                 presence "enable offset1";
                 description "Configure offset 1 value";
                 uses apply-advanced;
                 leaf base-offset1 {
                   description "Configure base-offset";
                   type enumeration {
                     enum "start-of-L2Header" {
                       description "Offset will be extracted from start of L2 header";
                     }
                     enum "start-of-L3-OuterHeader" {
                       description "Offset will be extracted from start of outer L3 header";
                     }
                     enum "start-of-L3-InnerHeader" {
                       description "Offset will be extracted from start of inner L3 header";
                     }
                     enum "start-of-L4-Header" {
                       description "Offset will be extracted from start of L4 header";
                     }
                   }
                 }
                 leaf offset1-value {
                   description "Offset of the data to be extracted from the base offset. Only even number";
                   type union {
                     type string {
                       pattern "<.*>|$.*";
                     }
                     type uint8 {
                       range "0 .. 126";
                     }
                   }
                 }
                 leaf offset1-mask {
                   description "Mask for the hash data extracted. 2 byte mask";
                   type string {
                     length 4;
                     junos:posix-pattern "^[[:xdigit:]]+$";
                     junos:pattern-message "Must be hexadecimal digits (0-9, a-f, A-F)";
                   }
                 }
                 container offset2 {
                   presence "enable offset2";
                   description "Configure offset 2 value";
                   uses apply-advanced;
                   leaf base-offset2 {
                     description "Configure base-offset";
                     type enumeration {
                       enum "start-of-L2Header" {
                         description "Offset will be extracted from start of L2 header";
                       }
                       enum "start-of-L3-OuterHeader" {
                         description "Offset will be extracted from start of outer L3 header";
                       }
                       enum "start-of-L3-InnerHeader" {
                         description "Offset will be extracted from start of inner L3 header";
                       }
                       enum "start-of-L4-Header" {
                         description "Offset will be extracted from start of L4 header";
                       }
                     }
                   }
                   leaf offset2-value {
                     description "Offset of the data to be extracted from the base offset. Only even number";
                     type union {
                       type string {
                         pattern "<.*>|$.*";
                       }
                       type uint8 {
                         range "0 .. 126";
                       }
                     }
                   }
                   leaf offset2-mask {
                     description "Mask for the hash data extracted. 2 byte mask";
                     type string {
                       length 4;
                       junos:posix-pattern "^[[:xdigit:]]+$";
                       junos:pattern-message "Must be hexadecimal digits (0-9, a-f, A-F)";
                     }
                   }
                 }
               }
             }
           }
           container inet6 {
             description "Enable flex-hashing on ipv6";
             uses apply-advanced;
             leaf interface {
               description "Incoming interface name. This is optional parameter";
               type union {
                 type jt:interface-name;
                 type string {
                   pattern "<.*>|$.*";
                 }
               }
             }
             leaf conditional-match {
               description "Conditional match to be matched in the packet";
               type string;
             }
             container hash-offset {
               description "Configure the offsets for hashing";
               uses apply-advanced;
               container offset1 {
                 presence "enable offset1";
                 description "Configure offset 1 value";
                 uses apply-advanced;
                 leaf base-offset1 {
                   description "Configure base-offset";
                   type enumeration {
                     enum "start-of-L2Header" {
                       description "Offset will be extracted from start of L2 header";
                     }
                     enum "start-of-L3-OuterHeader" {
                       description "Offset will be extracted from start of outer L3 header";
                     }
                     enum "start-of-L3-InnerHeader" {
                       description "Offset will be extracted from start of inner L3 header";
                     }
                     enum "start-of-L4-Header" {
                       description "Offset will be extracted from start of L4 header";
                     }
                   }
                 }
                 leaf offset1-value {
                   description "Offset of the data to be extracted from the base offset. Only even number";
                   type union {
                     type string {
                       pattern "<.*>|$.*";
                     }
                     type uint8 {
                       range "0 .. 126";
                     }
                   }
                 }
                 leaf offset1-mask {
                   description "Mask for the hash data extracted. 2 byte mask";
                   type string {
                     length 4;
                     junos:posix-pattern "^[[:xdigit:]]+$";
                     junos:pattern-message "Must be hexadecimal digits (0-9, a-f, A-F)";
                   }
                 }
                 container offset2 {
                   presence "enable offset2";
                   description "Configure offset 2 value";
                   uses apply-advanced;
                   leaf base-offset2 {
                     description "Configure base-offset";
                     type enumeration {
                       enum "start-of-L2Header" {
                         description "Offset will be extracted from start of L2 header";
                       }
                       enum "start-of-L3-OuterHeader" {
                         description "Offset will be extracted from start of outer L3 header";
                       }
                       enum "start-of-L3-InnerHeader" {
                         description "Offset will be extracted from start of inner L3 header";
                       }
                       enum "start-of-L4-Header" {
                         description "Offset will be extracted from start of L4 header";
                       }
                     }
                   }
                   leaf offset2-value {
                     description "Offset of the data to be extracted from the base offset. Only even number";
                     type union {
                       type string {
                         pattern "<.*>|$.*";
                       }
                       type uint8 {
                         range "0 .. 126";
                       }
                     }
                   }
                   leaf offset2-mask {
                     description "Mask for the hash data extracted. 2 byte mask";
                     type string {
                       length 4;
                       junos:posix-pattern "^[[:xdigit:]]+$";
                       junos:pattern-message "Must be hexadecimal digits (0-9, a-f, A-F)";
                     }
                   }
                 }
               }
             }
           }
           container mpls {
             description "Configure number of MPLS labels";
             uses apply-advanced;
             leaf num-labels {
               description "Configure number of MPLS labels";
               type union {
                 type string {
                   pattern "<.*>|$.*";
                 }
                 type uint8 {
                   range "1 .. 5";
                 }
               }
             }
             leaf interface {
               description "Incoming interface name. This is optional parameter";
               type union {
                 type jt:interface-name;
                 type string {
                   pattern "<.*>|$.*";
                 }
               }
             }
             leaf conditional-match {
               description "Conditional match to be matched in the packet";
               type string;
             }
             container hash-offset {
               description "Configure the offsets for hashing";
               uses apply-advanced;
               container offset1 {
                 presence "enable offset1";
                 description "Configure offset 1 value";
                 uses apply-advanced;
                 leaf base-offset1 {
                   description "Configure base-offset";
                   type enumeration {
                     enum "start-of-L2Header" {
                       description "Offset will be extracted from start of L2 header";
                     }
                     enum "start-of-L3-OuterHeader" {
                       description "Offset will be extracted from start of outer L3 header";
                     }
                     enum "start-of-L3-InnerHeader" {
                       description "Offset will be extracted from start of inner L3 header";
                     }
                     enum "start-of-L4-Header" {
                       description "Offset will be extracted from start of L4 header";
                     }
                   }
                 }
                 leaf offset1-value {
                   description "Offset of the data to be extracted from the base offset. Only even number";
                   type union {
                     type string {
                       pattern "<.*>|$.*";
                     }
                     type uint8 {
                       range "0 .. 126";
                     }
                   }
                 }
                 leaf offset1-mask {
                   description "Mask for the hash data extracted. 2 byte mask";
                   type string {
                     length 4;
                     junos:posix-pattern "^[[:xdigit:]]+$";
                     junos:pattern-message "Must be hexadecimal digits (0-9, a-f, A-F)";
                   }
                 }
                 container offset2 {
                   presence "enable offset2";
                   description "Configure offset 2 value";
                   uses apply-advanced;
                   leaf base-offset2 {
                     description "Configure base-offset";
                     type enumeration {
                       enum "start-of-L2Header" {
                         description "Offset will be extracted from start of L2 header";
                       }
                       enum "start-of-L3-OuterHeader" {
                         description "Offset will be extracted from start of outer L3 header";
                       }
                       enum "start-of-L3-InnerHeader" {
                         description "Offset will be extracted from start of inner L3 header";
                       }
                       enum "start-of-L4-Header" {
                         description "Offset will be extracted from start of L4 header";
                       }
                     }
                   }
                   leaf offset2-value {
                     description "Offset of the data to be extracted from the base offset. Only even number";
                     type union {
                       type string {
                         pattern "<.*>|$.*";
                       }
                       type uint8 {
                         range "0 .. 126";
                       }
                     }
                   }
                   leaf offset2-mask {
                     description "Mask for the hash data extracted. 2 byte mask";
                     type string {
                       length 4;
                       junos:posix-pattern "^[[:xdigit:]]+$";
                       junos:pattern-message "Must be hexadecimal digits (0-9, a-f, A-F)";
                     }
                   }
                 }
               }
             }
           }
         }
       }
       leaf symmetric {
         description "Enable symmetric load-balancing";
         type empty;
       }
     }
     container next-hop {
       description "Next hop throttle";
       uses apply-advanced;
       leaf arp-throttle {
         description "Change the arp throttling time(seconds)";
         type union {
           type string {
             pattern "<.*>|$.*";
           }
           type uint16 {
             range "10 .. 100";
           }
         }
       }
       leaf arp-detect {
         description "Change the arp throttling detect time(milliseconds)";
         type union {
           type string {
             pattern "<.*>|$.*";
           }
           type uint32 {
             range "1 .. 100000";
           }
         }
       }
     }
     container sflow {
       description "Sflow related";
       uses apply-advanced;
       container egress-multicast {
         description "Sflow for egress multicast";
         uses apply-advanced;
         leaf enable {
           description "To enable sflow for egress multicast";
           type empty;
         }
         leaf max-replication-rate {
           description "To configure max replication rate (0 to 2K pps)";
           type union {
             type string {
               pattern "<.*>|$.*";
             }
             type uint32 {
               range "0 .. 2000";
             }
           }
         }
       }
     }
     container multicast {
       description "Multicast resolve and mismatch rate";
       uses apply-advanced;
       leaf resolve-rate {
         description "Multicast resolve rate";
         units "per second";
         type union {
           type string {
             pattern "<.*>|$.*";
           }
           type uint32 {
             range "100 .. 1000";
           }
         }
       }
       leaf mismatch-rate {
         description "Multicast interface mismatch rate";
         units "per second";
         type union {
           type string {
             pattern "<.*>|$.*";
           }
           type uint32 {
             range "50 .. 1000";
           }
         }
       }
       container policer {
         presence "enable policer";
         uses apply-advanced;
         leaf bandwidth-limit {
           description "Bandwidth limit";
           units "bits per second";
           type string;
         }
         leaf burst-size-limit {
           description "Burst size limit";
           units "bytes";
           type string;
         }
       }
     }
     container packet-capture-telemetry {
       description "Packet capture telemetry options";
       uses apply-advanced;
       container egress {
         description "Egress options";
         uses packet-capture-egress-intf-type;
       }
     }
     container rpf-loose-mode-discard {
       description "Configure rpf loose mode behavior";
       uses apply-advanced;
       container family {
         description "Protocol family";
         uses apply-advanced;
         leaf inet {
           description "Configure rpf loose mode behavior for IPv4";
           type empty;
         }
         leaf inet6 {
           description "Configure rpf loose mode behavior for IPv6";
           type empty;
         }
       }
     }
     leaf l2circuit-control-passthrough {
       description "Configure passthrough for control protocol packets on L2 Circuit";
       type empty;
     }
     container explicit-null-cos {
       presence "enable explicit-null-cos";
       description "Configure to use MPLS explicit null exp for COS classification";
       uses apply-advanced;
       leaf inet {
         description "Include family inet";
         type empty;
       }
       leaf inet6 {
         description "Include family inet6";
         type empty;
       }
     }
     container helpers {
       description "Port forwarding configuration";
       uses apply-advanced;
       container traceoptions {
         description "Trace options for helper";
         uses apply-advanced;
         leaf no-remote-trace {
           description "Disable remote tracing";
           junos:must "(\"system tracing\")";
           junos:must-message "'no-remote-trace' is valid only when [system tracing] is configured";
           type empty;
         }
         container file {
           description "Trace file information";
           leaf filename {
             description "Name of file in which to write trace information";
             type string {
               length "1 .. 1024";
               junos:posix-pattern "![/ %]";
               junos:pattern-message "Must not contain '/', % or a space";
             }
           }
           leaf size {
             description "Maximum trace file size";
             type string;
           }
           leaf files {
             description "Maximum number of trace files";
             default "3";
             type union {
               type string {
                 pattern "<.*>|$.*";
               }
               type uint32 {
                 range "2 .. 1000";
               }
             }
           }
           choice world-readable-choice {
             leaf world-readable {
               description "Allow any user to read the log file";
               type empty;
             }
             leaf no-world-readable {
               description "Don't allow any user to read the log file";
               type empty;
             }
           }
           leaf match {
             description "Regular expression for lines to be logged";
             type jt:regular-expression;
           }
         }
         leaf level {
           description "Level of debugging output";
           default "error";
           type enumeration {
             enum "error" {
               description "Match error conditions";
             }
             enum "warning" {
               description "Match warning messages";
             }
             enum "notice" {
               description "Match conditions that should be handled specially";
             }
             enum "info" {
               description "Match informational messages";
             }
             enum "verbose" {
               description "Match verbose messages";
             }
             enum "all" {
               description "Match all levels";
             }
           }
         }
         list flag {
           key name;
           ordered-by user;
           description "Area of UDP forwarding helper process on which to enable debugging output";
           leaf name {
             type enumeration {
               enum "trace" {
                 description "Trace tracing code";
               }
               enum "address" {
                 description "Trace address management code";
               }
               enum "main" {
                 description "Trace main loop code";
               }
               enum "config" {
                 description "Trace configuration code";
               }
               enum "ifdb" {
                 description "Trace interface database code";
               }
               enum "io" {
                 description "Trace I/O code";
               }
               enum "rtsock" {
                 description "Trace routing socket code";
               }
               enum "ui" {
                 description "Trace user interface code";
               }
               enum "util" {
                 description "Trace miscellaneous utility code";
               }
               enum "gencfg" {
                 description "Trace fud gencfg message";
               }
               enum "domain" {
                 description "Trace DNS service-specific code";
               }
               enum "tftp" {
                 description "Trace TFTP service-specific code";
               }
               enum "bootp" {
                 description "Trace BOOTP/DHCP service-specific code";
               }
               enum "port" {
                 description "Trace arbitrary protocol code";
               }
               enum "if-rtsdb" {
                 description "Trace interface hierarchy rtsdb";
               }
               enum "all" {
                 description "Trace all areas of code";
               }
             }
           }
         }
       }
       container rtsdb-client-traceoptions {
         presence "enable rtsdb-client-traceoptions";
         description "SHM rtsock database client library trace options";
         status deprecated;
         uses apply-advanced;
         container if-rtsdb {
           presence "enable if-rtsdb";
           description "Trace interface hierarchy rtsdb";
           uses apply-advanced;
           list flag {
             key name;
             ordered-by user;
             description "Tracing parameters";
             leaf name {
               type enumeration {
                 enum "init" {
                   description "Trace initialization";
                 }
                 enum "routing-socket" {
                   description "Trace routing socket messages";
                 }
                 enum "map" {
                   description "Trace shared memory mapping";
                 }
                 enum "all" {
                   description "Trace all";
                 }
               }
             }
             leaf disable {
               description "Disable this trace flag";
               type empty;
             }
           }
         }
       }
       container domain {
         description "Incoming DNS request forwarding configuration";
         uses apply-advanced;
         leaf description {
           description "Text description of server";
           type string;
         }
         container server {
           description "Server information";
           leaf address {
             description "Name or address of server to which to forward";
             type jt:ipv4addr;
           }
           choice instance {
             case case_1 {
               container logical-system {
                 description "Logical system of server to which to forward";
                 leaf logical-system-name {
                   description "Name of logical system";
                   junos:must "(\"logical-systems $$\")";
                   junos:must-message "referenced logical system must be defined";
                   type string {
                     junos:posix-pattern "^[a-zA-Z0-9_-]{1,63}$";
                     junos:pattern-message "Logical-system name is a string consisting of up to 63 letters, numbers, dashes and underscores";
                   }
                 }
                 leaf routing-instance {
                   description "Routing instance of server to which to forward";
                   type union {
                     type string {
                       pattern "default";
                     }
                     type string {
                       junos:posix-pattern "!^((__.*__)|(all)|(.*[ ].*)|(\"\")|(.{129,}))$";
                       junos:pattern-message "Must be a non-reserved string of 128 characters or less with no spaces.";
                     }
                   }
                 }
               }
             }
             case case_2 {
               leaf routing-instance {
                 description "Routing instance of server to which to forward";
                 junos:must "(\"routing-instances $$\")";
                 junos:must-message "referenced routing instance must be defined";
                 type union {
                   type string {
                     pattern "default";
                   }
                   type string {
                     junos:posix-pattern "!^((__.*__)|(all)|(.*[ ].*)|(\"\")|(.{129,}))$";
                     junos:pattern-message "Must be a non-reserved string of 128 characters or less with no spaces.";
                   }
                 }
               }
             }
           }
         }
         list interface {
           key name;
           ordered-by user;
           description "Incoming DNS request forwarding interface configuration";
           leaf name {
             description "Name of interface or group of interfaces";
             type union {
               type jt:interface-wildcard;
               type string {
                 pattern "<.*>|$.*";
               }
             }
           }
           uses apply-advanced;
           leaf no-listen {
             description "Do not listen on this interface";
             type empty;
           }
           leaf broadcast {
             description "If the layer 2 interface is unknown then broadcast";
             type empty;
           }
           leaf description {
             description "Text description of server";
             type string;
           }
           container server {
             description "Server information";
             leaf address {
               description "Name or address of server to which to forward";
               type jt:ipv4addr;
             }
             choice instance {
               case case_1 {
                 container logical-system {
                   description "Logical system of server to which to forward";
                   leaf logical-system-name {
                     description "Name of logical system";
                     junos:must "(\"logical-systems $$\")";
                     junos:must-message "referenced logical system must be defined";
                     type string {
                       junos:posix-pattern "^[a-zA-Z0-9_-]{1,63}$";
                       junos:pattern-message "Logical-system name is a string consisting of up to 63 letters, numbers, dashes and underscores";
                     }
                   }
                   leaf routing-instance {
                     description "Routing instance of server to which to forward";
                     type union {
                       type string {
                         pattern "default";
                       }
                       type string {
                         junos:posix-pattern "!^((__.*__)|(all)|(.*[ ].*)|(\"\")|(.{129,}))$";
                         junos:pattern-message "Must be a non-reserved string of 128 characters or less with no spaces.";
                       }
                     }
                   }
                 }
               }
               case case_2 {
                 leaf routing-instance {
                   description "Routing instance of server to which to forward";
                   junos:must "(\"routing-instances $$\")";
                   junos:must-message "referenced routing instance must be defined";
                   type union {
                     type string {
                       pattern "default";
                     }
                     type string {
                       junos:posix-pattern "!^((__.*__)|(all)|(.*[ ].*)|(\"\")|(.{129,}))$";
                       junos:pattern-message "Must be a non-reserved string of 128 characters or less with no spaces.";
                     }
                   }
                 }
               }
             }
           }
         }
       }
       container tftp {
         description "Incoming TFTP request forwarding configuration";
         uses apply-advanced;
         leaf description {
           description "Text description of server";
           type string;
         }
         container server {
           description "Server information";
           leaf address {
             description "Name or address of server to which to forward";
             type jt:ipv4addr;
           }
           choice instance {
             case case_1 {
               container logical-system {
                 description "Logical system of server to which to forward";
                 leaf logical-system-name {
                   description "Name of logical system";
                   junos:must "(\"logical-systems $$\")";
                   junos:must-message "referenced logical system must be defined";
                   type string {
                     junos:posix-pattern "^[a-zA-Z0-9_-]{1,63}$";
                     junos:pattern-message "Logical-system name is a string consisting of up to 63 letters, numbers, dashes and underscores";
                   }
                 }
                 leaf routing-instance {
                   description "Routing instance of server to which to forward";
                   type union {
                     type string {
                       pattern "default";
                     }
                     type string {
                       junos:posix-pattern "!^((__.*__)|(all)|(.*[ ].*)|(\"\")|(.{129,}))$";
                       junos:pattern-message "Must be a non-reserved string of 128 characters or less with no spaces.";
                     }
                   }
                 }
               }
             }
             case case_2 {
               leaf routing-instance {
                 description "Routing instance of server to which to forward";
                 junos:must "(\"routing-instances $$\")";
                 junos:must-message "referenced routing instance must be defined";
                 type union {
                   type string {
                     pattern "default";
                   }
                   type string {
                     junos:posix-pattern "!^((__.*__)|(all)|(.*[ ].*)|(\"\")|(.{129,}))$";
                     junos:pattern-message "Must be a non-reserved string of 128 characters or less with no spaces.";
                   }
                 }
               }
             }
           }
         }
         list interface {
           key name;
           ordered-by user;
           description "Incoming TFTP request forwarding interface configuration";
           leaf name {
             description "Name of interface or group of interfaces";
             type union {
               type jt:interface-wildcard;
               type string {
                 pattern "<.*>|$.*";
               }
             }
           }
           uses apply-advanced;
           leaf no-listen {
             description "Do not listen on this interface";
             type empty;
           }
           leaf broadcast {
             description "If the layer 2 interface is unknown then broadcast";
             type empty;
           }
           leaf description {
             description "Text description of server";
             type string;
           }
           container server {
             description "Server information";
             leaf address {
               description "Name or address of server to which to forward";
               type jt:ipv4addr;
             }
             choice instance {
               case case_1 {
                 container logical-system {
                   description "Logical system of server to which to forward";
                   leaf logical-system-name {
                     description "Name of logical system";
                     junos:must "(\"logical-systems $$\")";
                     junos:must-message "referenced logical system must be defined";
                     type string {
                       junos:posix-pattern "^[a-zA-Z0-9_-]{1,63}$";
                       junos:pattern-message "Logical-system name is a string consisting of up to 63 letters, numbers, dashes and underscores";
                     }
                   }
                   leaf routing-instance {
                     description "Routing instance of server to which to forward";
                     type union {
                       type string {
                         pattern "default";
                       }
                       type string {
                         junos:posix-pattern "!^((__.*__)|(all)|(.*[ ].*)|(\"\")|(.{129,}))$";
                         junos:pattern-message "Must be a non-reserved string of 128 characters or less with no spaces.";
                       }
                     }
                   }
                 }
               }
               case case_2 {
                 leaf routing-instance {
                   description "Routing instance of server to which to forward";
                   junos:must "(\"routing-instances $$\")";
                   junos:must-message "referenced routing instance must be defined";
                   type union {
                     type string {
                       pattern "default";
                     }
                     type string {
                       junos:posix-pattern "!^((__.*__)|(all)|(.*[ ].*)|(\"\")|(.{129,}))$";
                       junos:pattern-message "Must be a non-reserved string of 128 characters or less with no spaces.";
                     }
                   }
                 }
               }
             }
           }
         }
       }
       container bootp {
         junos:must "(!(\"system autoinstallation\"))";
         junos:must-message "incompatible with 'system autoinstallation'";
         description "Incoming BOOTP/DHCP request forwarding configuration";
         uses apply-advanced;
         leaf relay-agent-option {
           description "Use DHCP Relay Agent option in relayed BOOTP/DHCP messages";
           type empty;
         }
         container dhcp-option82 {
           description "Configure DHCP option 82";
           presence "enable dhcp-option82";
           junos:must "(!(\"forwarding-options helpers bootp relay-agent-option\"))";
           junos:must-message "incompatible with relay-agent-option";
           uses dhcp-option82-type;
         }
         leaf description {
           description "Text description of servers";
           type string;
         }
         list server {
           key name;
           ordered-by user;
           description "Server information";
           leaf name {
             description "Name or address of servers to which to forward";
             type jt:ipv4addr;
           }
           uses apply-advanced;
           list logical-system {
             key name;
             ordered-by user;
             description "Logical system of server to which to forward";
             leaf name {
               description "Name of logical system";
               junos:must "(\"logical-systems $$\")";
               junos:must-message "referenced logical system must be defined";
               type string {
                 junos:posix-pattern "^[a-zA-Z0-9_-]{1,63}$";
                 junos:pattern-message "Logical-system name is a string consisting of up to 63 letters, numbers, dashes and underscores";
               }
             }
             leaf-list routing-instance {
               ordered-by user;
               description "Routing instance of server to which to forward";
               type string;
             }
           }
           leaf-list routing-instance {
             ordered-by user;
             description "Routing instance of server to which to forward";
             type string;
           }
         }
         leaf maximum-hop-count {
           description "Maximum number of hops per packet";
           default "4";
           type union {
             type string {
               pattern "<.*>|$.*";
             }
             type uint32 {
               range "1 .. 16";
             }
           }
         }
         leaf minimum-wait-time {
           description "Minimum number of seconds before requests are forwarded";
           default "0";
           type union {
             type string {
               pattern "<.*>|$.*";
             }
             type uint32 {
               range "0 .. 30000";
             }
           }
         }
         leaf client-response-ttl {
           description "IP time-to-live value to set in responses to client";
           type union {
             type string {
               pattern "<.*>|$.*";
             }
             type uint32 {
               range "1 .. 255";
             }
           }
         }
         leaf source-address-giaddr {
           description "Use GIADDR as the source IP address for relayed packets";
           type empty;
         }
         leaf vpn {
           description "Enable vpn encryption ";
           type empty;
         }
         leaf apply-secondary-as-giaddr {
           description "Enable DHCP relay to use secondary gateway ip on all interfaces";
           type empty;
         }
         list interface {
           key name;
           ordered-by user;
           description "Incoming BOOTP/DHCP request forwarding interface configuration";
           leaf name {
             description "Name of interface or group of interfaces";
             type union {
               type jt:interface-wildcard;
               type string {
                 pattern "<.*>|$.*";
               }
             }
           }
           uses apply-advanced;
           leaf no-listen {
             description "Do not listen on this interface";
             type empty;
           }
           leaf broadcast {
             description "If the layer 2 interface is unknown then broadcast";
             type empty;
           }
           leaf description {
             description "Text description of servers";
             type string;
           }
           list server {
             key name;
             ordered-by user;
             description "Server information";
             leaf name {
               description "Name or address of servers to which to forward";
               type jt:ipv4addr;
             }
             uses apply-advanced;
             list logical-system {
               key name;
               ordered-by user;
               description "Logical system of server to which to forward";
               leaf name {
                 description "Name of logical system";
                 junos:must "(\"logical-systems $$\")";
                 junos:must-message "referenced logical system must be defined";
                 type string {
                   junos:posix-pattern "^[a-zA-Z0-9_-]{1,63}$";
                   junos:pattern-message "Logical-system name is a string consisting of up to 63 letters, numbers, dashes and underscores";
                 }
               }
               leaf-list routing-instance {
                 ordered-by user;
                 description "Routing instance of server to which to forward";
                 type string;
               }
             }
             leaf-list routing-instance {
               ordered-by user;
               description "Routing instance of server to which to forward";
               type string;
             }
           }
           leaf maximum-hop-count {
             description "Maximum number of hops per packet";
             default "4";
             type union {
               type string {
                 pattern "<.*>|$.*";
               }
               type uint32 {
                 range "1 .. 16";
               }
             }
           }
           leaf minimum-wait-time {
             description "Minimum number of seconds before requests are forwarded";
             default "0";
             type union {
               type string {
                 pattern "<.*>|$.*";
               }
               type uint32 {
                 range "0 .. 30000";
               }
             }
           }
           leaf client-response-ttl {
             description "IP time-to-live value to set in responses to client";
             type union {
               type string {
                 pattern "<.*>|$.*";
               }
               type uint32 {
                 range "1 .. 255";
               }
             }
           }
           leaf source-address-giaddr {
             description "Use GIADDR as the source IP address for relayed packets";
             type empty;
           }
           leaf vpn {
             description "Enable vpn encryption ";
             type empty;
           }
           container dhcp-option82 {
             description "Configure DHCP option 82";
             presence "enable dhcp-option82";
             uses dhcp-option82-type;
           }
           leaf apply-secondary-as-giaddr {
             description "Enable DHCP relay to use secondary gateway ip on this interface";
             type empty;
           }
         }
       }
       list port {
         key name;
         ordered-by user;
         description "Incoming arbitrary protocol request forwarding configuration";
         leaf name {
           description "Port number of the protocol to listen";
           type union {
             type string {
               pattern "<.*>|$.*";
             }
             type uint32 {
               range "1 .. 65535";
             }
           }
         }
         uses apply-advanced;
         leaf description {
           description "Text description of server";
           type string;
         }
         list server {
           key name;
           ordered-by user;
           description "Server information";
           leaf name {
             description "Name or address of server to which to forward";
             type jt:ipv4addr;
           }
           uses apply-advanced;
           choice instance {
             case case_1 {
               container logical-system {
                 description "Logical system of server to which to forward";
                 leaf logical-system-name {
                   description "Name of logical system";
                   junos:must "(\"logical-systems $$\")";
                   junos:must-message "referenced logical system must be defined";
                   type string {
                     junos:posix-pattern "^[a-zA-Z0-9_-]{1,63}$";
                     junos:pattern-message "Logical-system name is a string consisting of up to 63 letters, numbers, dashes and underscores";
                   }
                 }
                 leaf routing-instance {
                   description "Routing instance of server to which to forward";
                   type union {
                     type string {
                       pattern "default";
                     }
                     type string {
                       junos:posix-pattern "!^((__.*__)|(all)|(.*[ ].*)|(\"\")|(.{129,}))$";
                       junos:pattern-message "Must be a non-reserved string of 128 characters or less with no spaces.";
                     }
                   }
                 }
               }
             }
             case case_2 {
               leaf routing-instance {
                 description "Routing instance of server to which to forward";
                 junos:must "(\"routing-instances $$\")";
                 junos:must-message "referenced routing instance must be defined";
                 type union {
                   type string {
                     pattern "default";
                   }
                   type string {
                     junos:posix-pattern "!^((__.*__)|(all)|(.*[ ].*)|(\"\")|(.{129,}))$";
                     junos:pattern-message "Must be a non-reserved string of 128 characters or less with no spaces.";
                   }
                 }
               }
             }
           }
         }
         list interface {
           key name;
           ordered-by user;
           description "Incoming request forwarding interface configuration";
           leaf name {
             description "Name of interface or group of interfaces";
             type union {
               type jt:interface-wildcard;
               type string {
                 pattern "<.*>|$.*";
               }
             }
           }
           uses apply-advanced;
           leaf no-listen {
             description "Do not listen on this interface";
             type empty;
           }
           leaf broadcast {
             description "If the layer 2 interface is unknown then broadcast";
             type empty;
           }
           leaf description {
             description "Text description of server";
             type string;
           }
           list server {
             key name;
             ordered-by user;
             description "Server information";
             leaf name {
               description "Name or address of server to which to forward";
               type jt:ipv4addr;
             }
             uses apply-advanced;
             choice instance {
               case case_1 {
                 container logical-system {
                   description "Logical system of server to which to forward";
                   leaf logical-system-name {
                     description "Name of logical system";
                     junos:must "(\"logical-systems $$\")";
                     junos:must-message "referenced logical system must be defined";
                     type string {
                       junos:posix-pattern "^[a-zA-Z0-9_-]{1,63}$";
                       junos:pattern-message "Logical-system name is a string consisting of up to 63 letters, numbers, dashes and underscores";
                     }
                   }
                   leaf routing-instance {
                     description "Routing instance of server to which to forward";
                     type union {
                       type string {
                         pattern "default";
                       }
                       type string {
                         junos:posix-pattern "!^((__.*__)|(all)|(.*[ ].*)|(\"\")|(.{129,}))$";
                         junos:pattern-message "Must be a non-reserved string of 128 characters or less with no spaces.";
                       }
                     }
                   }
                 }
               }
               case case_2 {
                 leaf routing-instance {
                   description "Routing instance of server to which to forward";
                   junos:must "(\"routing-instances $$\")";
                   junos:must-message "referenced routing instance must be defined";
                   type union {
                     type string {
                       pattern "default";
                     }
                     type string {
                       junos:posix-pattern "!^((__.*__)|(all)|(.*[ ].*)|(\"\")|(.{129,}))$";
                       junos:pattern-message "Must be a non-reserved string of 128 characters or less with no spaces.";
                     }
                   }
                 }
               }
             }
           }
         }
       }
     }
     container family {
       description "Protocol family";
       container inet {
         description "IPv4 parameters";
         uses apply-advanced;
         container filter {
           description "Filtering for forwarding table";
           uses apply-advanced;
           leaf input {
             description "Name of input filter to apply for forwarded packets";
             type string;
           }
           leaf output {
             description "Name of output filter to apply for forwarded packets";
             type string;
           }
         }
         leaf route-accounting {
           description "Enable IPv4 route accounting";
           type empty;
         }
       }
       container inet6 {
         description "IPv6 parameters";
         uses apply-advanced;
         container filter {
           description "Filtering for forwarding table";
           uses apply-advanced;
           leaf input {
             description "Name of input filter to apply for forwarded packets";
             type string;
           }
           leaf output {
             description "Name of output filter to apply for forwarded packets";
             type string;
           }
         }
         leaf route-accounting {
           description "Enable IPv6 route accounting";
           type empty;
         }
         leaf source-checking {
           description "Discard IPv6 packet when source address type is unspecified, loopback, multicast or link-local ";
           type empty;
         }
       }
       container mpls {
         description "MPLS parameters";
         uses apply-advanced;
         container filter {
           description "Filtering for forwarding table";
           uses apply-advanced;
           leaf input {
             description "Name of input filter to apply for forwarded packets";
             type string;
           }
           leaf output {
             description "Name of output filter to apply for forwarded packets";
             type string;
           }
         }
       }
       container vpls {
         description "VPLS parameters";
         uses apply-advanced;
         container filter {
           description "Filtering for VPLS DMAC forwarding table";
           uses apply-advanced;
           leaf input {
             description "Name of input filter to apply for forwarded packets";
             type string;
           }
         }
         container flood {
           description "Filtering for VPLS flood table";
           uses apply-advanced;
           leaf input {
             description "Name of input filter to apply for VPLS flood packets";
             type string;
           }
         }
       }
       container evpn {
         description "EVPN parameters";
         uses apply-advanced;
         container filter {
           description "Filtering for EVPN DMAC forwarding table";
           uses apply-advanced;
           leaf input {
             description "Name of input filter to apply for forwarded packets";
             type string;
           }
         }
         container flood {
           description "Filtering for EVPN flood table";
           uses apply-advanced;
           leaf input {
             description "Name of input filter to apply for EVPN flood packets";
             type string;
           }
         }
       }
     }
     list next-hop-group {
       key name;
       description "Next hop group forwarding option";
       uses juniper-next-hop-group-options;
     }
     container dhcp-relay {
       description "Dynamic Host Configuration Protocol relay configuration";
       junos:must "(!(\"system services dhcp\"))";
       junos:must-message "Incompatible with 'set system services dhcp'";
       junos:must "(!(\".. .. instance-type virtual-switch\"))";
       junos:must-message "forwarding-options dhcp-relay incompatible with routing-instances instance-type virtual-switch'";
       uses jdhcp-relay-type;
     }
     choice load-balance-label-capability-choice {
       leaf load-balance-label-capability {
         description "Load balance label capability";
         type empty;
       }
       leaf no-load-balance-label-capability {
         description "Don't load balance label capability";
         type empty;
       }
     }
     leaf fast-reroute-priority {
       description "Fast-reroute repair priority";
       junos:must "(\".. .. instance-type vpls\")";
       junos:must-message "'fast-reroute-priority' configuration can only be used for 'instance-type vpls'";
       type enumeration {
         enum "low" {
           description "Set priority to low";
         }
         enum "medium" {
           description "Set priority to medium";
         }
         enum "high" {
           description "Set priority to high";
         }
       }
     }
     list ip-options-protocol-queue {
       key name;
       ordered-by user;
       description "IP Options protocol logical queue parameters";
       leaf name {
         description "Protocol name";
         type string;
       }
       uses apply-advanced;
       leaf protocol-id {
         description "Protocol Identifier";
         type union {
           type string {
             pattern "<.*>|$.*";
           }
           type uint8 {
             range "1 .. 254";
           }
         }
       }
       leaf queue-depth {
         description "Size of the protocol logical options queue";
         type union {
           type string {
             pattern "<.*>|$.*";
           }
           type uint32 {
             range "1 .. 807";
           }
         }
       }
     }
     leaf link-layer-broadcast-inet-check {
       description "Enable destination mac and destination ip address check";
       type empty;
     }
     leaf cut-through {
       description "Enable cut-through forwarding";
       type empty;
     }
     container storm-control {
       presence "enable storm-control";
       description "Storm control config";
       uses apply-advanced;
       leaf enhanced {
         description "Enable enhanced storm control feature";
         type empty;
       }
     }
     leaf vrf-fallback {
       description "Enable vrf-fallback forwarding. This will restart PFE";
       type empty;
     }
     leaf mpls-tunnel-extend {
       description "Extend MPLS Tunnel table usage. This config will restart PFE";
       type empty;
     }
     leaf vxlan-disable-copy-tos-encap {
       description "Disable copy of TOS bits from Outer IP to Inner IP at VxLAN Tunnel Encap";
       type empty;
     }
     leaf vxlan-disable-copy-tos-decap {
       description "Disable copy of TOS bits from Outer IP to Inner IP at VxLAN Tunnel Decap";
       type empty;
     }
     leaf no-hierarchical-ecmp {
       description "Disable hierarchical ecmp. This will restart PFE";
       type empty;
     }
     leaf ipmc-miss-do-l2mc {
       description "Do L2MC forwarding when IPMC miss";
       type empty;
     }
     choice hyper-mode-choice {
       leaf hyper-mode {
         description "Enable hyper mode";
         type empty;
       }
       leaf no-hyper-mode {
         description "Don't enable hyper mode";
         type empty;
       }
     }
     leaf vxlan-flexflow {
       description "Enable VxLAN flexflow. This will restart PFE";
       type empty;
     }
     leaf ecmp-do-local-lookup {
       description "Do ECMP local lookup only";
       type empty;
     }
     container access-security {
       description "Access security configuration";
       uses jdhcp-access-security-type;
     }
     list forwarding-sandbox {
       key name;
       description "Create forwarding sandbox";
       max-elements 8;
       uses juniper-forwarding-sandbox-options;
     }
     container vxlan-routing {
       description "VXLAN Routing forwarding options";
       uses apply-advanced;
       leaf next-hop {
         description "Next-hop. Must be multiple of 4096. This will restart PFE";
         type union {
           type string {
             pattern "<.*>|$.*";
           }
           type uint32;
         }
       }
       leaf interface-num {
         description "Interface. Must be multiple of 2048. This will restart PFE";
         type union {
           type string {
             pattern "<.*>|$.*";
           }
           type uint32;
         }
       }
       leaf overlay-ecmp {
         description "Enable overlay ecmp for vxlan L3. This will restart PFE";
         type empty;
       }
       leaf loopback-port {
         description "AE loopback interface used for VXLAN routing. This will restart PFE";
         junos:must "(all \"interfaces $$ unit <*> family ethernet-switching interface-mode trunk\")";
         junos:must-message "Interface-mode trunk needs to be enabled for loopback AE";
         junos:must "(\"chassis aggregated-devices ethernet device-count\")";
         junos:must-message "Ethernet device-count needs to be configured for loopback AE";
         junos:must "(\"interfaces $$ aggregated-ether-options loopback\")";
         junos:must-message "Loopback needs to be enabled on the AE interface";
         type string;
       }
     }
     container satellite {
       description "Satellite forwarding options";
       uses apply-advanced;
       container traceoptions {
         description "Global tracing options for satellite control plane";
         uses apply-advanced;
         leaf no-remote-trace {
           description "Disable remote tracing";
           junos:must "(\"system tracing\")";
           junos:must-message "'no-remote-trace' is valid only when [system tracing] is configured";
           type empty;
         }
         container file {
           description "Trace file information";
           leaf filename {
             description "Name of file in which to write trace information";
             type string {
               length "1 .. 1024";
               junos:posix-pattern "![/ %]";
               junos:pattern-message "Must not contain '/', % or a space";
             }
           }
           leaf size {
             description "Maximum trace file size";
             type string;
           }
           leaf files {
             description "Maximum number of trace files";
             default "3";
             type union {
               type string {
                 pattern "<.*>|$.*";
               }
               type uint32 {
                 range "2 .. 1000";
               }
             }
           }
           choice world-readable-choice {
             leaf world-readable {
               description "Allow any user to read the log file";
               type empty;
             }
             leaf no-world-readable {
               description "Don't allow any user to read the log file";
               type empty;
             }
           }
           leaf match {
             description "Regular expression for lines to be logged";
             type jt:regular-expression;
           }
         }
         list flag {
           key name;
           ordered-by user;
           description "Tracing parameters";
           leaf name {
             type enumeration {
               enum "all" {
                 description "Trace everything";
               }
               enum "bd" {
                 description "Trace BD events";
               }
               enum "config-internal" {
                 description "Trace configuration internals";
               }
               enum "interface" {
                 description "Trace interface events";
               }
               enum "interface-vlan" {
                 description "Trace IFBD events";
               }
               enum "ipc" {
                 description "Trace internal IPC messages";
               }
               enum "kernel" {
                 description "Trace Kernel messages";
               }
               enum "krt" {
                 description "Trace communication over routing socket";
               }
               enum "mac" {
                 description "Trace MAC events ";
               }
               enum "nh" {
                 description "Trace NH events";
               }
               enum "normal" {
                 description "Trace normal events";
               }
               enum "parse" {
                 description "Trace configuration parsing";
               }
               enum "stp" {
                 description "Trace STP events";
               }
               enum "task" {
                 description "Trace task processing";
               }
               enum "timer" {
                 description "Trace task timer processing";
               }
               enum "firewall" {
                 description "Trace firewall processing";
               }
               enum "l3" {
                 description "Trace Layer-3 processing";
               }
               enum "fip-snooping" {
                 description "Trace FIP-Snooping processing";
               }
             }
           }
         }
       }
       leaf local-replication {
         description "Enable satellite multicast replication";
         type empty;
       }
       list fpc {
         key name;
         leaf name {
           description "Satellite slot identifier";
           type union {
             type string {
               pattern "<.*>|$.*";
             }
             type uint32 {
               range "65 .. 254";
             }
           }
         }
         uses apply-advanced;
         choice local-switching-mode-choice {
           case case_1 {
             container local-switching {
               presence "enable local-switching";
               description "Enable local-switching on Satellite device";
               uses apply-advanced;
               leaf l3 {
                 description "Enable L3 local switching on the Satellite device";
                 type empty;
               }
             }
           }
           case case_2 {
             container selective-vlan-switching {
               description "Enable selective-vlan-switching on Satellite device";
               uses apply-advanced;
               leaf routing-instance {
                 description "Associated Routing instance name";
                 type string {
                   junos:posix-pattern "!^((__.*__)|(all)|(.*[ ].*)|(\"\")|(.{129,}))$";
                   junos:pattern-message "Must be a non-reserved string of 128 characters or less with no spaces.";
                 }
               }
             }
           }
         }
       }
       container vlan-auto-sense {
         description "Vlan-auto-sense attributes provisioning";
         uses apply-advanced;
         leaf expiry-time {
           description "Expiry time (in seconds) after last MAC aged out";
           default "600";
           units "seconds";
           type union {
             type string {
               pattern "<.*>|$.*";
             }
             type uint32 {
               range "30 .. 3600";
             }
           }
         }
       }
       container analyzer-vlan {
         description "Output VLAN for Analyzer";
         uses apply-advanced;
         leaf vlan-name {
           description "Name of the analyzer VLAN";
           type string;
         }
       }
       choice disable-heartbeat-choice {
         leaf disable-heartbeat {
           description "Disable heartbeat between Aggregation and Satellite";
           type empty;
         }
         leaf no-disable-heartbeat {
           description "Don't disable heartbeat between Aggregation and Satellite";
           type empty;
         }
       }
     }
   }
   grouping dhcp-option82-type {
     uses apply-advanced;
     leaf disable {
       description "Disable DHCP option 82 on this VLAN";
       type empty;
     }
     container circuit-id {
       presence "enable circuit-id";
       description "Configure DHCP option 82 circuit id";
       uses apply-advanced;
       leaf prefix {
         description "Configure DHCP option 82 circuit id prefix";
         type enumeration {
           enum "hostname" {
             description "Set hostname as the prefix";
           }
         }
       }
       leaf use-interface-description {
         description "Use interface description instead of name";
         type empty;
       }
       leaf use-vlan-id {
         description "Use VLAN id instead of name";
         type empty;
       }
     }
     container remote-id {
       presence "enable remote-id";
       description "Configure DHCP option 82 remote id";
       uses apply-advanced;
       leaf prefix {
         description "Configure DHCP option 82 remote id prefix";
         type enumeration {
           enum "none" {
             description "Set no prefix";
           }
           enum "hostname" {
             description "Set hostname as the prefix";
           }
           enum "mac" {
             description "Set chassis MAC as the prefix";
           }
         }
       }
       leaf use-interface-description {
         description "Use interface description instead of name";
         type empty;
       }
       leaf use-string {
         description "Use raw string instead of the default remote id";
         junos:must "(!(\".. use-interface-description\"))";
         junos:must-message "use-string and use-interface-description cannot be configured together";
         type string;
       }
     }
     container vendor-id {
       presence "enable vendor-id";
       description "Configure DHCP option 82 vendor id";
       uses apply-advanced;
       leaf use-string {
         description "Use raw string instead of the default vendor id";
         type string;
       }
     }
   }
   grouping jdhcp-access-security-type {
     description "Access security configuration";
     uses apply-advanced;
     container slaac-snooping {
       description "Stateless address auto configuration options";
       uses slaacd-config-type;
     }
     container router-advertisement-guard {
       presence "enable router-advertisement-guard";
       description "Router Advertisement Guard Configuration";
       uses apply-advanced;
       list policy {
         key name;
         ordered-by user;
         description "Router Advertisement Guard policy";
         leaf name {
           description "Router Advertisement Guard policy name";
           type string {
             length "1 .. 64";
           }
         }
         uses apply-advanced;
         container discard {
           description "Discard parameters";
           uses apply-advanced;
           leaf source-ip-address-list {
             description "IPv6 Source address list name";
             type string;
           }
           leaf source-mac-address-list {
             description "Source mac address list name";
             type string;
           }
           leaf prefix-list-name {
             description "Prefix-list Name";
             type string;
           }
         }
         container accept {
           description "Accept parameters";
           uses apply-advanced;
           container match-list {
             description "List of parameters to check";
             uses apply-advanced;
             leaf source-ip-address-list {
               description "IPv6 Source address list name";
               type string;
             }
             leaf source-mac-address-list {
               description "Source mac address list name";
               type string;
             }
             leaf prefix-list-name {
               description "Prefix-list Name";
               type string;
             }
             leaf match-criteria {
               description "Match Criteria";
               type enumeration {
                 enum "match-all" {
                   description "A match from every list";
                 }
                 enum "match-any" {
                   description "A match from any list";
                 }
               }
             }
           }
           container match-options {
             presence "enable match-options";
             description "List of Options to check";
             uses apply-advanced;
             container hop-limit {
               description "Hop limit";
               uses apply-advanced;
               leaf maximum {
                 description "Maximum hop limit";
                 type union {
                   type string {
                     pattern "<.*>|$.*";
                   }
                   type uint32 {
                     range "1 .. 255";
                   }
                 }
               }
               leaf minimum {
                 description "Minimum hop limit";
                 type union {
                   type string {
                     pattern "<.*>|$.*";
                   }
                   type uint32 {
                     range "1 .. 255";
                   }
                 }
               }
             }
             container route-preference {
               description "Accept route preference";
               uses apply-advanced;
               leaf maximum {
                 description "Maximum route preference";
                 type enumeration {
                   enum "low" {
                     description "Route preference low";
                   }
                   enum "medium" {
                     description "Route preference medium";
                   }
                   enum "high" {
                     description "Route preference high";
                   }
                 }
               }
             }
             leaf managed-config-flag {
               description "Check Managed config flag";
               type empty;
             }
             leaf other-config-flag {
               description "Check Other config flag";
               type empty;
             }
           }
         }
       }
       container interface {
         description "RA Guard config on Interface";
         uses apply-advanced;
         list intf-config {
           key name;
           description "Interface Configuration";
           uses interface-policy;
         }
       }
       container vlans {
         description "RA Guard config on Vlan";
         uses apply-advanced;
         list vlan-config {
           key name;
           description "Virtual LAN Configuration";
           uses vlan-policy;
         }
       }
     }
   }
   grouping interface-policy {
     description "Interface Name";
     leaf name {
       description "Interface Name";
       type union {
         type jt:interface-name;
         type string {
           pattern "<.*>|$.*";
         }
       }
     }
     uses apply-advanced;
     container policy {
       description "Attach policy";
       uses apply-advanced;
       leaf policy-name {
         description "Router Advertisement Guard policy name";
         type string;
       }
       choice policy-type {
         case case_1 {
           leaf stateful {
             description "Stateful router advertisement guard";
             type empty;
           }
         }
         case case_2 {
           leaf stateless {
             description "Stateless router advertisement guard";
             type empty;
           }
         }
       }
     }
     container mark-interface {
       description "Mark interface";
       uses apply-advanced;
       choice mark-intf-type {
         case case_1 {
           leaf trusted {
             description "Mark interface trusted";
             junos:must "(!(\".. .. policy\"))";
             junos:must-message "Trusted interfaces cannot have policy attached";
             type empty;
           }
         }
         case case_2 {
           leaf block {
             description "Block router-advertisement";
             junos:must "(!(\".. .. policy\"))";
             junos:must-message "Blocked interfaces cannot have policy attached";
             type empty;
           }
         }
       }
     }
   }
   grouping juniper-forwarding-sandbox-options {
     leaf name {
       description "Sandbox name";
       junos:must "(\".. port\")";
       junos:must-message "At least one port is required for port configuration";
       type string;
     }
     uses apply-advanced;
     leaf size {
       description "Size of the sandbox";
       default "small";
       type enumeration {
         enum "small" {
           description "Sandbox size small";
         }
         enum "medium" {
           description "Sandbox size medium";
         }
         enum "large" {
           description "Sandbox size large";
         }
       }
     }
     list port {
       key name;
       description "Sandbox port";
       max-elements 64;
       uses juniper-forwarding-sandbox-port-options;
     }
   }
   grouping juniper-forwarding-sandbox-port-options {
     leaf name {
       description "Port name";
       junos:must "(\".. interface\")";
       junos:must-message "At least one interface is required for port configuration";
       type string;
     }
     uses apply-advanced;
     list interface {
       key name;
       ordered-by user;
       description "Interface to which the port is mapped";
       max-elements 1;
       leaf name {
         description "Interface name";
         junos:must "(!(\"interfaces $$ unit\"))";
         junos:must-message "Interface must not have configuration defined for adding to a forwarding sandbox";
         type union {
           type jt:interface-device;
           type string {
             pattern "<.*>|$.*";
           }
         }
       }
       uses apply-advanced;
     }
   }
   grouping juniper-igmp-snooping-options {
     uses apply-advanced;
     leaf use-p2mp-lsp {
       description "P2MP will be used to forward traffic instead of PW";
       junos:must "(\".. .. instance-type vpls\")";
       junos:must-message "use-p2mp-lsp supported only on instance type vpls";
       type empty;
     }
     container snoop-pseudowires {
       presence "enable snoop-pseudowires";
       junos:must "(\".. .. instance-type vpls\")";
       junos:must-message "snoop-pseudowires supported only on instance type vpls";
       junos:must "(!(\" .. use-p2mp-lsp\"))";
       junos:must-message "snoop-pseudowires and use-p2mp-lsp cannot be configured together";
       description "VPLS PE would send traffic selectively to PE's having interest";
       uses apply-advanced;
     }
   }
   grouping juniper-mld-snooping-options {
     uses apply-advanced;
     leaf use-p2mp-lsp {
       description "P2MP will be used to forward traffic instead of PW";
       junos:must "(\".. .. instance-type vpls\")";
       junos:must-message "use-p2mp-lsp supported only on instance type vpls";
       type empty;
     }
     container snoop-pseudowires {
       presence "enable snoop-pseudowires";
       junos:must "(\".. .. instance-type vpls\")";
       junos:must-message "snoop-pseudowires supported only on instance type vpls";
       junos:must "(!(\" .. use-p2mp-lsp\"))";
       junos:must-message "snoop-pseudowires and use-p2mp-lsp cannot be configured together";
       description "VPLS PE would send traffic selectively to PE's having interest";
       uses apply-advanced;
     }
   }
   grouping juniper-monitoring-options {
     leaf name {
       description "Name for monitoring group";
       type string;
     }
     uses apply-advanced;
     container family {
       description "Address family of packets to monitor";
       container inet {
         presence "enable inet";
         description "Monitor IPv4 packets";
         uses apply-advanced;
         container input {
           description "Monitor data acquisition";
           presence "enable input";
           status deprecated;
           uses monitoring_input_type;
         }
         container output {
           description "Monitoring data disposition";
           presence "enable output";
           uses monitoring_output_type;
         }
       }
     }
   }
   grouping juniper-multicast-snooping-options {
     uses apply-advanced;
     container options {
       description "Miscellaneous options";
       uses apply-advanced;
       container syslog {
         description "Set system logging level";
         uses apply-advanced;
         container level {
           description "Logging level";
           leaf emergency {
             description "Emergency level";
             type empty;
           }
           leaf alert {
             description "Alert level";
             type empty;
           }
           leaf critical {
             description "Critical level";
             type empty;
           }
           leaf error {
             description "Error level";
             type empty;
           }
           leaf warning {
             description "Warning level";
             type empty;
           }
           leaf notice {
             description "Notice level";
             type empty;
           }
           leaf info {
             description "Informational level";
             type empty;
           }
           leaf debug {
             description "Debugging level";
             type empty;
           }
         }
         leaf upto {
           description "Log up to a particular logging level";
           type enumeration {
             enum "emergency" {
               description "Emergency level";
             }
             enum "alert" {
               description "Alert level";
             }
             enum "critical" {
               description "Critical level";
             }
             enum "error" {
               description "Error level";
             }
             enum "warning" {
               description "Warning level";
             }
             enum "notice" {
               description "Notice level";
             }
             enum "info" {
               description "Informational level";
             }
             enum "debug" {
               description "Debugging level";
             }
           }
         }
         leaf mark {
           description "Periodically mark the trace file";
           units "seconds";
           type union {
             type int32;
             type string {
               pattern "<.*>|$.*";
             }
           }
         }
       }
     }
     container traceoptions {
       description "Multicast snooping trace options";
       uses apply-advanced;
       container file {
         description "Trace file options";
         leaf filename {
           description "Name of file in which to write trace information";
           type string {
             length "1 .. 1024";
             junos:posix-pattern "![/ %]";
             junos:pattern-message "Must not contain '/', % or a space";
           }
         }
         leaf replace {
           description "Replace trace file rather than appending to it";
           status deprecated;
           type empty;
         }
         leaf size {
           description "Maximum trace file size";
           type string;
         }
         leaf files {
           description "Maximum number of trace files";
           default "10";
           type union {
             type string {
               pattern "<.*>|$.*";
             }
             type uint32 {
               range "2 .. 1000";
             }
           }
         }
         leaf no-stamp {
           description "Do not timestamp trace file";
           status deprecated;
           type empty;
         }
         choice world-readable-choice {
           leaf world-readable {
             description "Allow any user to read the log file";
             type empty;
           }
           leaf no-world-readable {
             description "Don't allow any user to read the log file";
             type empty;
           }
         }
       }
       list flag {
         key name;
         ordered-by user;
         description "Tracing parameters";
         leaf name {
           type enumeration {
             enum "parse" {
               description "Trace configuration parsing";
             }
             enum "config-internal" {
               description "Trace configuration internals";
             }
             enum "route" {
               description "Trace routing information";
             }
             enum "normal" {
               description "Trace normal events";
             }
             enum "general" {
               description "Trace general events";
             }
             enum "state" {
               description "Trace state transitions";
             }
             enum "policy" {
               description "Trace policy processing";
             }
             enum "task" {
               description "Trace routing protocol task processing";
             }
             enum "timer" {
               description "Trace routing protocol timer processing";
             }
             enum "all" {
               description "Trace everything";
             }
           }
         }
         leaf disable {
           description "Disable this trace flag";
           type empty;
         }
       }
     }
     container forwarding-cache {
       description "Multicast forwarding cache";
       uses apply-advanced;
       container threshold {
         description "Threshold";
         uses apply-advanced;
         leaf suppress {
           description "Suppress threshold";
           type union {
             type string {
               pattern "<.*>|$.*";
             }
             type uint32 {
               range "1 .. 200000";
             }
           }
         }
         leaf reuse {
           description "Reuse threshold";
           type union {
             type string {
               pattern "<.*>|$.*";
             }
             type uint32 {
               range "1 .. 200000";
             }
           }
         }
       }
     }
     leaf-list flood-groups {
       ordered-by user;
       description "Groups for which the traffic will be flooded";
       type jt:ipaddr;
     }
     container host-outbound-traffic {
       description "Host generated protocol packets";
       uses apply-advanced;
       leaf forwarding-class {
         description "Forwarding class name";
         type string {
           junos:posix-pattern "^.{1,64}$";
           junos:pattern-message "Must be string of 64 characters or less";
         }
       }
       leaf dot1p {
         description "Dot1p bits";
         type union {
           type string {
             pattern "<.*>|$.*";
           }
           type uint32 {
             range "0 .. 7";
           }
         }
       }
     }
     container graceful-restart {
       description "Configure graceful restart attributes";
       uses apply-advanced;
       choice enable-disable {
         case case_1 {
           leaf disable {
             description "Disable graceful restart";
             type empty;
           }
         }
       }
       leaf restart-duration {
         description "Maximum time for graceful restart to finish";
         default "180";
         units "seconds";
         type union {
           type string {
             pattern "<.*>|$.*";
           }
           type uint32 {
             range "0 .. 300";
           }
         }
       }
     }
     leaf ignore-stp-topology-change {
       description "Don't process stp topology change";
       type empty;
     }
     container multichassis-lag-replicate-state {
       presence "enable multichassis-lag-replicate-state";
       description "Enable multichassis lag replication";
       uses apply-advanced;
       leaf suppress-report {
         description "Enable mclag report suppression";
         type empty;
       }
     }
     container oism {
       description "Optimized inter subnet multicast options";
       uses apply-advanced;
       leaf install-star-g-routes {
         description "Install (*,G) multicast routes in data plane";
         type empty;
       }
     }
     leaf nexthop-hold-time {
       description "Nexthop hold time in milliseconds";
       units "milliseconds";
       type union {
         type string {
           pattern "<.*>|$.*";
         }
         type uint32 {
           range "1 .. 1000";
         }
       }
     }
   }
   grouping juniper-next-hop-group-options {
     leaf name {
       description "Next hop group name";
       type string;
     }
     uses apply-advanced;
     leaf group-type {
       description "Next hop group type";
       default "inet";
       type enumeration {
         enum "inet" {
           description "Group of family inet next-hops";
         }
         enum "layer-2" {
           description "Layer-2 next-hop group";
         }
         enum "inet6" {
           description "Group of family inet6 next-hops";
         }
       }
     }
     list interface {
       key name;
       description "Interfaces through which to send sampled traffic";
       uses next_hop_group_intf_type;
     }
     list next-hop-subgroup {
       key name;
       description "Group of interfaces through which to send sampled traffic";
       uses juniper-next-hop-subgroup-options;
     }
   }
   grouping juniper-next-hop-subgroup-options {
     leaf name {
       description "Next-hop sub-group name";
       junos:must "(\".. interface\")";
       junos:must-message "At least two interfaces are required for next-hop-subgroup configuration";
       type string;
     }
     uses apply-advanced;
     list interface {
       key name;
       description "Interface through which to send the sampled traffic";
       max-elements 16;
       uses next_hop_subgroup_intf_type;
     }
   }
   grouping juniper-packet-accounting-options {
     leaf name {
       description "Name for accounting group";
       type string;
     }
     uses apply-advanced;
     container output {
       description "Accounting data disposition";
       uses packet_accounting_output_type;
     }
   }
   grouping juniper-packet-capture-options {
     description "Packet capture options";
     uses apply-advanced;
     choice enable-disable {
       case case_1 {
         leaf disable {
           description "Disable packet-capture";
           type empty;
         }
       }
     }
     container file {
       description "Parameters for file that contains captured packets";
       leaf filename {
         description "Name of file";
         type string {
           length "1 .. 900";
           junos:posix-pattern "![/ %.]";
           junos:pattern-message "Must not contain '/', '%', '.' or a space";
         }
       }
       leaf files {
         description "Maximum number of files";
         default "10";
         type union {
           type string {
             pattern "<.*>|$.*";
           }
           type uint32 {
             range "2 .. 10000";
           }
         }
       }
       leaf size {
         description "Maximum file size";
         type string;
       }
       choice world-readable-choice {
         leaf world-readable {
           description "Allow any user to read packet-capture files";
           type empty;
         }
         leaf no-world-readable {
           description "Don't allow any user to read packet-capture files";
           type empty;
         }
       }
     }
     leaf maximum-capture-size {
       description "Maximum packet size to capture";
       default "68";
       units "bytes";
       type union {
         type string {
           pattern "<.*>|$.*";
         }
         type uint32 {
           range "68 .. 1520";
         }
       }
     }
   }
   grouping juniper-port-mirror-options {
     uses apply-advanced;
     container traceoptions {
       description "Port-mirroring trace options";
       uses sampling_traceoptions_type;
     }
     leaf disable {
       description "Disable the global port-mirroring instance";
       type empty;
     }
     leaf disable-all-instances {
       description "Disable the all port-mirroring instances";
       type empty;
     }
     leaf mirror-once {
       description "Sample the packet for port mirroring only once";
       type empty;
     }
     leaf no-preserve-ingress-tag {
       description "Mirror the packet retaining tag value before normalization";
       type empty;
     }
     leaf remote-port-mirroring {
       description "Flag to specify about remote-port-mirroring";
       type empty;
     }
     container input {
       description "Settings for sampling of input packets";
       uses pm_family_input_type;
     }
     container family {
       description "Address family of packets to mirror";
       container inet {
         description "Mirror IPv4 packets";
         uses apply-advanced;
         container input {
           description "Settings for sampling of input packets";
           status deprecated;
           junos:must "(!(\".. .. .. input\"))";
           junos:must-message "input parameters under family and outside family are mutually exclusive";
           uses pm_family_input_type;
         }
         container output {
           description "One or more next hops for port-mirrored packets";
           uses inet_pm_family_output_type;
         }
       }
       container inet6 {
         description "Mirror IPv6 packets";
         uses apply-advanced;
         container input {
           description "Settings for sampling of input packets";
           status deprecated;
           junos:must "(!(\".. .. .. input\"))";
           junos:must-message "input parameters under family and outside family are mutually exclusive";
           uses pm_family_input_type;
         }
         container output {
           description "One or more next hops for port-mirrored packets";
           uses inet6_pm_family_output_type;
         }
       }
       container mpls {
         description "Mirror MPLS packets";
         uses apply-advanced;
         container input {
           description "Settings for sampling of input packets";
           status deprecated;
           junos:must "(!(\".. .. .. input\"))";
           junos:must-message "input parameters under family and outside family are mutually exclusive";
           uses pm_family_input_type;
         }
         container output {
           description "One or more next hops for port-mirrored packets";
           uses mpls_pm_family_output_type;
         }
       }
       container any {
         description "Mirror any packets";
         uses apply-advanced;
         container output {
           description "One or more next hops for port-mirrored packets";
           uses any_pm_family_output_type;
         }
       }
       container vpls {
         description "Mirror Layer-2 bridged/vpls packets";
         uses apply-advanced;
         container input {
           description "Settings for sampling of input packets";
           status deprecated;
           junos:must "(!(\".. .. ..  input\"))";
           junos:must-message "input parameters under family and outside family are mutually exclusive";
           uses pm_family_input_type;
         }
         container output {
           description "Destination for port-mirrored packets";
           uses layer2_pm_family_output_type;
         }
       }
       container ethernet-switching {
         description "Mirror Layer-2 ethernet-switched packets";
         uses apply-advanced;
         container output {
           description "Destination for port-mirrored packets";
           uses layer2_pm_family_output_type;
         }
       }
       container ccc {
         description "Mirror layer-2 ccc packets";
         uses apply-advanced;
         container input {
           description "Settings for sampling of input packets";
           status deprecated;
           junos:must "(!(\".. .. ..  input\"))";
           junos:must-message "input parameters under family and outside family are mutually exclusive";
           uses pm_family_input_type;
         }
         container output {
           description "Destination for port-mirrored packets";
           uses layer2_pm_family_output_type;
         }
       }
     }
     list instance {
       key name;
       ordered-by user;
       description "Instance of port-mirroring parameters";
       leaf name {
         description "Name for port-mirroring instance";
         type string {
           length "1 .. 63";
           junos:posix-pattern "!^((__.*)|(.{65,}))$";
           junos:pattern-message "Must be a non-reserved string of 64 characters or less";
         }
       }
       uses apply-advanced;
       leaf disable {
         description "Disable the this port-mirroring instance";
         type empty;
       }
       choice input_params_or_instance {
         case case_1 {
           container input {
             description "Settings for sampling of input packets";
             uses pm_family_input_type;
           }
         }
         case case_2 {
           leaf input-parameters-instance {
             description "Name of port-mirroring instance to use for input parameters";
             junos:must "(\"forwarding-options port-mirroring instance $$\")";
             junos:must-message "Referenced port-mirroring instance does not exist";
             type string;
           }
         }
       }
       container output {
         description "One or more next hops for port-mirrored packets";
         uses inet_pm_output_type;
       }
       container family {
         description "Address family of packets to mirror";
         container inet {
           description "Mirror IPv4 packets";
           uses apply-advanced;
           container input {
             description "Settings for sampling of input packets";
             status deprecated;
             junos:must "(!(\".. .. .. input\"))";
             junos:must-message "input parameters under family and outside family are mutually exclusive";
             uses pm_family_input_type;
           }
           container output {
             description "One or more next hops for port-mirrored packets";
             uses inet_pm_family_output_type;
           }
         }
         container inet6 {
           description "Mirror IPv6 packets";
           uses apply-advanced;
           container input {
             description "Settings for sampling of input packets";
             status deprecated;
             junos:must "(!(\".. .. .. input\"))";
             junos:must-message "input parameters under family and outside family are mutually exclusive";
             uses pm_family_input_type;
           }
           container output {
             description "One or more next hops for port-mirrored packets";
             uses inet6_pm_family_output_type;
           }
         }
         container mpls {
           description "Mirror MPLS packets";
           uses apply-advanced;
           container input {
             description "Settings for sampling of input packets";
             status deprecated;
             junos:must "(!(\".. .. .. input\"))";
             junos:must-message "input parameters under family and outside family are mutually exclusive";
             uses pm_family_input_type;
           }
           container output {
             description "One or more next hops for port-mirrored packets";
             uses mpls_pm_family_output_type;
           }
         }
         container any {
           description "Mirror any packets";
           uses apply-advanced;
           container output {
             description "One or more next hops for port-mirrored packets";
             uses any_pm_family_output_type;
           }
         }
         container vpls {
           description "Mirror Layer-2 bridged/vpls packets";
           uses apply-advanced;
           container input {
             description "Settings for sampling of input packets";
             status deprecated;
             junos:must "(!(\".. .. ..  input\"))";
             junos:must-message "input parameters under family and outside family are mutually exclusive";
             uses pm_family_input_type;
           }
           container output {
             description "Destination for port-mirrored packets";
             uses layer2_pm_family_output_type;
           }
         }
         container ethernet-switching {
           description "Mirror Layer-2 ethernet-switched packets";
           uses apply-advanced;
           container output {
             description "Destination for port-mirrored packets";
             uses layer2_pm_family_output_type;
           }
         }
         container ccc {
           description "Mirror layer-2 ccc packets";
           uses apply-advanced;
           container input {
             description "Settings for sampling of input packets";
             status deprecated;
             junos:must "(!(\".. .. ..  input\"))";
             junos:must-message "input parameters under family and outside family are mutually exclusive";
             uses pm_family_input_type;
           }
           container output {
             description "Destination for port-mirrored packets";
             uses layer2_pm_family_output_type;
           }
         }
       }
       container mirror-profile {
         description "Mirror profile to be attached to the instance";
         uses apply-advanced;
         leaf profile-name {
           description "Name of profile";
           type string {
             length "1 .. 63";
             junos:posix-pattern "!^((__.*__)|(all)|(.*[ ].*)|(\"\")|(.{129,}))$";
             junos:pattern-message "Must be a non-reserved string of 128 characters or less with no spaces.";
           }
         }
       }
     }
   }
   grouping any_pm_family_output_type {
     uses apply-advanced;
     choice interface-or-next-hop-index {
       case case_1 {
         list interface {
           key name;
           description "Interfaces through which to send sampled traffic";
           uses any_pm_intf_type;
         }
       }
       case case_2 {
         leaf next-hop-group {
           description "Next-hop-group through which to send port-mirror traffic";
           junos:must "(!(\".. no-filter-check\"))";
           junos:must-message "no-filter-check is not allowed with next-hop-group";
           junos:must "(\"forwarding-options next-hop-group $$ group-type layer-2\")";
           junos:must-message "Referenced next-hop-group must be defined as layer-2 group";
           type string;
         }
       }
     }
     leaf no-filter-check {
       description "Do not check for filters on port-mirroring interface";
       type empty;
     }
     container hosted-service {
       description "Configure Hosted Service";
       uses apply-advanced;
       leaf server-profile {
         description "Server profile name";
         junos:must "(\"services hosted-services server-profile $$\")";
         junos:must-message "Only server profiles configured under [services hosted-services server-profile] can be configured here";
         type string {
           length "3 .. 32";
         }
       }
     }
   }
   grouping any_pm_intf_type {
     leaf name {
       description "Interface through which to send sampled traffic";
       junos:must "(!((\"interfaces $$-IFL family inet\" || \"interfaces $$-IFL family inet6\")))";
       junos:must-message "An interface configured as family inet/inet6 cannot be configured as output interface";
       type union {
         type jt:interface-name;
         type string {
           pattern "<.*>|$.*";
         }
       }
     }
     uses apply-advanced;
     list next-hop {
       key name;
       ordered-by user;
       description "Address of next hop through which to send sampled traffic";
       uses inet_next_hop_type;
     }
   }
   grouping inet6_pm_family_output_type {
     uses apply-advanced;
     choice interface-or-next-hop-index {
       case case_1 {
         list interface {
           key name;
           description "Interfaces through which to send sampled traffic";
           uses inet6_pm_intf_type;
         }
       }
       case case_2 {
         leaf next-hop-group {
           description "Next-hop-group through which to send port-mirror traffic";
           junos:must "(!(\".. no-filter-check\"))";
           junos:must-message "no-filter-check is not allowed with next-hop-group";
           junos:must "(\"forwarding-options next-hop-group $$ group-type inet6\")";
           junos:must-message "Referenced next-hop-group must be defined as inet6 group";
           type string;
         }
       }
     }
     leaf policer {
       description "Name of policer to use to rate-limit traffic";
       junos:must "(\"firewall policer $$\")";
       junos:must-message "Referenced firewall policer does not exist";
       type string {
         junos:posix-pattern "!^((__.*)|(.{65,}))$";
         junos:pattern-message "Must be a non-reserved string of 64 characters or less";
       }
     }
     leaf forwarding-class {
       description "Forwarding-class for TOS";
       junos:must "(\"class-of-service forwarding-classes class $$\")";
       junos:must-message "Referenced forwarding-class does not exist";
       type string {
         length "1 .. 64";
       }
     }
     leaf no-filter-check {
       description "Do not check for filters on port-mirroring interface";
       type empty;
     }
     leaf ipv6-address {
       description "ERSPAN Destination IPv6 Address";
       type jt:ipv6addr;
     }
     list routing-instance {
       key name;
       description "Routing instances";
       max-elements 1;
       uses inet6_pm_output-routing-instance-type;
     }
     leaf server-profile {
       description "Server profile name";
       junos:must "((\"services hosted-services server-profile $$\" && (\"services hosted-services server-profile $$ server-address\" && \"services hosted-services server-profile $$ client-address\")))";
       junos:must-message "Only complete server profiles configured under [services hosted-services server-profile] can be configured here";
       type string {
         length "3 .. 32";
       }
     }
   }
   grouping inet6_pm_intf_type {
     leaf name {
       description "Interface through which to send sampled traffic";
       type union {
         type jt:interface-name;
         type string {
           pattern "<.*>|$.*";
         }
       }
     }
     uses apply-advanced;
     list next-hop {
       key name;
       ordered-by user;
       description "Address of next hop through which to send sampled traffic";
       uses inet6_next_hop_type;
     }
   }
   grouping inet6_next_hop_type {
     description "Address of next hop through which to send sampled traffic";
     leaf name {
       type jt:ipv6addr;
     }
     uses apply-advanced;
   }
   grouping inet6_pm_output-routing-instance-type {
     leaf name {
       description "Routing instance name";
       type string {
         junos:posix-pattern "!^((__.*__)|(all)|(.*[ ].*)|(\"\")|(.{129,}))$";
         junos:pattern-message "Must be a non-reserved string of 128 characters or less with no spaces.";
       }
     }
     uses apply-advanced;
     leaf ipv6-address {
       description "ERSPAN Destination IPv6 Address";
       type jt:ipv6addr;
     }
   }
   grouping inet_next_hop_type {
     description "Address of next hop through which to send sampled traffic";
     leaf name {
       type jt:ipv4addr;
     }
     uses apply-advanced;
   }
   grouping inet_pm_family_output_type {
     uses apply-advanced;
     choice interface-or-next-hop-index {
       case case_1 {
         list interface {
           key name;
           description "Interfaces through which to send sampled traffic";
           uses inet_pm_intf_type;
         }
       }
       case case_2 {
         leaf next-hop-group {
           description "Next-hop-group through which to send port-mirror traffic";
           junos:must "(!(\".. no-filter-check\"))";
           junos:must-message "no-filter-check is not allowed with next-hop-group";
           junos:must "(\"forwarding-options next-hop-group $$ group-type inet\")";
           junos:must-message "Referenced next-hop-group must be defined as inet group";
           type string;
         }
       }
     }
     leaf no-filter-check {
       description "Do not check for filters on port-mirroring interface";
       type empty;
     }
     leaf ip-address {
       description "ERSPAN Destination IP Address";
       type jt:ipv4addr;
     }
     list routing-instance {
       key name;
       description "Routing instances";
       max-elements 1;
       uses inet_pm_output-routing-instance-type;
     }
     leaf server-profile {
       description "Server profile name";
       junos:must "((\"services hosted-services server-profile $$\" && (\"services hosted-services server-profile $$ server-address\" && \"services hosted-services server-profile $$ client-address\")))";
       junos:must-message "Only complete server profiles configured under [services hosted-services server-profile] can be configured here";
       type string {
         length "3 .. 32";
       }
     }
     leaf policer {
       description "Name of policer to use to rate-limit traffic";
       junos:must "(\"firewall policer $$\")";
       junos:must-message "Referenced firewall policer does not exist";
       type string {
         junos:posix-pattern "!^((__.*)|(.{65,}))$";
         junos:pattern-message "Must be a non-reserved string of 64 characters or less";
       }
     }
     leaf forwarding-class {
       description "Forwarding-class for TOS";
       junos:must "(\"class-of-service forwarding-classes class $$\")";
       junos:must-message "Referenced forwarding-class does not exist";
       type string {
         length "1 .. 64";
       }
     }
   }
   grouping inet_pm_intf_type {
     leaf name {
       description "Interface through which to send sampled traffic";
       type union {
         type jt:interface-name;
         type string {
           pattern "<.*>|$.*";
         }
       }
     }
     uses apply-advanced;
     list next-hop {
       key name;
       ordered-by user;
       description "Address of next hop through which to send sampled traffic";
       uses inet_next_hop_type;
     }
   }
   grouping inet_pm_output-routing-instance-type {
     leaf name {
       description "Routing instance name";
       type string {
         junos:posix-pattern "!^((__.*__)|(all)|(.*[ ].*)|(\"\")|(.{129,}))$";
         junos:pattern-message "Must be a non-reserved string of 128 characters or less with no spaces.";
       }
     }
     uses apply-advanced;
     leaf ip-address {
       description "ERSPAN Destination IP Address";
       type jt:ipv4addr;
     }
   }
   grouping inet_pm_output_type {
     uses apply-advanced;
     leaf ip-source-address {
       description "IP source address";
       type jt:ipv4addr;
     }
     leaf ip-destination-address {
       description "IP destination address";
       type jt:ipv4addr;
     }
     leaf policer {
       description "Name of policer to use to rate-limit traffic";
       junos:must "(\"firewall policer $$\")";
       junos:must-message "Referenced firewall policer does not exist";
       type string {
         junos:posix-pattern "!^((__.*)|(.{65,}))$";
         junos:pattern-message "Must be a non-reserved string of 64 characters or less";
       }
     }
     leaf dscp {
       description "Numeric DSCP value in the range 0 to 63";
       type union {
         type string {
           pattern "<.*>|$.*";
         }
         type uint8 {
           range "0 .. 63";
         }
       }
     }
     leaf forwarding-class {
       description "Forwarding-class for TOS";
       junos:must "(\"class-of-service forwarding-classes class $$\")";
       junos:must-message "Referenced forwarding-class does not exist";
       type string {
         length "1 .. 64";
       }
     }
   }
   grouping juniper-protocols-amt {
     uses apply-advanced;
     container traceoptions {
       description "Trace options for AMT";
       uses apply-advanced;
       container file {
         description "Trace file options";
         leaf filename {
           description "Name of file in which to write trace information";
           type string {
             length "1 .. 1024";
             junos:posix-pattern "![/ %]";
             junos:pattern-message "Must not contain '/', % or a space";
           }
         }
         leaf replace {
           description "Replace trace file rather than appending to it";
           status deprecated;
           type empty;
         }
         leaf size {
           description "Maximum trace file size";
           type string;
         }
         leaf files {
           description "Maximum number of trace files";
           default "10";
           type union {
             type string {
               pattern "<.*>|$.*";
             }
             type uint32 {
               range "2 .. 1000";
             }
           }
         }
         leaf no-stamp {
           description "Do not timestamp trace file";
           status deprecated;
           type empty;
         }
         choice world-readable-choice {
           leaf world-readable {
             description "Allow any user to read the log file";
             type empty;
           }
           leaf no-world-readable {
             description "Don't allow any user to read the log file";
             type empty;
           }
         }
       }
       list flag {
         key name;
         ordered-by user;
         description "Tracing parameters";
         leaf name {
           type enumeration {
             enum "packets" {
               description "Trace all AMT packets";
             }
             enum "errors" {
               description "Trace all error messages";
             }
             enum "tunnels" {
               description "Trace all AMT tunnel messages";
             }
             enum "route" {
               description "Trace routing information";
             }
             enum "normal" {
               description "Trace normal events";
             }
             enum "general" {
               description "Trace general events";
             }
             enum "state" {
               description "Trace state transitions";
             }
             enum "policy" {
               description "Trace policy processing";
             }
             enum "task" {
               description "Trace routing protocol task processing";
             }
             enum "timer" {
               description "Trace routing protocol timer processing";
             }
             enum "all" {
               description "Trace everything";
             }
           }
         }
         leaf send {
           description "Trace transmitted packets";
           type empty;
         }
         leaf receive {
           description "Trace received packets";
           type empty;
         }
         leaf detail {
           description "Trace detailed information";
           type empty;
         }
         leaf disable {
           description "Disable this trace flag";
           type empty;
         }
       }
     }
     container relay {
       description "AMT relay";
       presence "enable relay";
       uses juniper-protocols-amt-relay;
     }
   }
   grouping juniper-protocols-amt-relay {
     uses apply-advanced;
     container family {
       presence "enable family";
       description "Protocol family";
       uses apply-advanced;
       container inet {
         presence "enable inet";
         uses apply-advanced;
         leaf anycast-prefix {
           description "IPv4 anycast prefix";
           type jt:ipv4prefix;
         }
         leaf local-address {
           description "IPv4 local address";
           type jt:ipv4addr;
         }
       }
     }
     leaf secret-key-timeout {
       description "Time interval for the secret key to expire";
       units "minutes";
       type union {
         type string {
           pattern "<.*>|$.*";
         }
         type uint32 {
           range "5 .. 1440";
         }
       }
     }
     leaf tunnel-limit {
       description "Number of AMT tunnels";
       type union {
         type uint32;
         type string {
           pattern "<.*>|$.*";
         }
       }
     }
     leaf unicast-stream-limit {
       description "Maximum number of AMT unicast streams(s,g,intf)";
       type union {
         type uint32;
         type string {
           pattern "<.*>|$.*";
         }
       }
     }
     leaf accounting {
       description "Enable AMT accounting";
       type empty;
     }
     leaf-list tunnel-devices {
       ordered-by user;
       description "Tunnel devices to be used for creating ud interfaces";
       type union {
         type jt:interface-device;
         type string {
           pattern "<.*>|$.*";
         }
       }
     }
   }
   grouping juniper-protocols-bd {
     description "Bridging configuration";
     uses apply-advanced;
     container mac-table-size {
       junos:must "(!(((\".. .. .. protocols vpls\" || \".. .. .. protocols evpn\") && \".. .. ..  instance-type virtual-switch\")))";
       junos:must-message "mac-table-size needs to be specified under switch-options for a virtual-switch instance";
       description "Size of MAC address forwarding table";
       uses apply-advanced;
       leaf limit {
         description "Maximum number of MAC addresses";
         type union {
           type string {
             pattern "<.*>|$.*";
           }
           type uint32;
         }
       }
       leaf packet-action {
         description "Action when MAC limit is reached";
         type enumeration {
           enum "none" {
             description "Forward the packet";
           }
           enum "drop" {
             description "Drop packets and do not learn. Default is forward";
           }
         }
       }
     }
     container mac-ip-table-size {
       junos:must "(!(((\".. .. .. protocols vpls\" || \".. .. .. protocols evpn\") && \".. .. ..  instance-type virtual-switch\")))";
       junos:must-message "mac-ip-table-size needs to be specified under switch-options for a virtual-switch instance";
       description "Size of MAC+IP bindings table";
       uses apply-advanced;
       leaf limit {
         description "Maximum number of MAC+IP bindings";
         type union {
           type string {
             pattern "<.*>|$.*";
           }
           type uint32;
         }
       }
     }
     container interface-mac-limit {
       junos:must "(!(((\".. .. .. protocols vpls\" || \".. .. .. protocols evpn\") && \".. .. ..  instance-type virtual-switch\")))";
       junos:must-message "interface-mac-limit needs to be specified under switch-options for a virtual-switch instance";
       description "Maximum MAC address learned per interface";
       uses apply-advanced;
       leaf limit {
         description "Maximum number of MAC addresses per interface";
         type union {
           type string {
             pattern "<.*>|$.*";
           }
           type uint32;
         }
       }
       leaf packet-action {
         description "Action when MAC limit is reached";
         type enumeration {
           enum "none" {
             description "Forward the packet";
           }
           enum "drop" {
             description "Drop packets and do not learn. Default is forward";
           }
           enum "log" {
             description "Do not drop the packet but generate an alarm, an SNMP trap or a system log entry";
           }
           enum "shutdown" {
             description "Disable the interface and generate an alarm, an SNMP trap or a system log entry";
           }
           enum "drop-and-log" {
             description "Drop the packet and generate an alarm, an SNMP trap or a system log entry";
           }
         }
       }
     }
     container interface-mac-ip-limit {
       junos:must "(!(((\".. .. .. protocols vpls\" || \".. .. .. protocols evpn\") && \".. .. ..  instance-type virtual-switch\")))";
       junos:must-message "interface-mac-ip-limit needs to be specified under switch-options for a virtual-switch instance";
       description "Maximum MAC+IP bindings learned per interface";
       uses apply-advanced;
       leaf limit {
         description "Maximum number of MAC+IP bindings per interface";
         type union {
           type string {
             pattern "<.*>|$.*";
           }
           type uint32;
         }
       }
     }
     container mac-notification {
       presence "enable mac-notification";
       description "MAC notification options";
       uses apply-advanced;
       leaf notification-interval {
         description "Interval for sending MAC notifications";
         default "30";
         units "seconds";
         type union {
           type string {
             pattern "<.*>|$.*";
           }
           type uint32 {
             range "1 .. 60";
           }
         }
       }
     }
     leaf mac-table-aging-time {
       description "Delay for discarding MAC address if no updates are received";
       units "seconds";
       type union {
         type string {
           pattern "<.*>|$.*";
         }
         type uint32;
       }
     }
     leaf no-mac-learning {
       description "Disable dynamic MAC address learning";
       junos:must "(!(((\".. .. .. protocols vpls\" || \".. .. .. protocols evpn\") && \".. .. ..  instance-type virtual-switch\")))";
       junos:must-message "no-mac-learning needs to be specified under switch-options for a virtual-switch instance";
       type empty;
     }
     leaf no-normalization {
       description "Disable vlan id normalization for interfaces";
       type empty;
     }
     leaf mac-statistics {
       description "Enable MAC address statistics";
       junos:must "(!(((\".. .. .. protocols vpls\" || \".. .. .. protocols evpn\") && \".. .. ..  instance-type virtual-switch\")))";
       junos:must-message "mac-statistics needs to be specified under switch-options for a virtual-switch instance";
       type empty;
     }
     container mib {
       presence "enable mib";
       description "Snmp mib options";
       uses apply-advanced;
       container dot1q-mib {
         presence "enable dot1q-mib";
         description "Dot1q MIB configuration options";
         uses apply-advanced;
         leaf port-list {
           description "Port list for staticegressports and staticuntaggedports MIB";
           type enumeration {
             enum "bit-map" {
               description "Port list is represented in bit-map format";
             }
             enum "string" {
               description "Port list is represented in string format";
             }
           }
         }
       }
     }
     container static-rvtep-mac {
       description "Configure Static MAC and remote VxLAN tunnel endpoint entries";
       uses apply-advanced;
       list mac {
         key "mac_addr remote-vtep";
         description "Unicast MAC address";
         leaf mac_addr {
           type jt:mac-unicast;
         }
         leaf remote-vtep {
           description "Configure static remote VXLAN tunnel endpoints";
           type jt:ipaddr;
         }
       }
     }
     container network-isolation-profile {
       description "Network isolation configuration";
       uses apply-advanced;
       list group {
         key name;
         description "Network isolation group";
         leaf name {
           description "Group name";
           type string;
         }
         uses apply-advanced;
       }
     }
     list interface {
       key name;
       ordered-by user;
       description "Interface that connect this site to the VPN";
       junos:must "(!((\".. .. .. protocols vpls\" && \".. .. ..  instance-type virtual-switch\")))";
       junos:must-message "interface needs to be specified under switch-options for a virtual-switch instance";
       leaf name {
         description "Interface name";
         junos:must "(((\".. .. .. interface $$\" || (\".. .. .. .. .. interface $$\" || \"interfaces $$-IFL family ethernet-switching vlan\")) || (!(\".. .. .. .. .. .. .. routing-instances\") && (\"interfaces $$-IFL family bridge interface-mode\" && !(any \"routing-instances <*> interface $$\")))))";
         junos:must-message "Interface must be part of this routing instance";
         junos:must "((\".. .. .. interface $$\" || (\".. .. .. .. .. interface $$\" || (\".. .. .. .. interface $$\" || \"interfaces $$-IFL family ethernet-switching\"))))";
         junos:must-message "Interface must be part of this routing instance";
         type union {
           type jt:interface-name;
           type string {
             pattern "<.*>|$.*";
           }
         }
       }
       uses apply-advanced;
       container interface-mac-limit {
         junos:must "(!(\".. .. .. .. .. vlans ${vlan} private-vlan\"))";
         junos:must-message "Switch-options configuration is not allowed on interfaces which are part of secondary VLANs";
         description "Maximum number of MAC addresses learned on the interface";
         uses apply-advanced;
         leaf limit {
           description "Maximum number of MAC addresses per interface";
           type union {
             type string {
               pattern "<.*>|$.*";
             }
             type uint32;
           }
         }
         leaf disable {
           description "Disable interface for interface-mac-limit";
           type empty;
         }
         leaf packet-action {
           description "Action when MAC limit is reached";
           type enumeration {
             enum "none" {
               description "Forward the packet";
             }
             enum "drop" {
               description "Drop packets and do not learn. Default is forward";
             }
             enum "log" {
               description "Do not drop the packet but generate an alarm, an SNMP trap or a system log entry";
             }
             enum "shutdown" {
               description "Disable the interface and generate an alarm, an SNMP trap or a system log entry";
             }
             enum "drop-and-log" {
               description "Drop the packet and generate an alarm, an SNMP trap or a system log entry";
             }
           }
         }
       }
       leaf action-priority {
         description "Blocking priority of this interface on mac move detection";
         junos:must "(!(\".. .. .. .. .. vlans ${vlan} private-vlan\"))";
         junos:must-message "Switch-options configuration is not allowed on interfaces which are part of secondary VLANs";
         type union {
           type string {
             pattern "<.*>|$.*";
           }
           type uint32 {
             range "0 .. 8";
           }
         }
       }
       list static-mac {
         key name;
         ordered-by user;
         description "Static MAC addresses assigned to this interface";
         junos:must "(!(\".. .. .. .. .. vlans ${vlan} private-vlan\"))";
         junos:must-message "Switch-options configuration is not allowed on interfaces which are part of secondary VLANs";
         leaf name {
           description "MAC address";
           junos:must "((!(\".. .. .. .. vlan-id all\") || all \".. vlan-id <*>\"))";
           junos:must-message " Specify vlan-id for qualified learning ";
           type jt:mac-addr;
         }
         uses apply-advanced;
         list vlan-id {
           key name;
           ordered-by user;
           description "VLAN ID of learning VLAN";
           junos:must "(\".. .. .. .. vlan-id all\")";
           junos:must-message "'vlan-id all' has to be configured for the bridging domain";
           leaf name {
             description "Learning VLAN";
             type union {
               type string {
                 pattern "<.*>|$.*";
               }
               type uint32 {
                 range "0 .. 4094";
               }
             }
           }
           uses apply-advanced;
         }
       }
       container interface-mac-ip-limit {
         description "Maximum number of MAC+IP bindings learned on the interface";
         uses apply-advanced;
         leaf limit {
           description "Maximum number of MAC+IP bindings per interface";
           type union {
             type string {
               pattern "<.*>|$.*";
             }
             type uint32;
           }
         }
       }
       leaf no-mac-learning {
         description "Disable dynamic MAC address learning";
         junos:must "(!(\".. .. .. .. .. vlans ${vlan} private-vlan\"))";
         junos:must-message "Switch-options configuration is not allowed on interfaces which are part of secondary VLANs";
         type empty;
       }
       leaf mac-pinning {
         description "Enable MAC pinning";
         type empty;
       }
       leaf persistent-learning {
         description "Enable persistent MAC learning on this interface";
         junos:must "(!(\"switch-options mac-table-aging-time \"))";
         junos:must-message "Persistent learning can not co-exist with mac-table-aging-time";
         type empty;
       }
     }
   }
   grouping juniper-protocols-bgp {
     uses apply-advanced;
     container path-selection {
       description "Configure path selection strategy";
       uses apply-advanced;
       leaf l2vpn-use-bgp-rules {
         description "Use standard BGP rules during L2VPN path selection";
         type empty;
       }
       leaf cisco-non-deterministic {
         description "Use Cisco IOS nondeterministic path selection algorithm";
         type empty;
       }
       leaf always-compare-med {
         description "Always compare MED values, regardless of neighbor AS";
         type empty;
       }
       container med-plus-igp {
         presence "enable med-plus-igp";
         description "Add IGP cost to next-hop to MED before comparing MED values";
         uses apply-advanced;
         leaf med-multiplier {
           description "Multiplier for MED";
           default "1";
           type union {
             type string {
               pattern "<.*>|$.*";
             }
             type uint16 {
               range "1 .. 1000";
             }
           }
         }
         leaf igp-multiplier {
           description "Multiplier for IGP cost to next-hop";
           default "1";
           type union {
             type string {
               pattern "<.*>|$.*";
             }
             type uint16 {
               range "1 .. 1000";
             }
           }
         }
       }
       leaf external-router-id {
         description "Compare router ID on BGP externals";
         type empty;
       }
       leaf as-path-ignore {
         description "Ignore AS path comparison during path selection";
         junos:must "(!(\".. .. .. .. routing-options multipath as-path-compare\"))";
         junos:must-message "Configuring 'as-path-ignore' is not allowed when 'as-path-compare' is enabled for this routing instance";
         type empty;
       }
     }
     container accept-prpd-connection {
       presence "enable accept-prpd-connection";
       description "Enable BGP to accept PRPD connections";
     }
     leaf advertise-from-main-vpn-tables {
       description "Advertise VPN routes from bgp.Xvpn.0 tables in master instance";
       type empty;
     }
     leaf stale-labels-holddown-period {
       description "Duration (sec) MPLS labels allocated by BGP are kept after they go stale";
       type union {
         type string {
           pattern "<.*>|$.*";
         }
         type int32 {
           range "1 .. 600";
         }
       }
     }
     leaf holddown-all-stale-labels {
       description "Hold all BGP stale-labels, facilating make-before-break for new label advertisements";
       type empty;
     }
     container egress-te-backup-paths {
       description "Backup-path for Egress-TE peer interface failure";
       uses apply-advanced;
       list template {
         key name;
         description "Backup-path template";
         leaf name {
           description "Name of Egress-TE backup path";
           type string {
             junos:posix-pattern "^.{1,64}$";
             junos:pattern-message "Must be a string of 64 characters or less";
           }
         }
         uses apply-advanced;
         list peer {
           key name;
           ordered-by user;
           description "Egress peer TE backup exit path";
           leaf name {
             description "Address of BGP peer to use as backup next-hop";
             type jt:ipaddr;
           }
           uses apply-advanced;
         }
         container remote-nexthop {
           description "Resolve and use tunnel to this next-hop as backup path";
           uses apply-advanced;
           leaf remote-nh-addr {
             description "Address of remote-nexthop to use as backup path";
             type jt:ipaddr;
           }
         }
         container ip-forward {
           presence "enable ip-forward";
           junos:must "(!(\".. remote-nexthop\"))";
           junos:must-message "'ip-forward' will not take effect as backup when 'remote-nexthop' is in use";
           description "Use IP-forward backup path for Egress TE";
           uses apply-advanced;
           leaf rti-name {
             description "Routing-instance to use as IP forward backup-path";
             type string {
               junos:posix-pattern "!^((__.*__)|(all)|(.*[ ].*)|(\"\")|(.{129,}))$";
               junos:pattern-message "Must be a non-reserved string of 128 characters or less with no spaces.";
             }
           }
         }
       }
     }
     leaf sr-preference-override {
       description "Replace received segment routing traffic engineering preference value with override value";
       type union {
         type uint32;
         type string {
           pattern "<.*>|$.*";
         }
       }
     }
     leaf vpn-apply-export {
       description "Apply BGP export policy when exporting VPN routes";
       type empty;
     }
     container family {
       description "Protocol family for NLRIs in updates";
       uses apply-advanced;
       container inet {
         description "IPv4 NLRI parameters";
         uses apply-advanced;
         container labeled-unicast {
           description "Include labeled unicast NLRI";
           presence "enable labeled-unicast";
           uses bgp-afi-labeled;
         }
         container segment-routing-te {
           description "Include segment-routing TE policy";
           presence "enable segment-routing-te";
           uses bgp-afi-srte;
         }
         container transport {
           description "Include Classful Transport NLRI";
           presence "enable transport";
           uses bgp-afi-inet-transport;
         }
         container unicast {
           description "Include unicast NLRI";
           presence "enable unicast";
           uses bgp-afi-topo;
         }
         container multicast {
           description "Include multicast NLRI";
           presence "enable multicast";
           uses bgp-afi-default;
         }
         container flow {
           description "Include flow NLRI";
           presence "enable flow";
           uses bgp-afi-flow-with-redirect-ip-action;
         }
         container any {
           description "Include unicast or multicast NLRI";
           presence "enable any";
           uses bgp-afi-default;
         }
       }
       container inet-vpn {
         description "IPv4 Layer 3 VPN NLRI parameters";
         uses apply-advanced;
         container unicast {
           description "Include unicast NLRI";
           presence "enable unicast";
           uses bgp-afi-l3vpn;
         }
         container multicast {
           description "Include multicast NLRI";
           presence "enable multicast";
           uses bgp-afi-vpn;
         }
         container flow {
           description "Include flow VPN NLRI";
           presence "enable flow";
           uses bgp-afi-flow-with-redirect-ip-action;
         }
         container any {
           description "Include unicast or multicast NLRI";
           presence "enable any";
           uses bgp-afi-vpn;
         }
       }
       container inet6 {
         description "IPv6 NLRI parameters";
         uses apply-advanced;
         container labeled-unicast {
           description "Include labeled unicast NLRI";
           presence "enable labeled-unicast";
           uses bgp-afi-inet6-labeled;
         }
         container segment-routing-te {
           description "Include segment-routing TE policy";
           presence "enable segment-routing-te";
           uses bgp-afi-srte;
         }
         container transport {
           description "Include Classful Transport NLRI";
           presence "enable transport";
           uses bgp-afi-inet6-transport;
         }
         container unicast {
           description "Include unicast NLRI";
           presence "enable unicast";
           uses bgp-afi-topo;
         }
         container multicast {
           description "Include multicast NLRI";
           presence "enable multicast";
           uses bgp-afi-default;
         }
         container flow {
           description "Include flow NLRI";
           presence "enable flow";
           uses bgp-afi-flow;
         }
         container any {
           description "Include unicast or multicast NLRI";
           presence "enable any";
           uses bgp-afi-default;
         }
       }
       container inet6-vpn {
         description "IPv6 Layer 3 VPN NLRI parameters";
         uses apply-advanced;
         container unicast {
           description "Include unicast NLRI";
           presence "enable unicast";
           uses bgp-afi-l3vpn;
         }
         container multicast {
           description "Include multicast NLRI";
           presence "enable multicast";
           uses bgp-afi-vpn;
         }
         container flow {
           description "Include flow VPN NLRI";
           presence "enable flow";
           uses bgp-afi-flow;
         }
         container any {
           description "Include unicast or multicast NLRI";
           presence "enable any";
           uses bgp-afi-vpn;
         }
       }
       container iso-vpn {
         description "ISO Layer 3 VPN NLRI parameters";
         uses apply-advanced;
         container unicast {
           description "Include unicast NLRI";
           presence "enable unicast";
           uses bgp-afi-vpn-protection;
         }
       }
       container l2vpn {
         description "MPLS-based Layer 2 VPN and VPLS NLRI parameters";
         uses apply-advanced;
         container auto-discovery-only {
           description "Include auto-discovery NLRI for LDP Layer 2 VPN and VPLS";
           presence "enable auto-discovery-only";
           uses bgp-afi-default;
         }
         container auto-discovery-mspw {
           description "Include auto-discovery NLRI for LDP Signalled MultiSegment PW";
           presence "enable auto-discovery-mspw";
           uses bgp-afi-default;
         }
         container signaling {
           description "Include Layer 2 VPN and VPLS signaling NLRI";
           presence "enable signaling";
           uses bgp-afi-l2vpn;
         }
       }
       container evpn {
         description "EVPN NLRI parameters";
         uses apply-advanced;
         container signaling {
           description "Include EVPN signaling NLRI";
           presence "enable signaling";
           uses bgp-afi-default;
         }
       }
       container inet-mvpn {
         description "IPv4 MVPN NLRI parameters";
         uses apply-advanced;
         container signaling {
           description "Include IPv4 multicast VPN signaling NLRI";
           presence "enable signaling";
           uses bgp-afi-default;
         }
       }
       container inet6-mvpn {
         description "IPv6 MVPN NLRI parameters";
         uses apply-advanced;
         container signaling {
           description "Include IPv6 multicast VPN signaling NLRI";
           presence "enable signaling";
           uses bgp-afi-default;
         }
       }
       container inet-mdt {
         description "IPv4 Multicast Distribution Tree (MDT) NLRI parameters";
         uses apply-advanced;
         container signaling {
           description "Include IPv4 multicast VPN auto-discovery NLRI";
           presence "enable signaling";
           uses bgp-afi-default;
         }
       }
       container traffic-engineering {
         description "Traffic Engineering (BGP-TE) NLRI parameters";
         uses apply-advanced;
         container unicast {
           description "Include BGP-TE NLRI";
           presence "enable unicast";
           uses bgp-afi-default;
         }
       }
       container route-target {
         presence "enable route-target";
         description "Route target NLRI used for VPN route filtering";
         uses apply-advanced;
         container prefix-limit {
           description "Limit maximum number of prefixes from a peer";
           uses bgpaf-prefix-limit;
         }
         container accepted-prefix-limit {
           description "Limit maximum number of prefixes accepted from a peer";
           uses bgpaf-accepted-prefix-limit;
         }
         container proxy-generate {
           presence "enable proxy-generate";
           description "Generate route target NLRI for peers that don't support it";
           uses apply-advanced;
           leaf-list route-target-policy {
             ordered-by user;
             description "Limit VPN routes that are used to generate proxy route-target filters";
             type jt:policy-algebra;
           }
         }
         leaf external-paths {
           description "Number of external paths accepted for route filtering";
           type union {
             type string {
               pattern "<.*>|$.*";
             }
             type uint32 {
               range "1 .. 256";
             }
           }
         }
         leaf advertise-default {
           description "Advertise default and suppress more specific routes";
           type empty;
         }
         leaf damping {
           description "Enable route flap damping";
           type empty;
         }
         container graceful-restart {
           description "BGP graceful restart options";
           uses bgp-af-gr;
         }
         leaf local-ipv4-address {
           description "Local IPv4 address";
           type jt:ipv4addr;
         }
         container output-queue-priority {
           description "Default output-queue to assign updates to";
           uses bgp-output-queue-priority-class;
         }
         container route-refresh-priority {
           description "Default output-queue to assign route refreshes to";
           uses bgp-output-queue-priority-class;
         }
         container withdraw-priority {
           description "Default output-queue to assign withdrawn routes to";
           uses bgp-output-queue-priority-class;
         }
       }
       container fabric {
         description "Fabric NLRI parameters";
         status deprecated;
         uses apply-advanced;
         container unicast {
           description "Include unicast NLRI";
           presence "enable unicast";
           uses bgp-afi-default;
         }
       }
       container bridge {
         description "Bridge NLRI parameters";
         status deprecated;
         uses apply-advanced;
         container unicast {
           description "Include unicast NLRI";
           presence "enable unicast";
           uses bgp-afi-default;
         }
       }
       container bridge-vpn {
         description "Bridge VPN NLRI parameters";
         status deprecated;
         uses apply-advanced;
         container unicast {
           description "Include unicast NLRI";
           presence "enable unicast";
           uses bgp-afi-vpn;
         }
       }
       container fabric-vpn {
         description "Fabric VPN NLRI parameters";
         status deprecated;
         uses apply-advanced;
         container unicast {
           description "Include unicast NLRI";
           presence "enable unicast";
           uses bgp-afi-vpn;
         }
       }
       container inet-bgpmcast {
         description "IPv4 BGPMCAST NLRI parameters";
         uses apply-advanced;
         container signaling {
           description "Include IPv4 BGP multicast signaling NLRI";
           presence "enable signaling";
           uses bgp-afi-default;
         }
       }
       container inet6-bgpmcast {
         description "IPv6 BGPMCAST NLRI parameters";
         uses apply-advanced;
         container signaling {
           description "Include IPv6 BGP multicast signaling NLRI";
           presence "enable signaling";
           uses bgp-afi-default;
         }
       }
     }
     container egress-te {
       presence "enable egress-te";
       description "Use Egress Peering traffic engineering";
       uses apply-advanced;
       leaf install-address {
         description "Address to use in egress-te created inet route";
         type jt:ipaddr;
       }
       container rib {
         description "Select primary table for Egress-TE routes";
         uses apply-advanced;
         leaf inet.0 {
           description "Install Egress-TE routes in inet.0";
           type empty;
         }
         leaf inet6.0 {
           description "Install Egress-TE routes in inet6.0";
           type empty;
         }
       }
       leaf no-install {
         description "Avoid installation to FIB or resolving over";
         type empty;
       }
       leaf-list import {
         ordered-by user;
         description "Import policy to set attributes";
         type jt:policy-algebra;
       }
       leaf backup-path {
         description "The 'egress-te-backup-paths template' to use for this peer";
         junos:must "(\"protocols bgp egress-te-backup-paths template $$\")";
         junos:must-message "bgp egress-te-backup-paths template not configured";
         type string {
           junos:posix-pattern "^.{1,64}$";
           junos:pattern-message "Must be a string of 64 characters or less";
         }
       }
     }
     leaf advertise-prefix-sid {
       description "Advertise prefix sid to E-BGP peers";
       type empty;
     }
     leaf accept-prefix-sid {
       description "Accept prefix sid from E-BGP peers";
       type empty;
     }
     leaf advertise-srgb {
       description "Advertise SRGB TLV";
       type empty;
     }
     leaf tcp-connect-port {
       description "TCP port number to connect with peer on";
       type union {
         type string {
           pattern "<.*>|$.*";
         }
         type uint16 {
           range "1 .. 65535";
         }
       }
     }
     leaf egress-te-sid-stats {
       description "Create BGP-Peer-SID sensor";
       type empty;
     }
     list egress-te-set-segment {
       key name;
       ordered-by user;
       description "Configure BGP-Peer-Set segment";
       leaf name {
         description "The BGP-Peer-Set segment name";
         type string {
           junos:posix-pattern "^.{1,64}$";
           junos:pattern-message "Must be a string of 64 characters or less";
         }
       }
       uses apply-advanced;
       container label {
         description "BGP-Peer-Set SID label from static label pool";
         uses apply-advanced;
         leaf label-value {
           description "BGP-Peer-Set SID label value from static label pool";
           type union {
             type string {
               pattern "<.*>|$.*";
             }
             type uint32 {
               range "16 .. 1048575";
             }
           }
         }
       }
       container egress-te-backup-segment {
         description "Backup segment for FRR";
         uses apply-advanced;
         container label {
           description "Backup segment label from static label pool";
           uses apply-advanced;
           leaf label-value {
             description "Backup segment label value from static label pool";
             type union {
               type string {
                 pattern "<.*>|$.*";
               }
               type uint32 {
                 range "16 .. 1048575";
               }
             }
           }
         }
       }
       container egress-te-backup-ip-forward {
         presence "enable egress-te-backup-ip-forward";
         description "Use IP-forward backup path for Egress TE";
         uses apply-advanced;
         leaf instance-name {
           description "Routing-instance to use as IP forward backup-path";
           type string {
             junos:posix-pattern "!^((__.*__)|(all)|(.*[ ].*)|(\"\")|(.{129,}))$";
             junos:pattern-message "Must be a non-reserved string of 128 characters or less with no spaces.";
           }
         }
       }
     }
     list group {
       key name;
       ordered-by user;
       description "Define a peer group";
       leaf name {
         description "Group name";
         type string;
       }
       uses apply-advanced;
       leaf type {
         description "Type of peer group";
         type enumeration {
           enum "internal" {
             description "IBGP group";
           }
           enum "external" {
             description "EBGP group";
           }
         }
       }
       leaf protocol {
         description "IGP to use to resolve the next hop";
         status deprecated;
         type enumeration {
           enum "rip" {
             description "Use RIP to resolve the BGP next hop";
             status deprecated;
           }
           enum "ospf" {
             description "Use OSPF to resolve the BGP next hop";
             status deprecated;
           }
           enum "isis" {
             description "Use IS-IS to resolve the BGP next hop";
             status deprecated;
           }
         }
       }
       container traceoptions {
         description "Trace options for BGP";
         uses apply-advanced;
         container file {
           description "Trace file options";
           leaf filename {
             description "Name of file in which to write trace information";
             type string {
               length "1 .. 1024";
               junos:posix-pattern "![/ %]";
               junos:pattern-message "Must not contain '/', % or a space";
             }
           }
           leaf replace {
             description "Replace trace file rather than appending to it";
             status deprecated;
             type empty;
           }
           leaf size {
             description "Maximum trace file size";
             type string;
           }
           leaf files {
             description "Maximum number of trace files";
             default "10";
             type union {
               type string {
                 pattern "<.*>|$.*";
               }
               type uint32 {
                 range "2 .. 1000";
               }
             }
           }
           leaf no-stamp {
             description "Do not timestamp trace file";
             status deprecated;
             type empty;
           }
           choice world-readable-choice {
             leaf world-readable {
               description "Allow any user to read the log file";
               type empty;
             }
             leaf no-world-readable {
               description "Don't allow any user to read the log file";
               type empty;
             }
           }
         }
         list flag {
           key name;
           ordered-by user;
           description "Tracing parameters";
           leaf name {
             type enumeration {
               enum "damping" {
                 description "Trace BGP damping information";
               }
               enum "packets" {
                 description "Trace all BGP protocol packets";
               }
               enum "open" {
                 description "Trace BGP open packets";
               }
               enum "update" {
                 description "Trace BGP update packets";
               }
               enum "keepalive" {
                 description "Trace BGP keepalive packets";
               }
               enum "refresh" {
                 description "Trace BGP refresh packets";
               }
               enum "nsr-synchronization" {
                 description "Trace NSR synchronization events";
               }
               enum "bfd" {
                 description "Trace BFD events";
               }
               enum "4byte-as" {
                 description "Trace 4 byte AS events";
               }
               enum "add-path" {
                 description "Trace add-path events";
               }
               enum "graceful-restart" {
                 description "Trace Graceful Restart events";
               }
               enum "egress-te" {
                 description "Egress Peering Traffic-Engineering events";
               }
               enum "thread-io" {
                 description "Trace threaded I/O processing";
               }
               enum "sharding" {
                 description "Trace BGP rib sharding";
               }
               enum "thread-update-io" {
                 description "Trace threaded update I/O processing";
               }
               enum "route-validation" {
                 description "Trace route validation";
               }
               enum "ipsec" {
                 description "Trace ipsec";
               }
               enum "route" {
                 description "Trace routing information";
               }
               enum "normal" {
                 description "Trace normal events";
               }
               enum "general" {
                 description "Trace general events";
               }
               enum "state" {
                 description "Trace state transitions";
               }
               enum "policy" {
                 description "Trace policy processing";
               }
               enum "task" {
                 description "Trace routing protocol task processing";
               }
               enum "timer" {
                 description "Trace routing protocol timer processing";
               }
               enum "all" {
                 description "Trace everything";
               }
             }
           }
           leaf send {
             description "Trace transmitted packets";
             type empty;
           }
           leaf receive {
             description "Trace received packets";
             type empty;
           }
           leaf detail {
             description "Trace detailed information";
             type empty;
           }
           leaf disable {
             description "Disable this trace flag";
             type empty;
           }
           container filter {
             description "Filter to apply to this flag";
             presence "enable filter";
             uses bgp_filter_obj;
           }
         }
       }
       leaf description {
         description "Text description";
         type string {
           length "1 .. 255";
         }
       }
       container metric-out {
         description "Route metric sent in MED";
         choice metric_param {
           case case_1 {
             leaf metric-value {
               description "Metric value";
               type union {
                 type string {
                   pattern "<.*>|$.*";
                 }
                 type uint32 {
                   range "0 .. 4294967295";
                 }
               }
             }
           }
           case case_2 {
             container minimum-igp {
               presence "enable minimum-igp";
               description "Track the minimum IGP metric";
               leaf metric-offset {
                 description "Metric offset for MED";
                 type union {
                   type int32;
                   type string {
                     pattern "<.*>|$.*";
                   }
                 }
               }
             }
           }
           case case_3 {
             container igp {
               presence "enable igp";
               description "Track the IGP metric";
               leaf metric-offset {
                 description "Metric offset for MED";
                 type union {
                   type int32;
                   type string {
                     pattern "<.*>|$.*";
                   }
                 }
               }
               leaf delay-med-update {
                 description "Delay updating MED when IGP metric increases";
                 type empty;
               }
             }
           }
           case case_4 {
             container effective-aigp {
               presence "enable effective-aigp";
               description "Track the effective AIGP metric";
               leaf metric-offset {
                 description "Metric offset for MED";
                 type union {
                   type int32;
                   type string {
                     pattern "<.*>|$.*";
                   }
                 }
               }
             }
           }
           case case_5 {
             container minimum-effective-aigp {
               presence "enable minimum-effective-aigp";
               description "Track the minimum effective AIGP metric";
               leaf metric-offset {
                 description "Metric offset for MED";
                 type union {
                   type int32;
                   type string {
                     pattern "<.*>|$.*";
                   }
                 }
               }
             }
           }
         }
       }
       container multihop {
         presence "enable multihop";
         description "Configure an EBGP multihop session";
         uses apply-advanced;
         leaf ttl {
           description "TTL value for the session";
           type union {
             type string {
               pattern "<.*>|$.*";
             }
             type uint8 {
               range "1 .. 255";
             }
           }
         }
         leaf no-nexthop-change {
           description "Do not change next hop to self in advertisements";
           type empty;
         }
       }
       leaf route-server-client {
         description "Enable route server client behavior";
         type empty;
       }
       leaf accept-remote-nexthop {
         description "Allow import policy to specify a non-directly connected next-hop";
         type empty;
       }
       leaf preference {
         description "Preference value";
         type union {
           type uint32;
           type string {
             pattern "<.*>|$.*";
           }
         }
       }
       leaf local-preference {
         description "Value of LOCAL_PREF path attribute";
         type union {
           type uint32;
           type string {
             pattern "<.*>|$.*";
           }
         }
       }
       leaf local-address {
         description "Address of local end of BGP session";
         type jt:ipaddr;
       }
       leaf local-interface {
         description "Local interface for IPv6 link local EBGP peering";
         type union {
           type jt:interface-name;
           type string {
             pattern "<.*>|$.*";
           }
         }
       }
       leaf forwarding-context {
         description "Routing-instance used for data-forwarding and transport-session";
         type string {
           junos:posix-pattern "!^((__.*__)|(all)|(.*[ ].*)|(\"\")|(.{129,}))$";
           junos:pattern-message "Must be a non-reserved string of 128 characters or less with no spaces.";
         }
       }
       leaf hold-time {
         description "Hold time used when negotiating with a peer";
         type union {
           type string {
             pattern "<.*>|$.*";
           }
           type uint32 {
             range "0 .. 65535";
           }
         }
       }
       leaf minimum-hold-time {
         description "Minimum hold time accepted from the peer";
         type union {
           type string {
             pattern "<.*>|$.*";
           }
           type uint32 {
             range "3 .. 65535";
           }
         }
       }
       leaf passive {
         description "Do not send open messages to a peer";
         type empty;
       }
       leaf advertise-inactive {
         description "Advertise inactive routes";
         type empty;
       }
       choice advertise-peer-as-choice {
         leaf advertise-peer-as {
           description "Advertise routes received from the same autonomous system";
           type empty;
         }
         leaf no-advertise-peer-as {
           description "Don't advertise routes received from the same autonomous system";
           type empty;
         }
       }
       container advertise-external {
         presence "enable advertise-external";
         description "Advertise best external routes";
         leaf conditional {
           description "Route matches active route upto med-comparison rule";
           type empty;
         }
       }
       leaf keep {
         description "How to retain routes in the routing table";
         type enumeration {
           enum "all" {
             description "Retain all routes";
           }
           enum "none" {
             description "Retain no routes";
           }
         }
       }
       leaf rfc6514-compliant-safi129 {
         description "Compliant with RFC6514 SAFI129 format";
         type empty;
       }
       leaf no-aggregator-id {
         description "Set router ID in aggregator path attribute to 0";
         type empty;
       }
       leaf mtu-discovery {
         description "Enable TCP path MTU discovery";
         type empty;
       }
       leaf enforce-first-as {
         description "Enforce first AS in AS-path is the neighbor's AS";
         type empty;
       }
       leaf out-delay {
         description "How long before exporting routes from routing table";
         type union {
           type string {
             pattern "<.*>|$.*";
           }
           type uint32 {
             range "0 .. 65535";
           }
         }
       }
       leaf ttl {
         description "TTL value for the single-hop peer";
         junos:must "((!(\".. .. type internal\") && !(\".. multihop\")))";
         junos:must-message "This option is valid only for single-hop EBGP neighbor";
         type enumeration {
           enum "1" {
           }
           enum "255" {
           }
         }
       }
       leaf log-updown {
         description "Log a message for peer state transitions";
         type empty;
       }
       leaf damping {
         description "Enable route flap damping";
         type empty;
       }
       leaf-list import {
         ordered-by user;
         description "Import policy";
         type jt:policy-algebra;
       }
       leaf-list nlri {
         ordered-by user;
         description "NLRI type to include in updates";
         status deprecated;
         type enumeration {
           enum "unicast" {
             description "Include unicast NLRI";
             status deprecated;
           }
           enum "multicast" {
             description "Include multicast NLRI";
             status deprecated;
           }
           enum "any" {
             description "Include any kind of NLRI";
             status deprecated;
           }
         }
       }
       container bgp-error-tolerance {
         presence "enable bgp-error-tolerance";
         description "Handle BGP malformed updates softly";
         uses apply-advanced;
         leaf malformed-update-log-interval {
           description "Time used when logging malformed update";
           default "300";
           units "seconds";
           type union {
             type string {
               pattern "<.*>|$.*";
             }
             type uint32 {
               range "10 .. 65535";
             }
           }
         }
         choice malformed-routes-limit-choice {
           case case_1 {
             leaf malformed-route-limit {
               description "Maximum number of malformed routes from a peer";
               default "1000";
               type union {
                 type string {
                   pattern "<.*>|$.*";
                 }
                 type uint32 {
                   range "0 .. 4294967295";
                 }
               }
             }
           }
           case case_2 {
             leaf no-malformed-route-limit {
               description "No malformed route limit";
               type empty;
             }
           }
         }
       }
       container family {
         description "Protocol family for NLRIs in updates";
         uses apply-advanced;
         container inet {
           description "IPv4 NLRI parameters";
           uses apply-advanced;
           container labeled-unicast {
             description "Include labeled unicast NLRI";
             presence "enable labeled-unicast";
             uses bgp-afi-labeled;
           }
           container segment-routing-te {
             description "Include segment-routing TE policy";
             presence "enable segment-routing-te";
             uses bgp-afi-srte;
           }
           container transport {
             description "Include Classful Transport NLRI";
             presence "enable transport";
             uses bgp-afi-inet-transport;
           }
           container unicast {
             description "Include unicast NLRI";
             presence "enable unicast";
             uses bgp-afi-topo;
           }
           container multicast {
             description "Include multicast NLRI";
             presence "enable multicast";
             uses bgp-afi-default;
           }
           container flow {
             description "Include flow NLRI";
             presence "enable flow";
             uses bgp-afi-flow-with-redirect-ip-action;
           }
           container any {
             description "Include unicast or multicast NLRI";
             presence "enable any";
             uses bgp-afi-default;
           }
         }
         container inet-vpn {
           description "IPv4 Layer 3 VPN NLRI parameters";
           uses apply-advanced;
           container unicast {
             description "Include unicast NLRI";
             presence "enable unicast";
             uses bgp-afi-l3vpn;
           }
           container multicast {
             description "Include multicast NLRI";
             presence "enable multicast";
             uses bgp-afi-vpn;
           }
           container flow {
             description "Include flow VPN NLRI";
             presence "enable flow";
             uses bgp-afi-flow-with-redirect-ip-action;
           }
           container any {
             description "Include unicast or multicast NLRI";
             presence "enable any";
             uses bgp-afi-vpn;
           }
         }
         container inet6 {
           description "IPv6 NLRI parameters";
           uses apply-advanced;
           container labeled-unicast {
             description "Include labeled unicast NLRI";
             presence "enable labeled-unicast";
             uses bgp-afi-inet6-labeled;
           }
           container segment-routing-te {
             description "Include segment-routing TE policy";
             presence "enable segment-routing-te";
             uses bgp-afi-srte;
           }
           container transport {
             description "Include Classful Transport NLRI";
             presence "enable transport";
             uses bgp-afi-inet6-transport;
           }
           container unicast {
             description "Include unicast NLRI";
             presence "enable unicast";
             uses bgp-afi-topo;
           }
           container multicast {
             description "Include multicast NLRI";
             presence "enable multicast";
             uses bgp-afi-default;
           }
           container flow {
             description "Include flow NLRI";
             presence "enable flow";
             uses bgp-afi-flow;
           }
           container any {
             description "Include unicast or multicast NLRI";
             presence "enable any";
             uses bgp-afi-default;
           }
         }
         container inet6-vpn {
           description "IPv6 Layer 3 VPN NLRI parameters";
           uses apply-advanced;
           container unicast {
             description "Include unicast NLRI";
             presence "enable unicast";
             uses bgp-afi-l3vpn;
           }
           container multicast {
             description "Include multicast NLRI";
             presence "enable multicast";
             uses bgp-afi-vpn;
           }
           container flow {
             description "Include flow VPN NLRI";
             presence "enable flow";
             uses bgp-afi-flow;
           }
           container any {
             description "Include unicast or multicast NLRI";
             presence "enable any";
             uses bgp-afi-vpn;
           }
         }
         container iso-vpn {
           description "ISO Layer 3 VPN NLRI parameters";
           uses apply-advanced;
           container unicast {
             description "Include unicast NLRI";
             presence "enable unicast";
             uses bgp-afi-vpn-protection;
           }
         }
         container l2vpn {
           description "MPLS-based Layer 2 VPN and VPLS NLRI parameters";
           uses apply-advanced;
           container auto-discovery-only {
             description "Include auto-discovery NLRI for LDP Layer 2 VPN and VPLS";
             presence "enable auto-discovery-only";
             uses bgp-afi-default;
           }
           container auto-discovery-mspw {
             description "Include auto-discovery NLRI for LDP Signalled MultiSegment PW";
             presence "enable auto-discovery-mspw";
             uses bgp-afi-default;
           }
           container signaling {
             description "Include Layer 2 VPN and VPLS signaling NLRI";
             presence "enable signaling";
             uses bgp-afi-l2vpn;
           }
         }
         container evpn {
           description "EVPN NLRI parameters";
           uses apply-advanced;
           container signaling {
             description "Include EVPN signaling NLRI";
             presence "enable signaling";
             uses bgp-afi-default;
           }
         }
         container inet-mvpn {
           description "IPv4 MVPN NLRI parameters";
           uses apply-advanced;
           container signaling {
             description "Include IPv4 multicast VPN signaling NLRI";
             presence "enable signaling";
             uses bgp-afi-default;
           }
         }
         container inet6-mvpn {
           description "IPv6 MVPN NLRI parameters";
           uses apply-advanced;
           container signaling {
             description "Include IPv6 multicast VPN signaling NLRI";
             presence "enable signaling";
             uses bgp-afi-default;
           }
         }
         container inet-mdt {
           description "IPv4 Multicast Distribution Tree (MDT) NLRI parameters";
           uses apply-advanced;
           container signaling {
             description "Include IPv4 multicast VPN auto-discovery NLRI";
             presence "enable signaling";
             uses bgp-afi-default;
           }
         }
         container traffic-engineering {
           description "Traffic Engineering (BGP-TE) NLRI parameters";
           uses apply-advanced;
           container unicast {
             description "Include BGP-TE NLRI";
             presence "enable unicast";
             uses bgp-afi-default;
           }
         }
         container route-target {
           presence "enable route-target";
           description "Route target NLRI used for VPN route filtering";
           uses apply-advanced;
           container prefix-limit {
             description "Limit maximum number of prefixes from a peer";
             uses bgpaf-prefix-limit;
           }
           container accepted-prefix-limit {
             description "Limit maximum number of prefixes accepted from a peer";
             uses bgpaf-accepted-prefix-limit;
           }
           container proxy-generate {
             presence "enable proxy-generate";
             description "Generate route target NLRI for peers that don't support it";
             uses apply-advanced;
             leaf-list route-target-policy {
               ordered-by user;
               description "Limit VPN routes that are used to generate proxy route-target filters";
               type jt:policy-algebra;
             }
           }
           leaf external-paths {
             description "Number of external paths accepted for route filtering";
             type union {
               type string {
                 pattern "<.*>|$.*";
               }
               type uint32 {
                 range "1 .. 256";
               }
             }
           }
           leaf advertise-default {
             description "Advertise default and suppress more specific routes";
             type empty;
           }
           leaf damping {
             description "Enable route flap damping";
             type empty;
           }
           container graceful-restart {
             description "BGP graceful restart options";
             uses bgp-af-gr;
           }
           leaf local-ipv4-address {
             description "Local IPv4 address";
             type jt:ipv4addr;
           }
           container output-queue-priority {
             description "Default output-queue to assign updates to";
             uses bgp-output-queue-priority-class;
           }
           container route-refresh-priority {
             description "Default output-queue to assign route refreshes to";
             uses bgp-output-queue-priority-class;
           }
           container withdraw-priority {
             description "Default output-queue to assign withdrawn routes to";
             uses bgp-output-queue-priority-class;
           }
         }
         container fabric {
           description "Fabric NLRI parameters";
           status deprecated;
           uses apply-advanced;
           container unicast {
             description "Include unicast NLRI";
             presence "enable unicast";
             uses bgp-afi-default;
           }
         }
         container bridge {
           description "Bridge NLRI parameters";
           status deprecated;
           uses apply-advanced;
           container unicast {
             description "Include unicast NLRI";
             presence "enable unicast";
             uses bgp-afi-default;
           }
         }
         container bridge-vpn {
           description "Bridge VPN NLRI parameters";
           status deprecated;
           uses apply-advanced;
           container unicast {
             description "Include unicast NLRI";
             presence "enable unicast";
             uses bgp-afi-vpn;
           }
         }
         container fabric-vpn {
           description "Fabric VPN NLRI parameters";
           status deprecated;
           uses apply-advanced;
           container unicast {
             description "Include unicast NLRI";
             presence "enable unicast";
             uses bgp-afi-vpn;
           }
         }
         container inet-bgpmcast {
           description "IPv4 BGPMCAST NLRI parameters";
           uses apply-advanced;
           container signaling {
             description "Include IPv4 BGP multicast signaling NLRI";
             presence "enable signaling";
             uses bgp-afi-default;
           }
         }
         container inet6-bgpmcast {
           description "IPv6 BGPMCAST NLRI parameters";
           uses apply-advanced;
           container signaling {
             description "Include IPv6 BGP multicast signaling NLRI";
             presence "enable signaling";
             uses bgp-afi-default;
           }
         }
       }
       leaf authentication-key {
         description "MD5 authentication key";
         type string {
           length "1 .. 126";
         }
       }
       leaf authentication-algorithm {
         description "Authentication algorithm name";
         junos:must "(\".. authentication-key-chain\")";
         junos:must-message "May not be configured without authentication-key-chain";
         junos:must "(!(\".. authentication-key\"))";
         junos:must-message "May not be configured with authentication-key";
         type enumeration {
           enum "md5" {
             description "Message Digest 5";
           }
           enum "hmac-sha-1-96" {
             description "Hash-based Message Authentication Code (SHA1) (96 bits)";
           }
           enum "aes-128-cmac-96" {
             description "Cipher-based Message Authentication Code (AES128) (96 bits)";
           }
           enum "ao" {
             description "TCP Authentication Option";
           }
         }
       }
       leaf tcpao-handling-with-digest-mismatch {
         description "Drop or continue without TCP-AO with digest mismatch with TCP-AO";
         junos:must "(!(\".. authentication-key\"))";
         junos:must-message "May not be configured with authentication-key";
         type enumeration {
           enum "drop-if-no-tcpao" {
             description "Drop the connection if Digest mismatched";
           }
           enum "allow-without-tcpao" {
             description "Allow the connection establishment without TCP-AO";
           }
         }
       }
       leaf authentication-key-chain {
         description "Key chain name";
         junos:must "(!(\".. authentication-key\"))";
         junos:must-message "May not be configured with authentication-key";
         junos:must "(\"security authentication-key-chains key-chain $$\")";
         junos:must-message "Referenced key-chain must be defined";
         type string {
           length "1 .. 128";
         }
       }
       leaf-list export {
         ordered-by user;
         description "Export policy";
         type jt:policy-algebra;
       }
       container remove-private {
         presence "enable remove-private";
         description "Remove well-known private AS numbers";
         uses apply-advanced;
         container all {
           presence "enable all";
           description "Remove all private AS numbers and do not stop at the first public AS number";
           container replace {
             presence "enable replace";
             description "Replace private AS numbers with the BGP Group's local AS number";
             leaf nearest {
               description "Use closest public AS number to replace a private AS number";
               type empty;
             }
           }
         }
         leaf no-peer-loop-check {
           description "Remove peer loop-check";
           type empty;
         }
       }
       leaf cluster {
         description "Cluster identifier";
         type jt:areaid;
       }
       leaf no-client-reflect {
         description "Disable intracluster route redistribution";
         type empty;
       }
       leaf peer-as {
         description " Autonomous system number in plain number or 'higher 16bits'.'Lower 16 bits' (asdot notation) format";
         type string {
           junos:posix-pattern "^[0-9]+(.[0-9]+)?$";
           junos:pattern-message "Use format 'x' or 'x.y' to specify number 'x' (Range 1 .. 4294967295) or number with higher 2 bytes 'x' (Range 0 .. 65535) and lower 2 bytes 'y' (Range 0 .. 65535) respectively";
         }
       }
       container local-as {
         description "Local autonomous system number";
         leaf as-number {
           description " Autonomous system number in plain number or 'higher 16bits'.'Lower 16 bits' (asdot notation) format";
           type string {
             junos:posix-pattern "^[0-9]+(.[0-9]+)?$";
             junos:pattern-message "Use format 'x' or 'x.y' to specify number 'x' (Range 1 .. 4294967295) or number with higher 2 bytes 'x' (Range 0 .. 65535) and lower 2 bytes 'y' (Range 0 .. 65535) respectively";
           }
         }
         leaf loops {
           description "Maximum number of times this AS can be in an AS path";
           type union {
             type string {
               pattern "<.*>|$.*";
             }
             type int32 {
               range "1 .. 10";
             }
           }
         }
         leaf private {
           description "Hide this local AS in paths learned from this peering";
           type empty;
         }
         leaf alias {
           description "Treat this AS as an alias to the system AS";
           type empty;
         }
         leaf no-prepend-global-as {
           description "Do not prepend global autonomous-system number in advertised paths";
           type empty;
         }
       }
       leaf ipsec-sa {
         description "IPSec SA name";
         junos:must "(\"security ipsec security-association $$\")";
         junos:must-message "Referenced IPSec Security Association must be defined";
         type string {
           length "1 .. 32";
         }
       }
       container graceful-shutdown {
         description "BGP peer graceful shutdown option";
         uses apply-advanced;
         container receiver {
           presence "enable receiver";
           description "BGP peer graceful-shutdown receiver";
           uses apply-advanced;
           leaf disable {
             description "Disable graceful-shutdown receiver";
             junos:must "(!(\".. .. sender\"))";
             junos:must-message "Receiver cannot be disabled on Sender";
             type empty;
           }
           leaf local-preference {
             description "Value of receiver LOCAL_PREF path attribute";
             type union {
               type uint32;
               type string {
                 pattern "<.*>|$.*";
               }
             }
           }
         }
         container sender {
           presence "enable sender";
           description "BGP peer graceful-shutdown sender";
           uses apply-advanced;
           leaf local-preference {
             description "Value of sender LOCAL_PREF path attribute";
             type union {
               type uint32;
               type string {
                 pattern "<.*>|$.*";
               }
             }
           }
         }
       }
       container shutdown {
         presence "enable shutdown";
         description "Shutdown";
         uses apply-advanced;
         leaf notify-message {
           description "Notification message";
           type string;
         }
       }
       leaf unconfigured-peer-graceful-restart {
         description "BGP unconfigured peer graceful restart options";
         junos:must "(\".. graceful-restart\")";
         junos:must-message "unconfigured-peer-graceful-restart is only valid with 'graceful-restart'";
         type empty;
       }
       container graceful-restart {
         presence "enable graceful-restart";
         description "BGP graceful restart options";
         uses apply-advanced;
         choice enable-disable {
           case case_1 {
             leaf disable {
               description "Disable graceful restart";
               type empty;
             }
           }
         }
         leaf restart-time {
           description "Restart time used when negotiating with a peer";
           junos:must "((\"routing-options graceful-restart\" || \"fabric routing-options graceful-restart\"))";
           junos:must-message "restart-time is only valid with 'routing-options graceful-restart'";
           type union {
             type string {
               pattern "<.*>|$.*";
             }
             type uint32 {
               range "1 .. 1800";
             }
           }
         }
         leaf stale-routes-time {
           description "Maximum time for which stale routes are kept";
           type union {
             type string {
               pattern "<.*>|$.*";
             }
             type uint32 {
               range "1 .. 1800";
             }
           }
         }
         container long-lived {
           description "Long-lived graceful restart options";
           uses apply-advanced;
           container receiver {
             description "Long-lived graceful restart receiver (helper) options";
             uses apply-advanced;
             choice enable-disable {
               case case_1 {
                 leaf disable {
                   description "Disable receiver (helper) functionality";
                   type empty;
                 }
               }
             }
           }
           container advertise-to-non-llgr-neighbor {
             presence "enable advertise-to-non-llgr-neighbor";
             description "Advertise stale routes to non-LLGR neighbors";
             uses apply-advanced;
             leaf omit-no-export {
               description "Do not attach no-export community to stale routes";
               type empty;
             }
           }
         }
         leaf disable-notification-extensions {
           description "Disable notification extensions";
           type empty;
         }
         leaf forwarding-state-bit {
           description "Control forwarding-state flag negotiation";
           type enumeration {
             enum "as-rr-client" {
               description "As for a route reflector client";
             }
             enum "from-fib" {
               description "Always use state of associated FIB(s)";
             }
           }
         }
         leaf dont-help-shared-fate-bfd-down {
           description "Honor BFD-Down(C=0) if GR-restart not in progress";
           type empty;
         }
       }
       leaf include-mp-next-hop {
         description "Include NEXT-HOP attribute in multiprotocol updates";
         type empty;
       }
       leaf disable-4byte-as {
         description "Disable 4 byte AS capability advertisement";
         type empty;
       }
       container idle-after-switch-over {
         description "Stop peer session from coming up after nonstop-routing switch-over";
         choice idle-interval {
           case case_1 {
             leaf forever {
               description "Idle the peer until the user intervenes";
               type empty;
             }
           }
           case case_2 {
             leaf timeout {
               description "Timeout value, in seconds, for starting peer after switch over";
               type union {
                 type string {
                   pattern "<.*>|$.*";
                 }
                 type uint32 {
                   range "1 .. 4294967295";
                 }
               }
             }
           }
         }
       }
       container outbound-route-filter {
         junos:must "(!(\"system processes routing bgp update-threading\"))";
         junos:must-message "Can't be configured together with update-threading";
         description "Dynamically negotiated cooperative route filtering";
         uses apply-advanced;
         leaf bgp-orf-cisco-mode {
           description "Using BGP ORF capability code 130 and Prefix ORF type 128";
           type empty;
         }
         container extended-community {
           description "Extended community filtering";
           status deprecated;
           uses apply-advanced;
           choice accept-choice {
             leaf accept {
               description "Honor remote requests for extended community ORF";
               type empty;
             }
             leaf no-accept {
               description "Don't honor remote requests for extended community ORF";
               type empty;
             }
           }
           leaf vrf-filter {
             description "Request remote filtering using locally configured VRF import targets";
             type empty;
           }
         }
         container prefix-based {
           presence "enable prefix-based";
           description "Prefix-based outbound route filtering";
           uses apply-advanced;
           container accept {
             presence "enable accept";
             description "Honor Prefix-based ORFs from remote peers";
             uses apply-advanced;
             leaf inet {
               description "Honor IPv4 prefix filters";
               type empty;
             }
             leaf inet6 {
               description "Honor IPv6 prefix filters";
               type empty;
             }
           }
         }
       }
       container message-batching {
         description "DEPRECATED - Batching of outgoing messages";
         status deprecated;
         uses apply-advanced;
         choice enable-disable {
           case case_1 {
             leaf enable {
               description "Enable parameter";
               type empty;
             }
           }
           case case_2 {
             leaf disable {
               description "Disable parameter";
               type empty;
             }
           }
         }
         leaf interval {
           description "DEPRECATED - Interval over which to batch messages";
           default "250";
           units "milliseconds";
           type union {
             type string {
               pattern "<.*>|$.*";
             }
             type uint32 {
               range "100 .. 1000";
             }
           }
         }
       }
       container multipath {
         presence "enable multipath";
         description "Allow load sharing among multiple BGP paths";
         uses apply-advanced;
         leaf disable {
           description "Disable Multipath";
           type empty;
         }
         leaf multiple-as {
           description "Use paths received from different ASs";
           type empty;
         }
         leaf allow-protection {
           description "Allow protection for multipath legs";
           type empty;
         }
         leaf pause-computation-during-churn {
           description "Pause multipath job to absorb churn";
           type empty;
         }
         leaf list-nexthop {
           description "Use List-NH for homogenous nexthop-set also";
           type empty;
         }
       }
       leaf tcp-mss {
         description "Maximum TCP segment size";
         type union {
           type string {
             pattern "<.*>|$.*";
           }
           type uint32 {
             range "1 .. 4096";
           }
         }
       }
       leaf bgp-identifier {
         description "BGP Identifier";
         type jt:ipv4addr;
       }
       leaf tcp-aggressive-transmission {
         description "Enable aggressive transmission of pure TCP ACKs and retransmissions";
         type empty;
       }
       container bmp {
         description "Specific settings to override the routing-options settings";
         uses apply-advanced;
         leaf monitor {
           description "Enable/Disable monitoring";
           type enumeration {
             enum "enable" {
               description "Enable monitoring of BGP peer(s)";
             }
             enum "disable" {
               description "Disable monitoring of BGP peer(s)";
             }
           }
         }
         container route-monitoring {
           description "Control route monitoring settings";
           uses apply-advanced;
           leaf none {
             description "Do not send route monitoring messages";
             junos:must "((!(\".. pre-policy\") && (!(\".. post-policy\") && !(\".. rib-out\"))))";
             junos:must-message "May not be configured with pre-policy or post-policy or rib-out";
             type empty;
           }
           container pre-policy {
             presence "enable pre-policy";
             description "Send pre-policy route monitoring messages";
             leaf exclude-non-feasible {
               description "Exclude looped routes, etc";
               type empty;
             }
           }
           container post-policy {
             presence "enable post-policy";
             description "Send post-policy route monitoring messages";
             leaf exclude-non-eligible {
               description "Exclude unresolved routes, etc.";
               type empty;
             }
           }
           container rib-out {
             presence "enable rib-out";
             junos:must "((!(\"system processes routing bgp update-threading\") || \"system processes routing bgp rib-sharding\"))";
             junos:must-message "Update threading can't be configured together with bmp rib-out monitoring";
             description "Send adj-ribs-out route monitoring messages";
             leaf pre-policy {
               description "Send pre-policy adj-ribs-out route monitoring messages";
               type empty;
             }
             leaf post-policy {
               description "Send post-policy adj-ribs-out route monitoring messages";
               type empty;
             }
           }
         }
       }
       container advertise-bgp-static {
         presence "enable advertise-bgp-static";
         description "Advertise bgp-static routes";
         uses apply-advanced;
         leaf-list policy {
           ordered-by user;
           description "Static route advertisement policy";
           type jt:policy-algebra;
         }
       }
       leaf add-path-display-ipv4-address {
         description "Display add-path path-id in IPv4 address format";
         type empty;
       }
       container bfd-liveness-detection {
         description "Bidirectional Forwarding Detection (BFD) options";
         uses apply-advanced;
         leaf version {
           description "BFD protocol version number";
           default "automatic";
           type enumeration {
             enum "0" {
               description "BFD version 0 (deprecated)";
             }
             enum "1" {
               description "BFD version 1";
             }
             enum "automatic" {
               description "Choose BFD version automatically";
             }
           }
         }
         leaf minimum-interval {
           description "Minimum transmit and receive interval";
           units "milliseconds";
           type union {
             type string {
               pattern "<.*>|$.*";
             }
             type uint32 {
               range "1 .. 255000";
             }
           }
         }
         leaf minimum-transmit-interval {
           description "Minimum transmit interval";
           status deprecated;
           units "milliseconds";
           type union {
             type string {
               pattern "<.*>|$.*";
             }
             type uint32 {
               range "1 .. 255000";
             }
           }
         }
         leaf minimum-receive-interval {
           description "Minimum receive interval";
           units "milliseconds";
           type union {
             type string {
               pattern "<.*>|$.*";
             }
             type uint32 {
               range "1 .. 255000";
             }
           }
         }
         leaf multiplier {
           description "Detection time multiplier";
           default "3";
           type union {
             type string {
               pattern "<.*>|$.*";
             }
             type uint32 {
               range "1 .. 255";
             }
           }
         }
         choice adaptation-choice {
           case case_1 {
             leaf no-adaptation {
               description "Disable adaptation";
               type empty;
             }
           }
         }
         container transmit-interval {
           description "Transmit-interval options";
           uses apply-advanced;
           leaf minimum-interval {
             description "Minimum transmit interval";
             units "milliseconds";
             type union {
               type string {
                 pattern "<.*>|$.*";
               }
               type uint32 {
                 range "1 .. 255000";
               }
             }
           }
           leaf threshold {
             description "High transmit interval triggering a trap";
             units "milliseconds";
             type union {
               type uint32;
               type string {
                 pattern "<.*>|$.*";
               }
             }
           }
         }
         container detection-time {
           description "Detection-time options";
           uses apply-advanced;
           leaf threshold {
             description "High detection-time triggering a trap";
             units "milliseconds";
             type union {
               type uint32;
               type string {
                 pattern "<.*>|$.*";
               }
             }
           }
         }
         container authentication {
           description "Authentication options";
           uses apply-advanced;
           leaf key-chain {
             description "Key chain name";
             junos:must "(\".. algorithm\")";
             junos:must-message "May not be configured without algorithm";
             junos:must "(\"security authentication-key-chains key-chain $$\")";
             junos:must-message "Referenced key-chain must be defined";
             type string;
           }
           leaf algorithm {
             description "Algorithm name";
             junos:must "(\".. key-chain\")";
             junos:must-message "May not be configured without key-chain";
             type enumeration {
               enum "simple-password" {
                 description "Simple password";
               }
               enum "keyed-md5" {
                 description "Keyed message Digest 5";
               }
               enum "meticulous-keyed-md5" {
                 description "Meticulous keyed message Digest 5";
               }
               enum "keyed-sha-1" {
                 description "Keyed secure hash algorithm (SHA1) ";
               }
               enum "meticulous-keyed-sha-1" {
                 description "Meticulous keyed secure hash algorithm (SHA1) ";
               }
             }
           }
           leaf loose-check {
             description "Verify authentication only if authentication is negotiated";
             type empty;
           }
         }
         leaf session-mode {
           description "BFD single-hop or multihop session-mode";
           default "automatic";
           type enumeration {
             enum "automatic" {
               description "Choose session-mode automatically";
             }
             enum "single-hop" {
               description "Use single-hop";
             }
             enum "multihop" {
               description "Use multihop";
             }
           }
         }
         leaf holddown-interval {
           description "Time to hold the session-UP notification to the client";
           units "milliseconds";
           junos:must "(!(\".. .. type internal\"))";
           junos:must-message "bfd holddown-interval is only valid for EBGP.";
           type union {
             type string {
               pattern "<.*>|$.*";
             }
             type uint32 {
               range "0 .. 255000";
             }
           }
         }
       }
       leaf as-override {
         description "Replace neighbor AS number with our AS number";
         type empty;
       }
       leaf-list allow {
         ordered-by user;
         description "Configure peer connections for specific networks";
         type jt:ipprefix;
       }
       list dynamic-neighbor {
         key name;
         ordered-by user;
         description "Configure peer options for specific networks";
         leaf name {
           description "Template name";
           junos:must "((\".. allow\" || \".. peer-auto-discovery\"))";
           junos:must-message "dynamic-neighbor must enable allow or peer-auto-discovery";
           type string;
         }
         uses apply-advanced;
         leaf-list allow {
           ordered-by user;
           description "Configure peer connections for specific networks";
           type jt:ipprefix;
         }
         leaf authentication-key {
           description "MD5 authentication key";
           type string {
             length "1 .. 126";
           }
         }
         leaf authentication-algorithm {
           description "Authentication algorithm name";
           junos:must "(\".. authentication-key-chain\")";
           junos:must-message "May not be configured without authentication-key-chain";
           junos:must "(!(\".. authentication-key\"))";
           junos:must-message "May not be configured with authentication-key";
           type enumeration {
             enum "md5" {
               description "Message Digest 5";
             }
             enum "hmac-sha-1-96" {
               description "Hash-based Message Authentication Code (SHA1) (96 bits)";
             }
             enum "aes-128-cmac-96" {
               description "Cipher-based Message Authentication Code (AES128) (96 bits)";
             }
             enum "ao" {
               description "TCP Authentication Option";
             }
           }
         }
         leaf tcpao-handling-with-digest-mismatch {
           description "Drop or continue without TCP-AO with digest mismatch with TCP-AO";
           junos:must "(!(\".. authentication-key\"))";
           junos:must-message "May not be configured with authentication-key";
           type enumeration {
             enum "drop-if-no-tcpao" {
               description "Drop the connection if Digest mismatched";
             }
             enum "allow-without-tcpao" {
               description "Allow the connection establishment without TCP-AO";
             }
           }
         }
         leaf authentication-key-chain {
           description "Key chain name";
           junos:must "(!(\".. authentication-key\"))";
           junos:must-message "May not be configured with authentication-key";
           junos:must "(\"security authentication-key-chains key-chain $$\")";
           junos:must-message "Referenced key-chain must be defined";
           type string {
             length "1 .. 128";
           }
         }
         container peer-auto-discovery {
           junos:must "((!(\".. authentication-algorithm\") && (!(\".. .. authentication-algorithm\") && !(\".. .. .. authentication-algorithm\"))))";
           junos:must-message "Can't be configured along with authentication-algorithm";
           junos:must "((!(\".. authentication-key\") && (!(\".. .. authentication-key\") && !(\".. .. .. authentication-key\"))))";
           junos:must-message "Can't be configured along with authentication-key";
           junos:must "(!(\".. allow\"))";
           junos:must-message "peer-auto-discovery and allow cannot be configured in the same dynamic-neighbor";
           junos:must "((!(\".. .. type internal\") && !(\".. .. multihop\")))";
           junos:must-message "peer-auto-discovery is valid only for single-hop EBGP neighbor";
           description "Configure auto-discovery options for BGP neighbors";
           uses apply-advanced;
           container family {
             description "Address family based neighbor auto-discovery parameters";
             container inet6 {
               uses apply-advanced;
               choice auto-discovery-type {
                 case case_1 {
                   container ipv6-nd {
                     presence "enable ipv6-nd";
                     description "Use ipv6 neighbor discovery to learn neighbor address";
                   }
                 }
               }
             }
           }
           list interface {
             key name;
             leaf name {
               description "Configure interfaces over which to discover bgp neighbors";
               type union {
                 type jt:interface-name;
                 type string {
                   pattern "<.*>|$.*";
                 }
               }
             }
             uses apply-advanced;
             choice enable-disable {
               case case_1 {
                 leaf disable {
                   description "Disable peer discovery on interface";
                   type empty;
                 }
               }
             }
           }
         }
       }
       container optimal-route-reflection {
         junos:must "(\".. type internal\")";
         junos:must-message "Must be configured with type internal";
         description "Enable optimal route reflection for this client group";
         uses apply-advanced;
         leaf igp-primary {
           description "Primary node identifier for this client group";
           type jt:ipv4addr;
         }
         leaf igp-backup {
           description "Backup node identifier for this client group";
           type jt:ipv4addr;
         }
       }
       leaf peer-as-list {
         description "Configure list of peer autonomous systems for unconfigured neighbors";
         junos:must "((\".. allow\" || \".. dynamic-neighbor\"))";
         junos:must-message "May be configured only with allow or dynamic-neighbor";
         type string;
       }
       leaf mvpn-iana-rt-import {
         description "Use IANA assigned rt-import type value for MVPN";
         status deprecated;
         type empty;
       }
       list neighbor {
         key name;
         ordered-by user;
         description "Configure a neighbor";
         leaf name {
           type jt:ipaddr-scoped;
         }
         uses apply-advanced;
         container traceoptions {
           description "Trace options for BGP";
           uses apply-advanced;
           container file {
             description "Trace file options";
             leaf filename {
               description "Name of file in which to write trace information";
               type string {
                 length "1 .. 1024";
                 junos:posix-pattern "![/ %]";
                 junos:pattern-message "Must not contain '/', % or a space";
               }
             }
             leaf replace {
               description "Replace trace file rather than appending to it";
               status deprecated;
               type empty;
             }
             leaf size {
               description "Maximum trace file size";
               type string;
             }
             leaf files {
               description "Maximum number of trace files";
               default "10";
               type union {
                 type string {
                   pattern "<.*>|$.*";
                 }
                 type uint32 {
                   range "2 .. 1000";
                 }
               }
             }
             leaf no-stamp {
               description "Do not timestamp trace file";
               status deprecated;
               type empty;
             }
             choice world-readable-choice {
               leaf world-readable {
                 description "Allow any user to read the log file";
                 type empty;
               }
               leaf no-world-readable {
                 description "Don't allow any user to read the log file";
                 type empty;
               }
             }
           }
           list flag {
             key name;
             ordered-by user;
             description "Tracing parameters";
             leaf name {
               type enumeration {
                 enum "damping" {
                   description "Trace BGP damping information";
                 }
                 enum "packets" {
                   description "Trace all BGP protocol packets";
                 }
                 enum "open" {
                   description "Trace BGP open packets";
                 }
                 enum "update" {
                   description "Trace BGP update packets";
                 }
                 enum "keepalive" {
                   description "Trace BGP keepalive packets";
                 }
                 enum "refresh" {
                   description "Trace BGP refresh packets";
                 }
                 enum "nsr-synchronization" {
                   description "Trace NSR synchronization events";
                 }
                 enum "bfd" {
                   description "Trace BFD events";
                 }
                 enum "4byte-as" {
                   description "Trace 4 byte AS events";
                 }
                 enum "add-path" {
                   description "Trace add-path events";
                 }
                 enum "graceful-restart" {
                   description "Trace Graceful Restart events";
                 }
                 enum "egress-te" {
                   description "Egress Peering Traffic-Engineering events";
                 }
                 enum "thread-io" {
                   description "Trace threaded I/O processing";
                 }
                 enum "sharding" {
                   description "Trace BGP rib sharding";
                 }
                 enum "thread-update-io" {
                   description "Trace threaded update I/O processing";
                 }
                 enum "route-validation" {
                   description "Trace route validation";
                 }
                 enum "ipsec" {
                   description "Trace ipsec";
                 }
                 enum "route" {
                   description "Trace routing information";
                 }
                 enum "normal" {
                   description "Trace normal events";
                 }
                 enum "general" {
                   description "Trace general events";
                 }
                 enum "state" {
                   description "Trace state transitions";
                 }
                 enum "policy" {
                   description "Trace policy processing";
                 }
                 enum "task" {
                   description "Trace routing protocol task processing";
                 }
                 enum "timer" {
                   description "Trace routing protocol timer processing";
                 }
                 enum "all" {
                   description "Trace everything";
                 }
               }
             }
             leaf send {
               description "Trace transmitted packets";
               type empty;
             }
             leaf receive {
               description "Trace received packets";
               type empty;
             }
             leaf detail {
               description "Trace detailed information";
               type empty;
             }
             leaf disable {
               description "Disable this trace flag";
               type empty;
             }
             container filter {
               description "Filter to apply to this flag";
               presence "enable filter";
               uses bgp_filter_obj;
             }
           }
         }
         leaf description {
           description "Text description";
           type string {
             length "1 .. 255";
           }
         }
         container metric-out {
           description "Route metric sent in MED";
           choice metric_param {
             case case_1 {
               leaf metric-value {
                 description "Metric value";
                 type union {
                   type string {
                     pattern "<.*>|$.*";
                   }
                   type uint32 {
                     range "0 .. 4294967295";
                   }
                 }
               }
             }
             case case_2 {
               container minimum-igp {
                 presence "enable minimum-igp";
                 description "Track the minimum IGP metric";
                 leaf metric-offset {
                   description "Metric offset for MED";
                   type union {
                     type int32;
                     type string {
                       pattern "<.*>|$.*";
                     }
                   }
                 }
               }
             }
             case case_3 {
               container igp {
                 presence "enable igp";
                 description "Track the IGP metric";
                 leaf metric-offset {
                   description "Metric offset for MED";
                   type union {
                     type int32;
                     type string {
                       pattern "<.*>|$.*";
                     }
                   }
                 }
                 leaf delay-med-update {
                   description "Delay updating MED when IGP metric increases";
                   type empty;
                 }
               }
             }
             case case_4 {
               container effective-aigp {
                 presence "enable effective-aigp";
                 description "Track the effective AIGP metric";
                 leaf metric-offset {
                   description "Metric offset for MED";
                   type union {
                     type int32;
                     type string {
                       pattern "<.*>|$.*";
                     }
                   }
                 }
               }
             }
             case case_5 {
               container minimum-effective-aigp {
                 presence "enable minimum-effective-aigp";
                 description "Track the minimum effective AIGP metric";
                 leaf metric-offset {
                   description "Metric offset for MED";
                   type union {
                     type int32;
                     type string {
                       pattern "<.*>|$.*";
                     }
                   }
                 }
               }
             }
           }
         }
         container multihop {
           presence "enable multihop";
           description "Configure an EBGP multihop session";
           uses apply-advanced;
           leaf ttl {
             description "TTL value for the session";
             type union {
               type string {
                 pattern "<.*>|$.*";
               }
               type uint8 {
                 range "1 .. 255";
               }
             }
           }
           leaf no-nexthop-change {
             description "Do not change next hop to self in advertisements";
             type empty;
           }
         }
         leaf route-server-client {
           description "Enable route server client behavior";
           type empty;
         }
         leaf accept-remote-nexthop {
           description "Allow import policy to specify a non-directly connected next-hop";
           type empty;
         }
         leaf preference {
           description "Preference value";
           type union {
             type uint32;
             type string {
               pattern "<.*>|$.*";
             }
           }
         }
         leaf local-preference {
           description "Value of LOCAL_PREF path attribute";
           type union {
             type uint32;
             type string {
               pattern "<.*>|$.*";
             }
           }
         }
         leaf local-address {
           description "Address of local end of BGP session";
           type jt:ipaddr;
         }
         leaf local-interface {
           description "Local interface for IPv6 link local EBGP peering";
           type union {
             type jt:interface-name;
             type string {
               pattern "<.*>|$.*";
             }
           }
         }
         leaf forwarding-context {
           description "Routing-instance used for data-forwarding and transport-session";
           type string {
             junos:posix-pattern "!^((__.*__)|(all)|(.*[ ].*)|(\"\")|(.{129,}))$";
             junos:pattern-message "Must be a non-reserved string of 128 characters or less with no spaces.";
           }
         }
         leaf hold-time {
           description "Hold time used when negotiating with a peer";
           type union {
             type string {
               pattern "<.*>|$.*";
             }
             type uint32 {
               range "0 .. 65535";
             }
           }
         }
         leaf minimum-hold-time {
           description "Minimum hold time accepted from the peer";
           type union {
             type string {
               pattern "<.*>|$.*";
             }
             type uint32 {
               range "3 .. 65535";
             }
           }
         }
         leaf passive {
           description "Do not send open messages to a peer";
           type empty;
         }
         leaf advertise-inactive {
           description "Advertise inactive routes";
           type empty;
         }
         choice advertise-peer-as-choice {
           leaf advertise-peer-as {
             description "Advertise routes received from the same autonomous system";
             type empty;
           }
           leaf no-advertise-peer-as {
             description "Don't advertise routes received from the same autonomous system";
             type empty;
           }
         }
         container advertise-external {
           presence "enable advertise-external";
           description "Advertise best external routes";
           leaf conditional {
             description "Route matches active route upto med-comparison rule";
             type empty;
           }
         }
         leaf keep {
           description "How to retain routes in the routing table";
           type enumeration {
             enum "all" {
               description "Retain all routes";
             }
             enum "none" {
               description "Retain no routes";
             }
           }
         }
         leaf rfc6514-compliant-safi129 {
           description "Compliant with RFC6514 SAFI129 format";
           type empty;
         }
         leaf no-aggregator-id {
           description "Set router ID in aggregator path attribute to 0";
           type empty;
         }
         leaf mtu-discovery {
           description "Enable TCP path MTU discovery";
           type empty;
         }
         leaf enforce-first-as {
           description "Enforce first AS in AS-path is the neighbor's AS";
           type empty;
         }
         leaf out-delay {
           description "How long before exporting routes from routing table";
           type union {
             type string {
               pattern "<.*>|$.*";
             }
             type uint32 {
               range "0 .. 65535";
             }
           }
         }
         leaf ttl {
           description "TTL value for the single-hop peer";
           junos:must "((!(\".. .. type internal\") && !(\".. multihop\")))";
           junos:must-message "This option is valid only for single-hop EBGP neighbor";
           type enumeration {
             enum "1" {
             }
             enum "255" {
             }
           }
         }
         leaf log-updown {
           description "Log a message for peer state transitions";
           type empty;
         }
         leaf damping {
           description "Enable route flap damping";
           type empty;
         }
         leaf-list import {
           ordered-by user;
           description "Import policy";
           type jt:policy-algebra;
         }
         leaf-list nlri {
           ordered-by user;
           description "NLRI type to include in updates";
           status deprecated;
           type enumeration {
             enum "unicast" {
               description "Include unicast NLRI";
               status deprecated;
             }
             enum "multicast" {
               description "Include multicast NLRI";
               status deprecated;
             }
             enum "any" {
               description "Include any kind of NLRI";
               status deprecated;
             }
           }
         }
         container bgp-error-tolerance {
           presence "enable bgp-error-tolerance";
           description "Handle BGP malformed updates softly";
           uses apply-advanced;
           leaf malformed-update-log-interval {
             description "Time used when logging malformed update";
             default "300";
             units "seconds";
             type union {
               type string {
                 pattern "<.*>|$.*";
               }
               type uint32 {
                 range "10 .. 65535";
               }
             }
           }
           choice malformed-routes-limit-choice {
             case case_1 {
               leaf malformed-route-limit {
                 description "Maximum number of malformed routes from a peer";
                 default "1000";
                 type union {
                   type string {
                     pattern "<.*>|$.*";
                   }
                   type uint32 {
                     range "0 .. 4294967295";
                   }
                 }
               }
             }
             case case_2 {
               leaf no-malformed-route-limit {
                 description "No malformed route limit";
                 type empty;
               }
             }
           }
         }
         container family {
           description "Protocol family for NLRIs in updates";
           uses apply-advanced;
           container inet {
             description "IPv4 NLRI parameters";
             uses apply-advanced;
             container labeled-unicast {
               description "Include labeled unicast NLRI";
               presence "enable labeled-unicast";
               uses bgp-afi-labeled;
             }
             container segment-routing-te {
               description "Include segment-routing TE policy";
               presence "enable segment-routing-te";
               uses bgp-afi-srte;
             }
             container transport {
               description "Include Classful Transport NLRI";
               presence "enable transport";
               uses bgp-afi-inet-transport;
             }
             container unicast {
               description "Include unicast NLRI";
               presence "enable unicast";
               uses bgp-afi-topo;
             }
             container multicast {
               description "Include multicast NLRI";
               presence "enable multicast";
               uses bgp-afi-default;
             }
             container flow {
               description "Include flow NLRI";
               presence "enable flow";
               uses bgp-afi-flow-with-redirect-ip-action;
             }
             container any {
               description "Include unicast or multicast NLRI";
               presence "enable any";
               uses bgp-afi-default;
             }
           }
           container inet-vpn {
             description "IPv4 Layer 3 VPN NLRI parameters";
             uses apply-advanced;
             container unicast {
               description "Include unicast NLRI";
               presence "enable unicast";
               uses bgp-afi-l3vpn;
             }
             container multicast {
               description "Include multicast NLRI";
               presence "enable multicast";
               uses bgp-afi-vpn;
             }
             container flow {
               description "Include flow VPN NLRI";
               presence "enable flow";
               uses bgp-afi-flow-with-redirect-ip-action;
             }
             container any {
               description "Include unicast or multicast NLRI";
               presence "enable any";
               uses bgp-afi-vpn;
             }
           }
           container inet6 {
             description "IPv6 NLRI parameters";
             uses apply-advanced;
             container labeled-unicast {
               description "Include labeled unicast NLRI";
               presence "enable labeled-unicast";
               uses bgp-afi-inet6-labeled;
             }
             container segment-routing-te {
               description "Include segment-routing TE policy";
               presence "enable segment-routing-te";
               uses bgp-afi-srte;
             }
             container transport {
               description "Include Classful Transport NLRI";
               presence "enable transport";
               uses bgp-afi-inet6-transport;
             }
             container unicast {
               description "Include unicast NLRI";
               presence "enable unicast";
               uses bgp-afi-topo;
             }
             container multicast {
               description "Include multicast NLRI";
               presence "enable multicast";
               uses bgp-afi-default;
             }
             container flow {
               description "Include flow NLRI";
               presence "enable flow";
               uses bgp-afi-flow;
             }
             container any {
               description "Include unicast or multicast NLRI";
               presence "enable any";
               uses bgp-afi-default;
             }
           }
           container inet6-vpn {
             description "IPv6 Layer 3 VPN NLRI parameters";
             uses apply-advanced;
             container unicast {
               description "Include unicast NLRI";
               presence "enable unicast";
               uses bgp-afi-l3vpn;
             }
             container multicast {
               description "Include multicast NLRI";
               presence "enable multicast";
               uses bgp-afi-vpn;
             }
             container flow {
               description "Include flow VPN NLRI";
               presence "enable flow";
               uses bgp-afi-flow;
             }
             container any {
               description "Include unicast or multicast NLRI";
               presence "enable any";
               uses bgp-afi-vpn;
             }
           }
           container iso-vpn {
             description "ISO Layer 3 VPN NLRI parameters";
             uses apply-advanced;
             container unicast {
               description "Include unicast NLRI";
               presence "enable unicast";
               uses bgp-afi-vpn-protection;
             }
           }
           container l2vpn {
             description "MPLS-based Layer 2 VPN and VPLS NLRI parameters";
             uses apply-advanced;
             container auto-discovery-only {
               description "Include auto-discovery NLRI for LDP Layer 2 VPN and VPLS";
               presence "enable auto-discovery-only";
               uses bgp-afi-default;
             }
             container auto-discovery-mspw {
               description "Include auto-discovery NLRI for LDP Signalled MultiSegment PW";
               presence "enable auto-discovery-mspw";
               uses bgp-afi-default;
             }
             container signaling {
               description "Include Layer 2 VPN and VPLS signaling NLRI";
               presence "enable signaling";
               uses bgp-afi-l2vpn;
             }
           }
           container evpn {
             description "EVPN NLRI parameters";
             uses apply-advanced;
             container signaling {
               description "Include EVPN signaling NLRI";
               presence "enable signaling";
               uses bgp-afi-default;
             }
           }
           container inet-mvpn {
             description "IPv4 MVPN NLRI parameters";
             uses apply-advanced;
             container signaling {
               description "Include IPv4 multicast VPN signaling NLRI";
               presence "enable signaling";
               uses bgp-afi-default;
             }
           }
           container inet6-mvpn {
             description "IPv6 MVPN NLRI parameters";
             uses apply-advanced;
             container signaling {
               description "Include IPv6 multicast VPN signaling NLRI";
               presence "enable signaling";
               uses bgp-afi-default;
             }
           }
           container inet-mdt {
             description "IPv4 Multicast Distribution Tree (MDT) NLRI parameters";
             uses apply-advanced;
             container signaling {
               description "Include IPv4 multicast VPN auto-discovery NLRI";
               presence "enable signaling";
               uses bgp-afi-default;
             }
           }
           container traffic-engineering {
             description "Traffic Engineering (BGP-TE) NLRI parameters";
             uses apply-advanced;
             container unicast {
               description "Include BGP-TE NLRI";
               presence "enable unicast";
               uses bgp-afi-default;
             }
           }
           container route-target {
             presence "enable route-target";
             description "Route target NLRI used for VPN route filtering";
             uses apply-advanced;
             container prefix-limit {
               description "Limit maximum number of prefixes from a peer";
               uses bgpaf-prefix-limit;
             }
             container accepted-prefix-limit {
               description "Limit maximum number of prefixes accepted from a peer";
               uses bgpaf-accepted-prefix-limit;
             }
             container proxy-generate {
               presence "enable proxy-generate";
               description "Generate route target NLRI for peers that don't support it";
               uses apply-advanced;
               leaf-list route-target-policy {
                 ordered-by user;
                 description "Limit VPN routes that are used to generate proxy route-target filters";
                 type jt:policy-algebra;
               }
             }
             leaf external-paths {
               description "Number of external paths accepted for route filtering";
               type union {
                 type string {
                   pattern "<.*>|$.*";
                 }
                 type uint32 {
                   range "1 .. 256";
                 }
               }
             }
             leaf advertise-default {
               description "Advertise default and suppress more specific routes";
               type empty;
             }
             leaf damping {
               description "Enable route flap damping";
               type empty;
             }
             container graceful-restart {
               description "BGP graceful restart options";
               uses bgp-af-gr;
             }
             leaf local-ipv4-address {
               description "Local IPv4 address";
               type jt:ipv4addr;
             }
             container output-queue-priority {
               description "Default output-queue to assign updates to";
               uses bgp-output-queue-priority-class;
             }
             container route-refresh-priority {
               description "Default output-queue to assign route refreshes to";
               uses bgp-output-queue-priority-class;
             }
             container withdraw-priority {
               description "Default output-queue to assign withdrawn routes to";
               uses bgp-output-queue-priority-class;
             }
           }
           container fabric {
             description "Fabric NLRI parameters";
             status deprecated;
             uses apply-advanced;
             container unicast {
               description "Include unicast NLRI";
               presence "enable unicast";
               uses bgp-afi-default;
             }
           }
           container bridge {
             description "Bridge NLRI parameters";
             status deprecated;
             uses apply-advanced;
             container unicast {
               description "Include unicast NLRI";
               presence "enable unicast";
               uses bgp-afi-default;
             }
           }
           container bridge-vpn {
             description "Bridge VPN NLRI parameters";
             status deprecated;
             uses apply-advanced;
             container unicast {
               description "Include unicast NLRI";
               presence "enable unicast";
               uses bgp-afi-vpn;
             }
           }
           container fabric-vpn {
             description "Fabric VPN NLRI parameters";
             status deprecated;
             uses apply-advanced;
             container unicast {
               description "Include unicast NLRI";
               presence "enable unicast";
               uses bgp-afi-vpn;
             }
           }
           container inet-bgpmcast {
             description "IPv4 BGPMCAST NLRI parameters";
             uses apply-advanced;
             container signaling {
               description "Include IPv4 BGP multicast signaling NLRI";
               presence "enable signaling";
               uses bgp-afi-default;
             }
           }
           container inet6-bgpmcast {
             description "IPv6 BGPMCAST NLRI parameters";
             uses apply-advanced;
             container signaling {
               description "Include IPv6 BGP multicast signaling NLRI";
               presence "enable signaling";
               uses bgp-afi-default;
             }
           }
         }
         leaf authentication-key {
           description "MD5 authentication key";
           type string {
             length "1 .. 126";
           }
         }
         leaf authentication-algorithm {
           description "Authentication algorithm name";
           junos:must "(\".. authentication-key-chain\")";
           junos:must-message "May not be configured without authentication-key-chain";
           junos:must "(!(\".. authentication-key\"))";
           junos:must-message "May not be configured with authentication-key";
           type enumeration {
             enum "md5" {
               description "Message Digest 5";
             }
             enum "hmac-sha-1-96" {
               description "Hash-based Message Authentication Code (SHA1) (96 bits)";
             }
             enum "aes-128-cmac-96" {
               description "Cipher-based Message Authentication Code (AES128) (96 bits)";
             }
             enum "ao" {
               description "TCP Authentication Option";
             }
           }
         }
         leaf tcpao-handling-with-digest-mismatch {
           description "Drop or continue without TCP-AO with digest mismatch with TCP-AO";
           junos:must "(!(\".. authentication-key\"))";
           junos:must-message "May not be configured with authentication-key";
           type enumeration {
             enum "drop-if-no-tcpao" {
               description "Drop the connection if Digest mismatched";
             }
             enum "allow-without-tcpao" {
               description "Allow the connection establishment without TCP-AO";
             }
           }
         }
         leaf authentication-key-chain {
           description "Key chain name";
           junos:must "(!(\".. authentication-key\"))";
           junos:must-message "May not be configured with authentication-key";
           junos:must "(\"security authentication-key-chains key-chain $$\")";
           junos:must-message "Referenced key-chain must be defined";
           type string {
             length "1 .. 128";
           }
         }
         leaf-list export {
           ordered-by user;
           description "Export policy";
           type jt:policy-algebra;
         }
         container remove-private {
           presence "enable remove-private";
           description "Remove well-known private AS numbers";
           uses apply-advanced;
           container all {
             presence "enable all";
             description "Remove all private AS numbers and do not stop at the first public AS number";
             container replace {
               presence "enable replace";
               description "Replace private AS numbers with the BGP Group's local AS number";
               leaf nearest {
                 description "Use closest public AS number to replace a private AS number";
                 type empty;
               }
             }
           }
           leaf no-peer-loop-check {
             description "Remove peer loop-check";
             type empty;
           }
         }
         leaf cluster {
           description "Cluster identifier";
           type jt:areaid;
         }
         leaf no-client-reflect {
           description "Disable intracluster route redistribution";
           type empty;
         }
         leaf peer-as {
           description " Autonomous system number in plain number or 'higher 16bits'.'Lower 16 bits' (asdot notation) format";
           type string {
             junos:posix-pattern "^[0-9]+(.[0-9]+)?$";
             junos:pattern-message "Use format 'x' or 'x.y' to specify number 'x' (Range 1 .. 4294967295) or number with higher 2 bytes 'x' (Range 0 .. 65535) and lower 2 bytes 'y' (Range 0 .. 65535) respectively";
           }
         }
         container local-as {
           description "Local autonomous system number";
           leaf as-number {
             description " Autonomous system number in plain number or 'higher 16bits'.'Lower 16 bits' (asdot notation) format";
             type string {
               junos:posix-pattern "^[0-9]+(.[0-9]+)?$";
               junos:pattern-message "Use format 'x' or 'x.y' to specify number 'x' (Range 1 .. 4294967295) or number with higher 2 bytes 'x' (Range 0 .. 65535) and lower 2 bytes 'y' (Range 0 .. 65535) respectively";
             }
           }
           leaf loops {
             description "Maximum number of times this AS can be in an AS path";
             type union {
               type string {
                 pattern "<.*>|$.*";
               }
               type int32 {
                 range "1 .. 10";
               }
             }
           }
           leaf private {
             description "Hide this local AS in paths learned from this peering";
             type empty;
           }
           leaf alias {
             description "Treat this AS as an alias to the system AS";
             type empty;
           }
           leaf no-prepend-global-as {
             description "Do not prepend global autonomous-system number in advertised paths";
             type empty;
           }
         }
         leaf ipsec-sa {
           description "IPSec SA name";
           junos:must "(\"security ipsec security-association $$\")";
           junos:must-message "Referenced IPSec Security Association must be defined";
           type string {
             length "1 .. 32";
           }
         }
         container graceful-shutdown {
           description "BGP peer graceful shutdown option";
           uses apply-advanced;
           container receiver {
             presence "enable receiver";
             description "BGP peer graceful-shutdown receiver";
             uses apply-advanced;
             leaf disable {
               description "Disable graceful-shutdown receiver";
               junos:must "(!(\".. .. sender\"))";
               junos:must-message "Receiver cannot be disabled on Sender";
               type empty;
             }
             leaf local-preference {
               description "Value of receiver LOCAL_PREF path attribute";
               type union {
                 type uint32;
                 type string {
                   pattern "<.*>|$.*";
                 }
               }
             }
           }
           container sender {
             presence "enable sender";
             description "BGP peer graceful-shutdown sender";
             uses apply-advanced;
             leaf local-preference {
               description "Value of sender LOCAL_PREF path attribute";
               type union {
                 type uint32;
                 type string {
                   pattern "<.*>|$.*";
                 }
               }
             }
           }
         }
         container shutdown {
           presence "enable shutdown";
           description "Shutdown";
           uses apply-advanced;
           leaf notify-message {
             description "Notification message";
             type string;
           }
         }
         leaf unconfigured-peer-graceful-restart {
           description "BGP unconfigured peer graceful restart options";
           junos:must "(\".. graceful-restart\")";
           junos:must-message "unconfigured-peer-graceful-restart is only valid with 'graceful-restart'";
           type empty;
         }
         container graceful-restart {
           presence "enable graceful-restart";
           description "BGP graceful restart options";
           uses apply-advanced;
           choice enable-disable {
             case case_1 {
               leaf disable {
                 description "Disable graceful restart";
                 type empty;
               }
             }
           }
           leaf restart-time {
             description "Restart time used when negotiating with a peer";
             junos:must "((\"routing-options graceful-restart\" || \"fabric routing-options graceful-restart\"))";
             junos:must-message "restart-time is only valid with 'routing-options graceful-restart'";
             type union {
               type string {
                 pattern "<.*>|$.*";
               }
               type uint32 {
                 range "1 .. 1800";
               }
             }
           }
           leaf stale-routes-time {
             description "Maximum time for which stale routes are kept";
             type union {
               type string {
                 pattern "<.*>|$.*";
               }
               type uint32 {
                 range "1 .. 1800";
               }
             }
           }
           container long-lived {
             description "Long-lived graceful restart options";
             uses apply-advanced;
             container receiver {
               description "Long-lived graceful restart receiver (helper) options";
               uses apply-advanced;
               choice enable-disable {
                 case case_1 {
                   leaf disable {
                     description "Disable receiver (helper) functionality";
                     type empty;
                   }
                 }
               }
             }
             container advertise-to-non-llgr-neighbor {
               presence "enable advertise-to-non-llgr-neighbor";
               description "Advertise stale routes to non-LLGR neighbors";
               uses apply-advanced;
               leaf omit-no-export {
                 description "Do not attach no-export community to stale routes";
                 type empty;
               }
             }
           }
           leaf disable-notification-extensions {
             description "Disable notification extensions";
             type empty;
           }
           leaf forwarding-state-bit {
             description "Control forwarding-state flag negotiation";
             type enumeration {
               enum "as-rr-client" {
                 description "As for a route reflector client";
               }
               enum "from-fib" {
                 description "Always use state of associated FIB(s)";
               }
             }
           }
           leaf dont-help-shared-fate-bfd-down {
             description "Honor BFD-Down(C=0) if GR-restart not in progress";
             type empty;
           }
         }
         leaf include-mp-next-hop {
           description "Include NEXT-HOP attribute in multiprotocol updates";
           type empty;
         }
         leaf disable-4byte-as {
           description "Disable 4 byte AS capability advertisement";
           type empty;
         }
         container idle-after-switch-over {
           description "Stop peer session from coming up after nonstop-routing switch-over";
           choice idle-interval {
             case case_1 {
               leaf forever {
                 description "Idle the peer until the user intervenes";
                 type empty;
               }
             }
             case case_2 {
               leaf timeout {
                 description "Timeout value, in seconds, for starting peer after switch over";
                 type union {
                   type string {
                     pattern "<.*>|$.*";
                   }
                   type uint32 {
                     range "1 .. 4294967295";
                   }
                 }
               }
             }
           }
         }
         container outbound-route-filter {
           junos:must "(!(\"system processes routing bgp update-threading\"))";
           junos:must-message "Can't be configured together with update-threading";
           description "Dynamically negotiated cooperative route filtering";
           uses apply-advanced;
           leaf bgp-orf-cisco-mode {
             description "Using BGP ORF capability code 130 and Prefix ORF type 128";
             type empty;
           }
           container extended-community {
             description "Extended community filtering";
             status deprecated;
             uses apply-advanced;
             choice accept-choice {
               leaf accept {
                 description "Honor remote requests for extended community ORF";
                 type empty;
               }
               leaf no-accept {
                 description "Don't honor remote requests for extended community ORF";
                 type empty;
               }
             }
             leaf vrf-filter {
               description "Request remote filtering using locally configured VRF import targets";
               type empty;
             }
           }
           container prefix-based {
             presence "enable prefix-based";
             description "Prefix-based outbound route filtering";
             uses apply-advanced;
             container accept {
               presence "enable accept";
               description "Honor Prefix-based ORFs from remote peers";
               uses apply-advanced;
               leaf inet {
                 description "Honor IPv4 prefix filters";
                 type empty;
               }
               leaf inet6 {
                 description "Honor IPv6 prefix filters";
                 type empty;
               }
             }
           }
         }
         container message-batching {
           description "DEPRECATED - Batching of outgoing messages";
           status deprecated;
           uses apply-advanced;
           choice enable-disable {
             case case_1 {
               leaf enable {
                 description "Enable parameter";
                 type empty;
               }
             }
             case case_2 {
               leaf disable {
                 description "Disable parameter";
                 type empty;
               }
             }
           }
           leaf interval {
             description "DEPRECATED - Interval over which to batch messages";
             default "250";
             units "milliseconds";
             type union {
               type string {
                 pattern "<.*>|$.*";
               }
               type uint32 {
                 range "100 .. 1000";
               }
             }
           }
         }
         container multipath {
           presence "enable multipath";
           description "Allow load sharing among multiple BGP paths";
           uses apply-advanced;
           leaf disable {
             description "Disable Multipath";
             type empty;
           }
           leaf multiple-as {
             description "Use paths received from different ASs";
             type empty;
           }
           leaf allow-protection {
             description "Allow protection for multipath legs";
             type empty;
           }
           leaf pause-computation-during-churn {
             description "Pause multipath job to absorb churn";
             type empty;
           }
           leaf list-nexthop {
             description "Use List-NH for homogenous nexthop-set also";
             type empty;
           }
         }
         leaf tcp-mss {
           description "Maximum TCP segment size";
           type union {
             type string {
               pattern "<.*>|$.*";
             }
             type uint32 {
               range "1 .. 4096";
             }
           }
         }
         leaf bgp-identifier {
           description "BGP Identifier";
           type jt:ipv4addr;
         }
         leaf tcp-aggressive-transmission {
           description "Enable aggressive transmission of pure TCP ACKs and retransmissions";
           type empty;
         }
         container bmp {
           description "Specific settings to override the routing-options settings";
           uses apply-advanced;
           leaf monitor {
             description "Enable/Disable monitoring";
             type enumeration {
               enum "enable" {
                 description "Enable monitoring of BGP peer(s)";
               }
               enum "disable" {
                 description "Disable monitoring of BGP peer(s)";
               }
             }
           }
           container route-monitoring {
             description "Control route monitoring settings";
             uses apply-advanced;
             leaf none {
               description "Do not send route monitoring messages";
               junos:must "((!(\".. pre-policy\") && (!(\".. post-policy\") && !(\".. rib-out\"))))";
               junos:must-message "May not be configured with pre-policy or post-policy or rib-out";
               type empty;
             }
             container pre-policy {
               presence "enable pre-policy";
               description "Send pre-policy route monitoring messages";
               leaf exclude-non-feasible {
                 description "Exclude looped routes, etc";
                 type empty;
               }
             }
             container post-policy {
               presence "enable post-policy";
               description "Send post-policy route monitoring messages";
               leaf exclude-non-eligible {
                 description "Exclude unresolved routes, etc.";
                 type empty;
               }
             }
             container rib-out {
               presence "enable rib-out";
               junos:must "((!(\"system processes routing bgp update-threading\") || \"system processes routing bgp rib-sharding\"))";
               junos:must-message "Update threading can't be configured together with bmp rib-out monitoring";
               description "Send adj-ribs-out route monitoring messages";
               leaf pre-policy {
                 description "Send pre-policy adj-ribs-out route monitoring messages";
                 type empty;
               }
               leaf post-policy {
                 description "Send post-policy adj-ribs-out route monitoring messages";
                 type empty;
               }
             }
           }
         }
         container advertise-bgp-static {
           presence "enable advertise-bgp-static";
           description "Advertise bgp-static routes";
           uses apply-advanced;
           leaf-list policy {
             ordered-by user;
             description "Static route advertisement policy";
             type jt:policy-algebra;
           }
         }
         leaf add-path-display-ipv4-address {
           description "Display add-path path-id in IPv4 address format";
           type empty;
         }
         container bfd-liveness-detection {
           description "Bidirectional Forwarding Detection (BFD) options";
           uses apply-advanced;
           leaf version {
             description "BFD protocol version number";
             default "automatic";
             type enumeration {
               enum "0" {
                 description "BFD version 0 (deprecated)";
               }
               enum "1" {
                 description "BFD version 1";
               }
               enum "automatic" {
                 description "Choose BFD version automatically";
               }
             }
           }
           leaf minimum-interval {
             description "Minimum transmit and receive interval";
             units "milliseconds";
             type union {
               type string {
                 pattern "<.*>|$.*";
               }
               type uint32 {
                 range "1 .. 255000";
               }
             }
           }
           leaf minimum-transmit-interval {
             description "Minimum transmit interval";
             status deprecated;
             units "milliseconds";
             type union {
               type string {
                 pattern "<.*>|$.*";
               }
               type uint32 {
                 range "1 .. 255000";
               }
             }
           }
           leaf minimum-receive-interval {
             description "Minimum receive interval";
             units "milliseconds";
             type union {
               type string {
                 pattern "<.*>|$.*";
               }
               type uint32 {
                 range "1 .. 255000";
               }
             }
           }
           leaf multiplier {
             description "Detection time multiplier";
             default "3";
             type union {
               type string {
                 pattern "<.*>|$.*";
               }
               type uint32 {
                 range "1 .. 255";
               }
             }
           }
           choice adaptation-choice {
             case case_1 {
               leaf no-adaptation {
                 description "Disable adaptation";
                 type empty;
               }
             }
           }
           container transmit-interval {
             description "Transmit-interval options";
             uses apply-advanced;
             leaf minimum-interval {
               description "Minimum transmit interval";
               units "milliseconds";
               type union {
                 type string {
                   pattern "<.*>|$.*";
                 }
                 type uint32 {
                   range "1 .. 255000";
                 }
               }
             }
             leaf threshold {
               description "High transmit interval triggering a trap";
               units "milliseconds";
               type union {
                 type uint32;
                 type string {
                   pattern "<.*>|$.*";
                 }
               }
             }
           }
           container detection-time {
             description "Detection-time options";
             uses apply-advanced;
             leaf threshold {
               description "High detection-time triggering a trap";
               units "milliseconds";
               type union {
                 type uint32;
                 type string {
                   pattern "<.*>|$.*";
                 }
               }
             }
           }
           container authentication {
             description "Authentication options";
             uses apply-advanced;
             leaf key-chain {
               description "Key chain name";
               junos:must "(\".. algorithm\")";
               junos:must-message "May not be configured without algorithm";
               junos:must "(\"security authentication-key-chains key-chain $$\")";
               junos:must-message "Referenced key-chain must be defined";
               type string;
             }
             leaf algorithm {
               description "Algorithm name";
               junos:must "(\".. key-chain\")";
               junos:must-message "May not be configured without key-chain";
               type enumeration {
                 enum "simple-password" {
                   description "Simple password";
                 }
                 enum "keyed-md5" {
                   description "Keyed message Digest 5";
                 }
                 enum "meticulous-keyed-md5" {
                   description "Meticulous keyed message Digest 5";
                 }
                 enum "keyed-sha-1" {
                   description "Keyed secure hash algorithm (SHA1) ";
                 }
                 enum "meticulous-keyed-sha-1" {
                   description "Meticulous keyed secure hash algorithm (SHA1) ";
                 }
               }
             }
             leaf loose-check {
               description "Verify authentication only if authentication is negotiated";
               type empty;
             }
           }
           leaf session-mode {
             description "BFD single-hop or multihop session-mode";
             default "automatic";
             type enumeration {
               enum "automatic" {
                 description "Choose session-mode automatically";
               }
               enum "single-hop" {
                 description "Use single-hop";
               }
               enum "multihop" {
                 description "Use multihop";
               }
             }
           }
           leaf holddown-interval {
             description "Time to hold the session-UP notification to the client";
             units "milliseconds";
             junos:must "(!(\".. .. .. type internal\"))";
             junos:must-message "bfd holddown-interval is only valid for EBGP.";
             type union {
               type string {
                 pattern "<.*>|$.*";
               }
               type uint32 {
                 range "0 .. 255000";
               }
             }
           }
         }
         leaf as-override {
           description "Replace neighbor AS number with our AS number";
           type empty;
         }
         container egress-te-node-segment {
           description "Configure BGP-Peer-Node segment";
           uses apply-advanced;
           container label {
             description "BGP-Peer-Node SID label from static label pool";
             uses apply-advanced;
             leaf label-value {
               description "BGP-Peer-Node SID label value from static label pool";
               type union {
                 type string {
                   pattern "<.*>|$.*";
                 }
                 type uint32 {
                   range "16 .. 1048575";
                 }
               }
             }
           }
           container egress-te-set {
             description "Configure as a member of a SET segment";
             uses apply-advanced;
             leaf set-name {
               description "Set name";
               junos:must "(\"protocols bgp egress-te-set-segment $$\")";
               junos:must-message "protocols bgp egress-te-set-segment not configured";
               type string {
                 junos:posix-pattern "^.{1,64}$";
                 junos:pattern-message "Must be a string of 64 characters or less";
               }
             }
             leaf weight {
               description "Weight for set segment";
               type union {
                 type string {
                   pattern "<.*>|$.*";
                 }
                 type uint32 {
                   range "1 .. 255";
                 }
               }
             }
           }
           container egress-te-backup-segment {
             description "Backup segment for FRR";
             uses apply-advanced;
             container label {
               description "Backup segment label from static label pool";
               uses apply-advanced;
               leaf label-value {
                 description "Backup segment label value from static label pool";
                 type union {
                   type string {
                     pattern "<.*>|$.*";
                   }
                   type uint32 {
                     range "16 .. 1048575";
                   }
                 }
               }
             }
           }
           container egress-te-backup-ip-forward {
             presence "enable egress-te-backup-ip-forward";
             description "Use IP-forward backup path for Egress TE";
             uses apply-advanced;
             leaf instance-name {
               description "Routing-instance to use as IP forward backup-path";
               type string {
                 junos:posix-pattern "!^((__.*__)|(all)|(.*[ ].*)|(\"\")|(.{129,}))$";
                 junos:pattern-message "Must be a non-reserved string of 128 characters or less with no spaces.";
               }
             }
           }
         }
         list egress-te-adj-segment {
           key name;
           description "Configure BGP-Peer-Adj segment";
           leaf name {
             description "The BGP-Adj-Set segment name";
             type string {
               junos:posix-pattern "^.{1,64}$";
               junos:pattern-message "Must be a string of 64 characters or less";
             }
           }
           uses apply-advanced;
           container label {
             junos:must "(\".. next-hop\")";
             junos:must-message "The 'egress-te-adj-segment next-hop' must be configured";
             description "BGP-Peer-Adj SID label from static label pool";
             uses apply-advanced;
             leaf label-value {
               description "BGP-Peer-Adj SID label value from static label pool";
               type union {
                 type string {
                   pattern "<.*>|$.*";
                 }
                 type uint32 {
                   range "16 .. 1048575";
                 }
               }
             }
           }
           container next-hop {
             junos:must "(\".. label\")";
             junos:must-message "The 'egress-te-adj-segment label' must be configured";
             description "Address of directly connected next-hop to use";
             uses apply-advanced;
             leaf next-hop-addr {
               description "Address of directly connected next-hop";
               type jt:ipaddr;
             }
           }
           container egress-te-set {
             description "Configure as a member of a SET segment";
             uses apply-advanced;
             leaf set-name {
               description "Set name";
               junos:must "(\"protocols bgp egress-te-set-segment $$\")";
               junos:must-message "protocols bgp egress-te-set-segment not configured";
               type string {
                 junos:posix-pattern "^.{1,64}$";
                 junos:pattern-message "Must be a string of 64 characters or less";
               }
             }
             leaf weight {
               description "Weight for set segment";
               type union {
                 type string {
                   pattern "<.*>|$.*";
                 }
                 type uint32 {
                   range "1 .. 255";
                 }
               }
             }
           }
           container egress-te-backup-segment {
             description "Backup segment for FRR";
             uses apply-advanced;
             container label {
               description "Backup segment label from static label pool";
               uses apply-advanced;
               leaf label-value {
                 description "Backup segment label value from static label pool";
                 type union {
                   type string {
                     pattern "<.*>|$.*";
                   }
                   type uint32 {
                     range "16 .. 1048575";
                   }
                 }
               }
             }
           }
           container egress-te-backup-ip-forward {
             presence "enable egress-te-backup-ip-forward";
             description "Use IP-forward backup path for Egress TE";
             uses apply-advanced;
             leaf instance-name {
               description "Routing-instance to use as IP forward backup-path";
               type string {
                 junos:posix-pattern "!^((__.*__)|(all)|(.*[ ].*)|(\"\")|(.{129,}))$";
                 junos:pattern-message "Must be a non-reserved string of 128 characters or less with no spaces.";
               }
             }
           }
           container te-link-attribute {
             presence "enable te-link-attribute";
             description "Link attribute";
             uses apply-advanced;
             leaf te-metric {
               description "TE Metric value";
               default "1";
               type union {
                 type string {
                   pattern "<.*>|$.*";
                 }
                 type uint32 {
                   range "1 .. 4294967295";
                 }
               }
             }
             leaf igp-metric {
               description "IGP Metric value";
               default "1";
               type union {
                 type string {
                   pattern "<.*>|$.*";
                 }
                 type uint32 {
                   range "1 .. 16777215";
                 }
               }
             }
             leaf delay-metric {
               description "Delay Metric";
               units "microseconds";
               type union {
                 type string {
                   pattern "<.*>|$.*";
                 }
                 type uint32 {
                   range "1 .. 16777215";
                 }
               }
             }
             leaf-list admin-group {
               ordered-by user;
               description "Administrative groups";
               type string;
               max-elements 16;
             }
           }
         }
         leaf vpn-apply-export {
           description "Apply BGP export policy when exporting VPN routes";
           type empty;
         }
         container egress-te {
           presence "enable egress-te";
           description "Use Egress Peering traffic engineering";
           uses apply-advanced;
           leaf install-address {
             description "Address to use in egress-te created inet route";
             type jt:ipaddr;
           }
           container rib {
             description "Select primary table for Egress-TE routes";
             uses apply-advanced;
             leaf inet.0 {
               description "Install Egress-TE routes in inet.0";
               type empty;
             }
             leaf inet6.0 {
               description "Install Egress-TE routes in inet6.0";
               type empty;
             }
           }
           leaf no-install {
             description "Avoid installation to FIB or resolving over";
             type empty;
           }
           leaf-list import {
             ordered-by user;
             description "Import policy to set attributes";
             type jt:policy-algebra;
           }
           leaf backup-path {
             description "The 'egress-te-backup-paths template' to use for this peer";
             junos:must "(\"protocols bgp egress-te-backup-paths template $$\")";
             junos:must-message "bgp egress-te-backup-paths template not configured";
             type string {
               junos:posix-pattern "^.{1,64}$";
               junos:pattern-message "Must be a string of 64 characters or less";
             }
           }
         }
         leaf advertise-prefix-sid {
           description "Advertise prefix sid to E-BGP peers";
           type empty;
         }
         leaf accept-prefix-sid {
           description "Accept prefix sid from E-BGP peers";
           type empty;
         }
         leaf advertise-srgb {
           description "Advertise SRGB TLV";
           type empty;
         }
         leaf tcp-connect-port {
           description "TCP port number to connect with peer on";
           type union {
             type string {
               pattern "<.*>|$.*";
             }
             type uint16 {
               range "1 .. 65535";
             }
           }
         }
       }
       leaf vpn-apply-export {
         description "Apply BGP export policy when exporting VPN routes";
         type empty;
       }
       container egress-te {
         presence "enable egress-te";
         description "Use Egress Peering traffic engineering";
         uses apply-advanced;
         leaf install-address {
           description "Address to use in egress-te created inet route";
           type jt:ipaddr;
         }
         container rib {
           description "Select primary table for Egress-TE routes";
           uses apply-advanced;
           leaf inet.0 {
             description "Install Egress-TE routes in inet.0";
             type empty;
           }
           leaf inet6.0 {
             description "Install Egress-TE routes in inet6.0";
             type empty;
           }
         }
         leaf no-install {
           description "Avoid installation to FIB or resolving over";
           type empty;
         }
         leaf-list import {
           ordered-by user;
           description "Import policy to set attributes";
           type jt:policy-algebra;
         }
         leaf backup-path {
           description "The 'egress-te-backup-paths template' to use for this peer";
           junos:must "(\"protocols bgp egress-te-backup-paths template $$\")";
           junos:must-message "bgp egress-te-backup-paths template not configured";
           type string {
             junos:posix-pattern "^.{1,64}$";
             junos:pattern-message "Must be a string of 64 characters or less";
           }
         }
       }
       leaf advertise-prefix-sid {
         description "Advertise prefix sid to E-BGP peers";
         type empty;
       }
       leaf accept-prefix-sid {
         description "Accept prefix sid from E-BGP peers";
         type empty;
       }
       leaf advertise-srgb {
         description "Advertise SRGB TLV";
         type empty;
       }
       leaf tcp-connect-port {
         description "TCP port number to connect with peer on";
         type union {
           type string {
             pattern "<.*>|$.*";
           }
           type uint16 {
             range "1 .. 65535";
           }
         }
       }
     }
     container traffic-statistics-labeled-path {
       presence "enable traffic-statistics-labeled-path";
       description "Collect periodic ingress labeled statistics for BGP label-switched paths ";
       uses apply-advanced;
       container file {
         description "Statistics file options";
         leaf filename {
           description "Name of file in which to write trace information";
           type string {
             length "1 .. 1024";
             junos:posix-pattern "![/ %]";
             junos:pattern-message "Must not contain '/', % or a space";
           }
         }
         leaf replace {
           description "Replace trace file rather than appending to it";
           status deprecated;
           type empty;
         }
         leaf size {
           description "Maximum trace file size";
           type string;
         }
         leaf files {
           description "Maximum number of trace files";
           default "10";
           type union {
             type string {
               pattern "<.*>|$.*";
             }
             type uint32 {
               range "2 .. 1000";
             }
           }
         }
         leaf no-stamp {
           description "Do not timestamp trace file";
           status deprecated;
           type empty;
         }
         choice world-readable-choice {
           leaf world-readable {
             description "Allow any user to read the log file";
             type empty;
           }
           leaf no-world-readable {
             description "Don't allow any user to read the log file";
             type empty;
           }
         }
       }
       leaf interval {
         description "Time interval to collect statistics";
         units "seconds";
         type union {
           type string {
             pattern "<.*>|$.*";
           }
           type int32 {
             range "60 .. 65535";
           }
         }
       }
     }
     container source-packet-routing {
       description "Enable Source Packet Routing (SPRING)";
       uses apply-advanced;
       container srgb {
         junos:must "(!(\".. .. .. .. protocols mpls disable\"))";
         junos:must-message "SPRING configuration is not allowed with 'protocols mpls disable'";
         junos:must "(\".. .. .. .. protocols mpls \")";
         junos:must-message "SPRING configuration is not allowed without 'protocols mpls'";
         description "Set the SRGB global block in SPRING";
         leaf start-label {
           description "Start range for SRGB label block";
           type union {
             type string {
               pattern "<.*>|$.*";
             }
             type uint32;
           }
         }
         leaf index-range {
           description "Index to the SRGB start label block";
           type union {
             type string {
               pattern "<.*>|$.*";
             }
             type uint32;
           }
         }
       }
       container srv6 {
         description "Enable IPv6 Segment Routing (SRv6)";
         uses apply-advanced;
         list locator {
           key name;
           ordered-by user;
           description "SRv6 Locator";
           leaf name {
             description "Locator name";
             junos:must "(\"routing-options source-packet-routing srv6 locator $$\")";
             junos:must-message "Referenced srv6 locator must be defined";
             type string;
           }
           uses apply-advanced;
           leaf end-dt4-sid {
             description "End dt4 sid with 128 bit address";
             type jt:ipv6addr;
           }
           leaf end-dt6-sid {
             description "End dt6 sid with 128 bit address";
             type jt:ipv6addr;
           }
         }
       }
     }
     choice enable-disable {
       case case_1 {
         leaf disable {
           description "Disable BGP";
           type empty;
         }
       }
     }
     choice precision-timers-choice {
       leaf precision-timers {
         description "Use precision timers for scheduling keepalives";
         type empty;
       }
       leaf no-precision-timers {
         description "Don't use precision timers for scheduling keepalives";
         type empty;
       }
     }
     container snmp-options {
       description "Customize SNMP behaviors specifically for BGP MIBs";
       uses apply-advanced;
       leaf backward-traps-only-from-established {
         description "Limit traps for backward transitions to only those moving from Established state.";
         type empty;
       }
       leaf emit-inet-address-length-in-oid {
         description "Emit Length in OID for InetAddress MIB type.";
         type empty;
       }
     }
     leaf route-age-bgp-view {
       description "Maintain BGP route's age based on Update messages only";
       type empty;
     }
     leaf prioritize-route-queueing {
       description "Let route-queue building happen without getting throttled";
       type empty;
     }
     container traceoptions {
       description "Trace options for BGP";
       uses apply-advanced;
       container file {
         description "Trace file options";
         leaf filename {
           description "Name of file in which to write trace information";
           type string {
             length "1 .. 1024";
             junos:posix-pattern "![/ %]";
             junos:pattern-message "Must not contain '/', % or a space";
           }
         }
         leaf replace {
           description "Replace trace file rather than appending to it";
           status deprecated;
           type empty;
         }
         leaf size {
           description "Maximum trace file size";
           type string;
         }
         leaf files {
           description "Maximum number of trace files";
           default "10";
           type union {
             type string {
               pattern "<.*>|$.*";
             }
             type uint32 {
               range "2 .. 1000";
             }
           }
         }
         leaf no-stamp {
           description "Do not timestamp trace file";
           status deprecated;
           type empty;
         }
         choice world-readable-choice {
           leaf world-readable {
             description "Allow any user to read the log file";
             type empty;
           }
           leaf no-world-readable {
             description "Don't allow any user to read the log file";
             type empty;
           }
         }
       }
       list flag {
         key name;
         ordered-by user;
         description "Tracing parameters";
         leaf name {
           type enumeration {
             enum "damping" {
               description "Trace BGP damping information";
             }
             enum "packets" {
               description "Trace all BGP protocol packets";
             }
             enum "open" {
               description "Trace BGP open packets";
             }
             enum "update" {
               description "Trace BGP update packets";
             }
             enum "keepalive" {
               description "Trace BGP keepalive packets";
             }
             enum "refresh" {
               description "Trace BGP refresh packets";
             }
             enum "nsr-synchronization" {
               description "Trace NSR synchronization events";
             }
             enum "bfd" {
               description "Trace BFD events";
             }
             enum "4byte-as" {
               description "Trace 4 byte AS events";
             }
             enum "add-path" {
               description "Trace add-path events";
             }
             enum "graceful-restart" {
               description "Trace Graceful Restart events";
             }
             enum "egress-te" {
               description "Egress Peering Traffic-Engineering events";
             }
             enum "thread-io" {
               description "Trace threaded I/O processing";
             }
             enum "sharding" {
               description "Trace BGP rib sharding";
             }
             enum "thread-update-io" {
               description "Trace threaded update I/O processing";
             }
             enum "route-validation" {
               description "Trace route validation";
             }
             enum "ipsec" {
               description "Trace ipsec";
             }
             enum "route" {
               description "Trace routing information";
             }
             enum "normal" {
               description "Trace normal events";
             }
             enum "general" {
               description "Trace general events";
             }
             enum "state" {
               description "Trace state transitions";
             }
             enum "policy" {
               description "Trace policy processing";
             }
             enum "task" {
               description "Trace routing protocol task processing";
             }
             enum "timer" {
               description "Trace routing protocol timer processing";
             }
             enum "all" {
               description "Trace everything";
             }
           }
         }
         leaf send {
           description "Trace transmitted packets";
           type empty;
         }
         leaf receive {
           description "Trace received packets";
           type empty;
         }
         leaf detail {
           description "Trace detailed information";
           type empty;
         }
         leaf disable {
           description "Disable this trace flag";
           type empty;
         }
         container filter {
           description "Filter to apply to this flag";
           presence "enable filter";
           uses bgp_filter_obj;
         }
       }
     }
     leaf description {
       description "Text description";
       type string {
         length "1 .. 255";
       }
     }
     container metric-out {
       description "Route metric sent in MED";
       choice metric_param {
         case case_1 {
           leaf metric-value {
             description "Metric value";
             type union {
               type string {
                 pattern "<.*>|$.*";
               }
               type uint32 {
                 range "0 .. 4294967295";
               }
             }
           }
         }
         case case_2 {
           container minimum-igp {
             presence "enable minimum-igp";
             description "Track the minimum IGP metric";
             leaf metric-offset {
               description "Metric offset for MED";
               type union {
                 type int32;
                 type string {
                   pattern "<.*>|$.*";
                 }
               }
             }
           }
         }
         case case_3 {
           container igp {
             presence "enable igp";
             description "Track the IGP metric";
             leaf metric-offset {
               description "Metric offset for MED";
               type union {
                 type int32;
                 type string {
                   pattern "<.*>|$.*";
                 }
               }
             }
             leaf delay-med-update {
               description "Delay updating MED when IGP metric increases";
               type empty;
             }
           }
         }
         case case_4 {
           container effective-aigp {
             presence "enable effective-aigp";
             description "Track the effective AIGP metric";
             leaf metric-offset {
               description "Metric offset for MED";
               type union {
                 type int32;
                 type string {
                   pattern "<.*>|$.*";
                 }
               }
             }
           }
         }
         case case_5 {
           container minimum-effective-aigp {
             presence "enable minimum-effective-aigp";
             description "Track the minimum effective AIGP metric";
             leaf metric-offset {
               description "Metric offset for MED";
               type union {
                 type int32;
                 type string {
                   pattern "<.*>|$.*";
                 }
               }
             }
           }
         }
       }
     }
     container multihop {
       presence "enable multihop";
       description "Configure an EBGP multihop session";
       uses apply-advanced;
       leaf ttl {
         description "TTL value for the session";
         type union {
           type string {
             pattern "<.*>|$.*";
           }
           type uint8 {
             range "1 .. 255";
           }
         }
       }
       leaf no-nexthop-change {
         description "Do not change next hop to self in advertisements";
         type empty;
       }
     }
     leaf route-server-client {
       description "Enable route server client behavior";
       type empty;
     }
     leaf accept-remote-nexthop {
       description "Allow import policy to specify a non-directly connected next-hop";
       type empty;
     }
     leaf preference {
       description "Preference value";
       type union {
         type uint32;
         type string {
           pattern "<.*>|$.*";
         }
       }
     }
     leaf local-preference {
       description "Value of LOCAL_PREF path attribute";
       type union {
         type uint32;
         type string {
           pattern "<.*>|$.*";
         }
       }
     }
     leaf local-address {
       description "Address of local end of BGP session";
       type jt:ipaddr;
     }
     leaf local-interface {
       description "Local interface for IPv6 link local EBGP peering";
       type union {
         type jt:interface-name;
         type string {
           pattern "<.*>|$.*";
         }
       }
     }
     leaf forwarding-context {
       description "Routing-instance used for data-forwarding and transport-session";
       type string {
         junos:posix-pattern "!^((__.*__)|(all)|(.*[ ].*)|(\"\")|(.{129,}))$";
         junos:pattern-message "Must be a non-reserved string of 128 characters or less with no spaces.";
       }
     }
     leaf hold-time {
       description "Hold time used when negotiating with a peer";
       type union {
         type string {
           pattern "<.*>|$.*";
         }
         type uint32 {
           range "0 .. 65535";
         }
       }
     }
     leaf minimum-hold-time {
       description "Minimum hold time accepted from the peer";
       type union {
         type string {
           pattern "<.*>|$.*";
         }
         type uint32 {
           range "3 .. 65535";
         }
       }
     }
     leaf passive {
       description "Do not send open messages to a peer";
       type empty;
     }
     leaf advertise-inactive {
       description "Advertise inactive routes";
       type empty;
     }
     choice advertise-peer-as-choice {
       leaf advertise-peer-as {
         description "Advertise routes received from the same autonomous system";
         type empty;
       }
       leaf no-advertise-peer-as {
         description "Don't advertise routes received from the same autonomous system";
         type empty;
       }
     }
     container advertise-external {
       presence "enable advertise-external";
       description "Advertise best external routes";
       leaf conditional {
         description "Route matches active route upto med-comparison rule";
         type empty;
       }
     }
     leaf keep {
       description "How to retain routes in the routing table";
       type enumeration {
         enum "all" {
           description "Retain all routes";
         }
         enum "none" {
           description "Retain no routes";
         }
       }
     }
     leaf rfc6514-compliant-safi129 {
       description "Compliant with RFC6514 SAFI129 format";
       type empty;
     }
     leaf no-aggregator-id {
       description "Set router ID in aggregator path attribute to 0";
       type empty;
     }
     leaf mtu-discovery {
       description "Enable TCP path MTU discovery";
       type empty;
     }
     leaf enforce-first-as {
       description "Enforce first AS in AS-path is the neighbor's AS";
       type empty;
     }
     leaf out-delay {
       description "How long before exporting routes from routing table";
       type union {
         type string {
           pattern "<.*>|$.*";
         }
         type uint32 {
           range "0 .. 65535";
         }
       }
     }
     leaf ttl {
       description "TTL value for the single-hop peer";
       junos:must "((!(\".. .. type internal\") && !(\".. multihop\")))";
       junos:must-message "This option is valid only for single-hop EBGP neighbor";
       type enumeration {
         enum "1" {
         }
         enum "255" {
         }
       }
     }
     leaf log-updown {
       description "Log a message for peer state transitions";
       type empty;
     }
     leaf damping {
       description "Enable route flap damping";
       type empty;
     }
     leaf-list import {
       ordered-by user;
       description "Import policy";
       type jt:policy-algebra;
     }
     leaf-list nlri {
       ordered-by user;
       description "NLRI type to include in updates";
       status deprecated;
       type enumeration {
         enum "unicast" {
           description "Include unicast NLRI";
           status deprecated;
         }
         enum "multicast" {
           description "Include multicast NLRI";
           status deprecated;
         }
         enum "any" {
           description "Include any kind of NLRI";
           status deprecated;
         }
       }
     }
     container bgp-error-tolerance {
       presence "enable bgp-error-tolerance";
       description "Handle BGP malformed updates softly";
       uses apply-advanced;
       leaf malformed-update-log-interval {
         description "Time used when logging malformed update";
         default "300";
         units "seconds";
         type union {
           type string {
             pattern "<.*>|$.*";
           }
           type uint32 {
             range "10 .. 65535";
           }
         }
       }
       choice malformed-routes-limit-choice {
         case case_1 {
           leaf malformed-route-limit {
             description "Maximum number of malformed routes from a peer";
             default "1000";
             type union {
               type string {
                 pattern "<.*>|$.*";
               }
               type uint32 {
                 range "0 .. 4294967295";
               }
             }
           }
         }
         case case_2 {
           leaf no-malformed-route-limit {
             description "No malformed route limit";
             type empty;
           }
         }
       }
     }
     leaf authentication-key {
       description "MD5 authentication key";
       type string {
         length "1 .. 126";
       }
     }
     leaf authentication-algorithm {
       description "Authentication algorithm name";
       default "hmac-sha-1-96";
       junos:must "(\".. authentication-key-chain\")";
       junos:must-message "May not be configured without authentication-key-chain";
       junos:must "(!(\".. authentication-key\"))";
       junos:must-message "May not be configured with authentication-key";
       type enumeration {
         enum "md5" {
           description "Message Digest 5";
         }
         enum "hmac-sha-1-96" {
           description "Hash-based Message Authentication Code (SHA1) (96 bits)";
         }
         enum "aes-128-cmac-96" {
           description "Cipher-based Message Authentication Code (AES128) (96 bits)";
         }
         enum "ao" {
           description "TCP Authentication Option";
         }
       }
     }
     leaf tcpao-handling-with-digest-mismatch {
       description "Drop or continue without TCP-AO with digest mismatch with TCP-AO";
       junos:must "(!(\".. authentication-key\"))";
       junos:must-message "May not be configured with authentication-key";
       type enumeration {
         enum "drop-if-no-tcpao" {
           description "Drop the connection if Digest mismatched";
         }
         enum "allow-without-tcpao" {
           description "Allow the connection establishment without TCP-AO";
         }
       }
     }
     leaf authentication-key-chain {
       description "Key chain name";
       junos:must "(!(\".. authentication-key\"))";
       junos:must-message "May not be configured with authentication-key";
       junos:must "(\"security authentication-key-chains key-chain $$\")";
       junos:must-message "Referenced key-chain must be defined";
       type string {
         length "1 .. 128";
       }
     }
     leaf-list export {
       ordered-by user;
       description "Export policy";
       type jt:policy-algebra;
     }
     container remove-private {
       presence "enable remove-private";
       description "Remove well-known private AS numbers";
       uses apply-advanced;
       container all {
         presence "enable all";
         description "Remove all private AS numbers and do not stop at the first public AS number";
         container replace {
           presence "enable replace";
           description "Replace private AS numbers with the BGP Group's local AS number";
           leaf nearest {
             description "Use closest public AS number to replace a private AS number";
             type empty;
           }
         }
       }
       leaf no-peer-loop-check {
         description "Remove peer loop-check";
         type empty;
       }
     }
     leaf cluster {
       description "Cluster identifier";
       type jt:areaid;
     }
     leaf no-client-reflect {
       description "Disable intracluster route redistribution";
       type empty;
     }
     leaf peer-as {
       description " Autonomous system number in plain number or 'higher 16bits'.'Lower 16 bits' (asdot notation) format";
       type string {
         junos:posix-pattern "^[0-9]+(.[0-9]+)?$";
         junos:pattern-message "Use format 'x' or 'x.y' to specify number 'x' (Range 1 .. 4294967295) or number with higher 2 bytes 'x' (Range 0 .. 65535) and lower 2 bytes 'y' (Range 0 .. 65535) respectively";
       }
     }
     container local-as {
       description "Local autonomous system number";
       leaf as-number {
         description " Autonomous system number in plain number or 'higher 16bits'.'Lower 16 bits' (asdot notation) format";
         type string {
           junos:posix-pattern "^[0-9]+(.[0-9]+)?$";
           junos:pattern-message "Use format 'x' or 'x.y' to specify number 'x' (Range 1 .. 4294967295) or number with higher 2 bytes 'x' (Range 0 .. 65535) and lower 2 bytes 'y' (Range 0 .. 65535) respectively";
         }
       }
       leaf loops {
         description "Maximum number of times this AS can be in an AS path";
         type union {
           type string {
             pattern "<.*>|$.*";
           }
           type int32 {
             range "1 .. 10";
           }
         }
       }
       leaf private {
         description "Hide this local AS in paths learned from this peering";
         type empty;
       }
       leaf alias {
         description "Treat this AS as an alias to the system AS";
         type empty;
       }
       leaf no-prepend-global-as {
         description "Do not prepend global autonomous-system number in advertised paths";
         type empty;
       }
     }
     leaf ipsec-sa {
       description "IPSec SA name";
       junos:must "(\"security ipsec security-association $$\")";
       junos:must-message "Referenced IPSec Security Association must be defined";
       type string {
         length "1 .. 32";
       }
     }
     container graceful-shutdown {
       description "BGP peer graceful shutdown option";
       uses apply-advanced;
       container receiver {
         presence "enable receiver";
         description "BGP peer graceful-shutdown receiver";
         uses apply-advanced;
         leaf disable {
           description "Disable graceful-shutdown receiver";
           junos:must "(!(\".. .. sender\"))";
           junos:must-message "Receiver cannot be disabled on Sender";
           type empty;
         }
         leaf local-preference {
           description "Value of receiver LOCAL_PREF path attribute";
           type union {
             type uint32;
             type string {
               pattern "<.*>|$.*";
             }
           }
         }
       }
       container sender {
         presence "enable sender";
         description "BGP peer graceful-shutdown sender";
         uses apply-advanced;
         leaf local-preference {
           description "Value of sender LOCAL_PREF path attribute";
           type union {
             type uint32;
             type string {
               pattern "<.*>|$.*";
             }
           }
         }
       }
     }
     container shutdown {
       presence "enable shutdown";
       description "Shutdown";
       uses apply-advanced;
       leaf notify-message {
         description "Notification message";
         type string;
       }
     }
     leaf unconfigured-peer-graceful-restart {
       description "BGP unconfigured peer graceful restart options";
       junos:must "(\".. graceful-restart\")";
       junos:must-message "unconfigured-peer-graceful-restart is only valid with 'graceful-restart'";
       type empty;
     }
     container graceful-restart {
       presence "enable graceful-restart";
       description "BGP graceful restart options";
       uses apply-advanced;
       choice enable-disable {
         case case_1 {
           leaf disable {
             description "Disable graceful restart";
             type empty;
           }
         }
       }
       leaf restart-time {
         description "Restart time used when negotiating with a peer";
         junos:must "((\"routing-options graceful-restart\" || \"fabric routing-options graceful-restart\"))";
         junos:must-message "restart-time is only valid with 'routing-options graceful-restart'";
         type union {
           type string {
             pattern "<.*>|$.*";
           }
           type uint32 {
             range "1 .. 1800";
           }
         }
       }
       leaf stale-routes-time {
         description "Maximum time for which stale routes are kept";
         type union {
           type string {
             pattern "<.*>|$.*";
           }
           type uint32 {
             range "1 .. 1800";
           }
         }
       }
       container long-lived {
         description "Long-lived graceful restart options";
         uses apply-advanced;
         container receiver {
           description "Long-lived graceful restart receiver (helper) options";
           uses apply-advanced;
           choice enable-disable {
             case case_1 {
               leaf disable {
                 description "Disable receiver (helper) functionality";
                 type empty;
               }
             }
           }
         }
         container advertise-to-non-llgr-neighbor {
           presence "enable advertise-to-non-llgr-neighbor";
           description "Advertise stale routes to non-LLGR neighbors";
           uses apply-advanced;
           leaf omit-no-export {
             description "Do not attach no-export community to stale routes";
             type empty;
           }
         }
       }
       leaf disable-notification-extensions {
         description "Disable notification extensions";
         type empty;
       }
       leaf forwarding-state-bit {
         description "Control forwarding-state flag negotiation";
         type enumeration {
           enum "as-rr-client" {
             description "As for a route reflector client";
           }
           enum "from-fib" {
             description "Always use state of associated FIB(s)";
           }
         }
       }
       leaf dont-help-shared-fate-bfd-down {
         description "Honor BFD-Down(C=0) if GR-restart not in progress";
         type empty;
       }
     }
     leaf include-mp-next-hop {
       description "Include NEXT-HOP attribute in multiprotocol updates";
       type empty;
     }
     leaf disable-4byte-as {
       description "Disable 4 byte AS capability advertisement";
       type empty;
     }
     container idle-after-switch-over {
       description "Stop peer session from coming up after nonstop-routing switch-over";
       choice idle-interval {
         case case_1 {
           leaf forever {
             description "Idle the peer until the user intervenes";
             type empty;
           }
         }
         case case_2 {
           leaf timeout {
             description "Timeout value, in seconds, for starting peer after switch over";
             type union {
               type string {
                 pattern "<.*>|$.*";
               }
               type uint32 {
                 range "1 .. 4294967295";
               }
             }
           }
         }
       }
     }
     container outbound-route-filter {
       junos:must "(!(\"system processes routing bgp update-threading\"))";
       junos:must-message "Can't be configured together with update-threading";
       description "Dynamically negotiated cooperative route filtering";
       uses apply-advanced;
       leaf bgp-orf-cisco-mode {
         description "Using BGP ORF capability code 130 and Prefix ORF type 128";
         type empty;
       }
       container extended-community {
         description "Extended community filtering";
         status deprecated;
         uses apply-advanced;
         choice accept-choice {
           leaf accept {
             description "Honor remote requests for extended community ORF";
             type empty;
           }
           leaf no-accept {
             description "Don't honor remote requests for extended community ORF";
             type empty;
           }
         }
         leaf vrf-filter {
           description "Request remote filtering using locally configured VRF import targets";
           type empty;
         }
       }
       container prefix-based {
         presence "enable prefix-based";
         description "Prefix-based outbound route filtering";
         uses apply-advanced;
         container accept {
           presence "enable accept";
           description "Honor Prefix-based ORFs from remote peers";
           uses apply-advanced;
           leaf inet {
             description "Honor IPv4 prefix filters";
             type empty;
           }
           leaf inet6 {
             description "Honor IPv6 prefix filters";
             type empty;
           }
         }
       }
     }
     container message-batching {
       description "DEPRECATED - Batching of outgoing messages";
       status deprecated;
       uses apply-advanced;
       choice enable-disable {
         case case_1 {
           leaf enable {
             description "Enable parameter";
             type empty;
           }
         }
         case case_2 {
           leaf disable {
             description "Disable parameter";
             type empty;
           }
         }
       }
       leaf interval {
         description "DEPRECATED - Interval over which to batch messages";
         default "250";
         units "milliseconds";
         type union {
           type string {
             pattern "<.*>|$.*";
           }
           type uint32 {
             range "100 .. 1000";
           }
         }
       }
     }
     container multipath {
       presence "enable multipath";
       description "Allow load sharing among multiple BGP paths";
       uses apply-advanced;
       leaf disable {
         description "Disable Multipath";
         type empty;
       }
       leaf multiple-as {
         description "Use paths received from different ASs";
         type empty;
       }
       leaf allow-protection {
         description "Allow protection for multipath legs";
         type empty;
       }
       leaf pause-computation-during-churn {
         description "Pause multipath job to absorb churn";
         type empty;
       }
       leaf list-nexthop {
         description "Use List-NH for homogenous nexthop-set also";
         type empty;
       }
     }
     leaf tcp-mss {
       description "Maximum TCP segment size";
       type union {
         type string {
           pattern "<.*>|$.*";
         }
         type uint32 {
           range "1 .. 4096";
         }
       }
     }
     leaf bgp-identifier {
       description "BGP Identifier";
       type jt:ipv4addr;
     }
     leaf tcp-aggressive-transmission {
       description "Enable aggressive transmission of pure TCP ACKs and retransmissions";
       type empty;
     }
     container bmp {
       description "Specific settings to override the routing-options settings";
       uses apply-advanced;
       leaf monitor {
         description "Enable/Disable monitoring";
         type enumeration {
           enum "enable" {
             description "Enable monitoring of BGP peer(s)";
           }
           enum "disable" {
             description "Disable monitoring of BGP peer(s)";
           }
         }
       }
       container route-monitoring {
         description "Control route monitoring settings";
         uses apply-advanced;
         leaf none {
           description "Do not send route monitoring messages";
           junos:must "((!(\".. pre-policy\") && (!(\".. post-policy\") && !(\".. rib-out\"))))";
           junos:must-message "May not be configured with pre-policy or post-policy or rib-out";
           type empty;
         }
         container pre-policy {
           presence "enable pre-policy";
           description "Send pre-policy route monitoring messages";
           leaf exclude-non-feasible {
             description "Exclude looped routes, etc";
             type empty;
           }
         }
         container post-policy {
           presence "enable post-policy";
           description "Send post-policy route monitoring messages";
           leaf exclude-non-eligible {
             description "Exclude unresolved routes, etc.";
             type empty;
           }
         }
         container rib-out {
           presence "enable rib-out";
           junos:must "((!(\"system processes routing bgp update-threading\") || \"system processes routing bgp rib-sharding\"))";
           junos:must-message "Update threading can't be configured together with bmp rib-out monitoring";
           description "Send adj-ribs-out route monitoring messages";
           leaf pre-policy {
             description "Send pre-policy adj-ribs-out route monitoring messages";
             type empty;
           }
           leaf post-policy {
             description "Send post-policy adj-ribs-out route monitoring messages";
             type empty;
           }
         }
       }
     }
     container advertise-bgp-static {
       presence "enable advertise-bgp-static";
       description "Advertise bgp-static routes";
       uses apply-advanced;
       leaf-list policy {
         ordered-by user;
         description "Static route advertisement policy";
         type jt:policy-algebra;
       }
     }
     leaf add-path-display-ipv4-address {
       description "Display add-path path-id in IPv4 address format";
       type empty;
     }
     container bfd-liveness-detection {
       description "Bidirectional Forwarding Detection (BFD) options";
       uses apply-advanced;
       leaf version {
         description "BFD protocol version number";
         default "automatic";
         type enumeration {
           enum "0" {
             description "BFD version 0 (deprecated)";
           }
           enum "1" {
             description "BFD version 1";
           }
           enum "automatic" {
             description "Choose BFD version automatically";
           }
         }
       }
       leaf minimum-interval {
         description "Minimum transmit and receive interval";
         units "milliseconds";
         type union {
           type string {
             pattern "<.*>|$.*";
           }
           type uint32 {
             range "1 .. 255000";
           }
         }
       }
       leaf minimum-transmit-interval {
         description "Minimum transmit interval";
         status deprecated;
         units "milliseconds";
         type union {
           type string {
             pattern "<.*>|$.*";
           }
           type uint32 {
             range "1 .. 255000";
           }
         }
       }
       leaf minimum-receive-interval {
         description "Minimum receive interval";
         units "milliseconds";
         type union {
           type string {
             pattern "<.*>|$.*";
           }
           type uint32 {
             range "1 .. 255000";
           }
         }
       }
       leaf multiplier {
         description "Detection time multiplier";
         default "3";
         type union {
           type string {
             pattern "<.*>|$.*";
           }
           type uint32 {
             range "1 .. 255";
           }
         }
       }
       choice adaptation-choice {
         case case_1 {
           leaf no-adaptation {
             description "Disable adaptation";
             type empty;
           }
         }
       }
       container transmit-interval {
         description "Transmit-interval options";
         uses apply-advanced;
         leaf minimum-interval {
           description "Minimum transmit interval";
           units "milliseconds";
           type union {
             type string {
               pattern "<.*>|$.*";
             }
             type uint32 {
               range "1 .. 255000";
             }
           }
         }
         leaf threshold {
           description "High transmit interval triggering a trap";
           units "milliseconds";
           type union {
             type uint32;
             type string {
               pattern "<.*>|$.*";
             }
           }
         }
       }
       container detection-time {
         description "Detection-time options";
         uses apply-advanced;
         leaf threshold {
           description "High detection-time triggering a trap";
           units "milliseconds";
           type union {
             type uint32;
             type string {
               pattern "<.*>|$.*";
             }
           }
         }
       }
       container authentication {
         description "Authentication options";
         uses apply-advanced;
         leaf key-chain {
           description "Key chain name";
           junos:must "(\".. algorithm\")";
           junos:must-message "May not be configured without algorithm";
           junos:must "(\"security authentication-key-chains key-chain $$\")";
           junos:must-message "Referenced key-chain must be defined";
           type string;
         }
         leaf algorithm {
           description "Algorithm name";
           junos:must "(\".. key-chain\")";
           junos:must-message "May not be configured without key-chain";
           type enumeration {
             enum "simple-password" {
               description "Simple password";
             }
             enum "keyed-md5" {
               description "Keyed message Digest 5";
             }
             enum "meticulous-keyed-md5" {
               description "Meticulous keyed message Digest 5";
             }
             enum "keyed-sha-1" {
               description "Keyed secure hash algorithm (SHA1) ";
             }
             enum "meticulous-keyed-sha-1" {
               description "Meticulous keyed secure hash algorithm (SHA1) ";
             }
           }
         }
         leaf loose-check {
           description "Verify authentication only if authentication is negotiated";
           type empty;
         }
       }
       leaf session-mode {
         description "BFD single-hop or multihop session-mode";
         default "automatic";
         type enumeration {
           enum "automatic" {
             description "Choose session-mode automatically";
           }
           enum "single-hop" {
             description "Use single-hop";
           }
           enum "multihop" {
             description "Use multihop";
           }
         }
       }
       leaf holddown-interval {
         description "Time to hold the session-UP notification to the client";
         units "milliseconds";
         type union {
           type string {
             pattern "<.*>|$.*";
           }
           type uint32 {
             range "0 .. 255000";
           }
         }
       }
     }
     container output-queue-priority {
       description "BGP output queue priority scheduler for updates";
       uses apply-advanced;
       container expedited {
         presence "enable expedited";
         description "Expedited queue; highest priority";
         leaf update-tokens {
           description "Number of tokens";
           type union {
             type string {
               pattern "<.*>|$.*";
             }
             type uint32 {
               range "1 .. 100";
             }
           }
         }
       }
       list priority {
         key name;
         description "Output queue priority 1..16; higher is better";
         leaf name {
           description "Output queue priority; higher is better";
           type union {
             type string {
               pattern "<.*>|$.*";
             }
             type uint32 {
               range "1 .. 16";
             }
           }
         }
         leaf update-tokens {
           description "Number of tokens";
           type union {
             type string {
               pattern "<.*>|$.*";
             }
             type uint32 {
               range "1 .. 100";
             }
           }
         }
       }
       container defaults {
         description "Map policy's priority class and BGP output-queue";
         uses apply-advanced;
         container low {
           description "Assign the 'low' priority class to this output-queue";
           uses bgp-output-queue-priority-class;
         }
         container medium {
           description "Assign the 'medium' priority class to this output-queue";
           uses bgp-output-queue-priority-class;
         }
         container high {
           description "Assign the 'high' priority class to this output-queue";
           uses bgp-output-queue-priority-class;
         }
       }
     }
     container multipath-build-priority {
       description "Configure the multipath build priority";
       uses apply-advanced;
       choice multipath-priority {
         case case_1 {
           leaf low {
             description "Do multipath build with low priority";
             type empty;
           }
         }
         case case_2 {
           leaf medium {
             description "Do multipath build with medium priority";
             type empty;
           }
         }
       }
     }
     leaf send-addpath-optimization {
       description "Enable BGP addpath advertisement optimization";
       type empty;
     }
     container defaults {
       uses apply-advanced;
       container ebgp {
         description "Options impacting external BGP default behaviors";
         uses apply-advanced;
         container no-policy {
           description "Default ebgp behaviors in the absence of configured policy";
           uses apply-advanced;
           leaf receive {
             description "Default ebgp receive behavior";
             type enumeration {
               enum "accept" {
                 description "By default, accept routes from all address families";
               }
               enum "reject" {
                 description "By default, reject routes from IPv4/IPv6 unicast address families";
               }
               enum "reject-always" {
                 description "By default, reject routes from all address families";
               }
             }
           }
           leaf advertise {
             description "Default ebgp advertise behavior";
             type enumeration {
               enum "accept" {
                 description "By default, advertise routes for all address families";
               }
               enum "reject" {
                 description "By default, do not advertise routes from IPv4/IPv6 unicast address families";
               }
               enum "reject-always" {
                 description "By default, do not advertise routes from any address families";
               }
             }
           }
         }
       }
     }
   }
   grouping bgp-af-gr {
     uses apply-advanced;
     container long-lived {
       description "Long-lived graceful restart options";
       uses apply-advanced;
       container restarter {
         description "Long-lived graceful restart restarter options";
         uses apply-advanced;
         choice enable-disable {
           case case_1 {
             leaf disable {
               description "Disable restarter functionality";
               type empty;
             }
           }
         }
         leaf stale-time {
           description "Stale time in seconds or dhms notation (1..16777215)";
           type string;
         }
       }
     }
     leaf forwarding-state-bit {
       description "Control forwarding-state flag negotiation";
       type enumeration {
         enum "set" {
           description "Always set";
         }
         enum "from-fib" {
           description "Use state of associated FIB(s)";
         }
       }
     }
   }
   grouping bgp-afi-default {
     uses apply-advanced;
     container prefix-limit {
       description "Limit maximum number of prefixes from a peer";
       uses bgpaf-prefix-limit;
     }
     container accepted-prefix-limit {
       description "Limit maximum number of prefixes accepted from a peer";
       uses bgpaf-accepted-prefix-limit;
     }
     container rib-group {
       description "Routing table group";
       uses rib_group_inet_type;
     }
     container add-path {
       description "Advertise multiple paths to peer";
       uses apath-options;
     }
     container aigp {
       description "Allow sending and receiving of AIGP attribute";
       presence "enable aigp";
       uses bgpaf-aigp-options;
     }
     leaf damping {
       description "Enable route flap damping";
       type empty;
     }
     leaf local-ipv4-address {
       description "Local IPv4 address";
       type jt:ipv4addr;
     }
     container loops {
       description "Allow local AS in received AS paths";
       uses bgpaf-loops;
     }
     container delay-route-advertisements {
       presence "enable delay-route-advertisements";
       junos:must "(!(\"system processes routing bgp rib-sharding\"))";
       junos:must-message "Can't be configured together with rib-sharding";
       description "Delay route updates for this family until FIB-sync";
       uses apply-advanced;
       leaf always-wait-for-krt-drain {
         description "Wait for KRT-queue drain for more-specific prefixes";
         type empty;
       }
       container minimum-delay {
         description "Minumum-delay to ensure KRT sees the route flash";
         uses apply-advanced;
         leaf routing-uptime {
           description "Min delay(sec) advertisement after RPD start";
           type union {
             type string {
               pattern "<.*>|$.*";
             }
             type uint32 {
               range "1 .. 36000";
             }
           }
         }
         leaf inbound-convergence {
           description "Min delay(sec) advertisement after source-peer sent all routes";
           type union {
             type string {
               pattern "<.*>|$.*";
             }
             type uint32 {
               range "1 .. 36000";
             }
           }
         }
       }
       container maximum-delay {
         description "Maximum delay deferring routes";
         uses apply-advanced;
         leaf route-age {
           description "Max delay(sec) advertisement route age";
           type union {
             type string {
               pattern "<.*>|$.*";
             }
             type uint32 {
               range "1 .. 36000";
             }
           }
         }
         leaf routing-uptime {
           description "Max delay(sec) advertisement after RPD start";
           type union {
             type string {
               pattern "<.*>|$.*";
             }
             type uint32 {
               range "1 .. 36000";
             }
           }
         }
       }
     }
     container nexthop-resolution {
       description "Configure nexthop resolution properties";
       uses apply-advanced;
       leaf no-resolution {
         description "Consider nexthop good without resolution attempt";
         type empty;
       }
       leaf preserve-nexthop-hierarchy {
         description "Attempt preserving resolved nexthop chain in forwarding";
         type empty;
       }
     }
     container defer-initial-multipath-build {
       presence "enable defer-initial-multipath-build";
       description "Defer initial multipath build until EOR is received";
       uses apply-advanced;
       leaf maximum-delay {
         description "Max delay(sec) multipath build after peer is up";
         type union {
           type string {
             pattern "<.*>|$.*";
           }
           type uint32 {
             range "1 .. 3600";
           }
         }
       }
     }
     container graceful-restart {
       description "BGP graceful restart options";
       uses bgp-af-gr;
     }
     leaf extended-nexthop {
       description "Extended nexthop encoding";
       junos:must "(!(\"system processes routing bgp rib-sharding\"))";
       junos:must-message "Can't be configured together with rib-sharding";
       type empty;
     }
     leaf extended-nexthop-color {
       description "Resolve using extended color nexthop";
       type empty;
     }
     leaf extended-nexthop-tunnel {
       description "Use BGP tunnel attribute";
       type empty;
     }
     leaf no-install {
       description "Dont install received routes in forwarding";
       type empty;
     }
     leaf route-age-bgp-view {
       description "Maintain BGP route's age based on Update messages only";
       type empty;
     }
     container output-queue-priority {
       description "Default output-queue to assign updates to";
       uses bgp-output-queue-priority-class;
     }
     container route-refresh-priority {
       description "Default output-queue to assign route refreshes to";
       uses bgp-output-queue-priority-class;
     }
     container withdraw-priority {
       description "Default output-queue to assign withdrawn routes to";
       uses bgp-output-queue-priority-class;
     }
     leaf advertise-srv6-service {
       description "Advertise SRv6 service";
       type empty;
     }
     leaf accept-srv6-service {
       description "Accept SRv6 service";
       type empty;
     }
   }
   grouping apath-options {
     description "Number of paths to advertise";
     uses apply-advanced;
     leaf receive {
       description "Receive multiple paths from peer";
       type empty;
     }
     container send {
       presence "enable send";
       description "Send multiple paths to peer";
       uses apply-advanced;
       container path-selection-mode {
         junos:must "(!(\".. multipath\"))";
         junos:must-message "Multipath must be disabled";
         description "Configure how to select add-path routes";
         uses apply-advanced;
         choice mode {
           case case_1 {
             leaf all-paths {
               description "Advertise all paths allowed by path count";
               type empty;
             }
           }
           case case_2 {
             leaf equal-cost-paths {
               description "Advertise equal cost paths";
               type empty;
             }
           }
         }
       }
       leaf-list prefix-policy {
         ordered-by user;
         description "Perform add-path only for prefixes that match policy";
         type jt:policy-algebra;
       }
       leaf path-count {
         description "Number of paths to advertise";
         type union {
           type string {
             pattern "<.*>|$.*";
           }
           type int32 {
             range "2 .. 64";
           }
         }
       }
       leaf include-backup-path {
         description "Number of backup paths to advertise";
         type union {
           type string {
             pattern "<.*>|$.*";
           }
           type int32 {
             range "1 .. 2";
           }
         }
       }
       leaf multipath {
         description "Include only multipath contributor routes";
         type empty;
       }
     }
   }
   grouping bgp-afi-flow {
     uses apply-advanced;
     container prefix-limit {
       description "Limit maximum number of prefixes from a peer";
       uses bgpaf-prefix-limit;
     }
     container accepted-prefix-limit {
       description "Limit maximum number of prefixes accepted from a peer";
       uses bgpaf-accepted-prefix-limit;
     }
     container rib-group {
       description "Routing table group";
       uses rib_group_inet_type;
     }
     container add-path {
       description "Advertise multiple paths to peer";
       uses apath-options;
     }
     container aigp {
       description "Allow sending and receiving of AIGP attribute";
       presence "enable aigp";
       uses bgpaf-aigp-options;
     }
     leaf damping {
       description "Enable route flap damping";
       type empty;
     }
     leaf local-ipv4-address {
       description "Local IPv4 address";
       type jt:ipv4addr;
     }
     container loops {
       description "Allow local AS in received AS paths";
       uses bgpaf-loops;
     }
     container delay-route-advertisements {
       presence "enable delay-route-advertisements";
       junos:must "(!(\"system processes routing bgp rib-sharding\"))";
       junos:must-message "Can't be configured together with rib-sharding";
       description "Delay route updates for this family until FIB-sync";
       uses apply-advanced;
       leaf always-wait-for-krt-drain {
         description "Wait for KRT-queue drain for more-specific prefixes";
         type empty;
       }
       container minimum-delay {
         description "Minumum-delay to ensure KRT sees the route flash";
         uses apply-advanced;
         leaf routing-uptime {
           description "Min delay(sec) advertisement after RPD start";
           type union {
             type string {
               pattern "<.*>|$.*";
             }
             type uint32 {
               range "1 .. 36000";
             }
           }
         }
         leaf inbound-convergence {
           description "Min delay(sec) advertisement after source-peer sent all routes";
           type union {
             type string {
               pattern "<.*>|$.*";
             }
             type uint32 {
               range "1 .. 36000";
             }
           }
         }
       }
       container maximum-delay {
         description "Maximum delay deferring routes";
         uses apply-advanced;
         leaf route-age {
           description "Max delay(sec) advertisement route age";
           type union {
             type string {
               pattern "<.*>|$.*";
             }
             type uint32 {
               range "1 .. 36000";
             }
           }
         }
         leaf routing-uptime {
           description "Max delay(sec) advertisement after RPD start";
           type union {
             type string {
               pattern "<.*>|$.*";
             }
             type uint32 {
               range "1 .. 36000";
             }
           }
         }
       }
     }
     container nexthop-resolution {
       description "Configure nexthop resolution properties";
       uses apply-advanced;
       leaf no-resolution {
         description "Consider nexthop good without resolution attempt";
         type empty;
       }
       leaf preserve-nexthop-hierarchy {
         description "Attempt preserving resolved nexthop chain in forwarding";
         type empty;
       }
     }
     container defer-initial-multipath-build {
       presence "enable defer-initial-multipath-build";
       description "Defer initial multipath build until EOR is received";
       uses apply-advanced;
       leaf maximum-delay {
         description "Max delay(sec) multipath build after peer is up";
         type union {
           type string {
             pattern "<.*>|$.*";
           }
           type uint32 {
             range "1 .. 3600";
           }
         }
       }
     }
     container graceful-restart {
       description "BGP graceful restart options";
       uses bgp-af-gr;
     }
     leaf extended-nexthop {
       description "Extended nexthop encoding";
       junos:must "(!(\"system processes routing bgp rib-sharding\"))";
       junos:must-message "Can't be configured together with rib-sharding";
       type empty;
     }
     leaf extended-nexthop-color {
       description "Resolve using extended color nexthop";
       type empty;
     }
     leaf extended-nexthop-tunnel {
       description "Use BGP tunnel attribute";
       type empty;
     }
     leaf no-install {
       description "Dont install received routes in forwarding";
       type empty;
     }
     leaf route-age-bgp-view {
       description "Maintain BGP route's age based on Update messages only";
       type empty;
     }
     container output-queue-priority {
       description "Default output-queue to assign updates to";
       uses bgp-output-queue-priority-class;
     }
     container route-refresh-priority {
       description "Default output-queue to assign route refreshes to";
       uses bgp-output-queue-priority-class;
     }
     container withdraw-priority {
       description "Default output-queue to assign withdrawn routes to";
       uses bgp-output-queue-priority-class;
     }
     leaf advertise-srv6-service {
       description "Advertise SRv6 service";
       type empty;
     }
     leaf accept-srv6-service {
       description "Accept SRv6 service";
       type empty;
     }
     leaf-list no-validate {
       ordered-by user;
       description "Bypass validation procedure for routes that match policy";
       type jt:policy-algebra;
     }
     leaf strip-nexthop {
       description "Strip the next-hop from the outgoing flow update";
       type empty;
     }
     leaf allow-policy-add-nexthop {
       description "Allow policy to add nexthop to a route without nexthop";
       status deprecated;
       type empty;
     }
   }
   grouping bgp-afi-flow-with-redirect-ip-action {
     uses apply-advanced;
     container prefix-limit {
       description "Limit maximum number of prefixes from a peer";
       uses bgpaf-prefix-limit;
     }
     container accepted-prefix-limit {
       description "Limit maximum number of prefixes accepted from a peer";
       uses bgpaf-accepted-prefix-limit;
     }
     container rib-group {
       description "Routing table group";
       uses rib_group_inet_type;
     }
     container add-path {
       description "Advertise multiple paths to peer";
       uses apath-options;
     }
     container aigp {
       description "Allow sending and receiving of AIGP attribute";
       presence "enable aigp";
       uses bgpaf-aigp-options;
     }
     leaf damping {
       description "Enable route flap damping";
       type empty;
     }
     leaf local-ipv4-address {
       description "Local IPv4 address";
       type jt:ipv4addr;
     }
     container loops {
       description "Allow local AS in received AS paths";
       uses bgpaf-loops;
     }
     container delay-route-advertisements {
       presence "enable delay-route-advertisements";
       junos:must "(!(\"system processes routing bgp rib-sharding\"))";
       junos:must-message "Can't be configured together with rib-sharding";
       description "Delay route updates for this family until FIB-sync";
       uses apply-advanced;
       leaf always-wait-for-krt-drain {
         description "Wait for KRT-queue drain for more-specific prefixes";
         type empty;
       }
       container minimum-delay {
         description "Minumum-delay to ensure KRT sees the route flash";
         uses apply-advanced;
         leaf routing-uptime {
           description "Min delay(sec) advertisement after RPD start";
           type union {
             type string {
               pattern "<.*>|$.*";
             }
             type uint32 {
               range "1 .. 36000";
             }
           }
         }
         leaf inbound-convergence {
           description "Min delay(sec) advertisement after source-peer sent all routes";
           type union {
             type string {
               pattern "<.*>|$.*";
             }
             type uint32 {
               range "1 .. 36000";
             }
           }
         }
       }
       container maximum-delay {
         description "Maximum delay deferring routes";
         uses apply-advanced;
         leaf route-age {
           description "Max delay(sec) advertisement route age";
           type union {
             type string {
               pattern "<.*>|$.*";
             }
             type uint32 {
               range "1 .. 36000";
             }
           }
         }
         leaf routing-uptime {
           description "Max delay(sec) advertisement after RPD start";
           type union {
             type string {
               pattern "<.*>|$.*";
             }
             type uint32 {
               range "1 .. 36000";
             }
           }
         }
       }
     }
     container nexthop-resolution {
       description "Configure nexthop resolution properties";
       uses apply-advanced;
       leaf no-resolution {
         description "Consider nexthop good without resolution attempt";
         type empty;
       }
       leaf preserve-nexthop-hierarchy {
         description "Attempt preserving resolved nexthop chain in forwarding";
         type empty;
       }
     }
     container defer-initial-multipath-build {
       presence "enable defer-initial-multipath-build";
       description "Defer initial multipath build until EOR is received";
       uses apply-advanced;
       leaf maximum-delay {
         description "Max delay(sec) multipath build after peer is up";
         type union {
           type string {
             pattern "<.*>|$.*";
           }
           type uint32 {
             range "1 .. 3600";
           }
         }
       }
     }
     container graceful-restart {
       description "BGP graceful restart options";
       uses bgp-af-gr;
     }
     leaf extended-nexthop {
       description "Extended nexthop encoding";
       junos:must "(!(\"system processes routing bgp rib-sharding\"))";
       junos:must-message "Can't be configured together with rib-sharding";
       type empty;
     }
     leaf extended-nexthop-color {
       description "Resolve using extended color nexthop";
       type empty;
     }
     leaf extended-nexthop-tunnel {
       description "Use BGP tunnel attribute";
       type empty;
     }
     leaf no-install {
       description "Dont install received routes in forwarding";
       type empty;
     }
     leaf route-age-bgp-view {
       description "Maintain BGP route's age based on Update messages only";
       type empty;
     }
     container output-queue-priority {
       description "Default output-queue to assign updates to";
       uses bgp-output-queue-priority-class;
     }
     container route-refresh-priority {
       description "Default output-queue to assign route refreshes to";
       uses bgp-output-queue-priority-class;
     }
     container withdraw-priority {
       description "Default output-queue to assign withdrawn routes to";
       uses bgp-output-queue-priority-class;
     }
     leaf advertise-srv6-service {
       description "Advertise SRv6 service";
       type empty;
     }
     leaf accept-srv6-service {
       description "Accept SRv6 service";
       type empty;
     }
     leaf-list no-validate {
       ordered-by user;
       description "Bypass validation procedure for routes that match policy";
       type jt:policy-algebra;
     }
     leaf strip-nexthop {
       description "Strip the next-hop from the outgoing flow update";
       type empty;
     }
     container legacy-redirect-ip-action {
       presence "enable legacy-redirect-ip-action";
       description "Configure legacy redirect to IP support";
       uses apply-advanced;
       leaf receive {
         description "Accept legacy encoded redirect-to-ip action attribute";
         type empty;
       }
       leaf send {
         description "Advertise Redirect action as legacy redirect attribute";
         type empty;
       }
     }
     leaf secondary-independent-resolution {
       description "Resolve FLOW routes in VRF table independent of VPN FLOW route";
       type empty;
     }
   }
   grouping bgp-afi-inet-transport {
     uses apply-advanced;
     container prefix-limit {
       description "Limit maximum number of prefixes from a peer";
       uses bgpaf-prefix-limit;
     }
     container accepted-prefix-limit {
       description "Limit maximum number of prefixes accepted from a peer";
       uses bgpaf-accepted-prefix-limit;
     }
     container rib-group {
       description "Routing table group";
       uses rib_group_inet_type;
     }
     container add-path {
       description "Advertise multiple paths to peer";
       uses apath-options;
     }
     container aigp {
       description "Allow sending and receiving of AIGP attribute";
       presence "enable aigp";
       uses bgpaf-aigp-options;
     }
     leaf damping {
       description "Enable route flap damping";
       type empty;
     }
     leaf local-ipv4-address {
       description "Local IPv4 address";
       type jt:ipv4addr;
     }
     container loops {
       description "Allow local AS in received AS paths";
       uses bgpaf-loops;
     }
     container delay-route-advertisements {
       presence "enable delay-route-advertisements";
       junos:must "(!(\"system processes routing bgp rib-sharding\"))";
       junos:must-message "Can't be configured together with rib-sharding";
       description "Delay route updates for this family until FIB-sync";
       uses apply-advanced;
       leaf always-wait-for-krt-drain {
         description "Wait for KRT-queue drain for more-specific prefixes";
         type empty;
       }
       container minimum-delay {
         description "Minumum-delay to ensure KRT sees the route flash";
         uses apply-advanced;
         leaf routing-uptime {
           description "Min delay(sec) advertisement after RPD start";
           type union {
             type string {
               pattern "<.*>|$.*";
             }
             type uint32 {
               range "1 .. 36000";
             }
           }
         }
         leaf inbound-convergence {
           description "Min delay(sec) advertisement after source-peer sent all routes";
           type union {
             type string {
               pattern "<.*>|$.*";
             }
             type uint32 {
               range "1 .. 36000";
             }
           }
         }
       }
       container maximum-delay {
         description "Maximum delay deferring routes";
         uses apply-advanced;
         leaf route-age {
           description "Max delay(sec) advertisement route age";
           type union {
             type string {
               pattern "<.*>|$.*";
             }
             type uint32 {
               range "1 .. 36000";
             }
           }
         }
         leaf routing-uptime {
           description "Max delay(sec) advertisement after RPD start";
           type union {
             type string {
               pattern "<.*>|$.*";
             }
             type uint32 {
               range "1 .. 36000";
             }
           }
         }
       }
     }
     container nexthop-resolution {
       description "Configure nexthop resolution properties";
       uses apply-advanced;
       leaf no-resolution {
         description "Consider nexthop good without resolution attempt";
         type empty;
       }
       leaf preserve-nexthop-hierarchy {
         description "Attempt preserving resolved nexthop chain in forwarding";
         type empty;
       }
     }
     container defer-initial-multipath-build {
       presence "enable defer-initial-multipath-build";
       description "Defer initial multipath build until EOR is received";
       uses apply-advanced;
       leaf maximum-delay {
         description "Max delay(sec) multipath build after peer is up";
         type union {
           type string {
             pattern "<.*>|$.*";
           }
           type uint32 {
             range "1 .. 3600";
           }
         }
       }
     }
     container graceful-restart {
       description "BGP graceful restart options";
       uses bgp-af-gr;
     }
     leaf extended-nexthop {
       description "Extended nexthop encoding";
       junos:must "(!(\"system processes routing bgp rib-sharding\"))";
       junos:must-message "Can't be configured together with rib-sharding";
       type empty;
     }
     leaf extended-nexthop-color {
       description "Resolve using extended color nexthop";
       type empty;
     }
     leaf extended-nexthop-tunnel {
       description "Use BGP tunnel attribute";
       type empty;
     }
     leaf no-install {
       description "Dont install received routes in forwarding";
       type empty;
     }
     leaf route-age-bgp-view {
       description "Maintain BGP route's age based on Update messages only";
       type empty;
     }
     container output-queue-priority {
       description "Default output-queue to assign updates to";
       uses bgp-output-queue-priority-class;
     }
     container route-refresh-priority {
       description "Default output-queue to assign route refreshes to";
       uses bgp-output-queue-priority-class;
     }
     container withdraw-priority {
       description "Default output-queue to assign withdrawn routes to";
       uses bgp-output-queue-priority-class;
     }
     leaf advertise-srv6-service {
       description "Advertise SRv6 service";
       type empty;
     }
     leaf accept-srv6-service {
       description "Accept SRv6 service";
       type empty;
     }
     container aggregate-label {
       presence "enable aggregate-label";
       description "Aggregate labels of incoming routes with the same FEC";
       uses apply-advanced;
       leaf community {
         description "Community to identify the FEC of incoming routes";
         type string;
       }
     }
     leaf per-prefix-label {
       description "Allocate a unique label to each advertised prefix";
       type empty;
     }
     leaf per-group-label {
       description "Advertise prefixes with unique labels per group";
       type empty;
     }
     container traffic-statistics {
       description "Collect statistics for BGP label-switched paths";
       presence "enable traffic-statistics";
       uses bgpaf-traffic-statistics;
     }
     container protection {
       presence "enable protection";
       description "Compute backup path for active nexthop failure";
     }
   }
   grouping bgp-afi-inet6-labeled {
     uses apply-advanced;
     container prefix-limit {
       description "Limit maximum number of prefixes from a peer";
       uses bgpaf-prefix-limit;
     }
     container accepted-prefix-limit {
       description "Limit maximum number of prefixes accepted from a peer";
       uses bgpaf-accepted-prefix-limit;
     }
     container rib-group {
       description "Routing table group";
       uses rib_group_inet_type;
     }
     container add-path {
       description "Advertise multiple paths to peer";
       uses apath-options;
     }
     container aigp {
       description "Allow sending and receiving of AIGP attribute";
       presence "enable aigp";
       uses bgpaf-aigp-options;
     }
     leaf damping {
       description "Enable route flap damping";
       type empty;
     }
     leaf local-ipv4-address {
       description "Local IPv4 address";
       type jt:ipv4addr;
     }
     container loops {
       description "Allow local AS in received AS paths";
       uses bgpaf-loops;
     }
     container delay-route-advertisements {
       presence "enable delay-route-advertisements";
       junos:must "(!(\"system processes routing bgp rib-sharding\"))";
       junos:must-message "Can't be configured together with rib-sharding";
       description "Delay route updates for this family until FIB-sync";
       uses apply-advanced;
       leaf always-wait-for-krt-drain {
         description "Wait for KRT-queue drain for more-specific prefixes";
         type empty;
       }
       container minimum-delay {
         description "Minumum-delay to ensure KRT sees the route flash";
         uses apply-advanced;
         leaf routing-uptime {
           description "Min delay(sec) advertisement after RPD start";
           type union {
             type string {
               pattern "<.*>|$.*";
             }
             type uint32 {
               range "1 .. 36000";
             }
           }
         }
         leaf inbound-convergence {
           description "Min delay(sec) advertisement after source-peer sent all routes";
           type union {
             type string {
               pattern "<.*>|$.*";
             }
             type uint32 {
               range "1 .. 36000";
             }
           }
         }
       }
       container maximum-delay {
         description "Maximum delay deferring routes";
         uses apply-advanced;
         leaf route-age {
           description "Max delay(sec) advertisement route age";
           type union {
             type string {
               pattern "<.*>|$.*";
             }
             type uint32 {
               range "1 .. 36000";
             }
           }
         }
         leaf routing-uptime {
           description "Max delay(sec) advertisement after RPD start";
           type union {
             type string {
               pattern "<.*>|$.*";
             }
             type uint32 {
               range "1 .. 36000";
             }
           }
         }
       }
     }
     container nexthop-resolution {
       description "Configure nexthop resolution properties";
       uses apply-advanced;
       leaf no-resolution {
         description "Consider nexthop good without resolution attempt";
         type empty;
       }
       leaf preserve-nexthop-hierarchy {
         description "Attempt preserving resolved nexthop chain in forwarding";
         type empty;
       }
     }
     container defer-initial-multipath-build {
       presence "enable defer-initial-multipath-build";
       description "Defer initial multipath build until EOR is received";
       uses apply-advanced;
       leaf maximum-delay {
         description "Max delay(sec) multipath build after peer is up";
         type union {
           type string {
             pattern "<.*>|$.*";
           }
           type uint32 {
             range "1 .. 3600";
           }
         }
       }
     }
     container graceful-restart {
       description "BGP graceful restart options";
       uses bgp-af-gr;
     }
     leaf extended-nexthop {
       description "Extended nexthop encoding";
       junos:must "(!(\"system processes routing bgp rib-sharding\"))";
       junos:must-message "Can't be configured together with rib-sharding";
       type empty;
     }
     leaf extended-nexthop-color {
       description "Resolve using extended color nexthop";
       type empty;
     }
     leaf extended-nexthop-tunnel {
       description "Use BGP tunnel attribute";
       type empty;
     }
     leaf no-install {
       description "Dont install received routes in forwarding";
       type empty;
     }
     leaf route-age-bgp-view {
       description "Maintain BGP route's age based on Update messages only";
       type empty;
     }
     container output-queue-priority {
       description "Default output-queue to assign updates to";
       uses bgp-output-queue-priority-class;
     }
     container route-refresh-priority {
       description "Default output-queue to assign route refreshes to";
       uses bgp-output-queue-priority-class;
     }
     container withdraw-priority {
       description "Default output-queue to assign withdrawn routes to";
       uses bgp-output-queue-priority-class;
     }
     leaf advertise-srv6-service {
       description "Advertise SRv6 service";
       type empty;
     }
     leaf accept-srv6-service {
       description "Accept SRv6 service";
       type empty;
     }
     container aggregate-label {
       presence "enable aggregate-label";
       description "Aggregate labels of incoming routes with the same FEC";
       uses apply-advanced;
       leaf community {
         description "Community to identify the FEC of incoming routes";
         type string;
       }
     }
     leaf per-group-label {
       description "Advertise prefixes with unique labels per group";
       type empty;
     }
     container traffic-statistics {
       description "Collect statistics for BGP label-switched paths";
       presence "enable traffic-statistics";
       uses bgpaf-traffic-statistics;
     }
     container rib {
       description "Select table used by labeled unicast routes";
       uses apply-advanced;
       leaf inet6.3 {
         description "Use inet6.3 to exchange labeled unicast routes";
         type empty;
       }
     }
     container explicit-null {
       presence "enable explicit-null";
       description "Advertise explicit null";
       leaf connected-only {
         description "Advertise explicit null only for connected routes";
         type empty;
       }
     }
     container protection {
       presence "enable protection";
       junos:must "((!(\".. .. .. .. type internal\") && !(\".. .. .. .. .. type internal\")))";
       junos:must-message "Protection for labeled-bgp valid only for EBGP";
       description "Compute backup path for active nexthop failure";
     }
     list topology {
       key name;
       ordered-by user;
       description "Multi topology routing tables";
       junos:must "(!(\"system processes routing bgp rib-sharding\"))";
       junos:must-message "Can't be configured together with rib-sharding";
       junos:must "(!(\"routing-options no-multi-topology-routing\"))";
       junos:must-message "Multi topology routing is disabled";
       leaf name {
         description "Topology name";
         type string {
           junos:posix-pattern "!^((.*:.*)|(.{129,}))$";
           junos:pattern-message "Must be a non-reserved string of 128 characters or less";
         }
       }
       uses apply-advanced;
       leaf community {
         description "Community to identify multi topology routes";
         type string;
       }
     }
   }
   grouping bgp-afi-inet6-transport {
     uses apply-advanced;
     container prefix-limit {
       description "Limit maximum number of prefixes from a peer";
       uses bgpaf-prefix-limit;
     }
     container accepted-prefix-limit {
       description "Limit maximum number of prefixes accepted from a peer";
       uses bgpaf-accepted-prefix-limit;
     }
     container rib-group {
       description "Routing table group";
       uses rib_group_inet_type;
     }
     container add-path {
       description "Advertise multiple paths to peer";
       uses apath-options;
     }
     container aigp {
       description "Allow sending and receiving of AIGP attribute";
       presence "enable aigp";
       uses bgpaf-aigp-options;
     }
     leaf damping {
       description "Enable route flap damping";
       type empty;
     }
     leaf local-ipv4-address {
       description "Local IPv4 address";
       type jt:ipv4addr;
     }
     container loops {
       description "Allow local AS in received AS paths";
       uses bgpaf-loops;
     }
     container delay-route-advertisements {
       presence "enable delay-route-advertisements";
       junos:must "(!(\"system processes routing bgp rib-sharding\"))";
       junos:must-message "Can't be configured together with rib-sharding";
       description "Delay route updates for this family until FIB-sync";
       uses apply-advanced;
       leaf always-wait-for-krt-drain {
         description "Wait for KRT-queue drain for more-specific prefixes";
         type empty;
       }
       container minimum-delay {
         description "Minumum-delay to ensure KRT sees the route flash";
         uses apply-advanced;
         leaf routing-uptime {
           description "Min delay(sec) advertisement after RPD start";
           type union {
             type string {
               pattern "<.*>|$.*";
             }
             type uint32 {
               range "1 .. 36000";
             }
           }
         }
         leaf inbound-convergence {
           description "Min delay(sec) advertisement after source-peer sent all routes";
           type union {
             type string {
               pattern "<.*>|$.*";
             }
             type uint32 {
               range "1 .. 36000";
             }
           }
         }
       }
       container maximum-delay {
         description "Maximum delay deferring routes";
         uses apply-advanced;
         leaf route-age {
           description "Max delay(sec) advertisement route age";
           type union {
             type string {
               pattern "<.*>|$.*";
             }
             type uint32 {
               range "1 .. 36000";
             }
           }
         }
         leaf routing-uptime {
           description "Max delay(sec) advertisement after RPD start";
           type union {
             type string {
               pattern "<.*>|$.*";
             }
             type uint32 {
               range "1 .. 36000";
             }
           }
         }
       }
     }
     container nexthop-resolution {
       description "Configure nexthop resolution properties";
       uses apply-advanced;
       leaf no-resolution {
         description "Consider nexthop good without resolution attempt";
         type empty;
       }
       leaf preserve-nexthop-hierarchy {
         description "Attempt preserving resolved nexthop chain in forwarding";
         type empty;
       }
     }
     container defer-initial-multipath-build {
       presence "enable defer-initial-multipath-build";
       description "Defer initial multipath build until EOR is received";
       uses apply-advanced;
       leaf maximum-delay {
         description "Max delay(sec) multipath build after peer is up";
         type union {
           type string {
             pattern "<.*>|$.*";
           }
           type uint32 {
             range "1 .. 3600";
           }
         }
       }
     }
     container graceful-restart {
       description "BGP graceful restart options";
       uses bgp-af-gr;
     }
     leaf extended-nexthop {
       description "Extended nexthop encoding";
       junos:must "(!(\"system processes routing bgp rib-sharding\"))";
       junos:must-message "Can't be configured together with rib-sharding";
       type empty;
     }
     leaf extended-nexthop-color {
       description "Resolve using extended color nexthop";
       type empty;
     }
     leaf extended-nexthop-tunnel {
       description "Use BGP tunnel attribute";
       type empty;
     }
     leaf no-install {
       description "Dont install received routes in forwarding";
       type empty;
     }
     leaf route-age-bgp-view {
       description "Maintain BGP route's age based on Update messages only";
       type empty;
     }
     container output-queue-priority {
       description "Default output-queue to assign updates to";
       uses bgp-output-queue-priority-class;
     }
     container route-refresh-priority {
       description "Default output-queue to assign route refreshes to";
       uses bgp-output-queue-priority-class;
     }
     container withdraw-priority {
       description "Default output-queue to assign withdrawn routes to";
       uses bgp-output-queue-priority-class;
     }
     leaf advertise-srv6-service {
       description "Advertise SRv6 service";
       type empty;
     }
     leaf accept-srv6-service {
       description "Accept SRv6 service";
       type empty;
     }
     container aggregate-label {
       presence "enable aggregate-label";
       description "Aggregate labels of incoming routes with the same FEC";
       uses apply-advanced;
       leaf community {
         description "Community to identify the FEC of incoming routes";
         type string;
       }
     }
     leaf per-prefix-label {
       description "Allocate a unique label to each advertised prefix";
       type empty;
     }
     leaf per-group-label {
       description "Advertise prefixes with unique labels per group";
       type empty;
     }
     container traffic-statistics {
       description "Collect statistics for BGP label-switched paths";
       presence "enable traffic-statistics";
       uses bgpaf-traffic-statistics;
     }
     container lu-export {
       presence "enable lu-export";
       description "Install Classful Transport routes in inet6.3";
       uses apply-advanced;
     }
     container protection {
       presence "enable protection";
       description "Compute backup path for active nexthop failure";
     }
   }
   grouping bgp-afi-l2vpn {
     uses apply-advanced;
     container prefix-limit {
       description "Limit maximum number of prefixes from a peer";
       uses bgpaf-prefix-limit;
     }
     container accepted-prefix-limit {
       description "Limit maximum number of prefixes accepted from a peer";
       uses bgpaf-accepted-prefix-limit;
     }
     container rib-group {
       description "Routing table group";
       uses rib_group_inet_type;
     }
     container add-path {
       description "Advertise multiple paths to peer";
       uses apath-options;
     }
     container aigp {
       description "Allow sending and receiving of AIGP attribute";
       presence "enable aigp";
       uses bgpaf-aigp-options;
     }
     leaf damping {
       description "Enable route flap damping";
       type empty;
     }
     leaf local-ipv4-address {
       description "Local IPv4 address";
       type jt:ipv4addr;
     }
     container loops {
       description "Allow local AS in received AS paths";
       uses bgpaf-loops;
     }
     container delay-route-advertisements {
       presence "enable delay-route-advertisements";
       junos:must "(!(\"system processes routing bgp rib-sharding\"))";
       junos:must-message "Can't be configured together with rib-sharding";
       description "Delay route updates for this family until FIB-sync";
       uses apply-advanced;
       leaf always-wait-for-krt-drain {
         description "Wait for KRT-queue drain for more-specific prefixes";
         type empty;
       }
       container minimum-delay {
         description "Minumum-delay to ensure KRT sees the route flash";
         uses apply-advanced;
         leaf routing-uptime {
           description "Min delay(sec) advertisement after RPD start";
           type union {
             type string {
               pattern "<.*>|$.*";
             }
             type uint32 {
               range "1 .. 36000";
             }
           }
         }
         leaf inbound-convergence {
           description "Min delay(sec) advertisement after source-peer sent all routes";
           type union {
             type string {
               pattern "<.*>|$.*";
             }
             type uint32 {
               range "1 .. 36000";
             }
           }
         }
       }
       container maximum-delay {
         description "Maximum delay deferring routes";
         uses apply-advanced;
         leaf route-age {
           description "Max delay(sec) advertisement route age";
           type union {
             type string {
               pattern "<.*>|$.*";
             }
             type uint32 {
               range "1 .. 36000";
             }
           }
         }
         leaf routing-uptime {
           description "Max delay(sec) advertisement after RPD start";
           type union {
             type string {
               pattern "<.*>|$.*";
             }
             type uint32 {
               range "1 .. 36000";
             }
           }
         }
       }
     }
     container nexthop-resolution {
       description "Configure nexthop resolution properties";
       uses apply-advanced;
       leaf no-resolution {
         description "Consider nexthop good without resolution attempt";
         type empty;
       }
       leaf preserve-nexthop-hierarchy {
         description "Attempt preserving resolved nexthop chain in forwarding";
         type empty;
       }
     }
     container defer-initial-multipath-build {
       presence "enable defer-initial-multipath-build";
       description "Defer initial multipath build until EOR is received";
       uses apply-advanced;
       leaf maximum-delay {
         description "Max delay(sec) multipath build after peer is up";
         type union {
           type string {
             pattern "<.*>|$.*";
           }
           type uint32 {
             range "1 .. 3600";
           }
         }
       }
     }
     container graceful-restart {
       description "BGP graceful restart options";
       uses bgp-af-gr;
     }
     leaf extended-nexthop {
       description "Extended nexthop encoding";
       junos:must "(!(\"system processes routing bgp rib-sharding\"))";
       junos:must-message "Can't be configured together with rib-sharding";
       type empty;
     }
     leaf extended-nexthop-color {
       description "Resolve using extended color nexthop";
       type empty;
     }
     leaf extended-nexthop-tunnel {
       description "Use BGP tunnel attribute";
       type empty;
     }
     leaf no-install {
       description "Dont install received routes in forwarding";
       type empty;
     }
     leaf route-age-bgp-view {
       description "Maintain BGP route's age based on Update messages only";
       type empty;
     }
     container output-queue-priority {
       description "Default output-queue to assign updates to";
       uses bgp-output-queue-priority-class;
     }
     container route-refresh-priority {
       description "Default output-queue to assign route refreshes to";
       uses bgp-output-queue-priority-class;
     }
     container withdraw-priority {
       description "Default output-queue to assign withdrawn routes to";
       uses bgp-output-queue-priority-class;
     }
     leaf advertise-srv6-service {
       description "Advertise SRv6 service";
       type empty;
     }
     leaf accept-srv6-service {
       description "Accept SRv6 service";
       type empty;
     }
     container egress-protection {
       presence "enable egress-protection";
       junos:must "(!(\".. .. .. .. type external\"))";
       junos:must-message "Egress-protection is valid only for IBGP";
       description "Egress router protection";
       uses apply-advanced;
       container context-identifier {
         description "Context identifier";
         uses apply-advanced;
         leaf context-id {
           description "IP address";
           junos:must "(\"protocols mpls egress-protection context-identifier $$ primary\")";
           junos:must-message "context-identifier must be type primary";
           junos:must "(\"protocols mpls egress-protection context-identifier $$\")";
           junos:must-message "same context-identifier must be defined in protocols mpls egress-protection";
           type jt:ipv4addr;
         }
       }
       leaf-list keep-import {
         ordered-by user;
         description "Import policy";
         junos:must "(\"policy-options policy-statement \")";
         junos:must-message "policy-options policy-statement";
         type jt:policy-algebra;
       }
     }
   }
   grouping bgp-afi-l3vpn {
     uses apply-advanced;
     container prefix-limit {
       description "Limit maximum number of prefixes from a peer";
       uses bgpaf-prefix-limit;
     }
     container accepted-prefix-limit {
       description "Limit maximum number of prefixes accepted from a peer";
       uses bgpaf-accepted-prefix-limit;
     }
     container rib-group {
       description "Routing table group";
       uses rib_group_inet_type;
     }
     container add-path {
       description "Advertise multiple paths to peer";
       uses apath-options;
     }
     container aigp {
       description "Allow sending and receiving of AIGP attribute";
       presence "enable aigp";
       uses bgpaf-aigp-options;
     }
     leaf damping {
       description "Enable route flap damping";
       type empty;
     }
     leaf local-ipv4-address {
       description "Local IPv4 address";
       type jt:ipv4addr;
     }
     container loops {
       description "Allow local AS in received AS paths";
       uses bgpaf-loops;
     }
     container delay-route-advertisements {
       presence "enable delay-route-advertisements";
       junos:must "(!(\"system processes routing bgp rib-sharding\"))";
       junos:must-message "Can't be configured together with rib-sharding";
       description "Delay route updates for this family until FIB-sync";
       uses apply-advanced;
       leaf always-wait-for-krt-drain {
         description "Wait for KRT-queue drain for more-specific prefixes";
         type empty;
       }
       container minimum-delay {
         description "Minumum-delay to ensure KRT sees the route flash";
         uses apply-advanced;
         leaf routing-uptime {
           description "Min delay(sec) advertisement after RPD start";
           type union {
             type string {
               pattern "<.*>|$.*";
             }
             type uint32 {
               range "1 .. 36000";
             }
           }
         }
         leaf inbound-convergence {
           description "Min delay(sec) advertisement after source-peer sent all routes";
           type union {
             type string {
               pattern "<.*>|$.*";
             }
             type uint32 {
               range "1 .. 36000";
             }
           }
         }
       }
       container maximum-delay {
         description "Maximum delay deferring routes";
         uses apply-advanced;
         leaf route-age {
           description "Max delay(sec) advertisement route age";
           type union {
             type string {
               pattern "<.*>|$.*";
             }
             type uint32 {
               range "1 .. 36000";
             }
           }
         }
         leaf routing-uptime {
           description "Max delay(sec) advertisement after RPD start";
           type union {
             type string {
               pattern "<.*>|$.*";
             }
             type uint32 {
               range "1 .. 36000";
             }
           }
         }
       }
     }
     container nexthop-resolution {
       description "Configure nexthop resolution properties";
       uses apply-advanced;
       leaf no-resolution {
         description "Consider nexthop good without resolution attempt";
         type empty;
       }
       leaf preserve-nexthop-hierarchy {
         description "Attempt preserving resolved nexthop chain in forwarding";
         type empty;
       }
     }
     container defer-initial-multipath-build {
       presence "enable defer-initial-multipath-build";
       description "Defer initial multipath build until EOR is received";
       uses apply-advanced;
       leaf maximum-delay {
         description "Max delay(sec) multipath build after peer is up";
         type union {
           type string {
             pattern "<.*>|$.*";
           }
           type uint32 {
             range "1 .. 3600";
           }
         }
       }
     }
     container graceful-restart {
       description "BGP graceful restart options";
       uses bgp-af-gr;
     }
     leaf extended-nexthop {
       description "Extended nexthop encoding";
       junos:must "(!(\"system processes routing bgp rib-sharding\"))";
       junos:must-message "Can't be configured together with rib-sharding";
       type empty;
     }
     leaf extended-nexthop-color {
       description "Resolve using extended color nexthop";
       type empty;
     }
     leaf extended-nexthop-tunnel {
       description "Use BGP tunnel attribute";
       type empty;
     }
     leaf no-install {
       description "Dont install received routes in forwarding";
       type empty;
     }
     leaf route-age-bgp-view {
       description "Maintain BGP route's age based on Update messages only";
       type empty;
     }
     container output-queue-priority {
       description "Default output-queue to assign updates to";
       uses bgp-output-queue-priority-class;
     }
     container route-refresh-priority {
       description "Default output-queue to assign route refreshes to";
       uses bgp-output-queue-priority-class;
     }
     container withdraw-priority {
       description "Default output-queue to assign withdrawn routes to";
       uses bgp-output-queue-priority-class;
     }
     leaf advertise-srv6-service {
       description "Advertise SRv6 service";
       type empty;
     }
     leaf accept-srv6-service {
       description "Accept SRv6 service";
       type empty;
     }
     container aggregate-label {
       presence "enable aggregate-label";
       description "Aggregate labels of incoming routes with the same FEC";
       uses apply-advanced;
       leaf community {
         description "Community to identify the FEC of incoming routes";
         type string;
       }
     }
     container egress-protection {
       presence "enable egress-protection";
       junos:must "(!(\".. .. .. .. type external\"))";
       junos:must-message "Egress-protection is valid only for IBGP";
       description "Egress router protection";
       uses apply-advanced;
       container context-identifier {
         description "Context identifier";
         uses apply-advanced;
         leaf context-id {
           description "IP address";
           junos:must "(\"protocols mpls egress-protection context-identifier $$ primary\")";
           junos:must-message "context-identifier must be type primary";
           junos:must "(\"protocols mpls egress-protection context-identifier $$\")";
           junos:must-message "same context-identifier must be defined in protocols mpls egress-protection";
           type jt:ipv4addr;
         }
       }
       leaf-list keep-import {
         ordered-by user;
         description "Import policy";
         junos:must "(\"policy-options policy-statement \")";
         junos:must-message "policy-options policy-statement";
         type jt:policy-algebra;
       }
     }
     leaf accept-local-nexthop {
       description "Enable processing of routes with own nexthop";
       type empty;
     }
     leaf accept-own {
       description "Enable processing of routes with own originator-id or nexthop";
       type empty;
     }
   }
   grouping bgp-afi-labeled {
     uses apply-advanced;
     container prefix-limit {
       description "Limit maximum number of prefixes from a peer";
       uses bgpaf-prefix-limit;
     }
     container accepted-prefix-limit {
       description "Limit maximum number of prefixes accepted from a peer";
       uses bgpaf-accepted-prefix-limit;
     }
     container rib-group {
       description "Routing table group";
       uses rib_group_inet_type;
     }
     container add-path {
       description "Advertise multiple paths to peer";
       uses apath-options;
     }
     container aigp {
       description "Allow sending and receiving of AIGP attribute";
       presence "enable aigp";
       uses bgpaf-aigp-options;
     }
     leaf damping {
       description "Enable route flap damping";
       type empty;
     }
     leaf local-ipv4-address {
       description "Local IPv4 address";
       type jt:ipv4addr;
     }
     container loops {
       description "Allow local AS in received AS paths";
       uses bgpaf-loops;
     }
     container delay-route-advertisements {
       presence "enable delay-route-advertisements";
       junos:must "(!(\"system processes routing bgp rib-sharding\"))";
       junos:must-message "Can't be configured together with rib-sharding";
       description "Delay route updates for this family until FIB-sync";
       uses apply-advanced;
       leaf always-wait-for-krt-drain {
         description "Wait for KRT-queue drain for more-specific prefixes";
         type empty;
       }
       container minimum-delay {
         description "Minumum-delay to ensure KRT sees the route flash";
         uses apply-advanced;
         leaf routing-uptime {
           description "Min delay(sec) advertisement after RPD start";
           type union {
             type string {
               pattern "<.*>|$.*";
             }
             type uint32 {
               range "1 .. 36000";
             }
           }
         }
         leaf inbound-convergence {
           description "Min delay(sec) advertisement after source-peer sent all routes";
           type union {
             type string {
               pattern "<.*>|$.*";
             }
             type uint32 {
               range "1 .. 36000";
             }
           }
         }
       }
       container maximum-delay {
         description "Maximum delay deferring routes";
         uses apply-advanced;
         leaf route-age {
           description "Max delay(sec) advertisement route age";
           type union {
             type string {
               pattern "<.*>|$.*";
             }
             type uint32 {
               range "1 .. 36000";
             }
           }
         }
         leaf routing-uptime {
           description "Max delay(sec) advertisement after RPD start";
           type union {
             type string {
               pattern "<.*>|$.*";
             }
             type uint32 {
               range "1 .. 36000";
             }
           }
         }
       }
     }
     container nexthop-resolution {
       description "Configure nexthop resolution properties";
       uses apply-advanced;
       leaf no-resolution {
         description "Consider nexthop good without resolution attempt";
         type empty;
       }
       leaf preserve-nexthop-hierarchy {
         description "Attempt preserving resolved nexthop chain in forwarding";
         type empty;
       }
     }
     container defer-initial-multipath-build {
       presence "enable defer-initial-multipath-build";
       description "Defer initial multipath build until EOR is received";
       uses apply-advanced;
       leaf maximum-delay {
         description "Max delay(sec) multipath build after peer is up";
         type union {
           type string {
             pattern "<.*>|$.*";
           }
           type uint32 {
             range "1 .. 3600";
           }
         }
       }
     }
     container graceful-restart {
       description "BGP graceful restart options";
       uses bgp-af-gr;
     }
     leaf extended-nexthop {
       description "Extended nexthop encoding";
       junos:must "(!(\"system processes routing bgp rib-sharding\"))";
       junos:must-message "Can't be configured together with rib-sharding";
       type empty;
     }
     leaf extended-nexthop-color {
       description "Resolve using extended color nexthop";
       type empty;
     }
     leaf extended-nexthop-tunnel {
       description "Use BGP tunnel attribute";
       type empty;
     }
     leaf no-install {
       description "Dont install received routes in forwarding";
       type empty;
     }
     leaf route-age-bgp-view {
       description "Maintain BGP route's age based on Update messages only";
       type empty;
     }
     container output-queue-priority {
       description "Default output-queue to assign updates to";
       uses bgp-output-queue-priority-class;
     }
     container route-refresh-priority {
       description "Default output-queue to assign route refreshes to";
       uses bgp-output-queue-priority-class;
     }
     container withdraw-priority {
       description "Default output-queue to assign withdrawn routes to";
       uses bgp-output-queue-priority-class;
     }
     leaf advertise-srv6-service {
       description "Advertise SRv6 service";
       type empty;
     }
     leaf accept-srv6-service {
       description "Accept SRv6 service";
       type empty;
     }
     container aggregate-label {
       presence "enable aggregate-label";
       description "Aggregate labels of incoming routes with the same FEC";
       uses apply-advanced;
       leaf community {
         description "Community to identify the FEC of incoming routes";
         type string;
       }
     }
     leaf per-prefix-label {
       description "Allocate a unique label to each advertised prefix";
       type empty;
     }
     leaf per-group-label {
       description "Advertise prefixes with unique labels per group";
       type empty;
     }
     container traffic-statistics {
       description "Collect statistics for BGP label-switched paths";
       presence "enable traffic-statistics";
       uses bgpaf-traffic-statistics;
     }
     list topology {
       key name;
       ordered-by user;
       description "Multi topology routing tables";
       junos:must "(!(\"system processes routing bgp rib-sharding\"))";
       junos:must-message "Can't be configured together with rib-sharding";
       junos:must "(!(\"routing-options no-multi-topology-routing\"))";
       junos:must-message "Multi topology routing is disabled";
       leaf name {
         description "Topology name";
         type string {
           junos:posix-pattern "!^((.*:.*)|(.{129,}))$";
           junos:pattern-message "Must be a non-reserved string of 128 characters or less";
         }
       }
       uses apply-advanced;
       leaf community {
         description "Community to identify multi topology routes";
         type string;
       }
     }
     container rib {
       description "Select table used by labeled unicast routes";
       uses rib-inet3;
     }
     container explicit-null {
       presence "enable explicit-null";
       description "Advertise explicit null";
       leaf connected-only {
         description "Advertise explicit null only for connected routes";
         type empty;
       }
     }
     container protection {
       presence "enable protection";
       junos:must "((!(\".. .. .. .. type internal\") && !(\".. .. .. .. .. type internal\")))";
       junos:must-message "Protection for labeled-bgp valid only for EBGP";
       description "Compute backup path for active nexthop failure";
       uses apply-advanced;
     }
     container egress-protection {
       presence "enable egress-protection";
       junos:must "(!(\".. .. .. .. type external\"))";
       junos:must-message "Egress-protection is valid only for IBGP";
       description "Egress router protection";
       uses apply-advanced;
       container context-identifier {
         description "Context identifier";
         uses apply-advanced;
         leaf context-id {
           description "IP address";
           junos:must "(\"protocols mpls egress-protection context-identifier $$ primary\")";
           junos:must-message "context-identifier must be type primary";
           junos:must "(\"protocols mpls egress-protection context-identifier $$\")";
           junos:must-message "same context-identifier must be defined in protocols mpls egress-protection";
           type jt:ipv4addr;
         }
       }
       leaf-list keep-import {
         ordered-by user;
         description "Import policy";
         junos:must "(\"policy-options policy-statement \")";
         junos:must-message "policy-options policy-statement";
         type jt:policy-algebra;
       }
     }
     leaf resolve-vpn {
       description "Install received NLRI in inet.3 also";
       type empty;
     }
     container entropy-label {
       presence "enable entropy-label";
       description "Use entropy label for entropy label capable BGP LSPs";
       uses apply-advanced;
       leaf-list import {
         ordered-by user;
         description "Policy to select BGP LSPs to use entropy label";
         type jt:policy-algebra;
       }
       leaf no-next-hop-validation {
         description "Don't validate next hop field against route next hop";
         type empty;
       }
     }
   }
   grouping bgp-afi-srte {
     uses apply-advanced;
     container prefix-limit {
       description "Limit maximum number of prefixes from a peer";
       uses bgpaf-prefix-limit;
     }
     container accepted-prefix-limit {
       description "Limit maximum number of prefixes accepted from a peer";
       uses bgpaf-accepted-prefix-limit;
     }
     leaf damping {
       description "Enable route flap damping";
       type empty;
     }
     container loops {
       description "Allow local AS in received AS paths";
       uses bgpaf-loops;
     }
     container graceful-restart {
       description "BGP graceful restart options";
       uses bgp-af-gr;
     }
     leaf no-install {
       description "Dont install received routes in forwarding";
       type empty;
     }
     container output-queue-priority {
       description "Default output-queue to assign updates to";
       uses bgp-output-queue-priority-class;
     }
     container route-refresh-priority {
       description "Default output-queue to assign route refreshes to";
       uses bgp-output-queue-priority-class;
     }
     container withdraw-priority {
       description "Default output-queue to assign withdrawn routes to";
       uses bgp-output-queue-priority-class;
     }
   }
   grouping bgp-afi-topo {
     uses apply-advanced;
     container prefix-limit {
       description "Limit maximum number of prefixes from a peer";
       uses bgpaf-prefix-limit;
     }
     container accepted-prefix-limit {
       description "Limit maximum number of prefixes accepted from a peer";
       uses bgpaf-accepted-prefix-limit;
     }
     container rib-group {
       description "Routing table group";
       uses rib_group_inet_type;
     }
     container add-path {
       description "Advertise multiple paths to peer";
       uses apath-options;
     }
     container aigp {
       description "Allow sending and receiving of AIGP attribute";
       presence "enable aigp";
       uses bgpaf-aigp-options;
     }
     leaf damping {
       description "Enable route flap damping";
       type empty;
     }
     leaf local-ipv4-address {
       description "Local IPv4 address";
       type jt:ipv4addr;
     }
     container loops {
       description "Allow local AS in received AS paths";
       uses bgpaf-loops;
     }
     container delay-route-advertisements {
       presence "enable delay-route-advertisements";
       junos:must "(!(\"system processes routing bgp rib-sharding\"))";
       junos:must-message "Can't be configured together with rib-sharding";
       description "Delay route updates for this family until FIB-sync";
       uses apply-advanced;
       leaf always-wait-for-krt-drain {
         description "Wait for KRT-queue drain for more-specific prefixes";
         type empty;
       }
       container minimum-delay {
         description "Minumum-delay to ensure KRT sees the route flash";
         uses apply-advanced;
         leaf routing-uptime {
           description "Min delay(sec) advertisement after RPD start";
           type union {
             type string {
               pattern "<.*>|$.*";
             }
             type uint32 {
               range "1 .. 36000";
             }
           }
         }
         leaf inbound-convergence {
           description "Min delay(sec) advertisement after source-peer sent all routes";
           type union {
             type string {
               pattern "<.*>|$.*";
             }
             type uint32 {
               range "1 .. 36000";
             }
           }
         }
       }
       container maximum-delay {
         description "Maximum delay deferring routes";
         uses apply-advanced;
         leaf route-age {
           description "Max delay(sec) advertisement route age";
           type union {
             type string {
               pattern "<.*>|$.*";
             }
             type uint32 {
               range "1 .. 36000";
             }
           }
         }
         leaf routing-uptime {
           description "Max delay(sec) advertisement after RPD start";
           type union {
             type string {
               pattern "<.*>|$.*";
             }
             type uint32 {
               range "1 .. 36000";
             }
           }
         }
       }
     }
     container nexthop-resolution {
       description "Configure nexthop resolution properties";
       uses apply-advanced;
       leaf no-resolution {
         description "Consider nexthop good without resolution attempt";
         type empty;
       }
       leaf preserve-nexthop-hierarchy {
         description "Attempt preserving resolved nexthop chain in forwarding";
         type empty;
       }
     }
     container defer-initial-multipath-build {
       presence "enable defer-initial-multipath-build";
       description "Defer initial multipath build until EOR is received";
       uses apply-advanced;
       leaf maximum-delay {
         description "Max delay(sec) multipath build after peer is up";
         type union {
           type string {
             pattern "<.*>|$.*";
           }
           type uint32 {
             range "1 .. 3600";
           }
         }
       }
     }
     container graceful-restart {
       description "BGP graceful restart options";
       uses bgp-af-gr;
     }
     leaf extended-nexthop {
       description "Extended nexthop encoding";
       junos:must "(!(\"system processes routing bgp rib-sharding\"))";
       junos:must-message "Can't be configured together with rib-sharding";
       type empty;
     }
     leaf extended-nexthop-color {
       description "Resolve using extended color nexthop";
       type empty;
     }
     leaf extended-nexthop-tunnel {
       description "Use BGP tunnel attribute";
       type empty;
     }
     leaf no-install {
       description "Dont install received routes in forwarding";
       type empty;
     }
     leaf route-age-bgp-view {
       description "Maintain BGP route's age based on Update messages only";
       type empty;
     }
     container output-queue-priority {
       description "Default output-queue to assign updates to";
       uses bgp-output-queue-priority-class;
     }
     container route-refresh-priority {
       description "Default output-queue to assign route refreshes to";
       uses bgp-output-queue-priority-class;
     }
     container withdraw-priority {
       description "Default output-queue to assign withdrawn routes to";
       uses bgp-output-queue-priority-class;
     }
     leaf advertise-srv6-service {
       description "Advertise SRv6 service";
       type empty;
     }
     leaf accept-srv6-service {
       description "Accept SRv6 service";
       type empty;
     }
     container protection {
       presence "enable protection";
       junos:must "((!(\".. .. .. .. type internal\") && !(\".. .. .. .. .. type internal\")))";
       junos:must-message "Protection is valid only for EBGP";
       description "Compute backup path for active nexthop failure";
     }
     list topology {
       key name;
       ordered-by user;
       description "Multi topology routing tables";
       junos:must "(!(\"system processes routing bgp rib-sharding\"))";
       junos:must-message "Can't be configured together with rib-sharding";
       junos:must "(!(\"routing-options no-multi-topology-routing\"))";
       junos:must-message "Multi topology routing is disabled";
       leaf name {
         description "Topology name";
         type string {
           junos:posix-pattern "!^((.*:.*)|(.{129,}))$";
           junos:pattern-message "Must be a non-reserved string of 128 characters or less";
         }
       }
       uses apply-advanced;
       leaf community {
         description "Community to identify multi topology routes";
         type string;
       }
     }
   }
   grouping bgp-afi-vpn {
     uses apply-advanced;
     container prefix-limit {
       description "Limit maximum number of prefixes from a peer";
       uses bgpaf-prefix-limit;
     }
     container accepted-prefix-limit {
       description "Limit maximum number of prefixes accepted from a peer";
       uses bgpaf-accepted-prefix-limit;
     }
     container rib-group {
       description "Routing table group";
       uses rib_group_inet_type;
     }
     container add-path {
       description "Advertise multiple paths to peer";
       uses apath-options;
     }
     container aigp {
       description "Allow sending and receiving of AIGP attribute";
       presence "enable aigp";
       uses bgpaf-aigp-options;
     }
     leaf damping {
       description "Enable route flap damping";
       type empty;
     }
     leaf local-ipv4-address {
       description "Local IPv4 address";
       type jt:ipv4addr;
     }
     container loops {
       description "Allow local AS in received AS paths";
       uses bgpaf-loops;
     }
     container delay-route-advertisements {
       presence "enable delay-route-advertisements";
       junos:must "(!(\"system processes routing bgp rib-sharding\"))";
       junos:must-message "Can't be configured together with rib-sharding";
       description "Delay route updates for this family until FIB-sync";
       uses apply-advanced;
       leaf always-wait-for-krt-drain {
         description "Wait for KRT-queue drain for more-specific prefixes";
         type empty;
       }
       container minimum-delay {
         description "Minumum-delay to ensure KRT sees the route flash";
         uses apply-advanced;
         leaf routing-uptime {
           description "Min delay(sec) advertisement after RPD start";
           type union {
             type string {
               pattern "<.*>|$.*";
             }
             type uint32 {
               range "1 .. 36000";
             }
           }
         }
         leaf inbound-convergence {
           description "Min delay(sec) advertisement after source-peer sent all routes";
           type union {
             type string {
               pattern "<.*>|$.*";
             }
             type uint32 {
               range "1 .. 36000";
             }
           }
         }
       }
       container maximum-delay {
         description "Maximum delay deferring routes";
         uses apply-advanced;
         leaf route-age {
           description "Max delay(sec) advertisement route age";
           type union {
             type string {
               pattern "<.*>|$.*";
             }
             type uint32 {
               range "1 .. 36000";
             }
           }
         }
         leaf routing-uptime {
           description "Max delay(sec) advertisement after RPD start";
           type union {
             type string {
               pattern "<.*>|$.*";
             }
             type uint32 {
               range "1 .. 36000";
             }
           }
         }
       }
     }
     container nexthop-resolution {
       description "Configure nexthop resolution properties";
       uses apply-advanced;
       leaf no-resolution {
         description "Consider nexthop good without resolution attempt";
         type empty;
       }
       leaf preserve-nexthop-hierarchy {
         description "Attempt preserving resolved nexthop chain in forwarding";
         type empty;
       }
     }
     container defer-initial-multipath-build {
       presence "enable defer-initial-multipath-build";
       description "Defer initial multipath build until EOR is received";
       uses apply-advanced;
       leaf maximum-delay {
         description "Max delay(sec) multipath build after peer is up";
         type union {
           type string {
             pattern "<.*>|$.*";
           }
           type uint32 {
             range "1 .. 3600";
           }
         }
       }
     }
     container graceful-restart {
       description "BGP graceful restart options";
       uses bgp-af-gr;
     }
     leaf extended-nexthop {
       description "Extended nexthop encoding";
       junos:must "(!(\"system processes routing bgp rib-sharding\"))";
       junos:must-message "Can't be configured together with rib-sharding";
       type empty;
     }
     leaf extended-nexthop-color {
       description "Resolve using extended color nexthop";
       type empty;
     }
     leaf extended-nexthop-tunnel {
       description "Use BGP tunnel attribute";
       type empty;
     }
     leaf no-install {
       description "Dont install received routes in forwarding";
       type empty;
     }
     leaf route-age-bgp-view {
       description "Maintain BGP route's age based on Update messages only";
       type empty;
     }
     container output-queue-priority {
       description "Default output-queue to assign updates to";
       uses bgp-output-queue-priority-class;
     }
     container route-refresh-priority {
       description "Default output-queue to assign route refreshes to";
       uses bgp-output-queue-priority-class;
     }
     container withdraw-priority {
       description "Default output-queue to assign withdrawn routes to";
       uses bgp-output-queue-priority-class;
     }
     leaf advertise-srv6-service {
       description "Advertise SRv6 service";
       type empty;
     }
     leaf accept-srv6-service {
       description "Accept SRv6 service";
       type empty;
     }
     container aggregate-label {
       presence "enable aggregate-label";
       description "Aggregate labels of incoming routes with the same FEC";
       uses apply-advanced;
       leaf community {
         description "Community to identify the FEC of incoming routes";
         type string;
       }
     }
   }
   grouping bgp-afi-vpn-protection {
     uses apply-advanced;
     container prefix-limit {
       description "Limit maximum number of prefixes from a peer";
       uses bgpaf-prefix-limit;
     }
     container accepted-prefix-limit {
       description "Limit maximum number of prefixes accepted from a peer";
       uses bgpaf-accepted-prefix-limit;
     }
     container rib-group {
       description "Routing table group";
       uses rib_group_inet_type;
     }
     container add-path {
       description "Advertise multiple paths to peer";
       uses apath-options;
     }
     container aigp {
       description "Allow sending and receiving of AIGP attribute";
       presence "enable aigp";
       uses bgpaf-aigp-options;
     }
     leaf damping {
       description "Enable route flap damping";
       type empty;
     }
     leaf local-ipv4-address {
       description "Local IPv4 address";
       type jt:ipv4addr;
     }
     container loops {
       description "Allow local AS in received AS paths";
       uses bgpaf-loops;
     }
     container delay-route-advertisements {
       presence "enable delay-route-advertisements";
       junos:must "(!(\"system processes routing bgp rib-sharding\"))";
       junos:must-message "Can't be configured together with rib-sharding";
       description "Delay route updates for this family until FIB-sync";
       uses apply-advanced;
       leaf always-wait-for-krt-drain {
         description "Wait for KRT-queue drain for more-specific prefixes";
         type empty;
       }
       container minimum-delay {
         description "Minumum-delay to ensure KRT sees the route flash";
         uses apply-advanced;
         leaf routing-uptime {
           description "Min delay(sec) advertisement after RPD start";
           type union {
             type string {
               pattern "<.*>|$.*";
             }
             type uint32 {
               range "1 .. 36000";
             }
           }
         }
         leaf inbound-convergence {
           description "Min delay(sec) advertisement after source-peer sent all routes";
           type union {
             type string {
               pattern "<.*>|$.*";
             }
             type uint32 {
               range "1 .. 36000";
             }
           }
         }
       }
       container maximum-delay {
         description "Maximum delay deferring routes";
         uses apply-advanced;
         leaf route-age {
           description "Max delay(sec) advertisement route age";
           type union {
             type string {
               pattern "<.*>|$.*";
             }
             type uint32 {
               range "1 .. 36000";
             }
           }
         }
         leaf routing-uptime {
           description "Max delay(sec) advertisement after RPD start";
           type union {
             type string {
               pattern "<.*>|$.*";
             }
             type uint32 {
               range "1 .. 36000";
             }
           }
         }
       }
     }
     container nexthop-resolution {
       description "Configure nexthop resolution properties";
       uses apply-advanced;
       leaf no-resolution {
         description "Consider nexthop good without resolution attempt";
         type empty;
       }
       leaf preserve-nexthop-hierarchy {
         description "Attempt preserving resolved nexthop chain in forwarding";
         type empty;
       }
     }
     container defer-initial-multipath-build {
       presence "enable defer-initial-multipath-build";
       description "Defer initial multipath build until EOR is received";
       uses apply-advanced;
       leaf maximum-delay {
         description "Max delay(sec) multipath build after peer is up";
         type union {
           type string {
             pattern "<.*>|$.*";
           }
           type uint32 {
             range "1 .. 3600";
           }
         }
       }
     }
     container graceful-restart {
       description "BGP graceful restart options";
       uses bgp-af-gr;
     }
     leaf extended-nexthop {
       description "Extended nexthop encoding";
       junos:must "(!(\"system processes routing bgp rib-sharding\"))";
       junos:must-message "Can't be configured together with rib-sharding";
       type empty;
     }
     leaf extended-nexthop-color {
       description "Resolve using extended color nexthop";
       type empty;
     }
     leaf extended-nexthop-tunnel {
       description "Use BGP tunnel attribute";
       type empty;
     }
     leaf no-install {
       description "Dont install received routes in forwarding";
       type empty;
     }
     leaf route-age-bgp-view {
       description "Maintain BGP route's age based on Update messages only";
       type empty;
     }
     container output-queue-priority {
       description "Default output-queue to assign updates to";
       uses bgp-output-queue-priority-class;
     }
     container route-refresh-priority {
       description "Default output-queue to assign route refreshes to";
       uses bgp-output-queue-priority-class;
     }
     container withdraw-priority {
       description "Default output-queue to assign withdrawn routes to";
       uses bgp-output-queue-priority-class;
     }
     leaf advertise-srv6-service {
       description "Advertise SRv6 service";
       type empty;
     }
     leaf accept-srv6-service {
       description "Accept SRv6 service";
       type empty;
     }
     container aggregate-label {
       presence "enable aggregate-label";
       description "Aggregate labels of incoming routes with the same FEC";
       uses apply-advanced;
       leaf community {
         description "Community to identify the FEC of incoming routes";
         type string;
       }
     }
     container egress-protection {
       presence "enable egress-protection";
       junos:must "(!(\".. .. .. .. type external\"))";
       junos:must-message "Egress-protection is valid only for IBGP";
       description "Egress router protection";
       uses apply-advanced;
       container context-identifier {
         description "Context identifier";
         uses apply-advanced;
         leaf context-id {
           description "IP address";
           junos:must "(\"protocols mpls egress-protection context-identifier $$ primary\")";
           junos:must-message "context-identifier must be type primary";
           junos:must "(\"protocols mpls egress-protection context-identifier $$\")";
           junos:must-message "same context-identifier must be defined in protocols mpls egress-protection";
           type jt:ipv4addr;
         }
       }
       leaf-list keep-import {
         ordered-by user;
         description "Import policy";
         junos:must "(\"policy-options policy-statement \")";
         junos:must-message "policy-options policy-statement";
         type jt:policy-algebra;
       }
     }
   }
   grouping bgp-output-queue-priority-class {
     choice class {
       case case_1 {
         leaf priority {
           description "Output queue priority; higher is better";
           type union {
             type string {
               pattern "<.*>|$.*";
             }
             type uint32 {
               range "1 .. 16";
             }
           }
         }
       }
       case case_2 {
         leaf expedited {
           description "Expedited queue; highest priority";
           type empty;
         }
       }
     }
   }
   grouping bgp_filter_obj {
     description "Filter to apply to tracing";
     leaf match-on {
       description "Argument on which to match";
       type enumeration {
         enum "prefix" {
           description "Filter based on prefix";
         }
       }
     }
     leaf-list policy {
       ordered-by user;
       description "Filter policy";
       type jt:policy-algebra;
     }
   }
   grouping bgpaf-accepted-prefix-limit {
     uses apply-advanced;
     leaf maximum {
       description "Maximum number of prefixes accepted from a peer";
       type union {
         type string {
           pattern "<.*>|$.*";
         }
         type uint32 {
           range "1 .. 4294967295";
         }
       }
     }
     container teardown {
       presence "enable teardown";
       junos:must "(!(\".. hide-excess\"))";
       junos:must-message "Can't be configured together with hide-excess";
       junos:must "(!(\".. drop-excess\"))";
       junos:must-message "Can't be configured together with drop-excess";
       description "Clear peer connection on reaching limit";
       uses apply-advanced;
       leaf limit-threshold {
         description "Percentage of prefix-limit to start warnings";
         type union {
           type string {
             pattern "<.*>|$.*";
           }
           type uint32 {
             range "1 .. 100";
           }
         }
       }
       container idle-timeout {
         presence "enable idle-timeout";
         description "Timeout before attempting to restart peer";
         choice idle-parm {
           case case_1 {
             leaf forever {
               description "Idle the peer until the user intervenes";
               type empty;
             }
           }
           case case_2 {
             leaf timeout {
               description "Timeout value, in minutes, for restarting peer";
               type union {
                 type string {
                   pattern "<.*>|$.*";
                 }
                 type uint32 {
                   range "1 .. 2400";
                 }
               }
             }
           }
         }
       }
     }
     container drop-excess {
       presence "enable drop-excess";
       junos:must "(!(\".. hide-excess\"))";
       junos:must-message "Can't be configured together with hide-excess";
       junos:must "(!(\".. teardown\"))";
       junos:must-message "Can't be configured together with teardown";
       description "Drop routes from peer on reaching limit";
       uses apply-advanced;
       leaf limit-threshold {
         description "Percentage of prefix-limit to start warnings";
         type union {
           type string {
             pattern "<.*>|$.*";
           }
           type uint32 {
             range "1 .. 100";
           }
         }
       }
     }
     container hide-excess {
       presence "enable hide-excess";
       junos:must "(!(\".. teardown\"))";
       junos:must-message "Can't be configured together with teardown";
       junos:must "(!(\".. drop-excess\"))";
       junos:must-message "Can't be configured together with drop-excess";
       description "Hide routes from peer on reaching limit";
       uses apply-advanced;
       leaf limit-threshold {
         description "Percentage of prefix-limit to start warnings";
         type union {
           type string {
             pattern "<.*>|$.*";
           }
           type uint32 {
             range "1 .. 100";
           }
         }
       }
     }
   }
   grouping bgpaf-aigp-options {
     uses apply-advanced;
     leaf disable {
       description "Disable sending and receiving of AIGP attribute";
       type empty;
     }
   }
   grouping bgpaf-loops {
     uses apply-advanced;
     leaf loops {
       description "AS-Path loop count";
       type union {
         type string {
           pattern "<.*>|$.*";
         }
         type int32 {
           range "1 .. 10";
         }
       }
     }
   }
   grouping bgpaf-prefix-limit {
     uses apply-advanced;
     leaf maximum {
       description "Maximum number of prefixes from a peer";
       type union {
         type string {
           pattern "<.*>|$.*";
         }
         type uint32 {
           range "1 .. 4294967295";
         }
       }
     }
     container teardown {
       presence "enable teardown";
       junos:must "(!(\".. hide-excess\"))";
       junos:must-message "Can't be configured together with hide-excess";
       junos:must "(!(\".. drop-excess\"))";
       junos:must-message "Can't be configured together with drop-excess";
       description "Clear peer connection on reaching limit";
       uses apply-advanced;
       leaf limit-threshold {
         description "Percentage of prefix-limit to start warnings";
         type union {
           type string {
             pattern "<.*>|$.*";
           }
           type uint32 {
             range "1 .. 100";
           }
         }
       }
       container idle-timeout {
         presence "enable idle-timeout";
         description "Timeout before attempting to restart peer";
         choice idle-parm {
           case case_1 {
             leaf forever {
               description "Idle the peer until the user intervenes";
               type empty;
             }
           }
           case case_2 {
             leaf timeout {
               description "Timeout value, in minutes, for restarting peer";
               type union {
                 type string {
                   pattern "<.*>|$.*";
                 }
                 type uint32 {
                   range "1 .. 2400";
                 }
               }
             }
           }
         }
       }
     }
     container drop-excess {
       presence "enable drop-excess";
       junos:must "(!(\".. hide-excess\"))";
       junos:must-message "Can't be configured together with hide-excess";
       junos:must "(!(\".. teardown\"))";
       junos:must-message "Can't be configured together with teardown";
       description "Drop routes from peer on reaching limit";
       uses apply-advanced;
       leaf limit-threshold {
         description "Percentage of prefix-limit to start warnings";
         type union {
           type string {
             pattern "<.*>|$.*";
           }
           type uint32 {
             range "1 .. 100";
           }
         }
       }
     }
     container hide-excess {
       presence "enable hide-excess";
       junos:must "(!(\".. teardown\"))";
       junos:must-message "Can't be configured together with teardown";
       junos:must "(!(\".. drop-excess\"))";
       junos:must-message "Can't be configured together with drop-excess";
       description "Hide routes from peer on reaching limit";
       uses apply-advanced;
       leaf limit-threshold {
         description "Percentage of prefix-limit to start warnings";
         type union {
           type string {
             pattern "<.*>|$.*";
           }
           type uint32 {
             range "1 .. 100";
           }
         }
       }
     }
   }
   grouping bgpaf-traffic-statistics {
     uses apply-advanced;
     leaf labeled-path {
       description "Ingress labeled path statistics";
       type empty;
     }
     container file {
       description "Statistics file options";
       leaf filename {
         description "Name of file in which to write trace information";
         type string {
           length "1 .. 1024";
           junos:posix-pattern "![/ %]";
           junos:pattern-message "Must not contain '/', % or a space";
         }
       }
       leaf replace {
         description "Replace trace file rather than appending to it";
         status deprecated;
         type empty;
       }
       leaf size {
         description "Maximum trace file size";
         type string;
       }
       leaf files {
         description "Maximum number of trace files";
         default "10";
         type union {
           type string {
             pattern "<.*>|$.*";
           }
           type uint32 {
             range "2 .. 1000";
           }
         }
       }
       leaf no-stamp {
         description "Do not timestamp trace file";
         status deprecated;
         type empty;
       }
       choice world-readable-choice {
         leaf world-readable {
           description "Allow any user to read the log file";
           type empty;
         }
         leaf no-world-readable {
           description "Don't allow any user to read the log file";
           type empty;
         }
       }
     }
     leaf interval {
       description "Time to collect statistics (seconds)";
       type union {
         type string {
           pattern "<.*>|$.*";
         }
         type int32 {
           range "60 .. 65535";
         }
       }
     }
   }
   grouping juniper-protocols-esis {
     uses apply-advanced;
     choice enable-disable {
       case case_1 {
         leaf disable {
           description "Disable ES-IS";
           type empty;
         }
       }
     }
     container traceoptions {
       description "Trace options for ES-IS";
       uses apply-advanced;
       container file {
         description "Trace file options";
         leaf filename {
           description "Name of file in which to write trace information";
           type string {
             length "1 .. 1024";
             junos:posix-pattern "![/ %]";
             junos:pattern-message "Must not contain '/', % or a space";
           }
         }
         leaf replace {
           description "Replace trace file rather than appending to it";
           status deprecated;
           type empty;
         }
         leaf size {
           description "Maximum trace file size";
           type string;
         }
         leaf files {
           description "Maximum number of trace files";
           default "10";
           type union {
             type string {
               pattern "<.*>|$.*";
             }
             type uint32 {
               range "2 .. 1000";
             }
           }
         }
         leaf no-stamp {
           description "Do not timestamp trace file";
           status deprecated;
           type empty;
         }
         choice world-readable-choice {
           leaf world-readable {
             description "Allow any user to read the log file";
             type empty;
           }
           leaf no-world-readable {
             description "Don't allow any user to read the log file";
             type empty;
           }
         }
       }
       list flag {
         key name;
         ordered-by user;
         description "Tracing parameters";
         leaf name {
           type enumeration {
             enum "error" {
               description "Trace errored packets";
             }
             enum "esh" {
               description "Trace end system hello packets";
             }
             enum "ish" {
               description "Trace intermediate system hello packets";
             }
             enum "graceful-restart" {
               description "Trace graceful restart events";
             }
             enum "route" {
               description "Trace routing information";
             }
             enum "normal" {
               description "Trace normal events";
             }
             enum "general" {
               description "Trace general events";
             }
             enum "state" {
               description "Trace state transitions";
             }
             enum "policy" {
               description "Trace policy processing";
             }
             enum "task" {
               description "Trace routing protocol task processing";
             }
             enum "timer" {
               description "Trace routing protocol timer processing";
             }
             enum "all" {
               description "Trace everything";
             }
           }
         }
         leaf send {
           description "Trace transmitted packets";
           type empty;
         }
         leaf receive {
           description "Trace received packets";
           type empty;
         }
         leaf detail {
           description "Trace detailed information";
           type empty;
         }
         leaf disable {
           description "Disable this trace flag";
           type empty;
         }
       }
     }
     leaf preference {
       description "Preference of routes";
       type union {
         type uint32;
         type string {
           pattern "<.*>|$.*";
         }
       }
     }
     container graceful-restart {
       description "ES-IS graceful restart options";
       choice enable-disable {
         case case_1 {
           leaf disable {
             description "Disable graceful restart";
             type empty;
           }
         }
       }
       leaf restart-duration {
         description "Maximum time for graceful restart to finish";
         units "seconds";
         type union {
           type string {
             pattern "<.*>|$.*";
           }
           type uint32 {
             range "30 .. 300";
           }
         }
       }
     }
     list interface {
       key name;
       description "Interface configuration";
       leaf name {
         description "Interface name";
         type union {
           type jt:interface-name;
           type string {
             pattern "<.*>|$.*";
           }
         }
       }
       uses apply-advanced;
       leaf hold-time {
         description "Time after which neighbors think the interface is down";
         units "seconds";
         type union {
           type string {
             pattern "<.*>|$.*";
           }
           type uint32 {
             range "1 .. 65535";
           }
         }
       }
       leaf end-system-configuration-timer {
         description "Suggested end system configuration timer";
         units "seconds";
         type union {
           type string {
             pattern "<.*>|$.*";
           }
           type uint32 {
             range "1 .. 65535";
           }
         }
       }
       choice enable-disable {
         case case_1 {
           leaf disable {
             description "Disable ES-IS on this interface";
             type empty;
           }
         }
       }
     }
   }
   grouping juniper-protocols-isis {
     uses apply-advanced;
     list interface {
       key name;
       description "Interface configuration";
       leaf name {
         description "Interface name";
         type union {
           type jt:interface-name;
           type string {
             pattern "<.*>|$.*";
           }
         }
       }
       uses apply-advanced;
       container ldp-synchronization {
         description "Advertise maximum metric until LDP is operational";
         presence "enable ldp-synchronization";
         uses ldp-sync-obj;
       }
       list level {
         key name;
         ordered-by user;
         description "Configure levels on this interface";
         leaf name {
           description "IS-IS level number";
           type union {
             type string {
               pattern "<.*>|$.*";
             }
             type uint32 {
               range "1 .. 2";
             }
           }
         }
         uses apply-advanced;
         leaf te-metric {
           description "Traffic engineering metric";
           type union {
             type string {
               pattern "<.*>|$.*";
             }
             type uint32 {
               range "0 .. 16777215";
             }
           }
         }
         leaf no-advertise-adjacency-segment {
           description "Do not advertise an adjacency segment for this level";
           type empty;
         }
         container ipv4-adjacency-segment {
           junos:must "(!(\".. no-advertise-adjacency-segment\"))";
           junos:must-message "ipv4-adjacency-segment can't be configured if no-advertise-adjacency-segment is configured in the level";
           junos:must "(!(\".. .. no-advertise-adjacency-segment\"))";
           junos:must-message "ipv4-adjacency-segment can't be configured if no-advertise-adjacency-segment is configured in the same interface";
           description "Configure ipv4 adjacency segment";
           uses apply-advanced;
           container protected {
             description "Adjacency SID is eligible for protection";
             choice adjsid-type {
               case case_1 {
                 container index {
                   description "Adjacency SID indexed from SRGB";
                   leaf index-number {
                     type union {
                       type string {
                         pattern "<.*>|$.*";
                       }
                       type uint32 {
                         range "0 .. 199999";
                       }
                     }
                   }
                 }
               }
               case case_2 {
                 leaf label {
                   description "Adjacency SID from static label pool";
                   type union {
                     type string {
                       pattern "<.*>|$.*";
                     }
                     type uint32 {
                       range "16 .. 1048575";
                     }
                   }
                 }
               }
               case case_3 {
                 leaf dynamic {
                   description "Dynamically allocate an adjacency segment";
                   type empty;
                 }
               }
             }
           }
           container unprotected {
             description "Adjacency SID uneligible for protection";
             choice adjsid-type {
               case case_1 {
                 container index {
                   description "Adjacency SID indexed from SRGB";
                   leaf index-number {
                     type union {
                       type string {
                         pattern "<.*>|$.*";
                       }
                       type uint32 {
                         range "0 .. 199999";
                       }
                     }
                   }
                 }
               }
               case case_2 {
                 leaf label {
                   description "Adjacency SID from static label pool";
                   type union {
                     type string {
                       pattern "<.*>|$.*";
                     }
                     type uint32 {
                       range "16 .. 1048575";
                     }
                   }
                 }
               }
               case case_3 {
                 leaf dynamic {
                   description "Dynamically allocate an adjacency segment";
                   type empty;
                 }
               }
             }
           }
         }
         container ipv6-adjacency-segment {
           junos:must "(!(\".. no-advertise-adjacency-segment\"))";
           junos:must-message "ipv6-adjacency-segment can't be configured if no-advertise-adjacency-segment is configured in the same level";
           junos:must "(!(\".. .. no-advertise-adjacency-segment\"))";
           junos:must-message "ipv6-adjacency-segment can't be configured if no-advertise-adjacency-segment is configured in the same interface";
           description "Configure ipv6 adjacency segment";
           uses apply-advanced;
           container protected {
             description "Adjacency SID is eligible for protection";
             choice adjsid-type {
               case case_1 {
                 container index {
                   description "Adjacency SID indexed from SRGB";
                   leaf index-number {
                     type union {
                       type string {
                         pattern "<.*>|$.*";
                       }
                       type uint32 {
                         range "0 .. 199999";
                       }
                     }
                   }
                 }
               }
               case case_2 {
                 leaf label {
                   description "Adjacency SID from static label pool";
                   type union {
                     type string {
                       pattern "<.*>|$.*";
                     }
                     type uint32 {
                       range "16 .. 1048575";
                     }
                   }
                 }
               }
               case case_3 {
                 leaf dynamic {
                   description "Dynamically allocate an adjacency segment";
                   type empty;
                 }
               }
             }
           }
           container unprotected {
             description "Adjacency SID uneligible for protection";
             choice adjsid-type {
               case case_1 {
                 container index {
                   description "Adjacency SID indexed from SRGB";
                   leaf index-number {
                     type union {
                       type string {
                         pattern "<.*>|$.*";
                       }
                       type uint32 {
                         range "0 .. 199999";
                       }
                     }
                   }
                 }
               }
               case case_2 {
                 leaf label {
                   description "Adjacency SID from static label pool";
                   type union {
                     type string {
                       pattern "<.*>|$.*";
                     }
                     type uint32 {
                       range "16 .. 1048575";
                     }
                   }
                 }
               }
               case case_3 {
                 leaf dynamic {
                   description "Dynamically allocate an adjacency segment";
                   type empty;
                 }
               }
             }
           }
         }
         container srm6-adjacency-segment {
           description "Configure srm6 adjacency segment";
           uses apply-advanced;
           container unprotected {
             description "Adjacency SID uneligible for protection";
             leaf sid {
               description "Set Adjacency SID Value";
               type union {
                 type string {
                   pattern "<.*>|$.*";
                 }
                 type uint32 {
                   range "1 .. 65535";
                 }
               }
             }
           }
         }
         container srv6-adjacency-segment {
           description "Configure srv6 adjacency segment";
           uses apply-advanced;
           container protected {
             presence "enable protected";
             description "SRv6 Adjacency segment is eligible for protection";
             uses apply-advanced;
             list locator {
               key name;
               ordered-by user;
               description "Locator to bind SRv6 adjacency segment";
               leaf name {
                 description "Locator name";
                 junos:must "(\"routing-options source-packet-routing srv6 locator $$\")";
                 junos:must-message "Referenced source-packet-routing srv6 must be defined";
                 type string;
               }
               uses apply-advanced;
               list end-x-sid {
                 key name;
                 ordered-by user;
                 description "Endpoint 128 bit address";
                 leaf name {
                   type jt:ipv6addr;
                 }
                 uses apply-advanced;
                 container flavor {
                   presence "enable flavor";
                   uses apply-advanced;
                   leaf psp {
                     description "Penultimate segment pop of the SRH";
                     type empty;
                   }
                   leaf usp {
                     description "Ultimate segment pop of the SRH";
                     type empty;
                   }
                   leaf usd {
                     description "Ultimate segment decapsulation";
                     type empty;
                   }
                 }
               }
             }
           }
           container unprotected {
             presence "enable unprotected";
             description "SRv6 Adjacency segment is uneligible for protection";
             uses apply-advanced;
             list locator {
               key name;
               ordered-by user;
               description "Locator to bind SRv6 adjacency segment";
               leaf name {
                 description "Locator name";
                 junos:must "(\"routing-options source-packet-routing srv6 locator $$\")";
                 junos:must-message "Referenced source-packet-routing srv6 must be defined";
                 type string;
               }
               uses apply-advanced;
               list end-x-sid {
                 key name;
                 ordered-by user;
                 description "Endpoint 128 bit address";
                 leaf name {
                   type jt:ipv6addr;
                 }
                 uses apply-advanced;
                 container flavor {
                   presence "enable flavor";
                   uses apply-advanced;
                   leaf psp {
                     description "Penultimate segment pop of the SRH";
                     type empty;
                   }
                   leaf usp {
                     description "Ultimate segment pop of the SRH";
                     type empty;
                   }
                   leaf usd {
                     description "Ultimate segment decapsulation";
                     type empty;
                   }
                 }
               }
             }
           }
         }
         list lan-neighbor {
           key name;
           ordered-by user;
           description "Configuration specific to a LAN neighbor";
           junos:must "(!(\".. ipv6-adjacency-segment\"))";
           junos:must-message "lan-neighbor can't be configured if ipv6-adjacency-segment is configured in the same interface";
           junos:must "(!(\".. ipv4-adjacency-segment\"))";
           junos:must-message "lan-neighbor can't be configured if ipv4-adjacency-segment is configured in the same interface";
           junos:must "(!(\".. no-advertise-adjacency-segment\"))";
           junos:must-message "lan-neighbor can't be configured if no-advertise-adjacency-segment is configured in the same level";
           junos:must "(!(\".. .. no-advertise-adjacency-segment\"))";
           junos:must-message "lan-neighbor can't be configured if  no-advertise-adjacency-segment is configured in the same interface";
           junos:must "(!(\".. .. point-to-point\"))";
           junos:must-message "lan-neighbor can't be configured for point-to-point interfaces";
           leaf name {
             description "Neighbor's sysid";
             type jt:sysid;
           }
           uses apply-advanced;
           container ipv4-adjacency-segment {
             junos:must "(!(\".. no-advertise-adjacency-segment\"))";
             junos:must-message "ipv4-adjacency-segment can't be configured if no-advertise-adjacency-segment is configured in the level";
             junos:must "(!(\".. .. no-advertise-adjacency-segment\"))";
             junos:must-message "ipv4-adjacency-segment can't be configured if no-advertise-adjacency-segment is configured in the same interface";
             description "Configure ipv4 adjacency segment";
             uses apply-advanced;
             container protected {
               description "Adjacency SID is eligible for protection";
               choice adjsid-type {
                 case case_1 {
                   container index {
                     description "Adjacency SID indexed from SRGB";
                     leaf index-number {
                       type union {
                         type string {
                           pattern "<.*>|$.*";
                         }
                         type uint32 {
                           range "0 .. 199999";
                         }
                       }
                     }
                   }
                 }
                 case case_2 {
                   leaf label {
                     description "Adjacency SID from static label pool";
                     type union {
                       type string {
                         pattern "<.*>|$.*";
                       }
                       type uint32 {
                         range "16 .. 1048575";
                       }
                     }
                   }
                 }
                 case case_3 {
                   leaf dynamic {
                     description "Dynamically allocate an adjacency segment";
                     type empty;
                   }
                 }
               }
             }
             container unprotected {
               description "Adjacency SID uneligible for protection";
               choice adjsid-type {
                 case case_1 {
                   container index {
                     description "Adjacency SID indexed from SRGB";
                     leaf index-number {
                       type union {
                         type string {
                           pattern "<.*>|$.*";
                         }
                         type uint32 {
                           range "0 .. 199999";
                         }
                       }
                     }
                   }
                 }
                 case case_2 {
                   leaf label {
                     description "Adjacency SID from static label pool";
                     type union {
                       type string {
                         pattern "<.*>|$.*";
                       }
                       type uint32 {
                         range "16 .. 1048575";
                       }
                     }
                   }
                 }
                 case case_3 {
                   leaf dynamic {
                     description "Dynamically allocate an adjacency segment";
                     type empty;
                   }
                 }
               }
             }
           }
           container ipv6-adjacency-segment {
             junos:must "(!(\".. no-advertise-adjacency-segment\"))";
             junos:must-message "ipv6-adjacency-segment can't be configured if no-advertise-adjacency-segment is configured in the same level";
             junos:must "(!(\".. .. no-advertise-adjacency-segment\"))";
             junos:must-message "ipv6-adjacency-segment can't be configured if no-advertise-adjacency-segment is configured in the same interface";
             description "Configure ipv6 adjacency segment";
             uses apply-advanced;
             container protected {
               description "Adjacency SID is eligible for protection";
               choice adjsid-type {
                 case case_1 {
                   container index {
                     description "Adjacency SID indexed from SRGB";
                     leaf index-number {
                       type union {
                         type string {
                           pattern "<.*>|$.*";
                         }
                         type uint32 {
                           range "0 .. 199999";
                         }
                       }
                     }
                   }
                 }
                 case case_2 {
                   leaf label {
                     description "Adjacency SID from static label pool";
                     type union {
                       type string {
                         pattern "<.*>|$.*";
                       }
                       type uint32 {
                         range "16 .. 1048575";
                       }
                     }
                   }
                 }
                 case case_3 {
                   leaf dynamic {
                     description "Dynamically allocate an adjacency segment";
                     type empty;
                   }
                 }
               }
             }
             container unprotected {
               description "Adjacency SID uneligible for protection";
               choice adjsid-type {
                 case case_1 {
                   container index {
                     description "Adjacency SID indexed from SRGB";
                     leaf index-number {
                       type union {
                         type string {
                           pattern "<.*>|$.*";
                         }
                         type uint32 {
                           range "0 .. 199999";
                         }
                       }
                     }
                   }
                 }
                 case case_2 {
                   leaf label {
                     description "Adjacency SID from static label pool";
                     type union {
                       type string {
                         pattern "<.*>|$.*";
                       }
                       type uint32 {
                         range "16 .. 1048575";
                       }
                     }
                   }
                 }
                 case case_3 {
                   leaf dynamic {
                     description "Dynamically allocate an adjacency segment";
                     type empty;
                   }
                 }
               }
             }
           }
           container srm6-adjacency-segment {
             description "Configure srm6 adjacency segment";
             uses apply-advanced;
             container unprotected {
               description "Adjacency SID uneligible for protection";
               leaf sid {
                 description "Set Adjacency SID Value";
                 type union {
                   type string {
                     pattern "<.*>|$.*";
                   }
                   type uint32 {
                     range "1 .. 65535";
                   }
                 }
               }
             }
           }
           container srv6-adjacency-segment {
             description "Configure srv6 adjacency segment";
             uses apply-advanced;
             container protected {
               presence "enable protected";
               description "SRv6 Adjacency segment is eligible for protection";
               uses apply-advanced;
               list locator {
                 key name;
                 ordered-by user;
                 description "Locator to bind SRv6 adjacency segment";
                 leaf name {
                   description "Locator name";
                   junos:must "(\"routing-options source-packet-routing srv6 locator $$\")";
                   junos:must-message "Referenced source-packet-routing srv6 must be defined";
                   type string;
                 }
                 uses apply-advanced;
                 list end-x-sid {
                   key name;
                   ordered-by user;
                   description "Endpoint 128 bit address";
                   leaf name {
                     type jt:ipv6addr;
                   }
                   uses apply-advanced;
                   container flavor {
                     presence "enable flavor";
                     uses apply-advanced;
                     leaf psp {
                       description "Penultimate segment pop of the SRH";
                       type empty;
                     }
                     leaf usp {
                       description "Ultimate segment pop of the SRH";
                       type empty;
                     }
                     leaf usd {
                       description "Ultimate segment decapsulation";
                       type empty;
                     }
                   }
                 }
               }
             }
             container unprotected {
               presence "enable unprotected";
               description "SRv6 Adjacency segment is uneligible for protection";
               uses apply-advanced;
               list locator {
                 key name;
                 ordered-by user;
                 description "Locator to bind SRv6 adjacency segment";
                 leaf name {
                   description "Locator name";
                   junos:must "(\"routing-options source-packet-routing srv6 locator $$\")";
                   junos:must-message "Referenced source-packet-routing srv6 must be defined";
                   type string;
                 }
                 uses apply-advanced;
                 list end-x-sid {
                   key name;
                   ordered-by user;
                   description "Endpoint 128 bit address";
                   leaf name {
                     type jt:ipv6addr;
                   }
                   uses apply-advanced;
                   container flavor {
                     presence "enable flavor";
                     uses apply-advanced;
                     leaf psp {
                       description "Penultimate segment pop of the SRH";
                       type empty;
                     }
                     leaf usp {
                       description "Ultimate segment pop of the SRH";
                       type empty;
                     }
                     leaf usd {
                       description "Ultimate segment decapsulation";
                       type empty;
                     }
                   }
                 }
               }
             }
           }
         }
         container post-convergence-lfa {
           presence "enable post-convergence-lfa";
           junos:must "(\".. .. .. backup-spf-options use-post-convergence-lfa\")";
           junos:must-message "Not allowed without 'protocols isis backup-spf-options use-post-convergence-lfa'";
           description "Configure backup along post convergence on this interface";
           uses apply-advanced;
           container node-protection {
             presence "enable node-protection";
             description "Enable node protection";
             uses apply-advanced;
             leaf cost {
               description "Cost for node protection";
               type union {
                 type string {
                   pattern "<.*>|$.*";
                 }
                 type uint32 {
                   range "0 .. 16777215";
                 }
               }
             }
           }
           leaf srlg-protection {
             description "Enable srlg protection";
             type empty;
           }
           leaf fate-sharing-protection {
             description "Enable fate-sharing protection";
             type empty;
           }
         }
         container application-specific {
           description "Advertise application-specific TE attributes";
           uses apply-advanced;
           list attribute-group {
             key name;
             ordered-by user;
             description "Link attribute group name";
             max-elements 1;
             leaf name {
               description "Link attribute group name";
               type string;
             }
             uses apply-advanced;
             leaf te-metric {
               description "Traffic engineering metric for this attribute group";
               junos:must "(\".. application\")";
               junos:must-message "Atleast one application is must";
               type union {
                 type string {
                   pattern "<.*>|$.*";
                 }
                 type uint32 {
                   range "0 .. 16777215";
                 }
               }
             }
             leaf-list admin-group {
               ordered-by user;
               description "Administrative groups for this attribute-group";
               type string;
               max-elements 16;
             }
             container application {
               junos:must "((\".. delay-metric\" || (\".. admin-group\" || (\".. te-metric\" || (\".. admin-groups\" || (\".. legacy\" || \".. advertise-delay-metric\"))))))";
               junos:must-message "Atleast one attribute must be configured";
               description "Standard Applications part of this attribute-group";
               uses apply-advanced;
               leaf flex-algorithm {
                 description "Set X flag in standard application bit mask";
                 type empty;
               }
             }
           }
         }
         choice enable-disable {
           case case_1 {
             leaf disable {
               description "Disable IS-IS for this level";
               type empty;
             }
           }
         }
         leaf metric {
           description "Metric for this level";
           type union {
             type string {
               pattern "<.*>|$.*";
             }
             type uint32 {
               range "0 .. 16777215";
             }
           }
         }
         leaf ipv4-multicast-metric {
           description "IPv4 multicast metric for this level";
           type union {
             type string {
               pattern "<.*>|$.*";
             }
             type uint32 {
               range "0 .. 16777215";
             }
           }
         }
         leaf ipv6-unicast-metric {
           description "IPv6 unicast metric for this level";
           type union {
             type string {
               pattern "<.*>|$.*";
             }
             type uint32 {
               range "0 .. 16777215";
             }
           }
         }
         leaf ipv6-multicast-metric {
           description "IPv6 multicast metric for this level";
           type union {
             type string {
               pattern "<.*>|$.*";
             }
             type uint32 {
               range "0 .. 16777215";
             }
           }
         }
         list topology {
           key name;
           ordered-by user;
           description "Topology specific attributes";
           leaf name {
             description "Topology name";
             type enumeration {
               enum "default" {
                 description "Default topology";
               }
               enum "ipv4-multicast" {
                 description "IPv4 multicast topology";
               }
               enum "ipv6-unicast" {
                 description "IPv6 unicast topology";
               }
               enum "ipv6-multicast" {
                 description "IPv6 multicast topology";
               }
             }
           }
           uses apply-advanced;
           leaf metric {
             description "Topology metric";
             type union {
               type string {
                 pattern "<.*>|$.*";
               }
               type uint32 {
                 range "0 .. 16777215";
               }
             }
           }
           container bandwidth-based-metrics {
             junos:must "(\".. metric\")";
             junos:must-message "Metric must be configured";
             description "Configure bandwidth based metrics";
             uses apply-advanced;
             list bandwidth {
               key name;
               description "Bandwidth threshold";
               leaf name {
                 type string;
               }
               leaf metric {
                 description "Metric associated with specified bandwidth";
                 type union {
                   type string {
                     pattern "<.*>|$.*";
                   }
                   type uint32 {
                     range "0 .. 16777215";
                   }
                 }
               }
             }
           }
         }
         leaf authentication-key {
           description "Authentication key (password)";
           status deprecated;
           type jt:unreadable;
         }
         leaf authentication-type {
           description "Authentication type";
           status deprecated;
           type enumeration {
             enum "md5" {
               description "MD5 authentication";
               status deprecated;
             }
             enum "simple" {
               description "Simple password authentication";
               status deprecated;
             }
           }
         }
         leaf hello-authentication-key {
           description "Authentication key (password) for hello packets";
           type jt:unreadable;
         }
         leaf hello-authentication-type {
           description "Authentication type for hello packets";
           type enumeration {
             enum "md5" {
               description "MD5 authentication";
             }
             enum "simple" {
               description "Simple password authentication";
             }
           }
         }
         leaf hello-authentication-key-chain {
           description "Key chain name";
           junos:must "(!(\".. hello-authentication-type\"))";
           junos:must-message "May not be configured with hello-authentication-type";
           junos:must "(!(\".. hello-authentication-key\"))";
           junos:must-message "May not be configured with hello-authentication-key";
           junos:must "(!(\".. authentication-key\"))";
           junos:must-message "May not be configured with authentication-key";
           junos:must "(\"security authentication-key-chains key-chain $$\")";
           junos:must-message "Referenced key-chain must be defined";
           type string {
             length "1 .. 128";
             junos:posix-pattern "[A-za-z]$";
             junos:pattern-message "Keychain name must not end with number.";
           }
         }
         leaf hello-interval {
           description "Interval between hello packet transmissions";
           units "seconds";
           type union {
             type string {
               pattern "<.*>|$.*";
             }
             type uint32 {
               range "1 .. 21845";
             }
           }
         }
         leaf hold-time {
           description "Time after which neighbors think the interface is down";
           units "seconds";
           type union {
             type string {
               pattern "<.*>|$.*";
             }
             type uint32 {
               range "1 .. 65535";
             }
           }
         }
         leaf priority {
           description "Designated router election priority";
           type union {
             type string {
               pattern "<.*>|$.*";
             }
             type uint32 {
               range "0 .. 127";
             }
           }
         }
         container flood-reflector {
           presence "enable flood-reflector";
           junos:must "(\".. .. level 1 disable\")";
           junos:must-message "flood-reflector cannot be enabled on level 1 interface";
           junos:must "((\".. .. .. level 2 flood-reflector\" && !(\".. .. level 1 flood-reflector\")))";
           junos:must-message "flood-reflector is only supported on level 2 interfaces";
           description "Configure interface as flood-reflector";
           uses apply-advanced;
           leaf cluster-id {
             description "Cluster-ID";
             junos:must "(\".. .. .. .. level 2 flood-reflector client\")";
             junos:must-message "flood-reflector client is not configured at isis level";
             type union {
               type string {
                 pattern "<.*>|$.*";
               }
               type uint32 {
                 range "1 .. 4294967295";
               }
             }
           }
         }
         container passive {
           presence "enable passive";
           description "Do not run IS-IS at this level, but advertise it";
           uses apply-advanced;
           leaf remote-node-iso {
             description "ISO System-ID of the remote node";
             junos:must "(\".. remote-node-id\")";
             junos:must-message "remote-node-id must be configured";
             type jt:sysid;
           }
           leaf remote-node-id {
             description "Remote address of the link";
             junos:must "(\".. remote-node-iso\")";
             junos:must-message "remote-node-iso must be configured";
             type jt:ipv4addr;
           }
         }
       }
       leaf delay-metric {
         description "Delay metric";
         units "microseconds";
         type union {
           type string {
             pattern "<.*>|$.*";
           }
           type uint32 {
             range "0 .. 16777215";
           }
         }
       }
       container delay-measurement {
         presence "enable delay-measurement";
         description "Enable delay measurement";
         uses apply-advanced;
         leaf probe-interval {
           description "Probe interval";
           units "seconds";
           type union {
             type string {
               pattern "<.*>|$.*";
             }
             type uint32 {
               range "1 .. 255";
             }
           }
         }
         leaf probe-count {
           description "Probe count";
           units "seconds";
           type union {
             type string {
               pattern "<.*>|$.*";
             }
             type uint32 {
               range "1 .. 15";
             }
           }
         }
         container advertisement {
           description "Delay advertisement";
           uses apply-advanced;
           container periodic {
             description "Periodic advertisement parameters";
             uses apply-advanced;
             leaf threshold {
               description "Threshold";
               units "percentage";
               type union {
                 type string {
                   pattern "<.*>|$.*";
                 }
                 type uint32 {
                   range "0 .. 100";
                 }
               }
             }
             leaf interval {
               description "Interval";
               units "seconds";
               type union {
                 type string {
                   pattern "<.*>|$.*";
                 }
                 type uint32 {
                   range "30 .. 3600";
                 }
               }
             }
           }
           container accelerated {
             presence "enable accelerated";
             description "Accelerated advertisement parameters";
             uses apply-advanced;
             leaf threshold {
               description "Threshold";
               units "percentage";
               type union {
                 type string {
                   pattern "<.*>|$.*";
                 }
                 type uint32 {
                   range "0 .. 100";
                 }
               }
             }
           }
         }
       }
       leaf no-advertise-adjacency-segment {
         description "Do not advertise an adjacency segment for this interface";
         type empty;
       }
       container auto-bandwidth {
         description "Auto bandwidth configuration";
         uses apply-advanced;
         leaf template-name {
           description "Auto bandwidth template name";
           junos:must "(\"protocols isis source-packet-routing traffic-statistics statistics-granularity per-interface\")";
           junos:must-message "Config protocols isis source-packet-routing traffic-statistics statistics-granularity per-interface is must";
           junos:must "(\"routing-options auto-bandwidth template $$\")";
           junos:must-message "Referenced auto-bandwidth template must be defined";
           type string;
         }
         choice enable-disable {
           case case_1 {
             leaf disable {
               description "Disable Auto bandwidth on this interface";
               type empty;
             }
           }
         }
       }
       choice protection-type {
         case case_1 {
           leaf link-protection {
             description "Protect interface from link faults only";
             type empty;
           }
         }
         case case_2 {
           leaf node-link-protection {
             description "Protect interface from both link and node faults";
             type empty;
           }
         }
       }
       leaf no-eligible-backup {
         description "Not eligible for backup traffic from protected interfaces";
         type empty;
       }
       leaf no-eligible-remote-backup {
         description "Not eligible for Remote-LFA backup traffic from protected interfaces";
         type empty;
       }
       container link-degradation-threshold {
         presence "enable link-degradation-threshold";
         description "Link up and down thresholds (in %) for proactive link protection";
         leaf link-down {
           description "Signal degradation threshold above which link marked down";
           type union {
             type string {
               pattern "<.*>|$.*";
             }
             type uint32 {
               range "0 .. 100";
             }
           }
         }
         leaf link-up {
           description "Signal degradation threshold below which link is marked up.";
           type union {
             type string {
               pattern "<.*>|$.*";
             }
             type uint32 {
               range "0 .. 100";
             }
           }
         }
       }
       choice enable-disable {
         case case_1 {
           leaf disable {
             description "Disable IS-IS on this interface";
             type empty;
           }
         }
       }
       leaf authentication-key {
         description "Authentication key (password)";
         status deprecated;
         type jt:unreadable;
       }
       leaf authentication-type {
         description "Authentication type";
         status deprecated;
         type enumeration {
           enum "md5" {
             description "MD5 authentication";
             status deprecated;
           }
           enum "simple" {
             description "Simple password authentication";
             status deprecated;
           }
         }
       }
       leaf flood-group {
         description "ISO Area that this interface should send LSPs to";
         type string {
           junos:posix-pattern "^[[:xdigit:]]{2}.(([[:xdigit:]]){2}){1,2}((.(([[:xdigit:]]){2}){1,2}){0,1}){0,5}$";
           junos:pattern-message "At max 26 hexa decimal digits, standard ISO area ID format";
         }
       }
       leaf hello-authentication-key {
         description "Authentication key (password) for hello packets";
         status deprecated;
         type jt:unreadable;
       }
       leaf hello-authentication-type {
         description "Authentication type for hello packets";
         status deprecated;
         type enumeration {
           enum "md5" {
             description "MD5 authentication";
             status deprecated;
           }
           enum "simple" {
             description "Simple password authentication";
             status deprecated;
           }
         }
       }
       leaf hello-padding-type {
         description "Type of padding for hello packets";
         default "loose";
         type enumeration {
           enum "strict" {
             description "Padding for all adjacency states";
           }
           enum "adaptive" {
             description "Padding until state of neighbor adjacency is 'up'";
           }
           enum "loose" {
             description "Padding until state of adjacency is 'initializing'";
           }
           enum "disable" {
             description "Do not add any padding for hello packets";
           }
         }
       }
       leaf interface-group-holddown-delay {
         description "Time to wait before including in BBM calculation";
         units "seconds";
         type union {
           type string {
             pattern "<.*>|$.*";
           }
           type uint32 {
             range "0 .. 60";
           }
         }
       }
       choice layer2-map-choice {
         leaf layer2-map {
           description "Kernel ARP/ND creation for nexthops";
           type empty;
         }
         leaf no-layer2-map {
           description "Don't kernel ARP/ND creation for nexthops";
           type empty;
         }
       }
       leaf max-hello-size {
         description "Maximum size allowed for ISIS Hello PDUs";
         type union {
           type string {
             pattern "<.*>|$.*";
           }
           type uint32 {
             range "512 .. 16000";
           }
         }
       }
       leaf lsp-interval {
         description "Interval between LSP transmissions";
         default "100";
         units "milliseconds";
         type union {
           type string {
             pattern "<.*>|$.*";
           }
           type uint32 {
             range "1 .. 1000";
           }
         }
       }
       container csnp-interval {
         description "Rate of CSN packets (for LAN interfaces only)";
         choice csnp_interval_option {
           case case_1 {
             leaf csnp-interval-number {
               description "Interval between CSN packets";
               units "seconds";
               type union {
                 type string {
                   pattern "<.*>|$.*";
                 }
                 type uint32 {
                   range "1 .. 65535";
                 }
               }
             }
           }
           case case_2 {
             leaf disable {
               description "Do not send CSN packets on this interface";
               type empty;
             }
           }
         }
       }
       container strict-dual-isis {
         presence "enable strict-dual-isis";
         junos:must "(!(\".. .. topologies\"))";
         junos:must-message "strict-dual-isis is not allowed with multi-topologies";
         description "Enable dual isis if spf computation is required for both ipv4 and ipv6 family";
         uses apply-advanced;
         leaf holdown {
           description "Time to wait for ipv4 and ipv6 connectivity";
           status deprecated;
           default "12";
           type union {
             type string {
               pattern "<.*>|$.*";
             }
             type uint32 {
               range "1 .. 65535";
             }
           }
         }
         leaf holddown {
           description "Time to wait for ipv4 and ipv6 connectivity";
           default "12";
           type union {
             type string {
               pattern "<.*>|$.*";
             }
             type uint32 {
               range "1 .. 65535";
             }
           }
         }
       }
       container mesh-group {
         description "Add the interface to a mesh group";
         choice mesh_group_option {
           case case_1 {
             leaf mesh-group-number {
               description "Mesh group number for this interface";
               type union {
                 type uint32;
                 type string {
                   pattern "<.*>|$.*";
                 }
               }
             }
           }
           case case_2 {
             leaf blocked {
               description "Do not flood new LSPs on this interface";
               type empty;
             }
           }
         }
       }
       leaf point-to-point {
         description "Treat interface as point to point";
         type empty;
       }
       container passive {
         presence "enable passive";
         description "Do not run IS-IS, but advertise it";
         uses apply-advanced;
         leaf remote-node-iso {
           description "ISO System-ID of the remote node";
           junos:must "(\".. remote-node-id\")";
           junos:must-message "remote-node-id must be configured";
           type jt:sysid;
         }
         leaf remote-node-id {
           description "Remote address of the link";
           junos:must "(\".. remote-node-iso\")";
           junos:must-message "remote-node-iso must be configured";
           type jt:ipv4addr;
         }
       }
       leaf checksum {
         description "Enable checksum for packets on this interface";
         type empty;
       }
       leaf no-unicast-topology {
         description "Do not include this interface in the unicast topology";
         type empty;
       }
       leaf no-ipv4-multicast {
         description "Do not include this interface in the IPv4 multicast topology";
         type empty;
       }
       leaf no-ipv6-unicast {
         description "Do not include this interface in the IPv6 unicast topology";
         type empty;
       }
       leaf no-ipv6-multicast {
         description "Do not include this interface in the IPv6 multicast topology";
         type empty;
       }
       leaf no-adjacency-down-notification {
         description "Do not inform other protocols about adjacency down events";
         type empty;
       }
       container bfd-liveness-detection {
         junos:must "(!(\".. family inet bfd-liveness-detection\"))";
         junos:must-message "To configure bfd-liveness-detection, 'family inet bfd-liveness-detection' must not be configured";
         description "Bidirectional Forwarding Detection options";
         status deprecated;
         uses apply-advanced;
         leaf version {
           description "BFD protocol version number";
           default "automatic";
           type enumeration {
             enum "0" {
               description "BFD version 0 (deprecated)";
             }
             enum "1" {
               description "BFD version 1";
             }
             enum "automatic" {
               description "Choose BFD version automatically";
             }
           }
         }
         leaf minimum-interval {
           description "Minimum transmit and receive interval";
           units "milliseconds";
           type union {
             type string {
               pattern "<.*>|$.*";
             }
             type uint32 {
               range "1 .. 255000";
             }
           }
         }
         leaf minimum-transmit-interval {
           description "Minimum transmit interval";
           status deprecated;
           units "milliseconds";
           type union {
             type string {
               pattern "<.*>|$.*";
             }
             type uint32 {
               range "1 .. 255000";
             }
           }
         }
         leaf minimum-receive-interval {
           description "Minimum receive interval";
           units "milliseconds";
           type union {
             type string {
               pattern "<.*>|$.*";
             }
             type uint32 {
               range "1 .. 255000";
             }
           }
         }
         leaf multiplier {
           description "Detection time multiplier";
           default "3";
           type union {
             type string {
               pattern "<.*>|$.*";
             }
             type uint32 {
               range "1 .. 255";
             }
           }
         }
         choice adaptation-choice {
           case case_1 {
             leaf no-adaptation {
               description "Disable adaptation";
               type empty;
             }
           }
         }
         container transmit-interval {
           description "Transmit-interval options";
           uses apply-advanced;
           leaf minimum-interval {
             description "Minimum transmit interval";
             units "milliseconds";
             type union {
               type string {
                 pattern "<.*>|$.*";
               }
               type uint32 {
                 range "1 .. 255000";
               }
             }
           }
           leaf threshold {
             description "High transmit interval triggering a trap";
             units "milliseconds";
             type union {
               type uint32;
               type string {
                 pattern "<.*>|$.*";
               }
             }
           }
         }
         container detection-time {
           description "Detection-time options";
           uses apply-advanced;
           leaf threshold {
             description "High detection-time triggering a trap";
             units "milliseconds";
             type union {
               type uint32;
               type string {
                 pattern "<.*>|$.*";
               }
             }
           }
         }
         container authentication {
           description "Authentication options";
           uses apply-advanced;
           leaf key-chain {
             description "Key chain name";
             junos:must "(\".. algorithm\")";
             junos:must-message "May not be configured without algorithm";
             junos:must "(\"security authentication-key-chains key-chain $$\")";
             junos:must-message "Referenced key-chain must be defined";
             type string;
           }
           leaf algorithm {
             description "Algorithm name";
             junos:must "(\".. key-chain\")";
             junos:must-message "May not be configured without key-chain";
             type enumeration {
               enum "simple-password" {
                 description "Simple password";
               }
               enum "keyed-md5" {
                 description "Keyed message Digest 5";
               }
               enum "meticulous-keyed-md5" {
                 description "Meticulous keyed message Digest 5";
               }
               enum "keyed-sha-1" {
                 description "Keyed secure hash algorithm (SHA1) ";
               }
               enum "meticulous-keyed-sha-1" {
                 description "Meticulous keyed secure hash algorithm (SHA1) ";
               }
             }
           }
           leaf loose-check {
             description "Verify authentication only if authentication is negotiated";
             type empty;
           }
         }
       }
       list family {
         key name;
         ordered-by user;
         description "Address family specific interface attributes";
         leaf name {
           type enumeration {
             enum "inet" {
               description "IPv4 family";
             }
             enum "inet6" {
               description "IPv6 family";
             }
           }
         }
         uses apply-advanced;
         container bfd-liveness-detection {
           junos:must "(!((\".. .. bfd-liveness-detection\" && \".. .. family inet bfd-liveness-detection\")))";
           junos:must-message "bfd-liveness-detection and 'family inet bfd-liveness-detection' cannot be configured at the same time";
           description "Bidirectional Forwarding Detection options";
           uses apply-advanced;
           leaf version {
             description "BFD protocol version number";
             default "automatic";
             type enumeration {
               enum "0" {
                 description "BFD version 0 (deprecated)";
               }
               enum "1" {
                 description "BFD version 1";
               }
               enum "automatic" {
                 description "Choose BFD version automatically";
               }
             }
           }
           leaf minimum-interval {
             description "Minimum transmit and receive interval";
             units "milliseconds";
             type union {
               type string {
                 pattern "<.*>|$.*";
               }
               type uint32 {
                 range "1 .. 255000";
               }
             }
           }
           leaf minimum-transmit-interval {
             description "Minimum transmit interval";
             status deprecated;
             units "milliseconds";
             type union {
               type string {
                 pattern "<.*>|$.*";
               }
               type uint32 {
                 range "1 .. 255000";
               }
             }
           }
           leaf minimum-receive-interval {
             description "Minimum receive interval";
             units "milliseconds";
             type union {
               type string {
                 pattern "<.*>|$.*";
               }
               type uint32 {
                 range "1 .. 255000";
               }
             }
           }
           leaf multiplier {
             description "Detection time multiplier";
             default "3";
             type union {
               type string {
                 pattern "<.*>|$.*";
               }
               type uint32 {
                 range "1 .. 255";
               }
             }
           }
           choice adaptation-choice {
             case case_1 {
               leaf no-adaptation {
                 description "Disable adaptation";
                 type empty;
               }
             }
           }
           container transmit-interval {
             description "Transmit-interval options";
             uses apply-advanced;
             leaf minimum-interval {
               description "Minimum transmit interval";
               units "milliseconds";
               type union {
                 type string {
                   pattern "<.*>|$.*";
                 }
                 type uint32 {
                   range "1 .. 255000";
                 }
               }
             }
             leaf threshold {
               description "High transmit interval triggering a trap";
               units "milliseconds";
               type union {
                 type uint32;
                 type string {
                   pattern "<.*>|$.*";
                 }
               }
             }
           }
           container detection-time {
             description "Detection-time options";
             uses apply-advanced;
             leaf threshold {
               description "High detection-time triggering a trap";
               units "milliseconds";
               type union {
                 type uint32;
                 type string {
                   pattern "<.*>|$.*";
                 }
               }
             }
           }
           container authentication {
             description "Authentication options";
             uses apply-advanced;
             leaf key-chain {
               description "Key chain name";
               junos:must "(\".. algorithm\")";
               junos:must-message "May not be configured without algorithm";
               junos:must "(\"security authentication-key-chains key-chain $$\")";
               junos:must-message "Referenced key-chain must be defined";
               type string;
             }
             leaf algorithm {
               description "Algorithm name";
               junos:must "(\".. key-chain\")";
               junos:must-message "May not be configured without key-chain";
               type enumeration {
                 enum "simple-password" {
                   description "Simple password";
                 }
                 enum "keyed-md5" {
                   description "Keyed message Digest 5";
                 }
                 enum "meticulous-keyed-md5" {
                   description "Meticulous keyed message Digest 5";
                 }
                 enum "keyed-sha-1" {
                   description "Keyed secure hash algorithm (SHA1) ";
                 }
                 enum "meticulous-keyed-sha-1" {
                   description "Meticulous keyed secure hash algorithm (SHA1) ";
                 }
               }
             }
             leaf loose-check {
               description "Verify authentication only if authentication is negotiated";
               type empty;
             }
           }
         }
       }
     }
     container source-packet-routing {
       presence "enable source-packet-routing";
       junos:must "(!(\".. srm6\"))";
       junos:must-message "must not have 'protocols isis srm6' configured";
       description "Enable Source Packet Routing (SPRING)";
       uses apply-advanced;
       container adjacency-segment {
         junos:must "(!(\".. .. .. .. protocols mpls disable\"))";
         junos:must-message "SPRING configuration is not allowed with 'protocols mpls disable'";
         description "Configure attributes for Adjacency Segments in SPRING";
         uses apply-advanced;
         leaf hold-time {
           description "Duration(ms) for which adjacency segments will be retained after isolating from an interface";
           type union {
             type string {
               pattern "<.*>|$.*";
             }
             type uint32 {
               range "180000 .. 900000";
             }
           }
         }
       }
       container udp-tunneling {
         junos:must "(!(\".. .. .. .. protocols mpls disable\"))";
         junos:must-message "SPRING configuration is not allowed with 'protocols mpls disable'";
         description "Enable SR over UDP feature";
         uses apply-advanced;
         leaf encapsulation {
           description "Enable UDP Tunnel Encapsulation";
           type empty;
         }
         leaf decapsulation {
           description "Enable UDP Tunnel decapsulation";
           type empty;
         }
       }
       container srgb {
         junos:must "(!(\".. node-segment index-range\"))";
         junos:must-message "May not be confiugred with node-segment index-range";
         junos:must "(!(\".. .. .. .. protocols mpls disable\"))";
         junos:must-message "SPRING configuration is not allowed with 'protocols mpls disable'";
         description "Set the SRGB global block in SPRING";
         leaf start-label {
           description "Start range for SRGB label block";
           type union {
             type string {
               pattern "<.*>|$.*";
             }
             type uint32;
           }
         }
         leaf index-range {
           description "Index to the SRGB start label block";
           type union {
             type string {
               pattern "<.*>|$.*";
             }
             type uint32;
           }
         }
       }
       container node-segment {
         junos:must "(!(\".. .. .. .. protocols mpls disable\"))";
         junos:must-message "SPRING configuration is not allowed with 'protocols mpls disable'";
         description "Enable support for Node segments in SPRING";
         uses apply-advanced;
         leaf ipv4-index {
           description "Set IPv4 Node Segment index";
           type union {
             type string {
               pattern "<.*>|$.*";
             }
             type uint32 {
               range "0 .. 199999";
             }
           }
         }
         leaf ipv6-index {
           description "Set IPv6 Node Segment index";
           type union {
             type string {
               pattern "<.*>|$.*";
             }
             type uint32 {
               range "0 .. 199999";
             }
           }
         }
         leaf index-range {
           description "Set Range of Node Segment indices allowed";
           type union {
             type string {
               pattern "<.*>|$.*";
             }
             type uint32 {
               range "32 .. 16385";
             }
           }
         }
       }
       leaf-list flex-algorithm {
         description "Flex-algorithms we would like to participate in";
         type union {
           type string {
             pattern "<.*>|$.*";
           }
           type uint32 {
             range "128 .. 255";
           }
         }
         max-elements 16;
       }
       leaf use-flex-algorithm-metric-always {
         description "Use flex-algo prefix metric whenever available";
         type empty;
       }
       leaf strict-asla-based-flex-algorithm {
         description "Flex-Algorithm to ignore links not having ASLA sub-TLVs";
         type empty;
       }
       leaf new-capability-subtlv {
         description "Advertise all ranges in single spring capability subtlv";
         junos:must "(!(\".. .. .. .. protocols mpls disable\"))";
         junos:must-message "SPRING configuration is not allowed with 'protocols mpls disable'";
         type empty;
       }
       leaf explicit-null {
         description "Set E and P bits in all Prefix SID advertisements";
         junos:must "(!(\".. .. .. .. protocols mpls disable\"))";
         junos:must-message "SPRING configuration is not allowed with 'protocols mpls disable'";
         type empty;
       }
       leaf mapping-server {
         description "Mapping server name";
         junos:must "(!(\".. .. .. .. protocols mpls disable\"))";
         junos:must-message "SPRING configuration is not allowed with 'protocols mpls disable'";
         junos:must "(\"routing-options source-packet-routing mapping-server-entry $$\")";
         junos:must-message "Referenced source-packet-routing mapping-server-entry must be defined";
         type string;
       }
       leaf no-strict-spf {
         description " Disable strict spf algo 1 advertisement";
         type empty;
       }
       leaf no-binding-sid-leaking {
         description " Disable SRMS binding sid leaking";
         type empty;
       }
       leaf ldp-stitching {
         description "Enable SR to LDP stitching";
         junos:must "(!(\".. .. .. .. protocols mpls disable\"))";
         junos:must-message "SPRING configuration is not allowed with 'protocols mpls disable'";
         type empty;
       }
       container srv6 {
         presence "enable srv6";
         description "Enable IPv6 Segment Routing (SRv6)";
         uses apply-advanced;
         list locator {
           key name;
           ordered-by user;
           description "SRv6 Locator";
           leaf name {
             description "Locator name";
             junos:must "(\"routing-options source-packet-routing srv6 locator $$\")";
             junos:must-message "Referenced source-packet-routing srv6 must be defined";
             type string;
           }
           uses apply-advanced;
           list end-sid {
             key name;
             ordered-by user;
             leaf name {
               type jt:ipv6addr;
             }
             uses apply-advanced;
             container flavor {
               presence "enable flavor";
               uses apply-advanced;
               leaf psp {
                 description "Penultimate segment pop of the SRH";
                 type empty;
               }
               leaf usp {
                 description "Ultimate segment pop of the SRH";
                 type empty;
               }
               leaf usd {
                 description "Ultimate segment decapsulation";
                 type empty;
               }
             }
           }
         }
       }
       container sensor-based-stats {
         junos:must "(!(\".. .. .. .. protocols mpls disable\"))";
         junos:must-message "SPRING configuration is not allowed with 'protocols mpls disable'";
         description "Configure sensor based stats in SPRING";
         uses apply-advanced;
         container per-interface-per-member-link {
           description "Configure sensor based stats per nexthop";
           leaf ingress {
             description "Enable sensor based stats on ingress interface";
             type empty;
           }
           leaf egress {
             description "Enable sensor based stats on egress interface";
             type empty;
           }
         }
         container per-sid {
           description "Configure sensor based stats per spring route";
           leaf ingress {
             description "Enable sensor based stats for per-sid ingress accounting";
             type empty;
           }
           leaf egress {
             description "Enable sensor based stats for IP-MPLS egress accounting";
             type empty;
           }
         }
       }
       container traffic-statistics {
         junos:must "(!(\".. .. .. .. protocols mpls disable\"))";
         junos:must-message "SPRING configuration is not allowed with 'protocols mpls disable'";
         description "Enable support for traffic statistics in SPRING";
         uses apply-advanced;
         container statistics-granularity {
           description "Granularity for traffic statistics in SPRING";
           uses apply-advanced;
           leaf per-interface {
             description "Interface Based traffic statistics in SPRING";
             type empty;
           }
         }
         leaf auto-bandwidth {
           description "Auto bandwidth name";
           junos:must "(\"protocols isis source-packet-routing traffic-statistics statistics-granularity per-interface\")";
           junos:must-message "Config protocols isis source-packet-routing traffic-statistics statistics-granularity per-interface is must";
           junos:must "(\"routing-options auto-bandwidth template $$\")";
           junos:must-message "Referenced auto-bandwidth template must be defined";
           type string;
         }
       }
     }
     container srm6 {
       presence "enable srm6";
       junos:must "(!(\".. source-packet-routing\"))";
       junos:must-message "must not have 'protocols isis source-packet-routing' configured";
       description "Enable SRm6";
       uses apply-advanced;
       container sid {
         description "Configure attributes for SID in srm6";
         uses apply-advanced;
         leaf node-sid {
           description "Set Node SID Value";
           type union {
             type string {
               pattern "<.*>|$.*";
             }
             type uint32 {
               range "1 .. 65535";
             }
           }
         }
         leaf address {
           description "IPv6 address corresponding to SID";
           type jt:ipv6addr;
         }
       }
     }
     list level {
       key name;
       ordered-by user;
       description "Configure global level attributes";
       leaf name {
         description "IS-IS level number";
         type union {
           type string {
             pattern "<.*>|$.*";
           }
           type uint32 {
             range "1 .. 2";
           }
         }
       }
       uses apply-advanced;
       leaf labeled-preference {
         description "Preference of labeled IS-IS routes";
         junos:must "(\".. .. source-packet-routing\")";
         junos:must-message "labeled-preference cannot be specified without 'protocols isis source-packet-routing'";
         type union {
           type uint32;
           type string {
             pattern "<.*>|$.*";
           }
         }
       }
       leaf srv6-preference {
         description "Preference of SRV6 IS-IS routes";
         junos:must "(\".. .. source-packet-routing\")";
         junos:must-message "srv6-preference cannot be specified without 'protocols isis source-packet-routing'";
         type union {
           type uint32;
           type string {
             pattern "<.*>|$.*";
           }
         }
       }
       leaf flex-algorithm-preference {
         description "Preference of flex-algorithm L-ISIS routes";
         junos:must "(\".. .. source-packet-routing\")";
         junos:must-message "flex-algorithm-preference cannot be specified without 'protocols isis source-packet-routing'";
         type union {
           type uint32;
           type string {
             pattern "<.*>|$.*";
           }
         }
       }
       container source-packet-routing {
         presence "enable source-packet-routing";
         description "Enable Source Packet Routing (SPRING)";
         uses apply-advanced;
         choice enable-disable {
           case case_1 {
             leaf disable {
               description "Disable Source Packet Routing on this level";
               type empty;
             }
           }
         }
         leaf srms-preference {
           description "Set SRMS preference value";
           type union {
             type string {
               pattern "<.*>|$.*";
             }
             type uint32 {
               range "0 .. 255";
             }
           }
         }
       }
       choice enable-disable {
         case case_1 {
           leaf disable {
             description "Disable IS-IS on this level";
             type empty;
           }
         }
       }
       leaf authentication-key {
         description "Authentication key (password)";
         type jt:unreadable;
       }
       leaf authentication-type {
         description "Authentication type";
         type enumeration {
           enum "md5" {
             description "MD5 authentication";
           }
           enum "simple" {
             description "Simple password authentication";
           }
         }
       }
       leaf purge-originator {
         description "Add Purge Originator information";
         type enumeration {
           enum "self" {
             description "Add POI only for self-originated purge LSPs";
           }
           enum "empty" {
             description "Add POI for purge LSPs who do not have POI information";
           }
         }
       }
       leaf no-hello-authentication {
         description "Disable authentication for hello packets";
         type empty;
       }
       leaf no-csnp-authentication {
         description "Disable authentication for CSN packets";
         type empty;
       }
       leaf no-psnp-authentication {
         description "Disable authentication for PSN packets";
         type empty;
       }
       leaf authentication-key-chain {
         description "Key chain name";
         junos:must "(!(\".. authentication-type\"))";
         junos:must-message "May not be configured with authentication-type";
         junos:must "(!(\".. authentication-key\"))";
         junos:must-message "May not be configured with authentication-key";
         junos:must "(\"security authentication-key-chains key-chain $$\")";
         junos:must-message "Referenced key-chain must be defined";
         type string {
           length "1 .. 128";
           junos:posix-pattern "[A-za-z]$";
           junos:pattern-message "Keychain name must not end with number.";
         }
       }
       leaf wide-metrics-only {
         description "Generate wide metrics only";
         junos:must "(!(\".. .. clns-routing\"))";
         junos:must-message "wide-metrics-only cannot be specified with clns-routing";
         type empty;
       }
       leaf preference {
         description "Preference of internal routes";
         type union {
           type uint32;
           type string {
             pattern "<.*>|$.*";
           }
         }
       }
       leaf external-preference {
         description "Preference of external routes";
         type union {
           type uint32;
           type string {
             pattern "<.*>|$.*";
           }
         }
       }
       leaf prefix-export-limit {
         description "Maximum number of external prefixes that can be exported";
         type union {
           type string {
             pattern "<.*>|$.*";
           }
           type uint32 {
             range "0 .. 4294967295";
           }
         }
       }
       container flood-reflector {
         junos:must "(!(\".. .. level 1 flood-reflector\"))";
         junos:must-message "Flood-reflector is supported only in level 2";
         description "Enable flood-reflector";
         uses apply-advanced;
         choice flood-reflector-choice {
           case case_1 {
             container reflector {
               junos:must "(!(\".. client\"))";
               junos:must-message "flood-reflector and client can't be configured together";
               description "Configure this as a flood-reflector";
               uses apply-advanced;
               leaf cluster-id {
                 description "Cluster-ID";
                 type union {
                   type string {
                     pattern "<.*>|$.*";
                   }
                   type uint32 {
                     range "1 .. 4294967295";
                   }
                 }
               }
             }
           }
           case case_2 {
             leaf client {
               description "Configure interface as flood-reflector client";
               type empty;
             }
           }
         }
       }
     }
     list interface-group {
       key name;
       description "Interface grouping configuration";
       leaf name {
         description "Interface group name";
         type string;
       }
       uses apply-advanced;
       list level {
         key name;
         ordered-by user;
         description "Configure levels on this interface-group";
         leaf name {
           description "IS-IS level number";
           type union {
             type string {
               pattern "<.*>|$.*";
             }
             type uint32 {
               range "1 .. 2";
             }
           }
         }
         uses apply-advanced;
         container ipv4-adjacency-segment {
           junos:must "(!(\".. no-advertise-adjacency-segment\"))";
           junos:must-message "ipv4-adjacency-segment can't be configured if no-advertise-adjacency-segment is configured in the level";
           junos:must "(!(\".. .. no-advertise-adjacency-segment\"))";
           junos:must-message "ipv4-adjacency-segment can't be configured if no-advertise-adjacency-segment is configured in the same interface";
           description "Configure ipv4 adjacency segment";
           uses apply-advanced;
           container protected {
             description "Adjacency SID is eligible for protection";
             choice adjsid-type {
               case case_1 {
                 container index {
                   description "Adjacency SID indexed from SRGB";
                   leaf index-number {
                     type union {
                       type string {
                         pattern "<.*>|$.*";
                       }
                       type uint32 {
                         range "0 .. 199999";
                       }
                     }
                   }
                 }
               }
               case case_2 {
                 leaf label {
                   description "Adjacency SID from static label pool";
                   type union {
                     type string {
                       pattern "<.*>|$.*";
                     }
                     type uint32 {
                       range "16 .. 1048575";
                     }
                   }
                 }
               }
               case case_3 {
                 leaf dynamic {
                   description "Dynamically allocate an adjacency segment";
                   type empty;
                 }
               }
             }
           }
           container unprotected {
             description "Adjacency SID uneligible for protection";
             choice adjsid-type {
               case case_1 {
                 container index {
                   description "Adjacency SID indexed from SRGB";
                   leaf index-number {
                     type union {
                       type string {
                         pattern "<.*>|$.*";
                       }
                       type uint32 {
                         range "0 .. 199999";
                       }
                     }
                   }
                 }
               }
               case case_2 {
                 leaf label {
                   description "Adjacency SID from static label pool";
                   type union {
                     type string {
                       pattern "<.*>|$.*";
                     }
                     type uint32 {
                       range "16 .. 1048575";
                     }
                   }
                 }
               }
               case case_3 {
                 leaf dynamic {
                   description "Dynamically allocate an adjacency segment";
                   type empty;
                 }
               }
             }
           }
         }
         container ipv6-adjacency-segment {
           junos:must "(!(\".. no-advertise-adjacency-segment\"))";
           junos:must-message "ipv6-adjacency-segment can't be configured if no-advertise-adjacency-segment is configured in the same level";
           junos:must "(!(\".. .. no-advertise-adjacency-segment\"))";
           junos:must-message "ipv6-adjacency-segment can't be configured if no-advertise-adjacency-segment is configured in the same interface";
           description "Configure ipv6 adjacency segment";
           uses apply-advanced;
           container protected {
             description "Adjacency SID is eligible for protection";
             choice adjsid-type {
               case case_1 {
                 container index {
                   description "Adjacency SID indexed from SRGB";
                   leaf index-number {
                     type union {
                       type string {
                         pattern "<.*>|$.*";
                       }
                       type uint32 {
                         range "0 .. 199999";
                       }
                     }
                   }
                 }
               }
               case case_2 {
                 leaf label {
                   description "Adjacency SID from static label pool";
                   type union {
                     type string {
                       pattern "<.*>|$.*";
                     }
                     type uint32 {
                       range "16 .. 1048575";
                     }
                   }
                 }
               }
               case case_3 {
                 leaf dynamic {
                   description "Dynamically allocate an adjacency segment";
                   type empty;
                 }
               }
             }
           }
           container unprotected {
             description "Adjacency SID uneligible for protection";
             choice adjsid-type {
               case case_1 {
                 container index {
                   description "Adjacency SID indexed from SRGB";
                   leaf index-number {
                     type union {
                       type string {
                         pattern "<.*>|$.*";
                       }
                       type uint32 {
                         range "0 .. 199999";
                       }
                     }
                   }
                 }
               }
               case case_2 {
                 leaf label {
                   description "Adjacency SID from static label pool";
                   type union {
                     type string {
                       pattern "<.*>|$.*";
                     }
                     type uint32 {
                       range "16 .. 1048575";
                     }
                   }
                 }
               }
               case case_3 {
                 leaf dynamic {
                   description "Dynamically allocate an adjacency segment";
                   type empty;
                 }
               }
             }
           }
         }
         container srm6-adjacency-segment {
           description "Configure srm6 adjacency segment";
           uses apply-advanced;
           container unprotected {
             description "Adjacency SID uneligible for protection";
             leaf sid {
               description "Set Adjacency SID Value";
               type union {
                 type string {
                   pattern "<.*>|$.*";
                 }
                 type uint32 {
                   range "1 .. 65535";
                 }
               }
             }
           }
         }
         list topology {
           key name;
           ordered-by user;
           description "Topology specific attributes";
           leaf name {
             description "Topology name";
             type enumeration {
               enum "default" {
                 description "Default topology";
               }
               enum "ipv4-multicast" {
                 description "IPv4 multicast topology";
               }
               enum "ipv6-unicast" {
                 description "IPv6 unicast topology";
               }
               enum "ipv6-multicast" {
                 description "IPv6 multicast topology";
               }
             }
           }
           uses apply-advanced;
           leaf metric {
             description "Topology metric";
             type union {
               type string {
                 pattern "<.*>|$.*";
               }
               type uint32 {
                 range "0 .. 16777215";
               }
             }
           }
           container bandwidth-based-metrics {
             junos:must "(\".. metric\")";
             junos:must-message "Metric must be configured";
             description "Configure bandwidth based metrics";
             uses apply-advanced;
             list bandwidth {
               key name;
               description "Bandwidth threshold";
               leaf name {
                 type string;
               }
               leaf metric {
                 description "Metric associated with specified bandwidth";
                 type union {
                   type string {
                     pattern "<.*>|$.*";
                   }
                   type uint32 {
                     range "0 .. 16777215";
                   }
                 }
               }
             }
           }
         }
       }
       container link-group-protection {
         junos:must "(!(\".. .. backup-spf-options\"))";
         junos:must-message "Backup SPF options can't be configured";
         description "Configure link group protection";
         uses apply-advanced;
         leaf minimum-bandwidth {
           description "Minimum bandwidth to carry traffic";
           type string;
         }
         leaf revert-bandwidth {
           description "Revert bandwidth to carry traffic";
           type string;
         }
       }
       list interface {
         key name;
         description "List interfaces for this group";
         leaf name {
           description "Interface name";
           type union {
             type jt:interface-name;
             type string {
               pattern "<.*>|$.*";
             }
           }
         }
         uses apply-advanced;
         leaf weight {
           description "Interface weight for adjacency set";
           type union {
             type string {
               pattern "<.*>|$.*";
             }
             type uint32 {
               range "1 .. 255";
             }
           }
         }
       }
     }
     container spf-options {
       description "Configure SPF attributes";
       uses apply-advanced;
       container microloop-avoidance {
         description "Configure microloop avoidance mechanisms";
         uses apply-advanced;
         container post-convergence-path {
           presence "enable post-convergence-path";
           junos:must "(\".. .. .. source-packet-routing\")";
           junos:must-message "Please configure source-packet-routing under isis/isis-instance";
           junos:must "(!(\".. use-route-convergence-delay\"))";
           junos:must-message "use-route-convergence-delay is not allowed with post-convergence-path";
           description "Temporarily install post-convergence path for routes potentially affected by microloops";
           uses apply-advanced;
           leaf delay {
             description "Time after which temporary post-convergence paths are removed";
             units "milliseconds";
             type union {
               type string {
                 pattern "<.*>|$.*";
               }
               type uint32 {
                 range "500 .. 60000";
               }
             }
           }
           leaf maximum-labels {
             description "Set maximum number of label supported for Micro-Loop-Avoidance calculations";
             type union {
               type string {
                 pattern "<.*>|$.*";
               }
               type uint32 {
                 range "2 .. 8";
               }
             }
           }
           leaf maximum-srv6-sids {
             description "Set maximum number of SRV6 SIDs supported for Micro-Loop-Avoidance calculations";
             type union {
               type string {
                 pattern "<.*>|$.*";
               }
               type uint32 {
                 range "2 .. 6";
               }
             }
           }
         }
       }
       leaf delay {
         description "Time to wait before running an SPF";
         units "milliseconds";
         type union {
           type string {
             pattern "<.*>|$.*";
           }
           type uint32 {
             range "50 .. 1000";
           }
         }
       }
       leaf holddown {
         description "Time to hold down before running an SPF";
         units "milliseconds";
         type union {
           type string {
             pattern "<.*>|$.*";
           }
           type uint32 {
             range "2000 .. 10000";
           }
         }
       }
       leaf rapid-runs {
         description "Number of rapid SPF runs before SPF holddown";
         type union {
           type string {
             pattern "<.*>|$.*";
           }
           type uint32 {
             range "1 .. 5";
           }
         }
       }
       container multipath {
         description "Configure multipath options";
         uses apply-advanced;
         container weighted {
           description "Weighted multipath options";
           uses apply-advanced;
           leaf one-hop {
             description "Enable load balancing on onehop multipath based on interface bandwidth";
             type empty;
           }
         }
       }
     }
     container traceoptions {
       description "Trace options for IS-IS";
       uses apply-advanced;
       list flag {
         key name;
         ordered-by user;
         description "Tracing parameters";
         leaf name {
           type enumeration {
             enum "traffic-statistics" {
               description "Trace traffic-statistics related events";
             }
             enum "post-convergence-lfa" {
               description "Trace post-convergence-lfa related events";
             }
             enum "error" {
               description "Trace errored packets";
             }
             enum "spf" {
               description "Trace SPF events";
             }
             enum "packets" {
               description "Trace IS-IS packets";
             }
             enum "hello" {
               description "Trace hello packets";
             }
             enum "lsp" {
               description "Trace link-state packets";
             }
             enum "psn" {
               description "Trace partial sequence number (PSN) packets";
             }
             enum "csn" {
               description "Trace complete sequence number (CSN) packets";
             }
             enum "layer2-map" {
               description "Trace ARP/ND kernel state manipulation";
             }
             enum "lsp-generation" {
               description "Trace LSP generation";
             }
             enum "graceful-restart" {
               description "Trace graceful restart events";
             }
             enum "ldp-synchronization" {
               description "Trace synchronization between IS-IS and LDP";
             }
             enum "nsr-synchronization" {
               description "Trace NSR synchronization events";
             }
             enum "spring" {
               description "Trace source packet routing";
             }
             enum "prefix-sid" {
               description "Trace source packet routing, prefix-sids";
             }
             enum "flex-algorithm" {
               description "Trace flex-algorithm related events";
             }
             enum "adj-sid" {
               description "Trace adj-sid related events";
             }
             enum "route" {
               description "Trace routing information";
             }
             enum "normal" {
               description "Trace normal events";
             }
             enum "general" {
               description "Trace general events";
             }
             enum "state" {
               description "Trace state transitions";
             }
             enum "policy" {
               description "Trace policy processing";
             }
             enum "task" {
               description "Trace routing protocol task processing";
             }
             enum "timer" {
               description "Trace routing protocol timer processing";
             }
             enum "srv6" {
               description "Trace srv6 related events";
             }
             enum "rmopd" {
               description "Trace rmopd interactions";
             }
             enum "mapping-server" {
               description "Trace mapping server related events";
             }
             enum "all" {
               description "Trace everything";
             }
           }
         }
         leaf send {
           description "Trace transmitted packets";
           type empty;
         }
         leaf receive {
           description "Trace received packets";
           type empty;
         }
         leaf detail {
           description "Trace detailed information";
           type empty;
         }
         leaf disable {
           description "Disable this trace flag";
           type empty;
         }
       }
       container file {
         description "Trace file options";
         leaf filename {
           description "Name of file in which to write trace information";
           type string {
             length "1 .. 1024";
             junos:posix-pattern "![/ %]";
             junos:pattern-message "Must not contain '/', % or a space";
           }
         }
         leaf replace {
           description "Replace trace file rather than appending to it";
           status deprecated;
           type empty;
         }
         leaf size {
           description "Maximum trace file size";
           type string;
         }
         leaf files {
           description "Maximum number of trace files";
           default "10";
           type union {
             type string {
               pattern "<.*>|$.*";
             }
             type uint32 {
               range "2 .. 1000";
             }
           }
         }
         leaf no-stamp {
           description "Do not timestamp trace file";
           status deprecated;
           type empty;
         }
         choice world-readable-choice {
           leaf world-readable {
             description "Allow any user to read the log file";
             type empty;
           }
           leaf no-world-readable {
             description "Don't allow any user to read the log file";
             type empty;
           }
         }
       }
     }
     container backup-spf-options {
       description "Configure backup SPF attributes";
       uses apply-advanced;
       container remote-backup-calculation {
         presence "enable remote-backup-calculation";
         junos:must "(!(\".. .. backup-spf-options use-post-convergence-lfa\"))";
         junos:must-message "Not allowed with 'protocols isis backup-spf-options use-post-convergence-lfa'";
         description "Calculate Remote LFA backup nexthops";
         uses apply-advanced;
       }
       container use-post-convergence-lfa {
         presence "enable use-post-convergence-lfa";
         junos:must "(\".. .. source-packet-routing\")";
         junos:must-message "Configuration of 'protocols isis source-packet-routing' is must";
         description "Calculate Post Convergence Backup Nexthops";
         uses apply-advanced;
         leaf maximum-labels {
           description "Set maximum number of label supported for post convergence path calculations";
           type union {
             type string {
               pattern "<.*>|$.*";
             }
             type uint32 {
               range "2 .. 8";
             }
           }
         }
         leaf maximum-srv6-sids {
           description "Set maximum number of SRV6 SIDs for post convergence path calculations";
           type union {
             type string {
               pattern "<.*>|$.*";
             }
             type uint32 {
               range "2 .. 6";
             }
           }
         }
         leaf maximum-backup-paths {
           description "Set maximum equal cost backup post convergence paths";
           type union {
             type string {
               pattern "<.*>|$.*";
             }
             type uint32 {
               range "1 .. 8";
             }
           }
         }
       }
       container use-source-packet-routing {
         presence "enable use-source-packet-routing";
         junos:must "(\".. .. source-packet-routing\")";
         junos:must-message "Use of SPRING paths as backup can't be configured without configuring 'protocols isis source-packet-routing'";
         description "Use SPRING routed paths for protection";
         uses apply-advanced;
       }
       leaf per-prefix-calculation {
         description "Calculate backup nexthops for non-best prefix originators";
         type empty;
       }
       leaf node-link-degradation {
         description "Degrade to link protection when nodelink protection not available";
         junos:must "(!(\".. .. backup-spf-options use-post-convergence-lfa\"))";
         junos:must-message "Not allowed with 'protocols isis backup-spf-options use-post-convergence-lfa'";
         type empty;
       }
     }
     list context-identifier {
       key name;
       ordered-by user;
       description "Configuration for advertisement of a context-identifier ";
       leaf name {
         description "Context identifier range";
         type jt:ipprefix;
       }
       uses apply-advanced;
       list level {
         key name;
         ordered-by user;
         description "Configure global level attributes";
         leaf name {
           description "IS-IS level number";
           type union {
             type string {
               pattern "<.*>|$.*";
             }
             type uint32 {
               range "1 .. 2";
             }
           }
         }
         uses apply-advanced;
         choice enable-disable {
           case case_1 {
             leaf disable {
               description "Disable advertisements to this level";
               type empty;
             }
           }
         }
       }
     }
     container traffic-engineering {
       description "Configure traffic engineering attributes";
       uses apply-advanced;
       choice enable-disable {
         case case_1 {
           leaf disable {
             description "Disable traffic engineering";
             type empty;
           }
         }
       }
       leaf l3-unicast-topology {
         description "Download IGP topology into TED";
         type empty;
       }
       leaf ipv6 {
         description "Enable TEDv6";
         type empty;
       }
       leaf credibility-protocol-preference {
         description "Follow IGP protocol preference for TED protocol credibility";
         type empty;
       }
       leaf ipv4-multicast-rpf-routes {
         description "Install IPv4 routes for multicast RPF checks into inet.2";
         status deprecated;
         junos:must "(!(\".. .. topologies ipv4-multicast\"))";
         junos:must-message "ipv4-multicast-rpf-routes cannot be used with the ipv4-multicast topology";
         junos:must "(!(\".. .. multicast-topology\"))";
         junos:must-message "ipv4-multicast-rpf-routes cannot be used with multicast-topology";
         junos:must "(\".. shortcuts\")";
         junos:must-message "ipv4-multicast-rpf-routes cannot be used without shortcuts";
         type empty;
       }
       leaf ignore-lsp-metrics {
         description "Ignore label-switched path metrics when doing shortcuts";
         type empty;
       }
       container tunnel-source-protocol {
         description "Protocols from which to pick label-switched paths";
         uses apply-advanced;
         container rsvp {
           presence "enable rsvp";
           description "Pick label-switched paths from rsvp";
           uses apply-advanced;
           leaf preference {
             description "Preference for label-switched paths from this protocol";
             type union {
               type string {
                 pattern "<.*>|$.*";
               }
               type uint32 {
                 range "1 .. 255";
               }
             }
           }
         }
         container spring-te {
           presence "enable spring-te";
           description "Pick label-switched paths from spring-te";
           uses apply-advanced;
           leaf preference {
             description "Preference for label-switched paths from this protocol";
             type union {
               type string {
                 pattern "<.*>|$.*";
               }
               type uint32 {
                 range "1 .. 255";
               }
             }
           }
         }
       }
       list family {
         key name;
         ordered-by user;
         description "Address family specific traffic-engineering attributes";
         leaf name {
           type enumeration {
             enum "inet" {
               description "IPv4 family";
             }
             enum "inet6" {
               description "IPv6 family";
             }
             enum "inet-mpls" {
               description "IPv4-MPLS family";
             }
             enum "inet6-mpls" {
               description "IPv6-MPLS family";
             }
           }
         }
         uses apply-advanced;
         container shortcuts {
           presence "enable shortcuts";
           junos:must "(!(\".. .. no-ldp-shortcuts\"))";
           junos:must-message "Shortcuts configuration cannot be used with no-ldp-shortcuts";
           junos:must "(!(\".. .. shortcuts\"))";
           junos:must-message "per-family shortcuts configuration cannot be used with global shortcuts enabled";
           junos:must "(!(\".. .. disable\"))";
           junos:must-message "shortcuts cannot be used without traffic-engineering enabled";
           description "Use label-switched paths as next hops, if possible";
           uses apply-advanced;
           leaf multicast-rpf-routes {
             description "Install routes for multicast RPF checks into multicast RIB";
             junos:must "(!(\".. .. .. .. multicast-topology\"))";
             junos:must-message "ipv4 multicast-rpf-routes cannot be used with the multicast-topology";
             junos:must "(!(\".. .. .. .. topologies ipv4-multicast\"))";
             junos:must-message "ipv4 multicast-rpf-routes cannot be used with the ipv4-multicast topology";
             type empty;
           }
           leaf-list import {
             ordered-by user;
             description "Import policy for shortcut";
             type jt:policy-algebra;
           }
         }
       }
       container shortcuts {
         presence "enable shortcuts";
         description "Use label-switched paths as next hops, if possible";
         status deprecated;
         uses apply-advanced;
         leaf ignore-lsp-metrics {
           description "Ignore label-switched path metrics when doing shortcuts";
           status deprecated;
           type empty;
         }
       }
       container multipath {
         description "Configure label-switched-path multipath behavior";
         uses apply-advanced;
         leaf lsp-equal-cost {
           description "Include equal cost label-switched-paths";
           junos:must "((\".. .. shortcuts\" || (\".. .. family $$={inet} shortcuts\" || (\".. .. family $$={inet6} shortcuts\" || \".. .. family $$={iso} shortcuts\"))))";
           junos:must-message "Traffic engineering shortcuts for inet, inet6 or iso family must be configured.";
           type empty;
         }
       }
       container advertisement {
         description "Configure traffic engineering attribute advertisements";
         uses apply-advanced;
         leaf always {
           description "Advertise applicable legacy TE attributes always";
           type empty;
         }
         container application-specific {
           description "Advertise application-specific TE attributes";
           uses apply-advanced;
           container all-applications {
             presence "enable all-applications";
             description "Advertise common application-specific link attributes";
             uses apply-advanced;
             leaf legacy {
               description "Use legacy TE attributes for this application";
               type empty;
             }
           }
         }
       }
     }
     list label-switched-path {
       key name;
       ordered-by user;
       description "Configuration for advertisement of a label-switched path";
       junos:must "(!(\".. traffic-engineering ipv4-multicast-rpf-routes\"))";
       junos:must-message "cannot advertise LSPs when using ipv4-multicast-rpf-routes";
       leaf name {
         description "Name of label-switched path to be advertised";
         type string {
           length "1 .. 64";
         }
       }
       uses apply-advanced;
       list level {
         key name;
         ordered-by user;
         description "Configure global level attributes";
         leaf name {
           description "IS-IS level number";
           type union {
             type string {
               pattern "<.*>|$.*";
             }
             type uint32 {
               range "1 .. 2";
             }
           }
         }
         uses apply-advanced;
         choice enable-disable {
           case case_1 {
             leaf disable {
               description "Disable advertisements to this level";
               type empty;
             }
           }
         }
         leaf metric {
           description "SPF metric for this level";
           type union {
             type string {
               pattern "<.*>|$.*";
             }
             type uint32 {
               range "0 .. 16777215";
             }
           }
         }
       }
     }
     choice enable-disable {
       case case_1 {
         leaf disable {
           description "Disable IS-IS";
           type empty;
         }
       }
     }
     leaf-list export {
       ordered-by user;
       description "Export policy";
       type jt:policy-algebra;
     }
     leaf-list import {
       ordered-by user;
       description "Import policy";
       type jt:policy-algebra;
     }
     leaf reference-bandwidth {
       description "Bandwidth for calculating metric defaults";
       type string;
     }
     choice layer2-map-choice {
       leaf layer2-map {
         description "Kernel ARP/ND creation for nexthops";
         type empty;
       }
       leaf no-layer2-map {
         description "Don't kernel ARP/ND creation for nexthops";
         type empty;
       }
     }
     leaf job-stats {
       description "Collect job statistics";
       type empty;
     }
     leaf lsp-lifetime {
       description "Lifetime of LSPs";
       units "seconds";
       type union {
         type string {
           pattern "<.*>|$.*";
         }
         type uint32 {
           range "350 .. 65535";
         }
       }
     }
     leaf max-lsp-size {
       description "Maximum size allowed for LSPs";
       default "1492";
       type union {
         type string {
           pattern "<.*>|$.*";
         }
         type uint32 {
           range "512 .. 1492";
         }
       }
     }
     leaf max-hello-size {
       description "Maximum size allowed for ISIS Hello PDUs";
       default "1492";
       type union {
         type string {
           pattern "<.*>|$.*";
         }
         type uint32 {
           range "512 .. 16000";
         }
       }
     }
     leaf max-snp-size {
       description "Maximum size allowed for Sequence Number (Complete/Partial) PDUs";
       default "1400";
       type union {
         type string {
           pattern "<.*>|$.*";
         }
         type uint32 {
           range "512 .. 1400";
         }
       }
     }
     leaf spf-delay {
       description "Time to wait before running an SPF";
       status deprecated;
       units "milliseconds";
       junos:must "(!(\".. spf-options delay\"))";
       junos:must-message "You can only configure either spf-delay or delay under spf-options";
       type union {
         type string {
           pattern "<.*>|$.*";
         }
         type uint32 {
           range "50 .. 120000";
         }
       }
     }
     leaf authentication-key {
       description "Authentication key (password)";
       status deprecated;
       type jt:unreadable;
     }
     leaf authentication-type {
       description "Authentication type";
       status deprecated;
       type enumeration {
         enum "md5" {
           description "MD5 authentication";
           status deprecated;
         }
         enum "simple" {
           description "Simple password authentication";
           status deprecated;
         }
       }
     }
     leaf loose-authentication-check {
       description "Verify authentication only if PDU has authentication TLV";
       type empty;
     }
     leaf max-areas {
       description "Maximum number of advertised Areas";
       default "3";
       type union {
         type string {
           pattern "<.*>|$.*";
         }
         type uint32 {
           range "3 .. 36";
         }
       }
     }
     leaf no-authentication-check {
       description "Disable authentication checking";
       type empty;
     }
     leaf no-ipv4-routing {
       description "Disable IPv4 routing";
       type empty;
     }
     leaf no-ipv6-routing {
       description "Disable IPv6 routing";
       type empty;
     }
     leaf clns-routing {
       description "Enable CLNS routing";
       type empty;
     }
     leaf clns-updown-compatibility {
       description "Set the Up/Down Bit in place of the I/E bit in CLNS TLVs";
       type empty;
     }
     leaf no-adjacency-holddown {
       description "Disable adjacency hold down";
       type empty;
     }
     leaf multicast-topology {
       description "Enable multicast topology";
       status deprecated;
       type empty;
     }
     leaf ignore-attached-bit {
       description "Ignore the attached bit in Level 1 LSPs";
       type empty;
     }
     container rib-group {
       description "Routing table group for importing IS-IS routes";
       uses rib_group_type;
     }
     container strict-dual-isis {
       presence "enable strict-dual-isis";
       junos:must "(!(\".. topologies\"))";
       junos:must-message "strict-dual-isis is not allowed with multi-topologies";
       description "Enable dual isis if spf computation is required for both ipv4 and ipv6 family";
       uses apply-advanced;
       leaf holdown {
         description "Time to wait for ipv4 and ipv6 connectivity";
         status deprecated;
         default "12";
         type union {
           type string {
             pattern "<.*>|$.*";
           }
           type uint32 {
             range "1 .. 65535";
           }
         }
       }
       leaf holddown {
         description "Time to wait for ipv4 and ipv6 connectivity";
         default "12";
         type union {
           type string {
             pattern "<.*>|$.*";
           }
           type uint32 {
             range "1 .. 65535";
           }
         }
       }
     }
     container topologies {
       description "Enable topologies";
       uses apply-advanced;
       leaf ipv4-multicast {
         description "Enable IPv4-multicast topology";
         type empty;
       }
       leaf ipv6-unicast {
         description "Enable IPv6-unicast topology";
         type empty;
       }
       leaf ipv6-multicast {
         description "Enable IPv6-multicast topology";
         type empty;
       }
     }
     container overload {
       presence "enable overload";
       description "Set the overload bit (no transit traffic)";
       uses apply-advanced;
       leaf timeout {
         description "Time after which overload bit is reset";
         units "seconds";
         type union {
           type string {
             pattern "<.*>|$.*";
           }
           type uint32 {
             range "60 .. 3600";
           }
         }
       }
       leaf advertise-high-metrics {
         description "Advertise high metrics instead of setting the overload bit";
         type empty;
       }
       leaf allow-route-leaking {
         description "Allow routes to be leaked when overload is configured";
         type empty;
       }
       leaf internal-prefixes {
         description "Allow internal prefixes to be advertised with high metric";
         type empty;
       }
       leaf external-prefixes {
         description "Allow external prefixes to be advertised with high metric";
         type empty;
       }
     }
     container graceful-restart {
       description "IS-IS graceful restart options";
       choice enable-disable {
         case case_1 {
           leaf disable {
             description "Disable graceful restart";
             type empty;
           }
         }
       }
       leaf helper-disable {
         description "Disable graceful restart helper capability";
         type empty;
       }
       leaf restart-duration {
         description "Maximum time for graceful restart to finish";
         units "seconds";
         type union {
           type string {
             pattern "<.*>|$.*";
           }
           type uint32 {
             range "30 .. 300";
           }
         }
       }
     }
   }
   grouping juniper-protocols-l2vpn {
     description "Layer 2 VPN, VPLS or EVPN configuration";
     uses apply-advanced;
     leaf bum-hashing {
       description "Enable BUM hashing feature in the instance";
       junos:must "(!((\".. .. .. protocols vpls\" && \".. .. ..  instance-type virtual-switch\")))";
       junos:must-message "Bum-hashing knob is only applicable for instance type vpls";
       type empty;
     }
     leaf enable-mac-move-action {
       description "Enable VPLS loop prevention feature in the instance";
       type empty;
     }
     leaf mac-pinning {
       description "Enable MAC pinning";
       junos:must "((\".. .. .. protocols vpls\" || \".. pbb-evpn-core\"))";
       junos:must-message "mac-pinning is allowed in VPLS or PBB EVPN instance";
       type empty;
     }
     container mac-table-size {
       junos:must "(!(((\".. .. .. protocols vpls\" || \".. .. .. protocols evpn\") && \".. .. ..  instance-type virtual-switch\")))";
       junos:must-message "mac-table-size needs to be specified under switch-options for a virtual-switch instance";
       description "Size of MAC address forwarding table";
       uses apply-advanced;
       leaf limit {
         description "Maximum number of MAC addresses";
         type union {
           type string {
             pattern "<.*>|$.*";
           }
           type uint32;
         }
       }
       leaf packet-action {
         description "Action when MAC limit is reached";
         type enumeration {
           enum "none" {
             description "Forward the packet";
           }
           enum "drop" {
             description "Drop packets and do not learn. Default is forward";
           }
         }
       }
     }
     container mac-ip-table-size {
       junos:must "(!(((\".. .. .. protocols vpls\" || \".. .. .. protocols evpn\") && \".. .. ..  instance-type virtual-switch\")))";
       junos:must-message "mac-ip-table-size needs to be specified under switch-options for a virtual-switch instance";
       description "Size of MAC+IP bindings table";
       uses apply-advanced;
       leaf limit {
         description "Maximum number of MAC+IP bindings";
         type union {
           type string {
             pattern "<.*>|$.*";
           }
           type uint32;
         }
       }
     }
     container interface-mac-limit {
       junos:must "(!(((\".. .. .. protocols vpls\" || \".. .. .. protocols evpn\") && \".. .. ..  instance-type virtual-switch\")))";
       junos:must-message "interface-mac-limit needs to be specified under switch-options for a virtual-switch instance";
       description "Maximum MAC address learned per interface";
       uses apply-advanced;
       leaf limit {
         description "Maximum number of MAC addresses per interface";
         type union {
           type string {
             pattern "<.*>|$.*";
           }
           type uint32;
         }
       }
       leaf packet-action {
         description "Action when MAC limit is reached";
         type enumeration {
           enum "none" {
             description "Forward the packet";
           }
           enum "drop" {
             description "Drop packets and do not learn. Default is forward";
           }
           enum "log" {
             description "Do not drop the packet but generate an alarm, an SNMP trap or a system log entry";
           }
           enum "shutdown" {
             description "Disable the interface and generate an alarm, an SNMP trap or a system log entry";
           }
           enum "drop-and-log" {
             description "Drop the packet and generate an alarm, an SNMP trap or a system log entry";
           }
         }
       }
     }
     container interface-mac-ip-limit {
       junos:must "(!(((\".. .. .. protocols vpls\" || \".. .. .. protocols evpn\") && \".. .. ..  instance-type virtual-switch\")))";
       junos:must-message "interface-mac-ip-limit needs to be specified under switch-options for a virtual-switch instance";
       description "Maximum MAC+IP bindings learned per interface";
       uses apply-advanced;
       leaf limit {
         description "Maximum number of MAC+IP bindings per interface";
         type union {
           type string {
             pattern "<.*>|$.*";
           }
           type uint32;
         }
       }
     }
     container mac-notification {
       presence "enable mac-notification";
       description "MAC notification options";
       uses apply-advanced;
       leaf notification-interval {
         description "Interval for sending MAC notifications";
         default "30";
         units "seconds";
         type union {
           type string {
             pattern "<.*>|$.*";
           }
           type uint32 {
             range "1 .. 60";
           }
         }
       }
     }
     leaf mac-table-aging-time {
       description "Delay for discarding MAC address if no updates are received";
       units "seconds";
       type union {
         type string {
           pattern "<.*>|$.*";
         }
         type uint32;
       }
     }
     leaf no-mac-learning {
       description "Disable dynamic MAC address learning";
       junos:must "(!(((\".. .. .. protocols vpls\" || \".. .. .. protocols evpn\") && \".. .. ..  instance-type virtual-switch\")))";
       junos:must-message "no-mac-learning needs to be specified under switch-options for a virtual-switch instance";
       type empty;
     }
     leaf no-normalization {
       description "Disable vlan id normalization for interfaces";
       type empty;
     }
     leaf mac-statistics {
       description "Enable MAC address statistics";
       junos:must "(!(((\".. .. .. protocols vpls\" || \".. .. .. protocols evpn\") && \".. .. ..  instance-type virtual-switch\")))";
       junos:must-message "mac-statistics needs to be specified under switch-options for a virtual-switch instance";
       type empty;
     }
     container mib {
       presence "enable mib";
       description "Snmp mib options";
       uses apply-advanced;
       container dot1q-mib {
         presence "enable dot1q-mib";
         description "Dot1q MIB configuration options";
         uses apply-advanced;
         leaf port-list {
           description "Port list for staticegressports and staticuntaggedports MIB";
           type enumeration {
             enum "bit-map" {
               description "Port list is represented in bit-map format";
             }
             enum "string" {
               description "Port list is represented in string format";
             }
           }
         }
       }
     }
     container static-rvtep-mac {
       description "Configure Static MAC and remote VxLAN tunnel endpoint entries";
       uses apply-advanced;
       list mac {
         key "mac_addr remote-vtep";
         description "Unicast MAC address";
         leaf mac_addr {
           type jt:mac-unicast;
         }
         leaf remote-vtep {
           description "Configure static remote VXLAN tunnel endpoints";
           type jt:ipaddr;
         }
       }
     }
     list interface {
       key name;
       ordered-by user;
       description "Interface that connect this site to the VPN";
       junos:must "(!(((\".. .. .. protocols vpls\" || \".. .. .. protocols evpn\") && \".. .. ..  instance-type virtual-switch\")))";
       junos:must-message "interface needs to be specified under switch-options for a virtual-switch instance";
       leaf name {
         description "Interface name";
         junos:must "(((\".. .. .. .. protocols evpn flexible-cross-connect-vlan-aware\" || \".. .. .. .. interface $$\") || \"FALSE\"))";
         junos:must-message "Interface must be part of this routing instance";
         junos:must "((\".. .. .. interface $$\" || (\".. .. .. .. .. interface $$\" || (\".. .. .. .. interface $$\" || \"interfaces $$-IFL family ethernet-switching\"))))";
         junos:must-message "Interface must be part of this routing instance";
         type union {
           type jt:interface-name;
           type string {
             pattern "<.*>|$.*";
           }
         }
       }
       uses apply-advanced;
       container interface-mac-limit {
         junos:must "(!(\".. .. .. .. .. vlans ${vlan} private-vlan\"))";
         junos:must-message "Switch-options configuration is not allowed on interfaces which are part of secondary VLANs";
         description "Maximum number of MAC addresses learned on the interface";
         uses apply-advanced;
         leaf limit {
           description "Maximum number of MAC addresses per interface";
           type union {
             type string {
               pattern "<.*>|$.*";
             }
             type uint32;
           }
         }
         leaf disable {
           description "Disable interface for interface-mac-limit";
           type empty;
         }
         leaf packet-action {
           description "Action when MAC limit is reached";
           type enumeration {
             enum "none" {
               description "Forward the packet";
             }
             enum "drop" {
               description "Drop packets and do not learn. Default is forward";
             }
             enum "log" {
               description "Do not drop the packet but generate an alarm, an SNMP trap or a system log entry";
             }
             enum "shutdown" {
               description "Disable the interface and generate an alarm, an SNMP trap or a system log entry";
             }
             enum "drop-and-log" {
               description "Drop the packet and generate an alarm, an SNMP trap or a system log entry";
             }
           }
         }
       }
       leaf action-priority {
         description "Blocking priority of this interface on mac move detection";
         junos:must "(!(\".. .. .. .. .. vlans ${vlan} private-vlan\"))";
         junos:must-message "Switch-options configuration is not allowed on interfaces which are part of secondary VLANs";
         type union {
           type string {
             pattern "<.*>|$.*";
           }
           type uint32 {
             range "0 .. 8";
           }
         }
       }
       list static-mac {
         key name;
         ordered-by user;
         description "Static MAC addresses assigned to this interface";
         junos:must "(!(\".. .. .. .. .. vlans ${vlan} private-vlan\"))";
         junos:must-message "Switch-options configuration is not allowed on interfaces which are part of secondary VLANs";
         leaf name {
           description "MAC address";
           junos:must "((!(\".. .. .. .. .. vlan-id all\") || all \".. vlan-id <*>\"))";
           junos:must-message " Specify vlan-id for qualified learning ";
           type jt:mac-addr;
         }
         uses apply-advanced;
         list vlan-id {
           key name;
           ordered-by user;
           description "VLAN ID of learning VLAN";
           junos:must "(\".. .. .. .. .. vlan-id all\")";
           junos:must-message "'vlan-id all' has to be configured for the bridging domain";
           leaf name {
             description "Learning VLAN";
             type union {
               type string {
                 pattern "<.*>|$.*";
               }
               type uint32 {
                 range "0 .. 4094";
               }
             }
           }
           uses apply-advanced;
         }
       }
       container interface-mac-ip-limit {
         description "Maximum number of MAC+IP bindings learned on the interface";
         uses apply-advanced;
         leaf limit {
           description "Maximum number of MAC+IP bindings per interface";
           type union {
             type string {
               pattern "<.*>|$.*";
             }
             type uint32;
           }
         }
       }
       leaf no-mac-learning {
         description "Disable dynamic MAC address learning";
         junos:must "(!(\".. .. .. .. .. vlans ${vlan} private-vlan\"))";
         junos:must-message "Switch-options configuration is not allowed on interfaces which are part of secondary VLANs";
         type empty;
       }
       leaf mac-pinning {
         description "Enable MAC pinning";
         type empty;
       }
       leaf persistent-learning {
         description "Enable persistent MAC learning on this interface";
         junos:must "(!(\"switch-options mac-table-aging-time \"))";
         junos:must-message "Persistent learning can not co-exist with mac-table-aging-time";
         type empty;
       }
       container vpws-service-id {
         presence "enable vpws-service-id";
         description "Service-id for EVPN VPWS routing instance";
         uses apply-advanced;
         leaf local {
           description "Local EVPN VPWS service id";
           junos:must "(unique \".. .. .. interface <*> vpws-service-id local $$\")";
           junos:must-message "Unique Local SID can only be configured ";
           type union {
             type string {
               pattern "<.*>|$.*";
             }
             type uint32 {
               range "1 .. 16777215";
             }
           }
         }
         leaf remote {
           description "Remote EVPN VPWS service id";
           junos:must "(unique \".. .. .. interface <*> vpws-service-id remote $$\")";
           junos:must-message "Unique Remote SID can only be configured ";
           type union {
             type string {
               pattern "<.*>|$.*";
             }
             type uint32 {
               range "1 .. 16777215";
             }
           }
         }
       }
       leaf flow-label-transmit-static {
         description "Push Flow Label on PW packets sent to remote PE";
         junos:must "(\".. .. .. .. instance-type evpn-vpws\")";
         junos:must-message "Flow-Label static only supported for EVPN-VPWS";
         type empty;
       }
       leaf flow-label-receive-static {
         description "Pop Flow Label from PW packets received from remote PE";
         junos:must "(\".. .. .. .. instance-type evpn-vpws\")";
         junos:must-message "Flow-Label static only supported for EVPN-VPWS";
         type empty;
       }
       leaf protect-interface {
         description "Name of protect interface";
         junos:must "(\"interfaces $$\")";
         junos:must-message "Interface must be part of this routing instance";
         junos:must "(!(\"interfaces ${inter_name} esi\"))";
         junos:must-message "ESI can not be configured for protect interface";
         type union {
           type jt:interface-name;
           type string {
             pattern "<.*>|$.*";
           }
         }
       }
       leaf remote-site-id {
         description "Site identifier associated with this interface";
         junos:must "(!(\".. .. .. .. .. l2vpn-id\"))";
         junos:must-message "Remote site identifier is not valid for FEC 129 VPWS instances";
         type union {
           type string {
             pattern "<.*>|$.*";
           }
           type uint32 {
             range "1 .. 65534";
           }
         }
       }
       leaf target-attachment-identifier {
         description "FEC 129 VPWS target attachment identifier";
         junos:must "(\".. .. source-attachment-identifier\")";
         junos:must-message "Source attachment identifier configuration required for the containing site";
         junos:must "(unique \".. .. interface <*> target-attachment-identifier $$\")";
         junos:must-message "All interface target attachment identifiers must be unique within a site";
         type string {
           junos:posix-pattern "^([[:digit:].]){1,15}$|^([[:digit:]]){0,10}:([[:digit:].]){0,15}:([[:digit:]]){1,10}$";
           junos:pattern-message "
	Use fec129 AII type 1 format with just <AC-ID> or    
	fec129 AII type 2 format <Global-ID>:<Prefix>:<AC-ID> where    
	<Global-ID> is a value between 0..4294967295,    
	<Prefix> is a value between 0..4294967295 or a valid IP address,    
	<AC-ID> is a value between 1..4294967295 (or a valid IP address for AII type 1).    
	e.g. 1, 0.0.0.1, 0:0:1, 1:2:3, 1:2.2.2.2:3, ::1, 1::2, :1:2";
         }
       }
       leaf flow-label-transmit {
         description "Advertise capability to push Flow Label in transmit direction to remote PE";
         junos:must "(\".. .. source-attachment-identifier\")";
         junos:must-message "Source attachment identifier configuration required for the containing site";
         type empty;
       }
       leaf flow-label-receive {
         description "Advertise capability to pop Flow Label in receive direction to remote PE";
         junos:must "(\".. .. source-attachment-identifier\")";
         junos:must-message "Source attachment identifier configuration required for the containing site";
         type empty;
       }
       leaf encapsulation-type {
         description "Encapsulation type for VPN";
         type enumeration {
           enum "atm-aal5" {
             description "ATM AAL/5 encapsulation";
           }
           enum "atm-cell" {
             description "ATM port promiscuous mode cell encapsulation";
           }
           enum "atm-cell-port-mode" {
             description "ATM port promiscuous mode cell encapsulation";
           }
           enum "atm-cell-vp-mode" {
             description "ATM VP promiscuous mode cell encapsulation";
           }
           enum "atm-cell-vc-mode" {
             description "ATM non-promiscuous cell encapsulation";
           }
           enum "frame-relay" {
             description "Frame Relay encapsulation";
           }
           enum "ppp" {
             description "PPP encapsulation";
           }
           enum "cisco-hdlc" {
             description "Cisco-compatible HDLC encapsulation";
           }
           enum "ethernet-vlan" {
             description "Ethernet VLAN encapsulation";
           }
           enum "ethernet" {
             description "Ethernet encapsulation";
           }
           enum "interworking" {
             description "Layer 2.5 interworking VPN";
           }
           enum "frame-relay-port-mode" {
             description "Frame Relay port mode encapsulation";
           }
           enum "satop-t1" {
             description "SATOP-T1 based Layer 2 VPN";
           }
           enum "satop-e1" {
             description "SATOP-E1 based Layer 2 VPN";
           }
           enum "satop-t3" {
             description "SATOP-T3 based Layer 2 VPN";
           }
           enum "satop-e3" {
             description "SATOP-E3 based Layer 2 VPN";
           }
           enum "cesop" {
             description "CESOP based Layer 2 VPN";
           }
         }
       }
       leaf ignore-encapsulation-mismatch {
         description "Allow different encapsulation types on local and remote end";
         type empty;
       }
       leaf mtu {
         description "MTU to be advertised to the remote end";
         type union {
           type string {
             pattern "<.*>|$.*";
           }
           type uint16 {
             range "512 .. 65535";
           }
         }
       }
       leaf ignore-mtu-mismatch {
         description "Allow different MTU values on local and remote end";
         type empty;
       }
       choice cword {
         case case_1 {
           leaf control-word {
             description "Adds control-word to the Layer 2 encapsulation";
             type empty;
           }
         }
         case case_2 {
           leaf no-control-word {
             description "Disables control-word to the Layer 2 encapsulation";
             type empty;
           }
         }
       }
       leaf pseudowire-status-tlv {
         description "Send pseudowire status TLV";
         type empty;
       }
       container oam {
         description "OAM Configuration for VPN";
         uses apply-advanced;
         leaf ping-interval {
           description "Time interval between ping messages";
           default "60";
           units "seconds";
           type union {
             type string {
               pattern "<.*>|$.*";
             }
             type uint16 {
               range "30 .. 3600";
             }
           }
         }
         leaf ping-multiplier {
           description "Number of ping reply missed before declaring BFD down";
           type union {
             type string {
               pattern "<.*>|$.*";
             }
             type uint8 {
               range "1 .. 5";
             }
           }
         }
         container bfd-liveness-detection {
           description "Bidirectional Forwarding Detection (BFD) options";
           uses apply-advanced;
           leaf version {
             description "BFD protocol version number";
             default "automatic";
             type enumeration {
               enum "0" {
                 description "BFD version 0 (deprecated)";
               }
               enum "1" {
                 description "BFD version 1";
               }
               enum "automatic" {
                 description "Choose BFD version automatically";
               }
             }
           }
           leaf minimum-interval {
             description "Minimum transmit and receive interval";
             units "milliseconds";
             type union {
               type string {
                 pattern "<.*>|$.*";
               }
               type uint32 {
                 range "1 .. 255000";
               }
             }
           }
           leaf minimum-transmit-interval {
             description "Minimum transmit interval";
             status deprecated;
             units "milliseconds";
             type union {
               type string {
                 pattern "<.*>|$.*";
               }
               type uint32 {
                 range "1 .. 255000";
               }
             }
           }
           leaf minimum-receive-interval {
             description "Minimum receive interval";
             units "milliseconds";
             type union {
               type string {
                 pattern "<.*>|$.*";
               }
               type uint32 {
                 range "1 .. 255000";
               }
             }
           }
           leaf multiplier {
             description "Detection time multiplier";
             default "3";
             type union {
               type string {
                 pattern "<.*>|$.*";
               }
               type uint32 {
                 range "1 .. 255";
               }
             }
           }
           choice adaptation-choice {
             case case_1 {
               leaf no-adaptation {
                 description "Disable adaptation";
                 type empty;
               }
             }
           }
           container transmit-interval {
             description "Transmit-interval options";
             uses apply-advanced;
             leaf minimum-interval {
               description "Minimum transmit interval";
               units "milliseconds";
               type union {
                 type string {
                   pattern "<.*>|$.*";
                 }
                 type uint32 {
                   range "1 .. 255000";
                 }
               }
             }
             leaf threshold {
               description "High transmit interval triggering a trap";
               units "milliseconds";
               type union {
                 type uint32;
                 type string {
                   pattern "<.*>|$.*";
                 }
               }
             }
           }
           container detection-time {
             description "Detection-time options";
             uses apply-advanced;
             leaf threshold {
               description "High detection-time triggering a trap";
               units "milliseconds";
               type union {
                 type uint32;
                 type string {
                   pattern "<.*>|$.*";
                 }
               }
             }
           }
         }
       }
       leaf community {
         description "Community associated with this interface";
         type string;
       }
       leaf description {
         description "Text description";
         type string;
       }
     }
     list site {
       key name;
       ordered-by user;
       description "Sites connected to this provider equipment";
       leaf name {
         description "Name of Layer 2 VPN or VPLS site";
         type string;
       }
       uses apply-advanced;
       leaf mac-pinning {
         description "Enable MAC pinning";
         type empty;
       }
       list mesh-group {
         key name;
         ordered-by user;
         description "Mesh-groups that are part of this site";
         leaf name {
           description "Mesh-group name";
           junos:must "(\".. .. .. mesh-group $$\")";
           junos:must-message "Mesh-group must be configured to associate with a site";
           type string;
         }
         uses apply-advanced;
       }
       list interface {
         key name;
         ordered-by user;
         description "Interface that connect this site to the VPN";
         junos:must "(!(!((\".. .. .. .. protocols vpls\" || \".. .. .. .. protocols l2vpn\"))))";
         junos:must-message "interface needs to be specified under switch-options for a virtual-switch instance";
         leaf name {
           description "Interface name";
           junos:must "((\".. .. .. .. .. interface $$\" || any \".. .. .. .. .. bridge-domains <*> interface $$\"))";
           junos:must-message "Interface must be part of this routing instance";
           junos:must "((\".. .. .. interface $$\" || (\".. .. .. .. .. interface $$\" || (\".. .. .. .. interface $$\" || \"interfaces $$-IFL family ethernet-switching\"))))";
           junos:must-message "Interface must be part of this routing instance";
           type union {
             type jt:interface-name;
             type string {
               pattern "<.*>|$.*";
             }
           }
         }
         uses apply-advanced;
         container interface-mac-limit {
           junos:must "(!(\".. .. .. .. .. vlans ${vlan} private-vlan\"))";
           junos:must-message "Switch-options configuration is not allowed on interfaces which are part of secondary VLANs";
           description "Maximum number of MAC addresses learned on the interface";
           uses apply-advanced;
           leaf limit {
             description "Maximum number of MAC addresses per interface";
             type union {
               type string {
                 pattern "<.*>|$.*";
               }
               type uint32;
             }
           }
           leaf disable {
             description "Disable interface for interface-mac-limit";
             type empty;
           }
           leaf packet-action {
             description "Action when MAC limit is reached";
             type enumeration {
               enum "none" {
                 description "Forward the packet";
               }
               enum "drop" {
                 description "Drop packets and do not learn. Default is forward";
               }
               enum "log" {
                 description "Do not drop the packet but generate an alarm, an SNMP trap or a system log entry";
               }
               enum "shutdown" {
                 description "Disable the interface and generate an alarm, an SNMP trap or a system log entry";
               }
               enum "drop-and-log" {
                 description "Drop the packet and generate an alarm, an SNMP trap or a system log entry";
               }
             }
           }
         }
         leaf action-priority {
           description "Blocking priority of this interface on mac move detection";
           junos:must "(!(\".. .. .. .. .. vlans ${vlan} private-vlan\"))";
           junos:must-message "Switch-options configuration is not allowed on interfaces which are part of secondary VLANs";
           type union {
             type string {
               pattern "<.*>|$.*";
             }
             type uint32 {
               range "0 .. 8";
             }
           }
         }
         list static-mac {
           key name;
           ordered-by user;
           description "Static MAC addresses assigned to this interface";
           junos:must "(!(\".. .. .. .. .. vlans ${vlan} private-vlan\"))";
           junos:must-message "Switch-options configuration is not allowed on interfaces which are part of secondary VLANs";
           leaf name {
             description "MAC address";
             junos:must "((!(\".. .. .. .. .. .. vlan-id all\") || all \".. vlan-id <*>\"))";
             junos:must-message " Specify vlan-id for qualified learning ";
             type jt:mac-addr;
           }
           uses apply-advanced;
           list vlan-id {
             key name;
             ordered-by user;
             description "VLAN ID of learning VLAN";
             junos:must "(\".. .. .. .. .. .. vlan-id all\")";
             junos:must-message "'vlan-id all' has to be configured for the bridging domain";
             leaf name {
               description "Learning VLAN";
               type union {
                 type string {
                   pattern "<.*>|$.*";
                 }
                 type uint32 {
                   range "0 .. 4094";
                 }
               }
             }
             uses apply-advanced;
           }
         }
         container interface-mac-ip-limit {
           description "Maximum number of MAC+IP bindings learned on the interface";
           uses apply-advanced;
           leaf limit {
             description "Maximum number of MAC+IP bindings per interface";
             type union {
               type string {
                 pattern "<.*>|$.*";
               }
               type uint32;
             }
           }
         }
         leaf no-mac-learning {
           description "Disable dynamic MAC address learning";
           junos:must "(!(\".. .. .. .. .. vlans ${vlan} private-vlan\"))";
           junos:must-message "Switch-options configuration is not allowed on interfaces which are part of secondary VLANs";
           type empty;
         }
         leaf mac-pinning {
           description "Enable MAC pinning";
           type empty;
         }
         leaf persistent-learning {
           description "Enable persistent MAC learning on this interface";
           junos:must "(!(\"switch-options mac-table-aging-time \"))";
           junos:must-message "Persistent learning can not co-exist with mac-table-aging-time";
           type empty;
         }
         leaf remote-site-id {
           description "Site identifier associated with this interface";
           junos:must "(!(\".. .. .. .. .. l2vpn-id\"))";
           junos:must-message "Remote site identifier is not valid for FEC 129 VPWS instances";
           type union {
             type string {
               pattern "<.*>|$.*";
             }
             type uint32 {
               range "1 .. 65534";
             }
           }
         }
         leaf target-attachment-identifier {
           description "FEC 129 VPWS target attachment identifier";
           junos:must "(\".. .. source-attachment-identifier\")";
           junos:must-message "Source attachment identifier configuration required for the containing site";
           junos:must "(unique \".. .. interface <*> target-attachment-identifier $$\")";
           junos:must-message "All interface target attachment identifiers must be unique within a site";
           type string {
             junos:posix-pattern "^([[:digit:].]){1,15}$|^([[:digit:]]){0,10}:([[:digit:].]){0,15}:([[:digit:]]){1,10}$";
             junos:pattern-message "
	Use fec129 AII type 1 format with just <AC-ID> or    
	fec129 AII type 2 format <Global-ID>:<Prefix>:<AC-ID> where    
	<Global-ID> is a value between 0..4294967295,    
	<Prefix> is a value between 0..4294967295 or a valid IP address,    
	<AC-ID> is a value between 1..4294967295 (or a valid IP address for AII type 1).    
	e.g. 1, 0.0.0.1, 0:0:1, 1:2:3, 1:2.2.2.2:3, ::1, 1::2, :1:2";
           }
         }
         leaf flow-label-transmit {
           description "Advertise capability to push Flow Label in transmit direction to remote PE";
           junos:must "(\".. .. source-attachment-identifier\")";
           junos:must-message "Source attachment identifier configuration required for the containing site";
           type empty;
         }
         leaf flow-label-receive {
           description "Advertise capability to pop Flow Label in receive direction to remote PE";
           junos:must "(\".. .. source-attachment-identifier\")";
           junos:must-message "Source attachment identifier configuration required for the containing site";
           type empty;
         }
         leaf encapsulation-type {
           description "Encapsulation type for VPN";
           type enumeration {
             enum "atm-aal5" {
               description "ATM AAL/5 encapsulation";
             }
             enum "atm-cell" {
               description "ATM port promiscuous mode cell encapsulation";
             }
             enum "atm-cell-port-mode" {
               description "ATM port promiscuous mode cell encapsulation";
             }
             enum "atm-cell-vp-mode" {
               description "ATM VP promiscuous mode cell encapsulation";
             }
             enum "atm-cell-vc-mode" {
               description "ATM non-promiscuous cell encapsulation";
             }
             enum "frame-relay" {
               description "Frame Relay encapsulation";
             }
             enum "ppp" {
               description "PPP encapsulation";
             }
             enum "cisco-hdlc" {
               description "Cisco-compatible HDLC encapsulation";
             }
             enum "ethernet-vlan" {
               description "Ethernet VLAN encapsulation";
             }
             enum "ethernet" {
               description "Ethernet encapsulation";
             }
             enum "interworking" {
               description "Layer 2.5 interworking VPN";
             }
             enum "frame-relay-port-mode" {
               description "Frame Relay port mode encapsulation";
             }
             enum "satop-t1" {
               description "SATOP-T1 based Layer 2 VPN";
             }
             enum "satop-e1" {
               description "SATOP-E1 based Layer 2 VPN";
             }
             enum "satop-t3" {
               description "SATOP-T3 based Layer 2 VPN";
             }
             enum "satop-e3" {
               description "SATOP-E3 based Layer 2 VPN";
             }
             enum "cesop" {
               description "CESOP based Layer 2 VPN";
             }
           }
         }
         leaf ignore-encapsulation-mismatch {
           description "Allow different encapsulation types on local and remote end";
           type empty;
         }
         leaf mtu {
           description "MTU to be advertised to the remote end";
           type union {
             type string {
               pattern "<.*>|$.*";
             }
             type uint16 {
               range "512 .. 65535";
             }
           }
         }
         leaf ignore-mtu-mismatch {
           description "Allow different MTU values on local and remote end";
           type empty;
         }
         choice cword {
           case case_1 {
             leaf control-word {
               description "Adds control-word to the Layer 2 encapsulation";
               type empty;
             }
           }
           case case_2 {
             leaf no-control-word {
               description "Disables control-word to the Layer 2 encapsulation";
               type empty;
             }
           }
         }
         leaf pseudowire-status-tlv {
           description "Send pseudowire status TLV";
           type empty;
         }
         container oam {
           description "OAM Configuration for VPN";
           uses apply-advanced;
           leaf ping-interval {
             description "Time interval between ping messages";
             default "60";
             units "seconds";
             type union {
               type string {
                 pattern "<.*>|$.*";
               }
               type uint16 {
                 range "30 .. 3600";
               }
             }
           }
           leaf ping-multiplier {
             description "Number of ping reply missed before declaring BFD down";
             type union {
               type string {
                 pattern "<.*>|$.*";
               }
               type uint8 {
                 range "1 .. 5";
               }
             }
           }
           container bfd-liveness-detection {
             description "Bidirectional Forwarding Detection (BFD) options";
             uses apply-advanced;
             leaf version {
               description "BFD protocol version number";
               default "automatic";
               type enumeration {
                 enum "0" {
                   description "BFD version 0 (deprecated)";
                 }
                 enum "1" {
                   description "BFD version 1";
                 }
                 enum "automatic" {
                   description "Choose BFD version automatically";
                 }
               }
             }
             leaf minimum-interval {
               description "Minimum transmit and receive interval";
               units "milliseconds";
               type union {
                 type string {
                   pattern "<.*>|$.*";
                 }
                 type uint32 {
                   range "1 .. 255000";
                 }
               }
             }
             leaf minimum-transmit-interval {
               description "Minimum transmit interval";
               status deprecated;
               units "milliseconds";
               type union {
                 type string {
                   pattern "<.*>|$.*";
                 }
                 type uint32 {
                   range "1 .. 255000";
                 }
               }
             }
             leaf minimum-receive-interval {
               description "Minimum receive interval";
               units "milliseconds";
               type union {
                 type string {
                   pattern "<.*>|$.*";
                 }
                 type uint32 {
                   range "1 .. 255000";
                 }
               }
             }
             leaf multiplier {
               description "Detection time multiplier";
               default "3";
               type union {
                 type string {
                   pattern "<.*>|$.*";
                 }
                 type uint32 {
                   range "1 .. 255";
                 }
               }
             }
             choice adaptation-choice {
               case case_1 {
                 leaf no-adaptation {
                   description "Disable adaptation";
                   type empty;
                 }
               }
             }
             container transmit-interval {
               description "Transmit-interval options";
               uses apply-advanced;
               leaf minimum-interval {
                 description "Minimum transmit interval";
                 units "milliseconds";
                 type union {
                   type string {
                     pattern "<.*>|$.*";
                   }
                   type uint32 {
                     range "1 .. 255000";
                   }
                 }
               }
               leaf threshold {
                 description "High transmit interval triggering a trap";
                 units "milliseconds";
                 type union {
                   type uint32;
                   type string {
                     pattern "<.*>|$.*";
                   }
                 }
               }
             }
             container detection-time {
               description "Detection-time options";
               uses apply-advanced;
               leaf threshold {
                 description "High detection-time triggering a trap";
                 units "milliseconds";
                 type union {
                   type uint32;
                   type string {
                     pattern "<.*>|$.*";
                   }
                 }
               }
             }
           }
         }
         leaf community {
           description "Community associated with this interface";
           type string;
         }
         leaf description {
           description "Text description";
           type string;
         }
       }
       choice site-identifier-mode {
         case case_1 {
           leaf site-identifier {
             description "Layer 2 VPN or VPLS site identifier (unique in the VPN)";
             type union {
               type string {
                 pattern "<.*>|$.*";
               }
               type uint32 {
                 range "1 .. 65534";
               }
             }
           }
         }
         case case_2 {
           container automatic-site-id {
             presence "enable automatic-site-id";
             junos:must "(!(\".. .. .. .. protocols l2vpn\"))";
             junos:must-message "Automatic site ID is supported only for VPLS service";
             junos:must "(!(any \".. .. mesh-group <*> peer-as\"))";
             junos:must-message "Automatic site cannot be configured with BGP mesh group";
             description "Enable automatic assignment of site identifier";
             uses apply-advanced;
             leaf startup-wait-time {
               description "Time to wait at startup before claming a site identifier (seconds)";
               units "seconds";
               type union {
                 type string {
                   pattern "<.*>|$.*";
                 }
                 type uint32 {
                   range "1 .. 3600";
                 }
               }
             }
             leaf new-site-wait-time {
               description "Time to wait before claiming a site identifier";
               units "seconds";
               type union {
                 type string {
                   pattern "<.*>|$.*";
                 }
                 type uint32 {
                   range "1 .. 3600";
                 }
               }
             }
             leaf collision-detect-time {
               description "Time to wait for detecting a collision";
               units "seconds";
               type union {
                 type string {
                   pattern "<.*>|$.*";
                 }
                 type uint32 {
                   range "1 .. 3600";
                 }
               }
             }
             container reclaim-wait-time {
               presence "enable reclaim-wait-time";
               description "Time to wait for reclaiming a site identifier";
               leaf minimum {
                 description "Minimum wait time";
                 units "milliseconds";
                 type union {
                   type uint32;
                   type string {
                     pattern "<.*>|$.*";
                   }
                 }
               }
               leaf maximum {
                 description "Maximum wait time";
                 units "milliseconds";
                 type union {
                   type uint32;
                   type string {
                     pattern "<.*>|$.*";
                   }
                 }
               }
             }
           }
         }
       }
       leaf source-attachment-identifier {
         description "FEC 129 VPWS source attachment identifier";
         junos:must "(\".. .. .. .. l2vpn-id\")";
         junos:must-message "Source attachment identifier only supported for FEC 129 VPWS instances";
         junos:must "(unique \".. .. site <*> source-attachment-identifier $$\")";
         junos:must-message "All site source attachment identifiers must be unique within an instance";
         type string {
           junos:posix-pattern "^([[:digit:].]){1,15}$|^([[:digit:]]){0,10}:([[:digit:].]){0,15}:([[:digit:]]){1,10}$";
           junos:pattern-message "
	Use fec129 AII type 1 format with just <AC-ID> or    
	fec129 AII type 2 format <Global-ID>:<Prefix>:<AC-ID> where    
	<Global-ID> is a value between 0..4294967295,    
	<Prefix> is a value between 0..4294967295 or a valid IP address,    
	<AC-ID> is a value between 1..4294967295 (or a valid IP address for AII type 1).    
	e.g. 1, 0.0.0.1, 0:0:1, 1:2:3, 1:2.2.2.2:3, ::1, 1::2, :1:2";
         }
       }
       leaf flow-label-transmit {
         description "Advertise capability to push Flow Label in transmit direction to remote PE";
         junos:must "(\".. .. .. .. l2vpn-id\")";
         junos:must-message "Per-site Flow Label Config is only supported for FEC129 VPWS";
         type empty;
       }
       leaf flow-label-receive {
         description "Advertise capability to push Flow Label in receive direction to remote PE";
         junos:must "(\".. .. .. .. l2vpn-id\")";
         junos:must-message "Per-site Flow Label Config is only supported for FEC129 VPWS";
         type empty;
       }
       leaf encapsulation-type {
         description "Encapsulation type for VPN";
         type enumeration {
           enum "atm-aal5" {
             description "ATM AAL/5 encapsulation";
           }
           enum "atm-cell" {
             description "ATM port promiscuous mode cell encapsulation";
           }
           enum "atm-cell-port-mode" {
             description "ATM port promiscuous mode cell encapsulation";
           }
           enum "atm-cell-vp-mode" {
             description "ATM VP promiscuous mode cell encapsulation";
           }
           enum "atm-cell-vc-mode" {
             description "ATM non-promiscuous cell encapsulation";
           }
           enum "frame-relay" {
             description "Frame Relay encapsulation";
           }
           enum "ppp" {
             description "PPP encapsulation";
           }
           enum "cisco-hdlc" {
             description "Cisco-compatible HDLC encapsulation";
           }
           enum "ethernet-vlan" {
             description "Ethernet VLAN encapsulation";
           }
           enum "ethernet" {
             description "Ethernet encapsulation";
           }
           enum "interworking" {
             description "Layer 2.5 interworking VPN";
           }
           enum "frame-relay-port-mode" {
             description "Frame Relay port mode encapsulation";
           }
           enum "satop-t1" {
             description "SATOP-T1 based Layer 2 VPN";
           }
           enum "satop-e1" {
             description "SATOP-E1 based Layer 2 VPN";
           }
           enum "satop-t3" {
             description "SATOP-T3 based Layer 2 VPN";
           }
           enum "satop-e3" {
             description "SATOP-E3 based Layer 2 VPN";
           }
           enum "cesop" {
             description "CESOP based Layer 2 VPN";
           }
         }
       }
       leaf ignore-encapsulation-mismatch {
         description "Allow different encapsulation types on local and remote end";
         type empty;
       }
       choice cword {
         case case_1 {
           leaf control-word {
             description "Adds control-word to the Layer 2 encapsulation";
             type empty;
           }
         }
         case case_2 {
           leaf no-control-word {
             description "Disables control-word to the Layer 2 encapsulation";
             type empty;
           }
         }
       }
       leaf pseudowire-status-tlv {
         description "Send pseudowire status TLV";
         type empty;
       }
       container oam {
         description "OAM Configuration for VPN";
         uses apply-advanced;
         leaf ping-interval {
           description "Time interval between ping messages";
           default "60";
           units "seconds";
           type union {
             type string {
               pattern "<.*>|$.*";
             }
             type uint16 {
               range "30 .. 3600";
             }
           }
         }
         leaf ping-multiplier {
           description "Number of ping reply missed before declaring BFD down";
           type union {
             type string {
               pattern "<.*>|$.*";
             }
             type uint8 {
               range "1 .. 5";
             }
           }
         }
         container bfd-liveness-detection {
           description "Bidirectional Forwarding Detection (BFD) options";
           uses apply-advanced;
           leaf version {
             description "BFD protocol version number";
             default "automatic";
             type enumeration {
               enum "0" {
                 description "BFD version 0 (deprecated)";
               }
               enum "1" {
                 description "BFD version 1";
               }
               enum "automatic" {
                 description "Choose BFD version automatically";
               }
             }
           }
           leaf minimum-interval {
             description "Minimum transmit and receive interval";
             units "milliseconds";
             type union {
               type string {
                 pattern "<.*>|$.*";
               }
               type uint32 {
                 range "1 .. 255000";
               }
             }
           }
           leaf minimum-transmit-interval {
             description "Minimum transmit interval";
             status deprecated;
             units "milliseconds";
             type union {
               type string {
                 pattern "<.*>|$.*";
               }
               type uint32 {
                 range "1 .. 255000";
               }
             }
           }
           leaf minimum-receive-interval {
             description "Minimum receive interval";
             units "milliseconds";
             type union {
               type string {
                 pattern "<.*>|$.*";
               }
               type uint32 {
                 range "1 .. 255000";
               }
             }
           }
           leaf multiplier {
             description "Detection time multiplier";
             default "3";
             type union {
               type string {
                 pattern "<.*>|$.*";
               }
               type uint32 {
                 range "1 .. 255";
               }
             }
           }
           choice adaptation-choice {
             case case_1 {
               leaf no-adaptation {
                 description "Disable adaptation";
                 type empty;
               }
             }
           }
           container transmit-interval {
             description "Transmit-interval options";
             uses apply-advanced;
             leaf minimum-interval {
               description "Minimum transmit interval";
               units "milliseconds";
               type union {
                 type string {
                   pattern "<.*>|$.*";
                 }
                 type uint32 {
                   range "1 .. 255000";
                 }
               }
             }
             leaf threshold {
               description "High transmit interval triggering a trap";
               units "milliseconds";
               type union {
                 type uint32;
                 type string {
                   pattern "<.*>|$.*";
                 }
               }
             }
           }
           container detection-time {
             description "Detection-time options";
             uses apply-advanced;
             leaf threshold {
               description "High detection-time triggering a trap";
               units "milliseconds";
               type union {
                 type uint32;
                 type string {
                   pattern "<.*>|$.*";
                 }
               }
             }
           }
         }
       }
       leaf community {
         description "Community associated with this site";
         type string;
       }
       container multi-homing {
         presence "enable multi-homing";
         junos:must "(!(\".. automatic-site-id\"))";
         junos:must-message "Multi-homing cannot be configured for automatic site";
         description "Enable multi-homing functionality for this site";
         uses apply-advanced;
         leaf hold-time {
           description "Enable multi-homing non-designated forwarder hold time (seconds)";
           units "seconds";
           type union {
             type string {
               pattern "<.*>|$.*";
             }
             type uint32 {
               range "1 .. 18000";
             }
           }
         }
       }
       leaf site-preference {
         description "Layer 2 VPN or VPLS site preference";
         type string;
       }
       leaf hot-standby {
         description "Keep backup pseudowire in continuous standby mode and ready for traffic forwarding";
         junos:must "(!(\".. site-preference primary\"))";
         junos:must-message "primary site cannot be hot-standby";
         type empty;
       }
       leaf mtu {
         description "MTU to be advertised to the remote end";
         type union {
           type string {
             pattern "<.*>|$.*";
           }
           type uint16 {
             range "512 .. 65535";
           }
         }
       }
       leaf ignore-mtu-mismatch {
         description "Allow different MTU values on local and remote end";
         type empty;
       }
       container active-interface {
         description "Configure interface to designate as active";
         choice interface_name {
           case case_1 {
             leaf any {
               description "One configured interface is designated active at random";
               type empty;
             }
           }
           case case_2 {
             leaf primary {
               description "Interface to designate as active if it is operational";
               type union {
                 type jt:interface-name;
                 type string {
                   pattern "<.*>|$.*";
                 }
               }
             }
           }
         }
       }
       leaf best-site {
         description "Activates best-site functionality for this instance";
         junos:must "(!(\".. .. .. l2vpn\"))";
         junos:must-message "'best-site' feature not supported for VPWS/BGP-L2VPN instances";
         junos:must "(!(\".. .. vpls-id\"))";
         junos:must-message "'best-site' feature not supported for LDP based VPLS instances";
         junos:must "(!(\".. interface\"))";
         junos:must-message "'interface' must not be defined when 'best-site' knob is activated";
         type empty;
       }
     }
     list neighbor {
       key name;
       ordered-by user;
       description "Neighbor for this VPLS instance";
       junos:must "(\".. vpls-id\")";
       junos:must-message "'vpls-id' must be defined";
       leaf name {
         description "Neighbor ID";
         type jt:ipv4addr;
       }
       uses apply-advanced;
       leaf mac-pinning {
         description "Enable MAC pinning";
         type empty;
       }
       container static {
         presence "enable static";
         junos:must "((!(\".. backup-neighbor\") || all \".. backup-neighbor <*> static\"))";
         junos:must-message "Backup neighbor should be static";
         description "Configuration of static vpls";
         uses apply-advanced;
         leaf incoming-label {
           description "VPLS incoming static label [1000000 - 1048575] or [29696 - 41983]";
           type union {
             type uint32;
             type string {
               pattern "<.*>|$.*";
             }
           }
         }
         leaf outgoing-label {
           description "VPLS outgoing static label";
           type union {
             type string {
               pattern "<.*>|$.*";
             }
             type uint32 {
               range "16 .. 1048575";
             }
           }
         }
         choice cword {
           case case_1 {
             leaf control-word {
               description "Adds control-word to the Layer 2 encapsulation";
               type empty;
             }
           }
           case case_2 {
             leaf no-control-word {
               description "Disables control-word to the Layer 2 encapsulation";
               type empty;
             }
           }
         }
       }
       container associate-profile {
         description "Associate profile options for dynamic IFL";
         uses apply-advanced;
         leaf profile-name {
           description "Associated profile name";
           type string {
             length "1 .. 81";
           }
         }
         leaf profile-variable-set {
           description "Associate dynamic variable set with the profile";
           type string {
             length "1 .. 81";
           }
         }
       }
       leaf psn-tunnel-endpoint {
         description "Endpoint of the transport tunnel on the remote PE";
         type jt:ipv4addr;
       }
       leaf community {
         description "Community associated with this neighbor";
         type string;
       }
       leaf encapsulation-type {
         description "Encapsulation type for VPN";
         type enumeration {
           enum "ethernet-vlan" {
             description "Ethernet VLAN encapsulation";
             junos:must "(!(\".. static\"))";
             junos:must-message "not supported for static vpls";
           }
           enum "ethernet" {
             description "Ethernet encapsulation";
             junos:must "(!(\".. static\"))";
             junos:must-message "not supported for static vpls";
           }
         }
       }
       leaf ignore-encapsulation-mismatch {
         description "Allow different encapsulation types on local and remote end";
         junos:must "(!(\".. static\"))";
         junos:must-message "not supported for static vpls";
         type empty;
       }
       container pseudowire-status-tlv {
         presence "enable pseudowire-status-tlv";
         junos:must "(!(\".. static\"))";
         junos:must-message "not supported for static vpls";
         description "Send pseudowire status TLV";
         uses apply-advanced;
         leaf hot-standby-vc-on {
           description "Activate pseudowire upon arrival of 'hot-standby' status TLV message";
           type empty;
         }
       }
       leaf switchover-delay {
         description "Pseudowire switchover delay ";
         default "10000";
         units "milliseconds";
         type union {
           type string {
             pattern "<.*>|$.*";
           }
           type uint32 {
             range "0 .. 180000";
           }
         }
       }
       container revert-time {
         presence "enable revert-time";
         description "Enable pseudowire redundancy reversion (seconds)";
         leaf delay {
           description "Reversion timer (seconds)";
           units "seconds";
           type union {
             type string {
               pattern "<.*>|$.*";
             }
             type uint32 {
               range "0 .. 600";
             }
           }
         }
         leaf maximum {
           description "Maximum reversion interval to add over revert-time delay";
           units "seconds";
           type union {
             type string {
               pattern "<.*>|$.*";
             }
             type uint32 {
               range "0 .. 1200";
             }
           }
         }
       }
       leaf connection-protection {
         description "End-2-end protection via OAM failure detection";
         junos:must "((!(\".. backup-neighbor\") || all \".. backup-neighbor <*> standby\"))";
         junos:must-message "For connection-protection services, backup neighbor must be standby";
         junos:must "(!(\".. switchover-delay\"))";
         junos:must-message "connection-protection cannot be configured with switchover-delay";
         junos:must "(!(\".. revert-time\"))";
         junos:must-message "connection-protection cannot be configured with revert-time";
         type empty;
       }
       list backup-neighbor {
         key name;
         ordered-by user;
         description "Configuration of redundant l2circuit";
         leaf name {
           description "Neighbor ID";
           type jt:ipv4addr;
         }
         uses apply-advanced;
         container static {
           presence "enable static";
           junos:must "(\".. .. static\")";
           junos:must-message "Primary Neighbor must be static";
           description "Configuration of static vpls";
           uses apply-advanced;
           leaf incoming-label {
             description "VPLS incoming static label [1000000 - 1048575] or [29696 - 41983]";
             type union {
               type uint32;
               type string {
                 pattern "<.*>|$.*";
               }
             }
           }
           leaf outgoing-label {
             description "VPLS outgoing static label";
             type union {
               type string {
                 pattern "<.*>|$.*";
               }
               type uint32 {
                 range "16 .. 1048575";
               }
             }
           }
         }
         leaf community {
           description "Community associated with this Layer 2 circuit";
           junos:must "(!(\".. .. connection-protection\"))";
           junos:must-message "The backup neighbor cannot be configured with community alongwith connection-protection";
           type string;
         }
         leaf psn-tunnel-endpoint {
           description "Endpoint of the transport tunnel on the remote PE";
           type jt:ipv4addr;
         }
         leaf standby {
           description "Keep backup pseudowire in continuous standby";
           type empty;
         }
         leaf hot-standby {
           description "Keep backup pseudowire in continuous standby mode and ready for traffic forwarding";
           junos:must "((!(\".. .. .. control-word\") && !(\".. .. .. .. control-word\")))";
           junos:must-message "Hot-standby cannot be configured while having control-word enabled";
           junos:must "(\".. .. pseudowire-status-tlv\")";
           junos:must-message "Pseudowire-status-tlv must be configured in order to have hot-standby enabled";
           junos:must "(!(\".. .. connection-protection\"))";
           junos:must-message "Hot-standby cannot be configured while having connection-protection enabled";
           junos:must "(!(\".. standby\"))";
           junos:must-message "The backup neighbor cannot be configured with standby and hot-standby features simultaneously";
           type empty;
         }
       }
       container oam {
         description "OAM Configuration for VPN";
         uses apply-advanced;
         leaf ping-interval {
           description "Time interval between ping messages";
           default "60";
           units "seconds";
           type union {
             type string {
               pattern "<.*>|$.*";
             }
             type uint16 {
               range "30 .. 3600";
             }
           }
         }
         leaf ping-multiplier {
           description "Number of ping reply missed before declaring BFD down";
           type union {
             type string {
               pattern "<.*>|$.*";
             }
             type uint8 {
               range "1 .. 5";
             }
           }
         }
         container bfd-liveness-detection {
           description "Bidirectional Forwarding Detection (BFD) options";
           uses apply-advanced;
           leaf version {
             description "BFD protocol version number";
             default "automatic";
             type enumeration {
               enum "0" {
                 description "BFD version 0 (deprecated)";
               }
               enum "1" {
                 description "BFD version 1";
               }
               enum "automatic" {
                 description "Choose BFD version automatically";
               }
             }
           }
           leaf minimum-interval {
             description "Minimum transmit and receive interval";
             units "milliseconds";
             type union {
               type string {
                 pattern "<.*>|$.*";
               }
               type uint32 {
                 range "1 .. 255000";
               }
             }
           }
           leaf minimum-transmit-interval {
             description "Minimum transmit interval";
             status deprecated;
             units "milliseconds";
             type union {
               type string {
                 pattern "<.*>|$.*";
               }
               type uint32 {
                 range "1 .. 255000";
               }
             }
           }
           leaf minimum-receive-interval {
             description "Minimum receive interval";
             units "milliseconds";
             type union {
               type string {
                 pattern "<.*>|$.*";
               }
               type uint32 {
                 range "1 .. 255000";
               }
             }
           }
           leaf multiplier {
             description "Detection time multiplier";
             default "3";
             type union {
               type string {
                 pattern "<.*>|$.*";
               }
               type uint32 {
                 range "1 .. 255";
               }
             }
           }
           choice adaptation-choice {
             case case_1 {
               leaf no-adaptation {
                 description "Disable adaptation";
                 type empty;
               }
             }
           }
           container transmit-interval {
             description "Transmit-interval options";
             uses apply-advanced;
             leaf minimum-interval {
               description "Minimum transmit interval";
               units "milliseconds";
               type union {
                 type string {
                   pattern "<.*>|$.*";
                 }
                 type uint32 {
                   range "1 .. 255000";
                 }
               }
             }
             leaf threshold {
               description "High transmit interval triggering a trap";
               units "milliseconds";
               type union {
                 type uint32;
                 type string {
                   pattern "<.*>|$.*";
                 }
               }
             }
           }
           container detection-time {
             description "Detection-time options";
             uses apply-advanced;
             leaf threshold {
               description "High detection-time triggering a trap";
               units "milliseconds";
               type union {
                 type uint32;
                 type string {
                   pattern "<.*>|$.*";
                 }
               }
             }
           }
         }
       }
     }
     list mesh-group {
       key name;
       description "Mesh-group under this VPLS instance";
       leaf name {
         description "Mesh-group name";
         type string {
           junos:posix-pattern "^.{1,32}$";
           junos:pattern-message "The mesh-group name should be between 1 and 32 characters";
         }
       }
       uses apply-advanced;
       leaf local-switching {
         description "Allow local-switching within interfaces in this mesh-group";
         type empty;
       }
       list neighbor {
         key name;
         ordered-by user;
         description "Neighbor belonging to this mesh-group";
         junos:must "(!(\".. peer-as\"))";
         junos:must-message "'peer-as' and 'neighbor' must not be defined in the same mesh-group";
         junos:must "(!(\".. interface\"))";
         junos:must-message "'interface' and 'neighbor' must not be defined in the same mesh-group";
         junos:must "((\".. vpls-id\" || \".. .. vpls-id\"))";
         junos:must-message "'vpls-id' must be defined";
         leaf name {
           description "Neighbor ID";
           type jt:ipv4addr;
         }
         uses apply-advanced;
         leaf mac-pinning {
           description "Enable MAC pinning";
           type empty;
         }
         container static {
           presence "enable static";
           junos:must "((!(\".. backup-neighbor\") || all \".. backup-neighbor <*> static\"))";
           junos:must-message "Backup neighbor should be static";
           description "Configuration of static vpls";
           uses apply-advanced;
           leaf incoming-label {
             description "VPLS incoming static label [1000000 - 1048575] or [29696 - 41983]";
             type union {
               type uint32;
               type string {
                 pattern "<.*>|$.*";
               }
             }
           }
           leaf outgoing-label {
             description "VPLS outgoing static label";
             type union {
               type string {
                 pattern "<.*>|$.*";
               }
               type uint32 {
                 range "16 .. 1048575";
               }
             }
           }
           choice cword {
             case case_1 {
               leaf control-word {
                 description "Adds control-word to the Layer 2 encapsulation";
                 type empty;
               }
             }
             case case_2 {
               leaf no-control-word {
                 description "Disables control-word to the Layer 2 encapsulation";
                 type empty;
               }
             }
           }
         }
         container associate-profile {
           description "Associate profile options for dynamic IFL";
           uses apply-advanced;
           leaf profile-name {
             description "Associated profile name";
             type string {
               length "1 .. 81";
             }
           }
           leaf profile-variable-set {
             description "Associate dynamic variable set with the profile";
             type string {
               length "1 .. 81";
             }
           }
         }
         leaf psn-tunnel-endpoint {
           description "Endpoint of the transport tunnel on the remote PE";
           type jt:ipv4addr;
         }
         leaf community {
           description "Community associated with this neighbor";
           type string;
         }
         leaf encapsulation-type {
           description "Encapsulation type for VPN";
           type enumeration {
             enum "ethernet-vlan" {
               description "Ethernet VLAN encapsulation";
               junos:must "(!(\".. static\"))";
               junos:must-message "not supported for static vpls";
             }
             enum "ethernet" {
               description "Ethernet encapsulation";
               junos:must "(!(\".. static\"))";
               junos:must-message "not supported for static vpls";
             }
           }
         }
         leaf ignore-encapsulation-mismatch {
           description "Allow different encapsulation types on local and remote end";
           junos:must "(!(\".. static\"))";
           junos:must-message "not supported for static vpls";
           type empty;
         }
         container pseudowire-status-tlv {
           presence "enable pseudowire-status-tlv";
           junos:must "(!(\".. static\"))";
           junos:must-message "not supported for static vpls";
           description "Send pseudowire status TLV";
           uses apply-advanced;
           leaf hot-standby-vc-on {
             description "Activate pseudowire upon arrival of 'hot-standby' status TLV message";
             type empty;
           }
         }
         leaf switchover-delay {
           description "Pseudowire switchover delay ";
           default "10000";
           units "milliseconds";
           type union {
             type string {
               pattern "<.*>|$.*";
             }
             type uint32 {
               range "0 .. 180000";
             }
           }
         }
         container revert-time {
           presence "enable revert-time";
           description "Enable pseudowire redundancy reversion (seconds)";
           leaf delay {
             description "Reversion timer (seconds)";
             units "seconds";
             type union {
               type string {
                 pattern "<.*>|$.*";
               }
               type uint32 {
                 range "0 .. 600";
               }
             }
           }
           leaf maximum {
             description "Maximum reversion interval to add over revert-time delay";
             units "seconds";
             type union {
               type string {
                 pattern "<.*>|$.*";
               }
               type uint32 {
                 range "0 .. 1200";
               }
             }
           }
         }
         leaf connection-protection {
           description "End-2-end protection via OAM failure detection";
           junos:must "((!(\".. backup-neighbor\") || all \".. backup-neighbor <*> standby\"))";
           junos:must-message "For connection-protection services, backup neighbor must be standby";
           junos:must "(!(\".. switchover-delay\"))";
           junos:must-message "connection-protection cannot be configured with switchover-delay";
           junos:must "(!(\".. revert-time\"))";
           junos:must-message "connection-protection cannot be configured with revert-time";
           type empty;
         }
         list backup-neighbor {
           key name;
           ordered-by user;
           description "Configuration of redundant l2circuit";
           leaf name {
             description "Neighbor ID";
             type jt:ipv4addr;
           }
           uses apply-advanced;
           container static {
             presence "enable static";
             junos:must "(\".. .. static\")";
             junos:must-message "Primary Neighbor must be static";
             description "Configuration of static vpls";
             uses apply-advanced;
             leaf incoming-label {
               description "VPLS incoming static label [1000000 - 1048575] or [29696 - 41983]";
               type union {
                 type uint32;
                 type string {
                   pattern "<.*>|$.*";
                 }
               }
             }
             leaf outgoing-label {
               description "VPLS outgoing static label";
               type union {
                 type string {
                   pattern "<.*>|$.*";
                 }
                 type uint32 {
                   range "16 .. 1048575";
                 }
               }
             }
           }
           leaf community {
             description "Community associated with this Layer 2 circuit";
             junos:must "(!(\".. .. connection-protection\"))";
             junos:must-message "The backup neighbor cannot be configured with community alongwith connection-protection";
             type string;
           }
           leaf psn-tunnel-endpoint {
             description "Endpoint of the transport tunnel on the remote PE";
             type jt:ipv4addr;
           }
           leaf standby {
             description "Keep backup pseudowire in continuous standby";
             type empty;
           }
           leaf hot-standby {
             description "Keep backup pseudowire in continuous standby mode and ready for traffic forwarding";
             junos:must "((!(\".. .. .. control-word\") && !(\".. .. .. .. control-word\")))";
             junos:must-message "Hot-standby cannot be configured while having control-word enabled";
             junos:must "(\".. .. pseudowire-status-tlv\")";
             junos:must-message "Pseudowire-status-tlv must be configured in order to have hot-standby enabled";
             junos:must "(!(\".. .. connection-protection\"))";
             junos:must-message "Hot-standby cannot be configured while having connection-protection enabled";
             junos:must "(!(\".. standby\"))";
             junos:must-message "The backup neighbor cannot be configured with standby and hot-standby features simultaneously";
             type empty;
           }
         }
         container oam {
           description "OAM Configuration for VPN";
           uses apply-advanced;
           leaf ping-interval {
             description "Time interval between ping messages";
             default "60";
             units "seconds";
             type union {
               type string {
                 pattern "<.*>|$.*";
               }
               type uint16 {
                 range "30 .. 3600";
               }
             }
           }
           leaf ping-multiplier {
             description "Number of ping reply missed before declaring BFD down";
             type union {
               type string {
                 pattern "<.*>|$.*";
               }
               type uint8 {
                 range "1 .. 5";
               }
             }
           }
           container bfd-liveness-detection {
             description "Bidirectional Forwarding Detection (BFD) options";
             uses apply-advanced;
             leaf version {
               description "BFD protocol version number";
               default "automatic";
               type enumeration {
                 enum "0" {
                   description "BFD version 0 (deprecated)";
                 }
                 enum "1" {
                   description "BFD version 1";
                 }
                 enum "automatic" {
                   description "Choose BFD version automatically";
                 }
               }
             }
             leaf minimum-interval {
               description "Minimum transmit and receive interval";
               units "milliseconds";
               type union {
                 type string {
                   pattern "<.*>|$.*";
                 }
                 type uint32 {
                   range "1 .. 255000";
                 }
               }
             }
             leaf minimum-transmit-interval {
               description "Minimum transmit interval";
               status deprecated;
               units "milliseconds";
               type union {
                 type string {
                   pattern "<.*>|$.*";
                 }
                 type uint32 {
                   range "1 .. 255000";
                 }
               }
             }
             leaf minimum-receive-interval {
               description "Minimum receive interval";
               units "milliseconds";
               type union {
                 type string {
                   pattern "<.*>|$.*";
                 }
                 type uint32 {
                   range "1 .. 255000";
                 }
               }
             }
             leaf multiplier {
               description "Detection time multiplier";
               default "3";
               type union {
                 type string {
                   pattern "<.*>|$.*";
                 }
                 type uint32 {
                   range "1 .. 255";
                 }
               }
             }
             choice adaptation-choice {
               case case_1 {
                 leaf no-adaptation {
                   description "Disable adaptation";
                   type empty;
                 }
               }
             }
             container transmit-interval {
               description "Transmit-interval options";
               uses apply-advanced;
               leaf minimum-interval {
                 description "Minimum transmit interval";
                 units "milliseconds";
                 type union {
                   type string {
                     pattern "<.*>|$.*";
                   }
                   type uint32 {
                     range "1 .. 255000";
                   }
                 }
               }
               leaf threshold {
                 description "High transmit interval triggering a trap";
                 units "milliseconds";
                 type union {
                   type uint32;
                   type string {
                     pattern "<.*>|$.*";
                   }
                 }
               }
             }
             container detection-time {
               description "Detection-time options";
               uses apply-advanced;
               leaf threshold {
                 description "High detection-time triggering a trap";
                 units "milliseconds";
                 type union {
                   type uint32;
                   type string {
                     pattern "<.*>|$.*";
                   }
                 }
               }
             }
           }
         }
         leaf-list vpls-id-list {
           ordered-by user;
           description "LDP VPLS Identifier list for this neighbor";
           type union {
             type string {
               pattern "<.*>|$.*";
             }
             type uint32 {
               range "1 .. 4294967295";
             }
           }
         }
       }
       list interface {
         key name;
         description "Interfaces belonging to this flood group";
         leaf name {
           description "Interface name";
           junos:must "(\".. .. .. .. .. interface $$\")";
           junos:must-message "Interface must be part of this VPLS routing instance";
           type union {
             type jt:interface-name;
             type string {
               pattern "<.*>|$.*";
             }
           }
         }
         uses apply-advanced;
       }
       container associate-profile {
         description "Associate profile options for dynamic IFL";
         uses apply-advanced;
         leaf profile-name {
           description "Associated profile name";
           type string {
             length "1 .. 81";
           }
         }
         leaf profile-variable-set {
           description "Associate dynamic variable set with the profile";
           type string {
             length "1 .. 81";
           }
         }
       }
       choice peer-as-choice {
         case case_1 {
           container peer-as {
             description "Autonomous system of the peer";
             uses apply-advanced;
             leaf all {
               description "Include peers from all autonomous systems";
               type empty;
             }
           }
         }
       }
       leaf vpls-id {
         description "LDP VPLS Identifier for this mesh-group";
         junos:must "(!(any \".. .. mesh-group <*> route-distinguisher\"))";
         junos:must-message "Does not support FEC129 and FEC128 LDP VPLS mesh-group under the same instance";
         junos:must "(!(\".. interface\"))";
         junos:must-message "'vpls-id' must not be defined when specifying 'interface' in a mesh-group";
         type string;
       }
       leaf-list vrf-import {
         ordered-by user;
         description "Import policy for VPLS instance mesh-group";
         junos:must "(\".. route-distinguisher\")";
         junos:must-message "route distinguisher must be defined";
         type jt:policy-algebra;
       }
       leaf-list vrf-export {
         ordered-by user;
         description "Export policy for VPLS instance mesh-group";
         junos:must "(\".. route-distinguisher\")";
         junos:must-message "route distinguisher must be defined";
         type jt:policy-algebra;
       }
       container vrf-target {
         junos:must "(\".. route-distinguisher\")";
         junos:must-message "route distinguisher must be defined";
         description "VPLS mesh-group target community configuration";
         uses apply-advanced;
         leaf community {
           description "Target community to use in import and export";
           type string {
             junos:posix-pattern "^[a-z]+:[0-9.]+L?:[0-9]+$";
             junos:pattern-message "Use format 'target:x:y' where 'x' is an AS number followed by an optional 'L' (To indicate 4 byte AS), or an IP address and 'y' is a number. e.g. target:123456L:100";
           }
         }
         leaf import {
           description "Target community to use when filtering on import";
           type string {
             junos:posix-pattern "^[a-z]+:[0-9.]+L?:[0-9]+$";
             junos:pattern-message "Use format 'target:x:y' where 'x' is an AS number followed by an optional 'L' (To indicate 4 byte AS), or an IP address and 'y' is a number. e.g. target:123456L:100";
           }
         }
         leaf export {
           description "Target community to use when marking routes on export";
           type string {
             junos:posix-pattern "^[a-z]+:[0-9.]+L?:[0-9]+$";
             junos:pattern-message "Use format 'target:x:y' where 'x' is an AS number followed by an optional 'L' (To indicate 4 byte AS), or an IP address and 'y' is a number. e.g. target:123456L:100";
           }
         }
       }
       container mac-flush {
         presence "enable mac-flush";
         description "Enables mac-flush processing";
         uses apply-advanced;
         leaf any-interface {
           description "Send mac-flush when any AC interface goes down";
           junos:must "((\".. .. vpls-id\" || \".. .. .. vpls-id\"))";
           junos:must-message "'any-interface' can be configured only for LDP VPLS";
           type empty;
         }
         leaf any-spoke {
           description "Send mac-flush when any spoke pseudo wire goes down";
           junos:must "((\".. .. vpls-id\" || \".. .. .. vpls-id\"))";
           junos:must-message "'any-spoke' can be configured only for LDP VPLS";
           type empty;
         }
         leaf propagate {
           description "Propagate mac-flush to the core";
           junos:must "((\".. .. vpls-id\" || \".. .. .. vpls-id\"))";
           junos:must-message "'propagate' can be configured only for LDP VPLS";
           type empty;
         }
       }
       container route-distinguisher {
         junos:must "(!(any \".. .. mesh-group <*> vpls-id\"))";
         junos:must-message "Does not support FEC129 and FEC128 LDP VPLS mesh-group under the same instance";
         description "Route distinguisher for this mesh-group";
         leaf rd-type {
           description "Number in (16 bit:32 bit) or (32 bit 'L':16 bit) or (IP address:16 bit) format";
           type string {
             junos:posix-pattern "^[0-9.]+L?:[0-9]+$";
             junos:pattern-message "Use format 'x:y' where 'x' is an AS number followed by an optional 'L' (To indicate 4 byte AS), or an IP address and 'y' is a number. e.g. 123456L:100";
           }
         }
       }
     }
     container proxy-mac {
       junos:must "(\".. .. .. instance-type evpn\")";
       junos:must-message "Applicable to instance-type evpn only";
       description "Proxy MAC settings";
       uses apply-advanced;
       leaf irb {
         description "Reply with virtual-gateway MAC or IRB MAC";
         junos:must "(!(\".. .. no-arp-suppression\"))";
         junos:must-message "Proxy MAC is not supported with no-arp-suppression";
         junos:must "(((\".. .. .. .. l3-interface\" || \".. .. .. .. routing-interface\") && !(\".. proxy-mac-address\")))";
         junos:must-message "Proxy MAC in IRB mode should have routing-interface configured";
         type empty;
       }
       leaf proxy-mac-address {
         description "Reply with configured MAC for all requests";
         junos:must "(!(\".. .. no-arp-suppression\"))";
         junos:must-message "Proxy MAC is not supported with no-arp-suppression";
         junos:must "((!(\".. .. .. .. routing-interface\") && (!(\".. .. .. .. l3-interface\") && !(\".. irb\"))))";
         junos:must-message "Proxy MAC with specified MAC should not have routing-interface configured";
         type jt:mac-unicast;
       }
     }
     container mclag {
       description "EVPN with MC-LAG support";
       uses apply-advanced;
       leaf bgp-peer {
         description "Configure IP address of BGP neighbor, which is also MC-LAG peer";
         junos:must "(!(\".. .. encapsulation vxlan\"))";
         junos:must-message "encapsulation vxlan cannot be configured with bgp-peer";
         junos:must "(!(\".. source-vtep-peer\"))";
         junos:must-message "bgp-peer cannot be configured with source-vtep-peer.";
         type jt:ipaddr;
       }
       leaf source-vtep-peer {
         description "Confiugure IP address of MC-LAG peer's source vtep IP address";
         junos:must "(\".. .. encapsulation vxlan\")";
         junos:must-message "encapsulation vxlan must be configured";
         type jt:ipaddr;
       }
     }
     leaf service-type {
       description "Specify service type for vpls";
       type enumeration {
         enum "single" {
           description "Only one service for the virtual-switch";
         }
       }
     }
     leaf designated-forwarder-election-hold-time {
       description "Time to wait before electing a DF(seconds)";
       units "seconds";
       type union {
         type string {
           pattern "<.*>|$.*";
         }
         type uint32 {
           range "1 .. 1800";
         }
       }
     }
     leaf designated-forwarder-preference-least {
       description "Use least preference in DF election";
       type empty;
     }
     leaf encapsulation {
       description "Encapsulation type for EVPN";
       default "mpls";
       junos:must "((((\".. .. .. instance-type virtual-switch\" || (\".. .. ..  instance-type evpn\" || (\".. .. .. instance-type mac-vrf\" || \".. .. .. instance-type evpn-vpws\"))) && !(\".. .. .. switch-options route-distinguisher\")) || \".. .. .. switch-options route-distinguisher\"))";
       junos:must-message "Encapsulation can only be configured for an EVPN instance";
       type enumeration {
         enum "mpls" {
           description "MPLS encapsulation";
         }
         enum "vxlan" {
           description "VXLAN encapsulation";
         }
         enum "mpls-inet6" {
           description "MPLS over IPv6 encapsulation";
         }
       }
     }
     leaf default-gateway {
       description "Default gateway mode";
       type enumeration {
         enum "advertise" {
           description "Advertise IRB MACs with default gateway community";
         }
         enum "no-gateway-community" {
           description "Advertise IRB MACs without default gateway community";
         }
         enum "do-not-advertise" {
           description "Do not advertise IRB MACs";
         }
       }
     }
     container duplicate-mac-detection {
       description "Duplicate MAC detection settings";
       uses apply-advanced;
       leaf detection-threshold {
         description "Number of moves to trigger duplicate MAC detection";
         type union {
           type string {
             pattern "<.*>|$.*";
           }
           type uint32 {
             range "2 .. 20";
           }
         }
       }
       leaf detection-window {
         description "Time window for detection of duplicate MACs";
         units "seconds";
         type union {
           type string {
             pattern "<.*>|$.*";
           }
           type uint32 {
             range "5 .. 600";
           }
         }
       }
       leaf auto-recovery-time {
         description "Automatically unblock duplicate MACs after a time delay";
         units "minutes";
         type union {
           type string {
             pattern "<.*>|$.*";
           }
           type uint32 {
             range "1 .. 360";
           }
         }
       }
     }
     choice extended-attributes {
       case case_1 {
         leaf-list extended-vlan-list {
           description "List of VLAN identifiers that are to be EVPN extended";
           junos:must "(!((\".. .. .. .. .. chassis satellite-management redundancy-groups\" && !(\".. mclag\"))))";
           junos:must-message "Need to configure 'protocols evpn mclag' when evpn is configured with mclag.";
           junos:must "(!(\".. pbb-evpn-core\"))";
           junos:must-message "Extended VLAN list can't be configured in the PBB EVPN";
           junos:must "(!(\".. encapsulation vxlan\"))";
           junos:must-message "Extended VLAN list cannot coexist with encapsulation vxlan option";
           junos:must "(\".. .. .. instance-type virtual-switch\")";
           junos:must-message "Extended VLAN list can only be configured in a virtual switch instance";
           type jt:vlan-range;
         }
       }
       case case_2 {
         leaf-list extended-vni-list {
           description "List of VNI identifiers (1..16777214) or all, that are to be EVPN extended";
           junos:must "(!((\".. .. .. .. .. chassis satellite-management redundancy-groups\" && !(\".. mclag\"))))";
           junos:must-message "Need to configure 'protocols evpn mclag' when evpn is configured with mclag.";
           junos:must "(\".. encapsulation vxlan\")";
           junos:must-message "Extended VNI list can only be configured with encapsulation vxlan";
           junos:must "((\".. .. .. instance-type virtual-switch\" || \".. .. .. instance-type mac-vrf\"))";
           junos:must-message "Extended VNI list can only be configured in a virtual switch instance";
           type string;
         }
       }
       case case_3 {
         leaf-list extended-isid-list {
           description "Configure list of isids or all for extending to PBB EVPN";
           junos:must "(\".. pbb-evpn-core\")";
           junos:must-message "Extended ISID list can only be configured in the PBB EVPN";
           junos:must "(\".. .. .. instance-type virtual-switch\")";
           junos:must-message "Extended ISID list can only be configured in a virtual switch instance";
           type string;
         }
       }
     }
     container evi-options {
       description "EVI options";
       junos:must "(\".. extended-isid-list\")";
       junos:must-message "Extended-isid-list must be configured";
       uses juniper-protocols-evi-options;
     }
     leaf p2mp-bud-support {
       description "Enable EVPN to act as P2MP transit and egress PE (bud)";
       type empty;
     }
     container remote-ip-host-routes {
       presence "enable remote-ip-host-routes";
       junos:must "(!(\".. encapsulation mpls-inet6\"))";
       junos:must-message "VMTO not supported with encapsulation mpls-inet6";
       junos:must "(!(\".. .. .. instance-type vrf\"))";
       junos:must-message "remote-ip-host-routes knob is for virtual-switch, EVPN or default instance";
       description "Virtual machine traffic optimization(VMTO) for EVPN";
       uses apply-advanced;
       leaf-list import {
         ordered-by user;
         description "Policy to control the creation of remote IP host routes";
         type jt:policy-algebra;
       }
       leaf no-advertise-community {
         description "Don't advertise Type 2 route's community";
         type empty;
       }
     }
     leaf pbb-evpn-core {
       description "Configure PBB EVPN core";
       junos:must "(!(\".. encapsulation mpls-inet6\"))";
       junos:must-message "PBB not supported with encapsulation mpls-inet6";
       junos:must "(\".. .. .. instance-type virtual-switch\")";
       junos:must-message "pbb-evpn-core can only be configured in a virtual switch instance";
       junos:must "(\"chassis network-services enhanced-ip\")";
       junos:must-message "PBB EVPN supported only with enhanced-ip mode";
       type empty;
     }
     leaf label-allocation {
       description "Label allocation policy";
       junos:must "(!(\".. encapsulation vxlan\"))";
       junos:must-message "label-allocation cannot coexist with encapsulation vxlan option";
       type enumeration {
         enum "per-instance" {
           description "Allocate one label for the entire instance";
         }
       }
     }
     leaf evpn-etree {
       description "Evpn etree mode";
       junos:must "(!(\".. encapsulation mpls-inet6\"))";
       junos:must-message "Not supported for encapsulation mpls-inet6";
       type empty;
     }
     container assisted-replication {
       junos:must "(!(\"forwarding-options multicast-replication evpn irb local-only\"))";
       junos:must-message "Assisted Replication is not valid with forwarding-options multicast-replication evpn irb local-only";
       junos:must "(\".. encapsulation vxlan\")";
       junos:must-message "Assisted Replication is supported only with encapsulation vxlan option";
       description "Option to enable Assisted Replication";
       uses apply-advanced;
       choice AR {
         case case_1 {
           container leaf {
             presence "enable leaf";
             description "Assisted Replicator Leaf";
             uses apply-advanced;
             leaf replicator-activation-delay {
               description "Dealy interval in starting replication";
               default "10";
               units "seconds";
               type union {
                 type string {
                   pattern "<.*>|$.*";
                 }
                 type uint32 {
                   range "0 .. 180";
                 }
               }
             }
           }
         }
         case case_2 {
           container replicator {
             presence "enable replicator";
             description "Assisted Replicator";
             uses apply-advanced;
             choice family {
               case case_1 {
                 container inet {
                   presence "enable inet";
                   description "IPv4 source";
                   uses apply-advanced;
                   leaf ip {
                     description "Assisted Replicator IP address";
                     type jt:ipv4addr;
                   }
                 }
               }
             }
             leaf vxlan-encapsulation-source-ip {
               description "VXLAN encapsulation source IP for replicated traffic";
               type enumeration {
                 enum "ingress-replication-ip" {
                   description "Use regular ingress replication IP address";
                 }
               }
             }
           }
         }
       }
     }
     container vrf-target {
       junos:must "((\".. extended-isid-list\" || \".. extended-vlan-list\"))";
       junos:must-message "Extended-isid-list or extended-vlan-list must be configured";
       description "VRF target community configuration";
       uses apply-advanced;
       leaf community {
         description "Target community to use in import and export";
         type string {
           junos:posix-pattern "^[a-z]+:[0-9.]+L?:[0-9]+$";
           junos:pattern-message "Use format 'target:x:y' where 'x' is an AS number followed by an optional 'L' (To indicate 4 byte AS), or an IP address and 'y' is a number. e.g. target:123456L:100";
         }
       }
     }
     container interconnect {
       description "Interconnect";
       uses juniper-protocols-evpn-interconnect;
     }
     leaf pmsi-tunnel-endpoint {
       description "IM IR PMSI tunnel Endpoint for remote PE";
       junos:must "(!(\".. pbb-evpn-core\"))";
       junos:must-message "Not Supported for PBB EVPN";
       junos:must "(!(\".. encapsulation mpls-inet6\"))";
       junos:must-message "Not supported for encapsulation mpls-inet6";
       junos:must "(!(\".. encapsulation vxlan\"))";
       junos:must-message "Not Supported for EVPN-VXLAN encapsulation";
       junos:must "(!(\".. .. .. provider-tunnel\"))";
       junos:must-message "Not Applicable for P2MP Tunnels";
       junos:must "(!(\".. .. .. instance-type evpn-vpws\"))";
       junos:must-message "Not Applicable for instance-type EVPN-VPWS";
       type jt:ipv4addr;
     }
     leaf pmsi-tunnel-endpoint-inet6 {
       description "IM IR PMSI IPv6 tunnel Endpoint for remote PE";
       junos:must "(\".. encapsulation mpls-inet6\")";
       junos:must-message "Supported for mpls-inet6 encapsulation only";
       junos:must "(!(\".. .. .. instance-type evpn-vpws\"))";
       junos:must-message "Not Applicable for instance-type EVPN-VPWS";
       type jt:ipv6addr;
     }
     leaf normalization {
       description "Enable vlan id normalization for interfaces";
       junos:must "(!(\".. encapsulation vxlan\"))";
       junos:must-message "Not applicable for EVPN-VXLAN encapsulation";
       junos:must "((\".. .. .. instance-type mac-vrf\" && \".. .. .. service-type vlan-based\"))";
       junos:must-message "Applicable for mac-vrf vlan-based service only";
       type empty;
     }
     leaf smet-etag-carry-vid {
       description "SMET Type 6,7 and 8 Routes to carry vlan id in Ethernet Tag field";
       junos:must "((\".. .. .. instance-type mac-vrf\" && \".. .. .. service-type vlan-based\"))";
       junos:must-message "Applicable for mac-vrf vlan-based service only";
       type empty;
     }
     container irb-symmetric-routing {
       junos:must "(\".. .. .. instance-type vrf\")";
       junos:must-message "EVPN T-2 symmetric-routing must be configured with instance-type vrf";
       description "Enable EVPN T-2 symmtric routing";
       uses apply-advanced;
       leaf vni {
         description "VXLAN network identifier used for T-2 Symmetric Routing IP prefixes";
         type union {
           type string {
             pattern "<.*>|$.*";
           }
           type uint32 {
             range "1 .. 16777214";
           }
         }
       }
     }
     container ip-prefix-routes {
       presence "enable ip-prefix-routes";
       junos:must "(\".. .. .. instance-type vrf\")";
       junos:must-message "ip-prefix-routes must be configured with instance-type vrf";
       description "Advertise IP prefixes through EVPN";
       uses apply-advanced;
       leaf advertise {
         description "Advertisement attributes for IP prefixes";
         type enumeration {
           enum "gateway-address" {
             description "Advertise a gateway address in exported IP prefix routes";
             junos:must "(\".. gateway-interface\")";
             junos:must-message "advertise gateway-address must be configured with gateway-interface";
           }
           enum "direct-nexthop" {
             description "Advertise a direct nexthop in exported IP prefix routes";
             junos:must "((\".. encapsulation vxlan\" || \".. .. .. .. vrf-table-label\"))";
             junos:must-message "vrf-table-label must be used unless encapsulation vxlan is configured";
           }
         }
       }
       leaf gateway-interface {
         description "Gateway interface used when gateway address is advertised";
         junos:must "(\".. advertise gateway-address\")";
         junos:must-message "gateway-interface must be configured with advertise gateway-address";
         junos:must "(\".. .. .. .. interface $$\")";
         junos:must-message "Interface must configured in this routing instance";
         junos:must "(\"interfaces $$ family inet\")";
         junos:must-message "Family inet must be defined";
         junos:must "(\"interfaces $$\")";
         junos:must-message "Interface must be defined";
         type union {
           type jt:interface-unit;
           type string {
             pattern "<.*>|$.*";
           }
         }
       }
       leaf encapsulation {
         description "Encapsulation used for IP prefixes";
         type enumeration {
           enum "mpls" {
             description "MPLS encapsulation";
             junos:must "(\".. advertise direct-nexthop\")";
             junos:must-message "encapsulation must be configured with advertise direct-nexthop";
           }
           enum "vxlan" {
             description "VXLAN encapsulation";
             junos:must "(\".. vni\")";
             junos:must-message "encapsulation vxlan must be configured with vni";
             junos:must "((\".. advertise direct-nexthop\" || \".. .. irb-symmetric-routing\"))";
             junos:must-message "encapsulation must be configured with advertise direct-nexthop or irb-symmetric-routing";
           }
         }
       }
       leaf reject-asymmetric-vni {
         description "Disable Type-5 asymmetric-vni";
         junos:must "(\".. encapsulation vxlan\")";
         junos:must-message "encapsulation must be configured as VxLAN";
         type empty;
       }
       leaf vni {
         description "VXLAN network identifier used for IP prefixes";
         junos:must "(\".. encapsulation vxlan\")";
         junos:must-message "vni must be configured with encapsulation vxlan";
         junos:must "((\".. advertise direct-nexthop\" || \".. .. irb-symmetric-routing\"))";
         junos:must-message "vni must be configured with advertise direct-nexthop or irb-symmetric-routing";
         type union {
           type string {
             pattern "<.*>|$.*";
           }
           type uint32 {
             range "1 .. 16777214";
           }
         }
       }
       leaf-list import {
         ordered-by user;
         description "Policy to control import of IP prefixes from EVPN";
         type jt:policy-algebra;
       }
       leaf-list export {
         ordered-by user;
         description "Policy to control export of IP prefixes through EVPN";
         type jt:policy-algebra;
       }
       container route-attributes {
         description "Route Attribute Import Export Option";
         uses apply-advanced;
         container as-path {
           description "AS-PATH Attribute";
           uses apply-advanced;
           leaf import-action {
             description "AS-PATH Attribute Inherit Option on Import";
             type enumeration {
               enum "allow" {
                 description "Inherit as-path from EVPN routes to IP routes";
               }
               enum "skip" {
                 description "Donot inehrit as-path from EVPN routes to IP routes";
               }
             }
           }
           leaf export-action {
             description "AS-PATH Attribute Inherit Option on Export";
             type enumeration {
               enum "allow" {
                 description "Inherit as-path from IP routes to EVPN routes";
               }
               enum "skip" {
                 description "Donot inherit as-path from IP routes to EVPN routes";
               }
             }
           }
         }
         container preference {
           description "Preference Attribute";
           uses apply-advanced;
           leaf import-action {
             description "Preference Attribute Inerit Option on Import";
             type enumeration {
               enum "allow" {
                 description "Inherit preference from EVPN routes to IP routes";
               }
               enum "skip" {
                 description "Donot inherit preference from EVPN routes to EVPN routes";
               }
             }
           }
           leaf export-action {
             description "Preference Attribute Inherit Option on Export";
             type enumeration {
               enum "allow" {
                 description "Inherit preference from IP routes to EVPN routes";
               }
               enum "skip" {
                 description "Donot inherit preference from IP routes to EVPN routes";
               }
             }
           }
         }
         container community {
           description "Community Attribute";
           uses apply-advanced;
           leaf import-action {
             description "Community Attribute Inherit Option on Import";
             type enumeration {
               enum "allow" {
                 description "Inherit community from EVPN routes to IP routes";
               }
               enum "skip" {
                 description "Donot inherit community from EVPN routes to IP routes";
               }
             }
           }
           leaf export-action {
             description "Community Attribute Inherit Option on Export";
             type enumeration {
               enum "allow" {
                 description "Inherit community from IP routes to EVPN routes";
               }
               enum "skip" {
                 description "Donot inherit community from IP route to EVPN routes";
               }
             }
           }
         }
       }
     }
     leaf igmp-id {
       description "EVPN IGMP Identifier value";
       junos:must "(!(\".. encapsulation mpls-inet6\"))";
       junos:must-message "IGMP snooping not supported with encapsulation mpls-inet6";
       type union {
         type string {
           pattern "<.*>|$.*";
         }
         type uint32 {
           range "1 .. 65535";
         }
       }
     }
     leaf multicast-mode {
       description "Multicast mode for EVPN";
       default "ingress-replication";
       junos:must "(\".. encapsulation vxlan\")";
       junos:must-message "multicast-mode can only be configured with encapsulation vxlan";
       junos:must "((((\".. .. .. instance-type virtual-switch\" || \".. .. .. instance-type mac-vrf\") && !(\".. .. .. switch-options route-distinguisher\")) || \".. .. .. switch-options route-distinguisher\"))";
       junos:must-message "multicast-mode can only be configured in a virtual switch instance";
       junos:must "(\".. .. .. switch-options route-distinguisher\")";
       junos:must-message "Multicast mode can only be configured if route-distinguisher is configured";
       type enumeration {
         enum "ingress-replication" {
           description "Ingress Replication";
         }
       }
     }
     container oism {
       junos:must "(\".. oism supplemental-bridge-domain-irb\")";
       junos:must-message "OISM must be configured with Supplemental Bridge Domain";
       junos:must "(\".. .. .. instance-type vrf\")";
       junos:must-message "oism must be configured with instance-type vrf";
       description "EVPN Multicast OISM features";
       uses apply-advanced;
       leaf supplemental-bridge-domain-irb {
         description "OISM SBD irb interface address";
         junos:must "(\".. .. .. .. interface $$\")";
         junos:must-message "Interface must configured in this routing instance";
         junos:must "(\"interfaces $$\")";
         junos:must-message "Interface must be defined";
         type union {
           type jt:interface-unit;
           type string {
             pattern "<.*>|$.*";
           }
         }
       }
       leaf originate-smet-on-revenue-vlan-too {
         description "Originate smet route on revenue vlan too";
         type empty;
       }
       container pim-evpn-gateway {
         presence "enable pim-evpn-gateway";
         description "Configure PIM EVPN Gateway PEG parameters";
         uses apply-advanced;
         list external-irb {
           key name;
           ordered-by user;
           description "List of IRBs for external connectivity";
           leaf name {
             description "External vlan interface name";
             junos:must "(\".. .. .. .. .. .. interface $$\")";
             junos:must-message "Interface must be configured in this instance";
             junos:must "(\"interfaces $$\")";
             junos:must-message "Interface must be defined";
             type union {
               type jt:interface-name;
               type string {
                 pattern "<.*>|$.*";
               }
             }
           }
           uses apply-advanced;
         }
       }
     }
     choice flexible-cross-connect-type {
       case case_1 {
         leaf flexible-cross-connect-vlan-aware {
           description "Enable EVPN flexible cross-connect VLAN aware Service";
           junos:must "(!(\".. encapsulation mpls-inet6\"))";
           junos:must-message "EVPN flexible cross-connect not supported with encapsulation mpls-inet6";
           junos:must "(!(\".. flexible-cross-connect-vlan-unaware\"))";
           junos:must-message "VPWS Instance can support either vlan aware or unaware service";
           junos:must "(\".. .. .. instance-type evpn-vpws\")";
           junos:must-message "instance-type evpn-vpws must be configured";
           type empty;
         }
       }
       case case_2 {
         leaf flexible-cross-connect-vlan-unaware {
           description "Enable EVPN flexible cross-connect VLAN unaware Service";
           junos:must "(!(\".. flexible-cross-connect-vlan-aware\"))";
           junos:must-message "VPWS Instance can support either vlan aware or unaware service";
           junos:must "(!(\".. encapsulation mpls-inet6\"))";
           junos:must-message "EVPN flexible cross-connect not supported with encapsulation mpls-inet6";
           junos:must "(\".. .. .. instance-type evpn-vpws\")";
           junos:must-message "instance-type evpn-vpws must be configured";
           type empty;
         }
       }
     }
     leaf auto-service-id {
       description "Enable auto-derivation of VPWS service instance identifier";
       junos:must "(\".. flexible-cross-connect-vlan-aware\")";
       junos:must-message "flexible-cross-connect-vlan-aware must be configured";
       junos:must "(\".. .. .. instance-type evpn-vpws\")";
       junos:must-message "instance-type evpn-vpws must be configured";
       type empty;
     }
     leaf hot-standby-on {
       description "Activate evpn vpws upon becoming DF";
       junos:must "(\".. .. .. instance-type evpn-vpws\")";
       junos:must-message "instance-type evpn-vpws must be configured";
       type empty;
     }
     list group {
       key name;
       ordered-by user;
       description "Enable EVPN flexible cross-connect VLAN unaware Service";
       junos:must "(\".. flexible-cross-connect-vlan-unaware\")";
       junos:must-message "flexible-cross-connect-vlan-unaware must be configured";
       junos:must "(\".. .. .. instance-type evpn-vpws\")";
       junos:must-message "instance-type evpn-vpws must be configured";
       leaf name {
         description "Group name to group vlan unaware cross connects";
         type string;
       }
       uses apply-advanced;
       container esi {
         presence "enable esi";
         description "ESI configuration to group vlan unaware cross connects";
         uses apply-advanced;
         leaf identifier {
           description "ESI value for grouping of vlan unaware cross connects";
           type jt:esi;
         }
       }
       list interface {
         key name;
         ordered-by user;
         description "Name of the  interface part of vlan unaware fxc";
         leaf name {
           description "Interface name";
           type union {
             type jt:interface-name;
             type string {
               pattern "<.*>|$.*";
             }
           }
         }
         uses apply-advanced;
       }
       container service-id {
         presence "enable service-id";
         description "Service-id for vlan unaware cross connects for  EVPN VPWS";
         uses apply-advanced;
         leaf local {
           description "Local service id for vlan unaware service";
           junos:must "(unique \".. .. group <*> service-id local $$\")";
           junos:must-message "Unique Local SID can only be configured ";
           junos:must "(unique \".. .. interface <*> vpws-service-id local $$\")";
           junos:must-message "Unique Local SID can only be configured ";
           type union {
             type string {
               pattern "<.*>|$.*";
             }
             type uint32 {
               range "1 .. 16777215";
             }
           }
         }
         leaf remote {
           description "Remote service id for vlan unaware service";
           junos:must "(unique \".. .. group <*> service-id remote $$\")";
           junos:must-message "Unique Remote SID can only be configured ";
           junos:must "(unique \".. .. interface <*> vpws-service-id remote $$\")";
           junos:must-message "Unique Remote SID can only be configured ";
           type union {
             type string {
               pattern "<.*>|$.*";
             }
             type uint32 {
               range "1 .. 16777215";
             }
           }
         }
       }
     }
     container vni-options {
       junos:must "(\".. .. .. vrf-target\")";
       junos:must-message "vrf-target must be configured";
       junos:must "((\".. extended-vni-list\" || \".. .. .. instance-type mac-vrf\"))";
       junos:must-message "Extended-vni-list must be configured for non mac-vrf instance";
       junos:must "(\".. encapsulation vxlan\")";
       junos:must-message "encapsulation vxlan must be configured";
       description "VNI options";
       uses apply-advanced;
       list vni {
         key name;
         description "Per-vni options";
         leaf name {
           type union {
             type string {
               pattern "<.*>|$.*";
             }
             type int32 {
               range "1 .. 16777214";
             }
           }
         }
         uses apply-advanced;
         container vrf-target {
           description "VRF target community configuration";
           uses apply-advanced;
           leaf export {
             description "Target community to use when marking routes on export";
             status deprecated;
             type string {
               junos:posix-pattern "^[a-z]+:[0-9.]+L?:[0-9]+$";
               junos:pattern-message "Use format 'target:x:y' where 'x' is an AS number followed by an optional 'L' (To indicate 4 byte AS), or an IP address and 'y' is a number. e.g. target:123456L:100";
             }
           }
           leaf community {
             description "Target community";
             type string {
               junos:posix-pattern "^[a-z]+:[0-9.]+L?:[0-9]+$";
               junos:pattern-message "Use format 'target:x:y' where 'x' is an AS number followed by an optional 'L' (To indicate 4 byte AS), or an IP address and 'y' is a number. e.g. target:123456L:100";
             }
           }
         }
       }
     }
     container traceoptions {
       description "Trace options for Layer 2 VPNs";
       uses apply-advanced;
       container file {
         description "Trace file options";
         leaf filename {
           description "Name of file in which to write trace information";
           type string {
             length "1 .. 1024";
             junos:posix-pattern "![/ %]";
             junos:pattern-message "Must not contain '/', % or a space";
           }
         }
         leaf replace {
           description "Replace trace file rather than appending to it";
           status deprecated;
           type empty;
         }
         leaf size {
           description "Maximum trace file size";
           type string;
         }
         leaf files {
           description "Maximum number of trace files";
           default "10";
           type union {
             type string {
               pattern "<.*>|$.*";
             }
             type uint32 {
               range "2 .. 1000";
             }
           }
         }
         leaf no-stamp {
           description "Do not timestamp trace file";
           status deprecated;
           type empty;
         }
         choice world-readable-choice {
           leaf world-readable {
             description "Allow any user to read the log file";
             type empty;
           }
           leaf no-world-readable {
             description "Don't allow any user to read the log file";
             type empty;
           }
         }
       }
       list flag {
         key name;
         ordered-by user;
         description "Tracing parameters";
         leaf name {
           type enumeration {
             enum "error" {
               description "Trace errors";
             }
             enum "topology" {
               description "Trace Layer 2 VPN, VPLS and EVPN topology changes";
             }
             enum "nlri" {
               description "Trace Layer 2 VPN, VPLS and EVPN remote site advertisements";
             }
             enum "connections" {
               description "Trace Layer 2 VPN and VPLS connections";
             }
             enum "automatic-site" {
               description "Trace VPLS automatic site state";
             }
             enum "oam" {
               description "Trace OAM messages";
             }
             enum "mac-database" {
               description "Trace MAC route database in a EVPN instance";
             }
             enum "nsr" {
               description "Trace NSR in a EVPN instance";
             }
             enum "egress-protection" {
               description "Trace Edge Protection messages";
             }
             enum "instance" {
               description "Evpn instance related messages";
             }
             enum "interface" {
               description "Interface related messages";
             }
             enum "l2aldsync" {
               description "Messages related to EVPN-L2ALD communication";
             }
             enum "p2mp" {
               description "P2MP messages";
             }
             enum "esi" {
               description "Evpn ethernet segment related messages";
             }
             enum "mcsn" {
               description "Evpn multicast snooping related messages";
             }
             enum "vpws" {
               description "VPWS messages";
             }
             enum "irb" {
               description "Integrated routing bridging messages";
             }
             enum "ar" {
               description "Assisted-replication messages";
             }
             enum "etree" {
               description "Evpn etree messages";
             }
             enum "kernel" {
               description "Messages related to rpd-kernel communication";
             }
             enum "bd" {
               description "Evpn bridge domain messages";
             }
             enum "pbb" {
               description "Evpn provider backbone bridging messages";
             }
             enum "infra" {
               description "Messages related to infrastructure in evpn";
             }
             enum "pfxdb" {
               description "Type-5 related messages";
             }
             enum "route" {
               description "Trace routing information";
             }
             enum "normal" {
               description "Trace normal events";
             }
             enum "general" {
               description "Trace general events";
             }
             enum "state" {
               description "Trace state transitions";
             }
             enum "policy" {
               description "Trace policy processing";
             }
             enum "task" {
               description "Trace routing protocol task processing";
             }
             enum "timer" {
               description "Trace routing protocol timer processing";
             }
             enum "all" {
               description "Trace everything";
             }
           }
         }
         leaf send {
           description "Trace transmitted packets";
           type empty;
         }
         leaf receive {
           description "Trace received packets";
           type empty;
         }
         leaf detail {
           description "Trace detailed information";
           type empty;
         }
         leaf disable {
           description "Disable this trace flag";
           type empty;
         }
       }
     }
     leaf encapsulation-type {
       description "Encapsulation type for VPN";
       type enumeration {
         enum "atm-aal5" {
           description "ATM AAL/5 encapsulation";
         }
         enum "atm-cell" {
           description "ATM port promiscuous mode cell encapsulation";
         }
         enum "atm-cell-port-mode" {
           description "ATM port promiscuous mode cell encapsulation";
         }
         enum "atm-cell-vp-mode" {
           description "ATM VP promiscuous mode cell encapsulation";
         }
         enum "atm-cell-vc-mode" {
           description "ATM non-promiscuous cell encapsulation";
         }
         enum "frame-relay" {
           description "Frame Relay encapsulation";
         }
         enum "ppp" {
           description "PPP encapsulation";
         }
         enum "cisco-hdlc" {
           description "Cisco-compatible HDLC encapsulation";
         }
         enum "ethernet-vlan" {
           description "Ethernet VLAN encapsulation";
         }
         enum "ethernet" {
           description "Ethernet encapsulation";
         }
         enum "interworking" {
           description "Layer 2.5 interworking VPN";
         }
         enum "frame-relay-port-mode" {
           description "Frame Relay port mode encapsulation";
         }
         enum "satop-t1" {
           description "SATOP-T1 based Layer 2 VPN";
         }
         enum "satop-e1" {
           description "SATOP-E1 based Layer 2 VPN";
         }
         enum "satop-t3" {
           description "SATOP-T3 based Layer 2 VPN";
         }
         enum "satop-e3" {
           description "SATOP-E3 based Layer 2 VPN";
         }
         enum "cesop" {
           description "CESOP based Layer 2 VPN";
         }
       }
     }
     leaf control-word {
       description "Add control word to the Layer 2 encapsulation";
       type empty;
     }
     leaf no-control-word {
       description "Disables control word on the Layer 2 encapsulation";
       type empty;
     }
     leaf site-range {
       description "Maximum site identifier in this VPLS domain";
       type union {
         type string {
           pattern "<.*>|$.*";
         }
         type uint32 {
           range "1 .. 65534";
         }
       }
     }
     leaf label-block-size {
       description "Label block size for this VPLS instance";
       type enumeration {
         enum "2" {
           description "Label block size of 2";
         }
         enum "4" {
           description "Label block size of 4";
         }
         enum "8" {
           description "Label block size of 8";
         }
         enum "16" {
           description "Label block size of 16";
         }
       }
     }
     choice tunnel-services-choice {
       case case_1 {
         container tunnel-services {
           description "Use tunnel services for this VPLS instance";
           uses apply-advanced;
           leaf-list devices {
             ordered-by user;
             description "Tunnel services devices to use for this VPLS instance";
             type union {
               type jt:interface-device;
               type string {
                 pattern "<.*>|$.*";
               }
             }
           }
           leaf primary {
             description "Primary tunnel services device to use for VPLS instance";
             type union {
               type jt:interface-device;
               type string {
                 pattern "<.*>|$.*";
               }
             }
           }
         }
       }
       case case_2 {
         leaf no-tunnel-services {
           description "Do not use tunnel services for this VPLS instance";
           type empty;
         }
       }
     }
     leaf community {
       description "Community associated with this VPLS instance";
       type string;
     }
     leaf vpls-id {
       description "Identifier for this VPLS instance";
       type string;
     }
     leaf mtu {
       description "MTU to be advertised to the remote end";
       type union {
         type string {
           pattern "<.*>|$.*";
         }
         type uint16 {
           range "512 .. 65535";
         }
       }
     }
     leaf ignore-mtu-mismatch {
       description "Allow different MTU values on local and remote end";
       type empty;
     }
     container mac-flush {
       presence "enable mac-flush";
       description "Enables mac-flush processing";
       uses apply-advanced;
       leaf any-interface {
         description "Send mac-flush when any AC interface goes down";
         junos:must "((\".. .. vpls-id\" || any \".. .. mesh-group <*> vpls-id\"))";
         junos:must-message "'any-interface' can be configured only for LDP VPLS";
         type empty;
       }
       leaf any-spoke {
         description "Send mac-flush when any spoke pseudo wire goes down";
         junos:must "((\".. .. vpls-id\" || any \".. .. mesh-group <*> vpls-id\"))";
         junos:must-message "'any-spoke' can be configured only for LDP VPLS";
         type empty;
       }
       leaf propagate {
         description "Propagate mac-flush to the core";
         junos:must "((\".. .. vpls-id\" || any \".. .. mesh-group <*> vpls-id\"))";
         junos:must-message "'propagate' can be configured only for LDP VPLS";
         type empty;
       }
     }
     leaf ignore-encapsulation-mismatch {
       description "Allow different encapsulation types on local and remote end";
       type empty;
     }
     leaf pseudowire-status-tlv {
       description "Send pseudowire status TLV";
       type empty;
     }
     leaf flow-label-transmit {
       description "Advertise capability to push Flow Label in transmit direction to remote PE";
       type empty;
     }
     leaf flow-label-receive {
       description "Advertise capability to pop Flow Label in receive direction to remote PE";
       type empty;
     }
     leaf flow-label-transmit-static {
       description "Push Flow Label on PW packets sent to remote PE";
       junos:must "((\".. vpls-id\" || (\".. .. .. l2vpn-id\" || (\".. .. .. instance-type evpn-vpws\" || (\".. .. .. instance-type evpn\" || \".. .. .. instance-type virtual-switch\")))))";
       junos:must-message "Flow-Label static only supported for FEC128 or FEC129 VPLS, EVPN, Virtual-switch or VPWS";
       junos:must "(!(\".. flow-label-transmit\"))";
       junos:must-message "Can't have flow-label-transmit-static along with flow-label-transmit";
       type empty;
     }
     leaf flow-label-receive-static {
       description "Pop Flow Label from PW packets received from remote PE";
       junos:must "((\".. vpls-id\" || (\".. .. .. l2vpn-id\" || (\".. .. .. instance-type evpn-vpws\" || (\".. .. .. instance-type evpn\" || \".. .. .. instance-type virtual-switch\")))))";
       junos:must-message "Flow-Label static only supported for FEC128 or FEC129 VPLS, EVPN, Virtual-switch or VPWS";
       junos:must "(!(\".. flow-label-receive\"))";
       junos:must-message "Can't have flow-label-receive-static along with flow-label-receive";
       type empty;
     }
     container associate-profile {
       description "Associate profile options for dynamic IFL";
       uses apply-advanced;
       leaf profile-name {
         description "Associated profile name";
         type string {
           length "1 .. 81";
         }
       }
       leaf profile-variable-set {
         description "Associate dynamic variable set with the profile";
         type string {
           length "1 .. 81";
         }
       }
     }
     leaf connectivity-type {
       description "Specify type of interface sufficient to bring vpls connection up";
       type enumeration {
         enum "ce" {
           description "CE interface is required";
         }
         enum "irb" {
           description "IRB interface is sufficient";
         }
         enum "permanent" {
           description "Pseudowire permanently up";
         }
       }
     }
     list import-labeled-routes {
       key name;
       ordered-by user;
       description "Import ingress label route to instance.mpls.0 from mpls.0";
       junos:must "(!(\".. neighbor\"))";
       junos:must-message "not supported for static vpls";
       leaf name {
         description "Routing instance name where label route has to be imported";
         junos:must "(\"routing-instances $$ protocols mpls\")";
         junos:must-message "protocols MPLS must be configured on routing-instance to import the labeled routes";
         junos:must "(\"routing-instances $$ instance-type virtual-router\")";
         junos:must-message "Ingress labelled route can be imported only to routing-instance type virtual-router";
         junos:must "(\"routing-instances $$\")";
         junos:must-message "Referenced routing instance must be defined";
         type string;
       }
     }
     container oam {
       description "OAM Configuration for VPN";
       uses apply-advanced;
       leaf ping-interval {
         description "Time interval between ping messages";
         default "60";
         units "seconds";
         type union {
           type string {
             pattern "<.*>|$.*";
           }
           type uint16 {
             range "30 .. 3600";
           }
         }
       }
       leaf ping-multiplier {
         description "Number of ping reply missed before declaring BFD down";
         type union {
           type string {
             pattern "<.*>|$.*";
           }
           type uint8 {
             range "1 .. 5";
           }
         }
       }
       container bfd-liveness-detection {
         description "Bidirectional Forwarding Detection (BFD) options";
         uses apply-advanced;
         leaf version {
           description "BFD protocol version number";
           default "automatic";
           type enumeration {
             enum "0" {
               description "BFD version 0 (deprecated)";
             }
             enum "1" {
               description "BFD version 1";
             }
             enum "automatic" {
               description "Choose BFD version automatically";
             }
           }
         }
         leaf minimum-interval {
           description "Minimum transmit and receive interval";
           units "milliseconds";
           type union {
             type string {
               pattern "<.*>|$.*";
             }
             type uint32 {
               range "1 .. 255000";
             }
           }
         }
         leaf minimum-transmit-interval {
           description "Minimum transmit interval";
           status deprecated;
           units "milliseconds";
           type union {
             type string {
               pattern "<.*>|$.*";
             }
             type uint32 {
               range "1 .. 255000";
             }
           }
         }
         leaf minimum-receive-interval {
           description "Minimum receive interval";
           units "milliseconds";
           type union {
             type string {
               pattern "<.*>|$.*";
             }
             type uint32 {
               range "1 .. 255000";
             }
           }
         }
         leaf multiplier {
           description "Detection time multiplier";
           default "3";
           type union {
             type string {
               pattern "<.*>|$.*";
             }
             type uint32 {
               range "1 .. 255";
             }
           }
         }
         choice adaptation-choice {
           case case_1 {
             leaf no-adaptation {
               description "Disable adaptation";
               type empty;
             }
           }
         }
         container transmit-interval {
           description "Transmit-interval options";
           uses apply-advanced;
           leaf minimum-interval {
             description "Minimum transmit interval";
             units "milliseconds";
             type union {
               type string {
                 pattern "<.*>|$.*";
               }
               type uint32 {
                 range "1 .. 255000";
               }
             }
           }
           leaf threshold {
             description "High transmit interval triggering a trap";
             units "milliseconds";
             type union {
               type uint32;
               type string {
                 pattern "<.*>|$.*";
               }
             }
           }
         }
         container detection-time {
           description "Detection-time options";
           uses apply-advanced;
           leaf threshold {
             description "High detection-time triggering a trap";
             units "milliseconds";
             type union {
               type uint32;
               type string {
                 pattern "<.*>|$.*";
               }
             }
           }
         }
       }
       container control-channel {
         description "Supported control channel type ";
         uses apply-advanced;
         choice action-choice {
           case case_1 {
             leaf pwe3-control-word {
               description "For BGP based PW send oam packets with control word, with 0001b as first nibble";
               type empty;
             }
           }
           case case_2 {
             leaf router-alert-label {
               description "For BGP based PW send oam packets with router alert label";
               type empty;
             }
           }
           case case_3 {
             leaf pw-label-ttl-1 {
               description "For BGP based PW send oam packets with MPLS pw label TTL = 1";
               type empty;
             }
           }
         }
       }
     }
     container multi-homing {
       description "Multi-homing configuration for FEC129 VPLS";
       uses apply-advanced;
       leaf peer-active {
         description "Keep CE interfaces in up state when all BGP peers go down";
         type empty;
       }
       list site {
         key name;
         description "Sites connected to this provider equipment";
         leaf name {
           description "Name of Layer 2 VPN or VPLS site";
           type string;
         }
         uses apply-advanced;
         leaf identifier {
           description "Layer 2 VPN or VPLS multi-homing identifier";
           type union {
             type string {
               pattern "<.*>|$.*";
             }
             type uint16 {
               range "1 .. 65534";
             }
           }
         }
         leaf preference {
           description "Layer 2 VPN or VPLS multi-homing preference";
           type string;
         }
         container active-interface {
           description "Configure interface to designate as active";
           uses apply-advanced;
           choice interface_name {
             case case_1 {
               leaf any {
                 description "One configured interface is designated active at random";
                 type empty;
               }
             }
             case case_2 {
               leaf primary {
                 description "Interface to designate as active if it is operational";
                 junos:must "(\".. .. .. .. .. .. interface $$\")";
                 junos:must-message "Interface must be part of this VPLS routing instance";
                 type union {
                   type jt:interface-name;
                   type string {
                     pattern "<.*>|$.*";
                   }
                 }
               }
             }
           }
         }
         list interface {
           key name;
           ordered-by user;
           description "Interface that connects this site to the VPN";
           leaf name {
             description "Interface name";
             junos:must "(\".. .. .. .. .. .. interface $$\")";
             junos:must-message "Interface must be part of this VPLS routing instance";
             type union {
               type jt:interface-name;
               type string {
                 pattern "<.*>|$.*";
               }
             }
           }
           uses apply-advanced;
           leaf preference {
             description "Layer 2 VPN or VPLS multi-homing preference for the interface";
             type union {
               type string {
                 pattern "<.*>|$.*";
               }
               type uint16 {
                 range "1 .. 65535";
               }
             }
           }
         }
         leaf peer-active {
           description "Keep CE interfaces in up state when all BGP peers go down";
           type empty;
         }
       }
     }
   }
   grouping juniper-protocols-evi-options {
     uses apply-advanced;
     list isid {
       key name;
       description "Per-evi options";
       leaf name {
         type union {
           type string {
             pattern "<.*>|$.*";
           }
           type int32 {
             range "256 .. 16777214";
           }
         }
       }
       uses apply-advanced;
       container vrf-target {
         description "VRF target community configuration";
         uses apply-advanced;
         leaf community {
           description "Target community";
           type string {
             junos:posix-pattern "^[a-z]+:[0-9.]+L?:[0-9]+$";
             junos:pattern-message "Use format 'target:x:y' where 'x' is an AS number followed by an optional 'L' (To indicate 4 byte AS), or an IP address and 'y' is a number. e.g. target:123456L:100";
           }
         }
       }
     }
   }
   grouping juniper-protocols-evpn-interconnect {
     description "Interconnect configuration for the routing instance";
     uses apply-advanced;
     leaf-list vrf-import {
       ordered-by user;
       description "Import policy for Interconnect";
       junos:must "(\".. route-distinguisher\")";
       junos:must-message "route distinguisher must be defined for vrf-import";
       type jt:policy-algebra;
     }
     leaf-list vrf-export {
       ordered-by user;
       description "Export policy for Interconnect";
       junos:must "(\".. route-distinguisher\")";
       junos:must-message "route distinguisher must be defined for vrf-export";
       type jt:policy-algebra;
     }
     container vrf-target {
       junos:must "(\".. route-distinguisher\")";
       junos:must-message "route distinguisher must be defined for vrf-target";
       description "Interconnect target community configuration";
       uses apply-advanced;
       leaf community {
         description "Target community to use in import and export";
         type string {
           junos:posix-pattern "^[a-z]+:[0-9.]+L?:[0-9]+$";
           junos:pattern-message "Use format 'target:x:y' where 'x' is an AS number followed by an optional 'L' (To indicate 4 byte AS), or an IP address and 'y' is a number. e.g. target:123456L:100";
         }
       }
       leaf import {
         description "Target community to use when filtering on import";
         type string {
           junos:posix-pattern "^[a-z]+:[0-9.]+L?:[0-9]+$";
           junos:pattern-message "Use format 'target:x:y' where 'x' is an AS number followed by an optional 'L' (To indicate 4 byte AS), or an IP address and 'y' is a number. e.g. target:123456L:100";
         }
       }
       leaf export {
         description "Target community to use when marking routes on export";
         type string {
           junos:posix-pattern "^[a-z]+:[0-9.]+L?:[0-9]+$";
           junos:pattern-message "Use format 'target:x:y' where 'x' is an AS number followed by an optional 'L' (To indicate 4 byte AS), or an IP address and 'y' is a number. e.g. target:123456L:100";
         }
       }
     }
     container route-distinguisher {
       description "Route distinguisher for this interconnect";
       leaf rd-type {
         description "Number in (16 bit:32 bit) or (32 bit 'L':16 bit) or (IP address:16 bit) format";
         type string {
           junos:posix-pattern "^[0-9.]+L?:[0-9]+$";
           junos:pattern-message "Use format 'x:y' where 'x' is an AS number followed by an optional 'L' (To indicate 4 byte AS), or an IP address and 'y' is a number. e.g. 123456L:100";
         }
       }
     }
     container esi {
       description "ESI configuration of interconnect";
       uses apply-advanced;
       leaf identifier {
         description "ESI value for interconnect";
         junos:must "(unique \"interfaces <*> esi $$\")";
         junos:must-message "ESI value must be unique across all IFDs and IFLs";
         type jt:esi;
       }
       choice mode {
         case case_1 {
           leaf all-active {
             description "All-active mode";
             type empty;
           }
         }
       }
       container df-election-type {
         presence "enable df-election-type";
         description "DF Election Type";
         uses apply-advanced;
         choice pref_choice {
           case case_1 {
             container preference {
               presence "enable preference";
               description "Preference based DF election";
               uses apply-advanced;
               leaf value {
                 description "Preference value for EVPN Multihoming DF election";
                 default "32767";
                 type union {
                   type string {
                     pattern "<.*>|$.*";
                   }
                   type uint32 {
                     range "0 .. 65535";
                   }
                 }
               }
             }
           }
         }
         choice mod_choice {
           case case_1 {
             container mod {
               presence "enable mod";
               junos:must "(!(\".. preference\"))";
               junos:must-message "preference must not be configured";
               description "MOD based DF election";
             }
           }
         }
       }
     }
     leaf-list interconnected-vni-list {
       description "List of translated VNIs (1..16777214) or all, that are to be EVPN interconnected";
       type string;
     }
     leaf-list interconnected-vlan-list {
       ordered-by user;
       description "List of VLAN identifiers that are to be EVPN interconnected";
       type string;
     }
     leaf encapsulation {
       type enumeration {
         enum "mpls" {
           description "MPLS encapsulation";
         }
         enum "vxlan" {
           description "VXLAN encapsulation";
         }
       }
     }
   }
   grouping juniper-protocols-ldp {
     uses apply-advanced;
     container traceoptions {
       description "Trace options for LDP";
       uses apply-advanced;
       container file {
         description "Trace file options";
         leaf filename {
           description "Name of file in which to write trace information";
           type string {
             length "1 .. 1024";
             junos:posix-pattern "![/ %]";
             junos:pattern-message "Must not contain '/', % or a space";
           }
         }
         leaf replace {
           description "Replace trace file rather than appending to it";
           status deprecated;
           type empty;
         }
         leaf size {
           description "Maximum trace file size";
           type string;
         }
         leaf files {
           description "Maximum number of trace files";
           default "10";
           type union {
             type string {
               pattern "<.*>|$.*";
             }
             type uint32 {
               range "2 .. 1000";
             }
           }
         }
         leaf no-stamp {
           description "Do not timestamp trace file";
           status deprecated;
           type empty;
         }
         choice world-readable-choice {
           leaf world-readable {
             description "Allow any user to read the log file";
             type empty;
           }
           leaf no-world-readable {
             description "Don't allow any user to read the log file";
             type empty;
           }
         }
       }
       list flag {
         key name;
         ordered-by user;
         description "Tracing parameters";
         leaf name {
           type enumeration {
             enum "error" {
               description "Trace errored packets";
             }
             enum "event" {
               description "Trace LDP state machine events";
             }
             enum "packet-dump" {
               description "Dump the contents of selected packet types";
             }
             enum "packets" {
               description "Trace all LDP packets";
             }
             enum "periodic" {
               description "Trace periodic (hello and keepalive) packets";
             }
             enum "initialization" {
               description "Trace initialization packets";
             }
             enum "notification" {
               description "Trace notification packets";
             }
             enum "address" {
               description "Trace address packets";
             }
             enum "label" {
               description "Trace label packets";
             }
             enum "binding" {
               description "Trace label binding state";
             }
             enum "path" {
               description "Trace label path state";
             }
             enum "ppmd" {
               description "Trace state and events for ppmd process";
             }
             enum "nsr-synchronization" {
               description "Trace NSR synchronization events";
             }
             enum "link-protection" {
               description "Trace link protection events";
             }
             enum "p2mp-nsr-synchronization" {
               description "Trace p2mp NSR synchronization events";
             }
             enum "route" {
               description "Trace routing information";
             }
             enum "normal" {
               description "Trace normal events";
             }
             enum "general" {
               description "Trace general events";
             }
             enum "state" {
               description "Trace state transitions";
             }
             enum "policy" {
               description "Trace policy processing";
             }
             enum "task" {
               description "Trace routing protocol task processing";
             }
             enum "timer" {
               description "Trace routing protocol timer processing";
             }
             enum "all" {
               description "Trace everything";
             }
           }
         }
         leaf send {
           description "Trace transmitted packets";
           type empty;
         }
         leaf receive {
           description "Trace received packets";
           type empty;
         }
         leaf detail {
           description "Trace detailed information";
           type empty;
         }
         leaf disable {
           description "Disable this trace flag";
           type empty;
         }
         container filter {
           description "Filter to apply to this flag";
           presence "enable filter";
           uses ldp_filter_obj;
         }
       }
     }
     container traffic-statistics {
       description "Collect statistics for LDP label-switched paths";
       uses apply-advanced;
       container file {
         description "Statistics file options";
         leaf filename {
           description "Name of file in which to write trace information";
           type string {
             length "1 .. 1024";
             junos:posix-pattern "![/ %]";
             junos:pattern-message "Must not contain '/', % or a space";
           }
         }
         leaf replace {
           description "Replace trace file rather than appending to it";
           status deprecated;
           type empty;
         }
         leaf size {
           description "Maximum trace file size";
           type string;
         }
         leaf files {
           description "Maximum number of trace files";
           default "10";
           type union {
             type string {
               pattern "<.*>|$.*";
             }
             type uint32 {
               range "2 .. 1000";
             }
           }
         }
         leaf no-stamp {
           description "Do not timestamp trace file";
           status deprecated;
           type empty;
         }
         choice world-readable-choice {
           leaf world-readable {
             description "Allow any user to read the log file";
             type empty;
           }
           leaf no-world-readable {
             description "Don't allow any user to read the log file";
             type empty;
           }
         }
       }
       leaf interval {
         description "Time to collect statistics (seconds)";
         type union {
           type string {
             pattern "<.*>|$.*";
           }
           type int32 {
             range "60 .. 65535";
           }
         }
       }
       leaf no-penultimate-hop {
         description "No penultimate hop statistics collection";
         type empty;
       }
     }
     container graceful-restart {
       description "Configure graceful restart attributes";
       uses apply-advanced;
       choice enable-disable {
         case case_1 {
           leaf disable {
             description "Disable graceful restart";
             type empty;
           }
         }
       }
       leaf helper-disable {
         description "Disable the graceful restart helper capability";
         type empty;
       }
       leaf recovery-time {
         description "Time required for recovery";
         units "seconds";
         type union {
           type string {
             pattern "<.*>|$.*";
           }
           type uint32 {
             range "120 .. 1800";
           }
         }
       }
       leaf maximum-neighbor-recovery-time {
         description "Maximum time stale mappings are maintained";
         units "seconds";
         type union {
           type string {
             pattern "<.*>|$.*";
           }
           type uint32 {
             range "140 .. 1900";
           }
         }
       }
       leaf reconnect-time {
         description "Time required to reestablish session after graceful restart";
         units "seconds";
         type union {
           type string {
             pattern "<.*>|$.*";
           }
           type uint32 {
             range "30 .. 300";
           }
         }
       }
       leaf maximum-neighbor-reconnect-time {
         description "Maximum reconnect time allowed from a restarting neighbor";
         units "seconds";
         type union {
           type string {
             pattern "<.*>|$.*";
           }
           type uint32 {
             range "30 .. 300";
           }
         }
       }
     }
     container auto-targeted-session {
       presence "enable auto-targeted-session";
       description "Configure auto targeted session parameters";
       uses apply-advanced;
       leaf teardown-delay {
         description "Auto targeted session tear down delay";
         default "90";
         units "seconds";
         type union {
           type string {
             pattern "<.*>|$.*";
           }
           type uint32 {
             range "1 .. 300";
           }
         }
       }
       leaf maximum-sessions {
         description "Auto targeted maximum sessions";
         default "100";
         type union {
           type string {
             pattern "<.*>|$.*";
           }
           type uint32 {
             range "1 .. 1000";
           }
         }
       }
       leaf no-rlfa {
         description "Do not allow RLFA in auto targeted sessions";
         type empty;
       }
       leaf no-dynamic-tunnels {
         description "Do not allow dynamic tunnels in auto targeted sessions";
         type empty;
       }
     }
     leaf preference {
       description "Route preference";
       type union {
         type uint32;
         type string {
           pattern "<.*>|$.*";
         }
       }
     }
     leaf no-forwarding {
       description "Do not use LDP ingress routes for forwarding";
       type empty;
     }
     leaf rib-group {
       description "Routing table group for importing ingress routes";
       junos:must "(\"routing-options rib-groups $$\")";
       junos:must-message "Referenced rib-group must be defined";
       type string;
     }
     leaf rib-group6 {
       description "Routing table group for importing ingress v6 routes";
       junos:must "(\"routing-options rib-groups $$\")";
       junos:must-message "Referenced rib-group must be defined";
       type string;
     }
     leaf l2-smart-policy {
       description "Do not export or import Layer 3 FECs for Layer 2 sessions";
       type empty;
     }
     leaf track-igp-metric {
       description "Track the IGP metric";
       type empty;
     }
     leaf strict-targeted-hellos {
       description "Do not send targeted hellos to unconfigured neighbors";
       type empty;
     }
     container longest-match {
       presence "enable longest-match";
       description "Configure longest match";
       uses apply-advanced;
       leaf-list policy {
         ordered-by user;
         description "Longest match import policy";
         type jt:policy-algebra;
       }
     }
     leaf-list color-import-policy {
       ordered-by user;
       description "Import color policy";
       type jt:policy-algebra;
     }
     leaf-list import {
       ordered-by user;
       description "Import policy";
       type jt:policy-algebra;
     }
     leaf-list export {
       ordered-by user;
       description "Export policy";
       type jt:policy-algebra;
     }
     leaf-list egress-policy {
       ordered-by user;
       description "Configure LSP egress policy";
       type jt:policy-algebra;
     }
     leaf-list dod-request-policy {
       ordered-by user;
       description "Configure DoD label request policy";
       type jt:policy-algebra;
     }
     container next-hop {
       description "LDP next-hop control";
       uses apply-advanced;
       container merged {
         junos:must "(\"protocols ldp deaggregate\")";
         junos:must-message "next-hop merged policy requires deaggregate to be enabled.";
         description "Merged next hop";
         uses apply-advanced;
         leaf-list policy {
           ordered-by user;
           description "Merged next-hop policy";
           type jt:policy-algebra;
         }
       }
       container no-rsvp-tunneling {
         junos:must "(\"protocols ldp deaggregate\")";
         junos:must-message "next-hop no-rsvp-tunneling policy requires deaggregate to be enabled.";
         description "No rsvp tunneling";
         uses apply-advanced;
         leaf-list policy {
           ordered-by user;
           description "No rsvp tunneling next-hop policy";
           type jt:policy-algebra;
         }
       }
     }
     choice mtu-discovery-choice {
       leaf mtu-discovery {
         description "Enable TCP path MTU discovery";
         type empty;
       }
       leaf no-mtu-discovery {
         description "Don't enable TCP path MTU discovery";
         type empty;
       }
     }
     choice deaggregate-choice {
       leaf deaggregate {
         description "Deaggregate FECs into separate labels";
         type empty;
       }
       leaf no-deaggregate {
         description "Don't deaggregate FECs into separate labels";
         type empty;
       }
     }
     leaf explicit-null {
       description "Advertise the EXPLICIT_NULL label for egress FECs";
       type empty;
     }
     leaf label-withdrawal-delay {
       description "Delay label withdrawal for FECs to avoid label churn";
       default "60";
       units "seconds";
       type union {
         type string {
           pattern "<.*>|$.*";
         }
         type uint32 {
           range "0 .. 120";
         }
       }
     }
     container make-before-break {
       presence "enable make-before-break";
       description "Configure make before break";
       uses apply-advanced;
       leaf timeout {
         description "Make before break timeout";
         default "30";
         units "seconds";
         type union {
           type string {
             pattern "<.*>|$.*";
           }
           type uint32 {
             range "1 .. 300";
           }
         }
       }
       leaf switchover-delay {
         description "Make before break switchover delay";
         default "3";
         units "seconds";
         type union {
           type string {
             pattern "<.*>|$.*";
           }
           type uint32 {
             range "1 .. 300";
           }
         }
       }
     }
     container transport-address {
       description "Address used for TCP sessions";
       choice address-choice {
         case case_1 {
           leaf router-id {
             description "Use router ID for TCP connections";
             type empty;
           }
         }
         case case_2 {
           leaf interface {
             description "Use interface address for TCP connections";
             type empty;
           }
         }
         case case_3 {
           leaf address {
             description "Use specified address for TCP connections";
             type jt:ipaddr;
           }
         }
       }
     }
     leaf keepalive-interval {
       description "Keepalive interval (seconds)";
       type union {
         type string {
           pattern "<.*>|$.*";
         }
         type uint32 {
           range "1 .. 65535";
         }
       }
     }
     leaf keepalive-timeout {
       description "Keepalive timeout (seconds)";
       type union {
         type string {
           pattern "<.*>|$.*";
         }
         type uint32 {
           range "1 .. 65535";
         }
       }
     }
     list interface {
       key name;
       description "Enable LDP on this interface";
       leaf name {
         description "Interface name";
         type union {
           type jt:interface-name;
           type string {
             pattern "<.*>|$.*";
           }
         }
       }
       uses apply-advanced;
       choice enable-disable {
         case case_1 {
           leaf disable {
             description "Disable LDP on this interface";
             type empty;
           }
         }
       }
       leaf hello-interval {
         description "Hello interval (seconds)";
         type union {
           type string {
             pattern "<.*>|$.*";
           }
           type uint32 {
             range "1 .. 65535";
           }
         }
       }
       leaf hold-time {
         description "Hello hold time (seconds)";
         type union {
           type string {
             pattern "<.*>|$.*";
           }
           type uint32 {
             range "1 .. 65535";
           }
         }
       }
       container link-protection {
         presence "enable link-protection";
         description "Enable link protection to protect interface for link faults only";
         uses apply-advanced;
         choice enable-disable {
           case case_1 {
             leaf disable {
               description "Disable link-protection";
               type empty;
             }
           }
         }
         leaf dynamic-rsvp-lsp {
           description "Enable setup of dynamic rsvp lsp for link protection";
           type empty;
         }
       }
       container transport-address {
         description "Address used for TCP sessions";
         choice address-choice {
           case case_1 {
             leaf router-id {
               description "Use router ID for TCP connections";
               type empty;
             }
           }
           case case_2 {
             leaf interface {
               description "Use interface address for TCP connections";
               type empty;
             }
           }
           case case_3 {
             leaf address {
               description "Use specified address for TCP connections";
               type jt:ipaddr;
             }
           }
         }
       }
       choice allow-subnet-mismatch-choice {
         leaf allow-subnet-mismatch {
           description "Allow subnet mismatch for source address in hello packet";
           type empty;
         }
         leaf no-allow-subnet-mismatch {
           description "Don't allow subnet mismatch for source address in hello packet";
           type empty;
         }
       }
     }
     list neighbor {
       key name;
       description "Configure a remote LDP neighbor";
       leaf name {
         description "Neighbor address";
         type jt:ipaddr;
       }
       uses apply-advanced;
     }
     list session {
       key name;
       description "Configure session parameters";
       leaf name {
         description "Session destination address";
         type jt:ipaddr;
       }
       uses apply-advanced;
       leaf authentication-key {
         description "MD5 authentication key";
         type string {
           length "1 .. 126";
         }
       }
       leaf authentication-algorithm {
         description "Authentication algorithm name";
         default "hmac-sha-1-96";
         junos:must "(\".. authentication-key-chain\")";
         junos:must-message "May not be configured without authentication-key-chain";
         junos:must "(!(\".. authentication-key\"))";
         junos:must-message "May not be configured with authentication-key";
         type enumeration {
           enum "md5" {
             description "Message Digest 5";
           }
           enum "hmac-sha-1-96" {
             description "Hash-based Message Authentication Code (SHA1) (96 bits)";
           }
           enum "aes-128-cmac-96" {
             description "Cipher-based Message Authentication Code (AES128) (96 bits)";
           }
           enum "ao" {
             description "TCP Authentication Option";
           }
         }
       }
       leaf tcpao-handling-with-digest-mismatch {
         description "Drop or continue without TCP-AO with digest mismatch with TCP-AO";
         junos:must "(!(\".. authentication-key\"))";
         junos:must-message "May not be configured with authentication-key";
         type enumeration {
           enum "drop-if-no-tcpao" {
             description "Drop the connection if Digest mismatched";
           }
           enum "allow-without-tcpao" {
             description "Allow the connection establishment without TCP-AO";
           }
         }
       }
       leaf authentication-key-chain {
         description "Key chain name";
         junos:must "(!(\".. authentication-key\"))";
         junos:must-message "May not be configured with authentication-key";
         junos:must "(\"security authentication-key-chains key-chain $$\")";
         junos:must-message "Referenced key-chain must be defined";
         type string {
           length "1 .. 128";
         }
       }
       leaf downstream-on-demand {
         description "Configure downstream on demand label distribution mode";
         type empty;
       }
       leaf transport-address {
         description "Address used for TCP sessions to the neighbor";
         type jt:ipaddr;
       }
       choice mtu-discovery-choice {
         leaf mtu-discovery {
           description "Enable TCP path MTU discovery";
           type empty;
         }
         leaf no-mtu-discovery {
           description "Don't enable TCP path MTU discovery";
           type empty;
         }
       }
     }
     list session-group {
       key name;
       description "Configure session group parameters";
       leaf name {
         description "Session destination address/prefix length";
         type jt:ipprefix;
       }
       uses apply-advanced;
       leaf authentication-key {
         description "MD5 authentication key";
         type string {
           length "1 .. 126";
         }
       }
       leaf authentication-algorithm {
         description "Authentication algorithm name";
         default "hmac-sha-1-96";
         junos:must "(\".. authentication-key-chain\")";
         junos:must-message "May not be configured without authentication-key-chain";
         junos:must "(!(\".. authentication-key\"))";
         junos:must-message "May not be configured with authentication-key";
         type enumeration {
           enum "md5" {
             description "Message Digest 5";
           }
           enum "hmac-sha-1-96" {
             description "Hash-based Message Authentication Code (SHA1) (96 bits)";
           }
           enum "aes-128-cmac-96" {
             description "Cipher-based Message Authentication Code (AES128) (96 bits)";
           }
           enum "ao" {
             description "TCP Authentication Option";
           }
         }
       }
       leaf tcpao-handling-with-digest-mismatch {
         description "Drop or continue without TCP-AO with digest mismatch with TCP-AO";
         junos:must "(!(\".. authentication-key\"))";
         junos:must-message "May not be configured with authentication-key";
         type enumeration {
           enum "drop-if-no-tcpao" {
             description "Drop the connection if Digest mismatched";
           }
           enum "allow-without-tcpao" {
             description "Allow the connection establishment without TCP-AO";
           }
         }
       }
       leaf authentication-key-chain {
         description "Key chain name";
         junos:must "(!(\".. authentication-key\"))";
         junos:must-message "May not be configured with authentication-key";
         junos:must "(\"security authentication-key-chains key-chain $$\")";
         junos:must-message "Referenced key-chain must be defined";
         type string {
           length "1 .. 128";
         }
       }
       leaf downstream-on-demand {
         description "Configure downstream on demand label distribution mode";
         type empty;
       }
       leaf transport-address {
         description "Address used for TCP sessions to the neighbor";
         type jt:ipaddr;
       }
       choice mtu-discovery-choice {
         leaf mtu-discovery {
           description "Enable TCP path MTU discovery";
           type empty;
         }
         leaf no-mtu-discovery {
           description "Don't enable TCP path MTU discovery";
           type empty;
         }
       }
     }
     container session-protection {
       presence "enable session-protection";
       description "Configure session protection";
       leaf timeout {
         description "Session protection timeout";
         units "seconds";
         type union {
           type string {
             pattern "<.*>|$.*";
           }
           type uint16 {
             range "1 .. 65535";
           }
         }
       }
     }
     container igp-synchronization {
       description "Configure IGP synchronization parameters";
       uses apply-advanced;
       leaf holddown-interval {
         description "Time to hold the up notification to the IGPs";
         units "seconds";
         type union {
           type string {
             pattern "<.*>|$.*";
           }
           type uint32 {
             range "10 .. 300";
           }
         }
       }
     }
     container log-updown {
       description "Logging actions for LSP up/down events";
       uses apply-advanced;
       container trap {
         description "SNMP traps options";
         choice enable-disable {
           case case_1 {
             leaf disable {
               description "Disable LDP LSP up/down trap";
               type empty;
             }
           }
         }
       }
     }
     container policing {
       description "Configure policing for an LDP FEC";
       uses apply-advanced;
       list fec {
         key name;
         ordered-by user;
         description "Forwarding equivalence class";
         leaf name {
           description "Forwarding equivalence class address";
           type jt:ipv4prefix;
         }
         uses apply-advanced;
         leaf ingress-traffic {
           description "Name of filter to use for policing ingress LDP traffic";
           junos:must "((\"firewall family any filter $$\" || (!(\"firewall\") && \".. .. .. .. .. .. .. .. firewall family any filter $$\")))";
           junos:must-message "referenced filter must be defined under firewall family any";
           type string {
             junos:posix-pattern "!^((__.*)|(.{65,}))$";
             junos:pattern-message "Must be a non-reserved string of 64 characters or less";
           }
         }
         leaf transit-traffic {
           description "Name of filter to use for policing transit LDP traffic";
           junos:must "((\"firewall family any filter $$\" || (!(\"firewall\") && \".. .. .. .. .. .. .. .. firewall family any filter $$\")))";
           junos:must-message "referenced filter must be defined under firewall family any";
           type string {
             junos:posix-pattern "!^((__.*)|(.{65,}))$";
             junos:pattern-message "Must be a non-reserved string of 64 characters or less";
           }
         }
       }
     }
     container entropy-label {
       description "Insert entropy label for  a LDP FEC";
       uses apply-advanced;
       leaf-list ingress-policy {
         ordered-by user;
         description "Entropy label ingress policy";
         type jt:policy-algebra;
       }
     }
     container oam {
       description "Configure periodic OAM for a LDP FEC";
       uses apply-advanced;
       leaf-list ingress-policy {
         ordered-by user;
         description "OAM ingress policy";
         type jt:policy-algebra;
       }
       leaf-list bfd-port-egress-policy {
         ordered-by user;
         description "OAM egress policy";
         type jt:policy-algebra;
       }
       list fec {
         key name;
         ordered-by user;
         description "Forwarding equivalence class";
         leaf name {
           description "Forwarding equivalence class address";
           type jt:ipv4prefix;
         }
         uses apply-advanced;
         choice bfd_liveness_detection_type {
           case case_1 {
             container bfd-liveness-detection {
               description "Bidirectional Forwarding Detection (BFD) options";
               uses apply-advanced;
               leaf version {
                 description "BFD protocol version number";
                 default "automatic";
                 type enumeration {
                   enum "0" {
                     description "BFD version 0 (deprecated)";
                   }
                   enum "1" {
                     description "BFD version 1";
                   }
                   enum "automatic" {
                     description "Choose BFD version automatically";
                   }
                 }
               }
               leaf minimum-interval {
                 description "Minimum transmit and receive interval";
                 units "milliseconds";
                 type union {
                   type string {
                     pattern "<.*>|$.*";
                   }
                   type uint32 {
                     range "1 .. 255000";
                   }
                 }
               }
               leaf minimum-transmit-interval {
                 description "Minimum transmit interval";
                 status deprecated;
                 units "milliseconds";
                 type union {
                   type string {
                     pattern "<.*>|$.*";
                   }
                   type uint32 {
                     range "1 .. 255000";
                   }
                 }
               }
               leaf minimum-receive-interval {
                 description "Minimum receive interval";
                 units "milliseconds";
                 type union {
                   type string {
                     pattern "<.*>|$.*";
                   }
                   type uint32 {
                     range "1 .. 255000";
                   }
                 }
               }
               leaf multiplier {
                 description "Detection time multiplier";
                 default "3";
                 type union {
                   type string {
                     pattern "<.*>|$.*";
                   }
                   type uint32 {
                     range "1 .. 255";
                   }
                 }
               }
               choice adaptation-choice {
                 case case_1 {
                   leaf no-adaptation {
                     description "Disable adaptation";
                     type empty;
                   }
                 }
               }
               container transmit-interval {
                 description "Transmit-interval options";
                 uses apply-advanced;
                 leaf minimum-interval {
                   description "Minimum transmit interval";
                   units "milliseconds";
                   type union {
                     type string {
                       pattern "<.*>|$.*";
                     }
                     type uint32 {
                       range "1 .. 255000";
                     }
                   }
                 }
                 leaf threshold {
                   description "High transmit interval triggering a trap";
                   units "milliseconds";
                   type union {
                     type uint32;
                     type string {
                       pattern "<.*>|$.*";
                     }
                   }
                 }
               }
               container detection-time {
                 description "Detection-time options";
                 uses apply-advanced;
                 leaf threshold {
                   description "High detection-time triggering a trap";
                   units "milliseconds";
                   type union {
                     type uint32;
                     type string {
                       pattern "<.*>|$.*";
                     }
                   }
                 }
               }
               leaf ecmp {
                 description "Enable equal cost multipath (ECMP) support for BFD";
                 type empty;
               }
               container failure-action {
                 description "Action to take when BFD session goes down";
                 choice action-choice {
                   case case_1 {
                     leaf remove-route {
                       description "Remove LDP route from the ribs";
                       type empty;
                     }
                   }
                   case case_2 {
                     leaf remove-nexthop {
                       description "Remove LDP nexthop from the route";
                       type empty;
                     }
                   }
                 }
               }
               leaf holddown-interval {
                 description "Time to hold the session-UP notification to the client";
                 default "0";
                 units "milliseconds";
                 type union {
                   type string {
                     pattern "<.*>|$.*";
                   }
                   type uint32 {
                     range "0 .. 255000";
                   }
                 }
               }
               leaf no-router-alert-option {
                 description "Do not set Router-Alert options in IP header for MPLS-BFD";
                 type empty;
               }
               leaf use-ip-ttl-1 {
                 description "Set TTL value to 1 in IP header for MPLS-BFD";
                 type empty;
               }
             }
           }
           case case_2 {
             leaf no-bfd-liveness-detection {
               description "Disable BFD liveness detection";
               type empty;
             }
           }
         }
         container periodic-traceroute {
           presence "enable periodic-traceroute";
           description "Configure periodic traceroute";
           uses apply-advanced;
           leaf frequency {
             description "Time between traceroute attempts";
             units "minutes";
             type union {
               type string {
                 pattern "<.*>|$.*";
               }
               type uint16 {
                 range "15 .. 120";
               }
             }
           }
           leaf ttl {
             description "Maximum time-to-live value";
             type union {
               type string {
                 pattern "<.*>|$.*";
               }
               type uint16 {
                 range "1 .. 255";
               }
             }
           }
           leaf retries {
             description "Number of times to resend probe";
             type union {
               type string {
                 pattern "<.*>|$.*";
               }
               type uint16 {
                 range "1 .. 9";
               }
             }
           }
           leaf wait {
             description "Time to wait before resending probe";
             units "seconds";
             type union {
               type string {
                 pattern "<.*>|$.*";
               }
               type uint16 {
                 range "5 .. 15";
               }
             }
           }
           leaf paths {
             description "Maximum number of paths to traverse";
             type union {
               type string {
                 pattern "<.*>|$.*";
               }
               type uint16 {
                 range "1 .. 255";
               }
             }
           }
           leaf source {
             description "Source address to use when sending probes";
             type jt:ipv4addr;
           }
           leaf exp {
             description "Class-of-service value to use when sending probes";
             type union {
               type string {
                 pattern "<.*>|$.*";
               }
               type uint16 {
                 range "0 .. 7";
               }
             }
           }
           leaf fanout {
             description "Maximum number of nexthops to search per node";
             type union {
               type string {
                 pattern "<.*>|$.*";
               }
               type uint16 {
                 range "1 .. 64";
               }
             }
           }
           leaf disable {
             description "Disable periodic traceroute for a FEC";
             type empty;
           }
         }
       }
       container bfd-liveness-detection {
         description "Bidirectional Forwarding Detection (BFD) options";
         uses apply-advanced;
         leaf version {
           description "BFD protocol version number";
           default "automatic";
           type enumeration {
             enum "0" {
               description "BFD version 0 (deprecated)";
             }
             enum "1" {
               description "BFD version 1";
             }
             enum "automatic" {
               description "Choose BFD version automatically";
             }
           }
         }
         leaf minimum-interval {
           description "Minimum transmit and receive interval";
           units "milliseconds";
           type union {
             type string {
               pattern "<.*>|$.*";
             }
             type uint32 {
               range "1 .. 255000";
             }
           }
         }
         leaf minimum-transmit-interval {
           description "Minimum transmit interval";
           status deprecated;
           units "milliseconds";
           type union {
             type string {
               pattern "<.*>|$.*";
             }
             type uint32 {
               range "1 .. 255000";
             }
           }
         }
         leaf minimum-receive-interval {
           description "Minimum receive interval";
           units "milliseconds";
           type union {
             type string {
               pattern "<.*>|$.*";
             }
             type uint32 {
               range "1 .. 255000";
             }
           }
         }
         leaf multiplier {
           description "Detection time multiplier";
           default "3";
           type union {
             type string {
               pattern "<.*>|$.*";
             }
             type uint32 {
               range "1 .. 255";
             }
           }
         }
         choice adaptation-choice {
           case case_1 {
             leaf no-adaptation {
               description "Disable adaptation";
               type empty;
             }
           }
         }
         container transmit-interval {
           description "Transmit-interval options";
           uses apply-advanced;
           leaf minimum-interval {
             description "Minimum transmit interval";
             units "milliseconds";
             type union {
               type string {
                 pattern "<.*>|$.*";
               }
               type uint32 {
                 range "1 .. 255000";
               }
             }
           }
           leaf threshold {
             description "High transmit interval triggering a trap";
             units "milliseconds";
             type union {
               type uint32;
               type string {
                 pattern "<.*>|$.*";
               }
             }
           }
         }
         container detection-time {
           description "Detection-time options";
           uses apply-advanced;
           leaf threshold {
             description "High detection-time triggering a trap";
             units "milliseconds";
             type union {
               type uint32;
               type string {
                 pattern "<.*>|$.*";
               }
             }
           }
         }
         leaf ecmp {
           description "Enable equal cost multipath (ECMP) support for BFD";
           type empty;
         }
         container failure-action {
           description "Action to take when BFD session goes down";
           choice action-choice {
             case case_1 {
               leaf remove-route {
                 description "Remove LDP route from the ribs";
                 type empty;
               }
             }
             case case_2 {
               leaf remove-nexthop {
                 description "Remove LDP nexthop from the route";
                 type empty;
               }
             }
           }
         }
         leaf holddown-interval {
           description "Time to hold the session-UP notification to the client";
           default "0";
           units "milliseconds";
           type union {
             type string {
               pattern "<.*>|$.*";
             }
             type uint32 {
               range "0 .. 255000";
             }
           }
         }
         leaf no-router-alert-option {
           description "Do not set Router-Alert options in IP header for MPLS-BFD";
           type empty;
         }
         leaf use-ip-ttl-1 {
           description "Set TTL value to 1 in IP header for MPLS-BFD";
           type empty;
         }
       }
       container periodic-traceroute {
         presence "enable periodic-traceroute";
         description "Configure periodic traceroute";
         uses apply-advanced;
         leaf frequency {
           description "Time between traceroute attempts";
           units "minutes";
           type union {
             type string {
               pattern "<.*>|$.*";
             }
             type uint16 {
               range "15 .. 120";
             }
           }
         }
         leaf ttl {
           description "Maximum time-to-live value";
           type union {
             type string {
               pattern "<.*>|$.*";
             }
             type uint16 {
               range "1 .. 255";
             }
           }
         }
         leaf retries {
           description "Number of times to resend probe";
           type union {
             type string {
               pattern "<.*>|$.*";
             }
             type uint16 {
               range "1 .. 9";
             }
           }
         }
         leaf wait {
           description "Time to wait before resending probe";
           units "seconds";
           type union {
             type string {
               pattern "<.*>|$.*";
             }
             type uint16 {
               range "5 .. 15";
             }
           }
         }
         leaf paths {
           description "Maximum number of paths to traverse";
           type union {
             type string {
               pattern "<.*>|$.*";
             }
             type uint16 {
               range "1 .. 255";
             }
           }
         }
         leaf source {
           description "Source address to use when sending probes";
           type jt:ipv4addr;
         }
         leaf exp {
           description "Class-of-service value to use when sending probes";
           type union {
             type string {
               pattern "<.*>|$.*";
             }
             type uint16 {
               range "0 .. 7";
             }
           }
         }
         leaf fanout {
           description "Maximum number of nexthops to search per node";
           type union {
             type string {
               pattern "<.*>|$.*";
             }
             type uint16 {
               range "1 .. 64";
             }
           }
         }
       }
       leaf lsp-ping-interval {
         description "Time interval between LSP ping messages";
         default "60";
         units "seconds";
         type union {
           type string {
             pattern "<.*>|$.*";
           }
           type uint16 {
             range "30 .. 3600";
           }
         }
       }
       leaf lsp-ping-multiplier {
         description "Number of ping reply missed before declaring BFD down";
         type union {
           type string {
             pattern "<.*>|$.*";
           }
           type uint8 {
             range "1 .. 5";
           }
         }
       }
     }
     container targeted-hello {
       description "Configure targeted hello parameters";
       uses apply-advanced;
       leaf hello-interval {
         description "Hello interval (seconds)";
         type union {
           type string {
             pattern "<.*>|$.*";
           }
           type uint32 {
             range "1 .. 65535";
           }
         }
       }
       leaf hold-time {
         description "Hold interval (seconds)";
         type union {
           type string {
             pattern "<.*>|$.*";
           }
           type uint32 {
             range "1 .. 65535";
           }
         }
       }
     }
     container p2mp {
       presence "enable p2mp";
       description "Advertise P2MP capability to peers";
       uses apply-advanced;
       container recursive {
         description "Configure P2MP recursive parameters";
         uses apply-advanced;
         leaf route {
           description "Allow recursive route resolution to signal P2MP FEC";
           type empty;
         }
       }
       list root-address {
         key name;
         description "Configure the root address of P2MP LSP";
         leaf name {
           description "Root address of the P2MP LSP";
           type jt:ipaddr;
         }
         uses apply-advanced;
         list lsp-id {
           key name;
           description "Configure the generic LSP identifier";
           leaf name {
             description "Generic LSP identifier value";
             type union {
               type string {
                 pattern "<.*>|$.*";
               }
               type uint32 {
                 range "1 .. 65535";
               }
             }
           }
           uses apply-advanced;
         }
         list group-address {
           key name;
           description "IPv4/Ipv6 group address for mLDP LSP";
           leaf name {
             description "IPv4/Ipv6 group address";
             type jt:ipaddr;
           }
           uses apply-advanced;
           list source-address {
             key name;
             description "IPv4/Ipv6 source address";
             leaf name {
               description "IPv4/Ipv6 source address for mLDP LSP";
               type jt:ipaddr;
             }
             uses apply-advanced;
           }
         }
       }
       leaf no-rsvp-tunneling {
         description "Do not allow LDP P2MP to use RSVP-TE LSPs for tunneling";
         type empty;
       }
     }
     container sr-mapping-client {
       presence "enable sr-mapping-client";
       description "Enable LDP to SR mapping-client functionality";
       uses apply-advanced;
       leaf-list policy {
         ordered-by user;
         description "SR mapping-client policy";
         type jt:policy-algebra;
       }
     }
     leaf upstream-label-assignment {
       description "Allow Upstream Label Assignment capability";
       type empty;
     }
     list family {
       key name;
       ordered-by user;
       description "Address family";
       leaf name {
         type enumeration {
           enum "inet" {
             description "IPv4 family";
           }
           enum "inet6" {
             description "IPv6 family";
           }
         }
       }
       uses apply-advanced;
     }
     leaf transport-preference {
       description "TCP transport preference";
       type enumeration {
         enum "ipv4" {
           description "Use IPv4 for TCP connections";
         }
         enum "ipv6" {
           description "Use IPv6 for TCP connections";
         }
       }
     }
     container dual-transport {
       presence "enable dual-transport";
       description "Use separate IPv4 and IPv6 TCP transport";
       uses apply-advanced;
       leaf inet-lsr-id {
         description "LSR identifier for address family inet";
         type jt:ipv4addr;
       }
       leaf inet6-lsr-id {
         description "LSR identifier for address family inet6";
         type jt:ipv4addr;
       }
     }
   }
   grouping juniper-protocols-mpls {
     description "Multiprotocol Label Switching options";
     uses apply-advanced;
     list lsp-external-controller {
       key name;
       ordered-by user;
       description "External path computing entity";
       leaf name {
         description "Name of the external path computing entity";
         type string {
           junos:posix-pattern "^.{1,64}$";
           junos:pattern-message "Must be a string of less than 64 characters";
         }
       }
       uses apply-advanced;
       container label-switched-path-template {
         description "Template for externally provisioned LSP parameters";
         uses apply-advanced;
         choice dynamic-template {
           case case_1 {
             leaf template-name {
               description "Name of point-to-point LSP template";
               junos:must "(!(\"protocols mpls label-switched-path $$ p2mp\"))";
               junos:must-message "Referenced template cannot be a p2mp template";
               junos:must "(\"protocols mpls label-switched-path $$ template\")";
               junos:must-message "Referenced point-to-point LSP template does not exist";
               type string {
                 length "1 .. 32";
                 junos:posix-pattern "![*<>]";
                 junos:pattern-message "Template name should not contain '*' and angle brackets";
               }
             }
           }
           case case_2 {
             leaf default-template {
               description "Use default parameters";
               type empty;
             }
           }
         }
       }
       container label-switched-path-p2mp-template {
         description "Template for externally provisioned P2MP LSP parameters";
         uses apply-advanced;
         choice dynamic-template {
           case case_1 {
             leaf template-name {
               description "Name of point-to-multipoint LSP template";
               junos:must "(\"protocols mpls label-switched-path $$ p2mp\")";
               junos:must-message "Referenced template should be a p2mp template";
               junos:must "(\"protocols mpls label-switched-path $$ template\")";
               junos:must-message "Referenced point-to-multipoint LSP template does not exist";
               type string {
                 length "1 .. 32";
                 junos:posix-pattern "![*<>]";
                 junos:pattern-message "Template name should not contain '*' and angle brackets";
               }
             }
           }
           case case_2 {
             leaf default-template {
               description "Use default parameters";
               type empty;
             }
           }
         }
       }
       list pce-controlled-lsp {
         key name;
         ordered-by user;
         description "Template for externally provisioned LSP using regular expression";
         leaf name {
           description "Template regular expression";
           type string {
             junos:posix-pattern "^.{1,64}$";
             junos:pattern-message "Must be a string of less than 64 characters";
           }
         }
         uses apply-advanced;
         container label-switched-path-template {
           description "Template for externally provisioned LSP parameters";
           uses apply-advanced;
           leaf template-name {
             description "Name of point-to-point LSP template";
             junos:must "(!(\"protocols mpls label-switched-path $$ p2mp\"))";
             junos:must-message "Referenced template cannot be a p2mp template";
             junos:must "(\"protocols mpls label-switched-path $$ template\")";
             junos:must-message "Referenced point-to-point LSP template does not exist";
             type string {
               length "1 .. 64";
               junos:posix-pattern "![*<>]";
               junos:pattern-message "Template name should not contain '*' and angle brackets";
             }
           }
         }
         container label-switched-path-p2mp-template {
           description "Template for externally provisioned P2MP LSP parameters";
           uses apply-advanced;
           leaf template-name {
             description "Name of point-to-multipoint LSP template";
             junos:must "(\"protocols mpls label-switched-path $$ p2mp\")";
             junos:must-message "Referenced template should be a p2mp template";
             junos:must "(\"protocols mpls label-switched-path $$ template\")";
             junos:must-message "Referenced point-to-multipoint LSP template does not exist";
             type string {
               length "1 .. 64";
               junos:posix-pattern "![*<>]";
               junos:pattern-message "Template name should not contain '*' and angle brackets";
             }
           }
         }
       }
     }
     container path-mtu {
       presence "enable path-mtu";
       description "Path MTU configuration";
       uses apply-advanced;
       leaf allow-fragmentation {
         description "If needed, fragment IP before encapsulating in MPLS";
         type empty;
       }
       container rsvp {
         presence "enable rsvp";
         description "RSVP-specific path MTU options";
         uses apply-advanced;
         leaf mtu-signaling {
           description "Enable RSVP path MTU signaling";
           type empty;
         }
       }
     }
     container diffserv-te {
       description "Global diffserv-traffic-engineering options";
       uses apply-advanced;
       leaf bandwidth-model {
         description "Bandwidth constraint model supported";
         type enumeration {
           enum "extended-mam" {
             description "Maximum allocation model with support for E-LSPs";
           }
           enum "mam" {
             description "Maximum allocation model";
           }
           enum "rdm" {
             description "Russian dolls model";
           }
         }
       }
       container te-class-matrix {
         description "Supported combinations of traffic-class and preemption";
         uses apply-advanced;
         container te0 {
           description "Definition for traffic-engineering class te0";
           uses te-class-object;
         }
         container te1 {
           description "Definition for traffic-engineering class te1";
           uses te-class-object;
         }
         container te2 {
           description "Definition for traffic-engineering class te2";
           uses te-class-object;
         }
         container te3 {
           description "Definition for traffic-engineering class te3";
           uses te-class-object;
         }
         container te4 {
           description "Definition for traffic-engineering class te4";
           uses te-class-object;
         }
         container te5 {
           description "Definition for traffic-engineering class te5";
           uses te-class-object;
         }
         container te6 {
           description "Definition for traffic-engineering class te6";
           uses te-class-object;
         }
         container te7 {
           description "Definition for traffic-engineering class te7";
           uses te-class-object;
         }
       }
     }
     container auto-policing {
       description "Automatic policing of LSPs";
       uses apply-advanced;
       list class {
         key name;
         ordered-by user;
         description "Forwarding class";
         leaf name {
           type enumeration {
             enum "all" {
               description "All forwarding classes";
             }
             enum "ct0" {
               description "Forwarding class 0";
             }
             enum "ct1" {
               description "Forwarding class 1";
             }
             enum "ct2" {
               description "Forwarding class 2";
             }
             enum "ct3" {
               description "Forwarding class 3";
             }
           }
         }
         uses apply-advanced;
         choice policing-action {
           case case_1 {
             leaf drop {
               description "Drop packets if bandwidth is exceeded";
               type empty;
             }
           }
           case case_2 {
             leaf loss-priority-high {
               description "Set loss priority to high if bandwidth is exceeded";
               type empty;
             }
           }
           case case_3 {
             leaf loss-priority-low {
               description "Set loss priority to low if bandwidth is exceeded";
               type empty;
             }
           }
         }
       }
     }
     container statistics {
       description "Collect statistics for signaled label-switched paths";
       uses apply-advanced;
       container file {
         presence "enable file";
         description "Statistics file options";
         leaf filename {
           description "Name of file in which to write trace information";
           type string {
             length "1 .. 1024";
             junos:posix-pattern "![/ %]";
             junos:pattern-message "Must not contain '/', % or a space";
           }
         }
         leaf replace {
           description "Replace trace file rather than appending to it";
           status deprecated;
           type empty;
         }
         leaf size {
           description "Maximum trace file size";
           type string;
         }
         leaf files {
           description "Maximum number of trace files";
           default "10";
           type union {
             type string {
               pattern "<.*>|$.*";
             }
             type uint32 {
               range "2 .. 1000";
             }
           }
         }
         leaf no-stamp {
           description "Do not timestamp trace file";
           status deprecated;
           type empty;
         }
         choice world-readable-choice {
           leaf world-readable {
             description "Allow any user to read the log file";
             type empty;
           }
           leaf no-world-readable {
             description "Don't allow any user to read the log file";
             type empty;
           }
         }
       }
       leaf interval {
         description "Time to collect statistics (seconds)";
         type union {
           type string {
             pattern "<.*>|$.*";
           }
           type int32 {
             range "1 .. 65535";
           }
         }
       }
       leaf auto-bandwidth {
         description "Enable auto bandwidth allocation";
         type empty;
       }
       leaf no-transit-statistics {
         description "Disable transit LSP statistics collection";
         type empty;
       }
       choice transit-polling-type {
         case case_1 {
           leaf no-transit-statistics-polling {
             description "Disable polling and display of transit lsp statistics";
             status deprecated;
             type empty;
           }
         }
         case case_2 {
           leaf transit-statistics-polling {
             description "Enable polling and display of transit lsp statistics";
             junos:must "(!(\" .. no-transit-statistics\"))";
             junos:must-message "no-transit-statistics and transit-statistics-polling cannot coexist";
             type empty;
           }
         }
       }
       leaf no-bypass-statistics-polling {
         description "Disable polling and display of bypass lsp statistics";
         type empty;
       }
       leaf statistics-query-batch-size {
         description "Number of LSPs for which statistics will be queried together";
         type union {
           type string {
             pattern "<.*>|$.*";
           }
           type int32 {
             range "1 .. 25";
           }
         }
       }
       leaf traffic-class-statistics {
         description "Create per traffic class statistics sensors for LSPs";
         type empty;
       }
     }
     container p2mp-lsp {
       description "P2MP LSP control configuration";
       uses apply-advanced;
       leaf single-abr {
         description "Try to use same exit node for all inter-domain sub LSPs";
         type empty;
       }
       leaf no-re-merge {
         description "Avoid LSP CSPF creating remerge";
         type empty;
       }
     }
     container log-updown {
       description "Logging actions for LSP up/down events";
       uses apply-advanced;
       choice syslog-choice {
         leaf syslog {
           description "Send syslog messages";
           type empty;
         }
         leaf no-syslog {
           description "Don't send syslog messages";
           type empty;
         }
       }
       choice trap-choice {
         case case_1 {
           leaf trap {
             description "Send SNMP traps";
             type empty;
           }
         }
         case case_2 {
           container no-trap {
             presence "enable no-trap";
             description "Don't send SNMP traps";
             uses apply-advanced;
             leaf mpls-lsp-traps {
               description "Dont send mpls lsp up/down traps";
               type empty;
             }
             leaf rfc3812-traps {
               description "Dont send rfc3812 traps";
               type empty;
             }
           }
         }
       }
       leaf trap-path-down {
         description "Send SNMP traps when a path goes down";
         type empty;
       }
       leaf trap-path-up {
         description "Send SNMP traps when a path goes up";
         type empty;
       }
     }
     container optimize-adaptive-teardown {
       description "Post make before break adaptive teardown";
       uses apply-advanced;
       leaf p2p {
         description "Turn on post make before break adaptive teardown for p2p";
         type empty;
       }
       leaf timeout {
         description "Timeout for adaptive teardown to clean up LSP";
         units "seconds";
         junos:must "(\".. p2p\")";
         junos:must-message "adaptive-teardown must include 'p2p' attribute";
         type union {
           type string {
             pattern "<.*>|$.*";
           }
           type int32 {
             range "1 .. 65535";
           }
         }
       }
       container delay {
         junos:must "(\".. p2p\")";
         junos:must-message "adaptive-teardown must include 'p2p' attribute";
         description "Delay tearing down old optimized path after adaptive-teardown kicks in";
         uses apply-advanced;
         leaf delay-value {
           description "Delay tearing down old optimized path after adaptive-teardown kicks in";
           units "seconds";
           type union {
             type string {
               pattern "<.*>|$.*";
             }
             type int32 {
               range "3 .. 65535";
             }
           }
         }
       }
     }
     container traffic-engineering {
       presence "enable traffic-engineering";
       description "Traffic-engineering control";
       uses apply-advanced;
       choice protocols {
         case case_1 {
           leaf bgp {
             description "BGP destinations only";
             type empty;
           }
         }
         case case_2 {
           leaf bgp-igp {
             description "BGP and IGP destinations";
             type empty;
           }
         }
         case case_3 {
           leaf bgp-igp-both-ribs {
             description "BGP and IGP destinations with routes in both routing tables";
             type empty;
           }
         }
         case case_4 {
           leaf mpls-forwarding {
             description "Use MPLS routes for forwarding, not routing";
             type empty;
           }
         }
       }
       container database {
         description "Traffic engineering database";
         uses apply-advanced;
         container import {
           description "Configure TED import parameters";
           uses apply-advanced;
           container l3-unicast-topology {
             presence "enable l3-unicast-topology";
             description "Download L3-Unicast topology into RIB";
             uses apply-advanced;
             leaf bgp-link-state {
               description "Export L3-Unicast topology, instead of TE topology, into BGP-LS";
               type empty;
             }
           }
           leaf-list policy {
             ordered-by user;
             description "Configure import policy";
             type jt:policy-algebra;
           }
           leaf identifier {
             description "BGP-TE identifier";
             type union {
               type string {
                 pattern "<.*>|$.*";
               }
               type uint64 {
                 range "2 .. 18446744073709551615";
               }
             }
           }
           leaf bgp-ls-identifier {
             description "BGP-TE domain identifier";
             type union {
               type uint32;
               type string {
                 pattern "<.*>|$.*";
               }
             }
           }
           leaf ipv6 {
             description "Import ipv6 addresses";
             type empty;
           }
         }
         container export {
           description "Configure TED export related parameters";
           uses apply-advanced;
           leaf-list policy {
             ordered-by user;
             description "Export policy";
             type jt:policy-algebra;
           }
           container credibility {
             description "TED credibility value for entries from BGP-TE";
             uses apply-advanced;
             leaf unknown {
               description "Entries sourced from unknown entities";
               type union {
                 type string {
                   pattern "<.*>|$.*";
                 }
                 type uint32 {
                   range "0 .. 512";
                 }
               }
             }
             leaf direct {
               description "Entries sourced from directly connected links";
               type union {
                 type string {
                   pattern "<.*>|$.*";
                 }
                 type uint32 {
                   range "0 .. 512";
                 }
               }
             }
             leaf static {
               description "Entries sourced from static configuration";
               type union {
                 type string {
                   pattern "<.*>|$.*";
                 }
                 type uint32 {
                   range "0 .. 512";
                 }
               }
             }
             leaf ospf {
               description "Entries sourced from ospf";
               type union {
                 type string {
                   pattern "<.*>|$.*";
                 }
                 type uint32 {
                   range "0 .. 512";
                 }
               }
             }
             leaf isis-level-1 {
               description "Entries sourced from ISIS Level 1";
               type union {
                 type string {
                   pattern "<.*>|$.*";
                 }
                 type uint32 {
                   range "0 .. 512";
                 }
               }
             }
             leaf isis-level-2 {
               description "Entries sourced from ISIS Level 2";
               type union {
                 type string {
                   pattern "<.*>|$.*";
                 }
                 type uint32 {
                   range "0 .. 512";
                 }
               }
             }
             leaf bgp {
               description "Entries sourced from BGP";
               type union {
                 type string {
                   pattern "<.*>|$.*";
                 }
                 type uint32 {
                   range "0 .. 512";
                 }
               }
             }
           }
           leaf l3-unicast-topology {
             description "Download RIB entries into L3-Unicast topology";
             type empty;
           }
         }
       }
     }
     list admin-groups {
       key name;
       ordered-by user;
       description "Administrative groups";
       leaf name {
         description "Group name";
         type string;
       }
       uses apply-advanced;
       leaf group-value {
         description "Group bit position";
         type union {
           type string {
             pattern "<.*>|$.*";
           }
           type uint32 {
             range "0 .. 31";
           }
         }
       }
     }
     leaf advertisement-hold-time {
       description "Time that an 'LSP down' advertisement will be delayed";
       default "5";
       units "seconds";
       type union {
         type string {
           pattern "<.*>|$.*";
         }
         type uint32 {
           range "0 .. 65535";
         }
       }
     }
     leaf rsvp-error-hold-time {
       description "Time that RSVP PathErr events will be remembered";
       default "25";
       units "seconds";
       type union {
         type string {
           pattern "<.*>|$.*";
         }
         type uint32 {
           range "0 .. 240";
         }
       }
     }
     leaf optimize-aggressive {
       description "Run aggressive optimization algorithm based on IGP metric only";
       type empty;
     }
     leaf smart-optimize-timer {
       description "Path optimization interval after a link traversed by the path goes down";
       units "seconds";
       type union {
         type string {
           pattern "<.*>|$.*";
         }
         type int32 {
           range "0 .. 65535";
         }
       }
     }
     leaf optimize-switchover-delay {
       description "Delay before switching LSP to newly optimized path";
       units "seconds";
       type union {
         type string {
           pattern "<.*>|$.*";
         }
         type int32 {
           range "1 .. 900";
         }
       }
     }
     leaf no-propagate-ttl {
       description "Disable TTL propagation from IP to MPLS (on push) and MPLS to IP (on pop)";
       type empty;
     }
     leaf sensor-based-stats {
       description "Enable sensor based statistics collection";
       type empty;
     }
     leaf explicit-null {
       description "Advertise the EXPLICIT_NULL label when the router is the egress";
       type empty;
     }
     leaf icmp-tunneling {
       description "Allow MPLS LSPs to be used for tunneling ICMP error packets";
       type empty;
     }
     leaf revert-timer {
       description "Hold-down window before reverting back to primary path, 0 means disable";
       units "seconds";
       type union {
         type string {
           pattern "<.*>|$.*";
         }
         type int32 {
           range "0 .. 65535";
         }
       }
     }
     leaf optimize-hold-dead-delay {
       description "Delay before tearing down the old optimized path";
       units "seconds";
       type union {
         type string {
           pattern "<.*>|$.*";
         }
         type int32 {
           range "0 .. 65535";
         }
       }
     }
     leaf cspf-backoff-time {
       description "Delay before CSPF, when there is PathErr on backup path";
       units "seconds";
       type union {
         type string {
           pattern "<.*>|$.*";
         }
         type int32 {
           range "0 .. 65535";
         }
       }
     }
     leaf expand-loose-hop {
       description "Perform CSPF path computation to expand loose hops";
       type empty;
     }
     leaf mib-mpls-show-p2mp {
       description "Show p2mp tunnels entries in mpls mib walk";
       type empty;
     }
     container bandwidth {
       description "Bandwidth to reserve (bps)";
       uses bandwidth-type;
     }
     container admin-group {
       description "Administrative group policy";
       uses admin_group_include_exclude;
     }
     container admin-group-extended {
       description "Extended administrative group policy";
       uses admin_group_include_exclude;
     }
     container priority {
       presence "enable priority";
       description "Preemption priorities";
     }
     leaf setup-priority {
       description "Set-up priority";
       type union {
         type string {
           pattern "<.*>|$.*";
         }
         type uint32 {
           range "0 .. 7";
         }
       }
     }
     leaf reservation-priority {
       description "Reservation priority";
       type union {
         type string {
           pattern "<.*>|$.*";
         }
         type uint32 {
           range "0 .. 7";
         }
       }
     }
     container oam {
       description "Periodic OAM";
       uses periodic_oam;
     }
     leaf class-of-service {
       description "Class-of-service value";
       type union {
         type string {
           pattern "<.*>|$.*";
         }
         type int32 {
           range "0 .. 7";
         }
       }
     }
     leaf no-decrement-ttl {
       description "Do not decrement the TTL within an LSP";
       type empty;
     }
     leaf hop-limit {
       description "Maximum allowed router hops";
       type union {
         type string {
           pattern "<.*>|$.*";
         }
         type int32 {
           range "2 .. 255";
         }
       }
     }
     leaf no-cspf {
       description "Disable automatic path computation";
       type empty;
     }
     leaf admin-down {
       description "Set GMPLS LSP to administrative down state";
       type empty;
     }
     leaf optimize-timer {
       description "Periodical path reoptimizations";
       units "seconds";
       type union {
         type string {
           pattern "<.*>|$.*";
         }
         type int32 {
           range "0 .. 65535";
         }
       }
     }
     leaf preference {
       description "Preference value";
       type union {
         type uint32;
         type string {
           pattern "<.*>|$.*";
         }
       }
     }
     choice record-choice {
       leaf record {
         description "Record transit routers";
         type empty;
       }
       leaf no-record {
         description "Don't record transit routers";
         type empty;
       }
     }
     leaf standby {
       description "Keep backup paths in continuous standby";
       type empty;
     }
     leaf exclude-srlg {
       description "Exclude SRLG links for secondary path";
       type empty;
     }
     leaf ultimate-hop-popping {
       description "Request ultimate hop popping from egress";
       type empty;
     }
     leaf sync-active-path-bandwidth {
       description "Signal standby path with bandwidth obtained from active path";
       type empty;
     }
     leaf cross-credibility-cspf {
       description "Compute paths across multi-protocol links and nodes";
       type empty;
     }
     list label-switched-path {
       key name;
       ordered-by user;
       description "Label-switched path";
       leaf name {
         description "Name of path";
         type string {
           length "1 .. 64";
         }
       }
       uses apply-advanced;
       choice enable-disable {
         case case_1 {
           leaf disable {
             description "Disable MPLS label-switched path";
             type empty;
           }
         }
       }
       container traceoptions {
         description "Trace options for MPLS label-switched path";
         uses apply-advanced;
         container file {
           description "Trace file options";
           leaf filename {
             description "Name of file in which to write trace information";
             type string {
               length "1 .. 1024";
               junos:posix-pattern "![/ %]";
               junos:pattern-message "Must not contain '/', % or a space";
             }
           }
           leaf replace {
             description "Replace trace file rather than appending to it";
             status deprecated;
             type empty;
           }
           leaf size {
             description "Maximum trace file size";
             type string;
           }
           leaf files {
             description "Maximum number of trace files";
             default "10";
             type union {
               type string {
                 pattern "<.*>|$.*";
               }
               type uint32 {
                 range "2 .. 1000";
               }
             }
           }
           leaf no-stamp {
             description "Do not timestamp trace file";
             status deprecated;
             type empty;
           }
           choice world-readable-choice {
             leaf world-readable {
               description "Allow any user to read the log file";
               type empty;
             }
             leaf no-world-readable {
               description "Don't allow any user to read the log file";
               type empty;
             }
           }
         }
         list flag {
           key name;
           ordered-by user;
           description "Tracing parameters";
           leaf name {
             type enumeration {
               enum "cspf" {
                 description "Trace CSPF computation";
               }
               enum "cspf-node" {
                 description "Trace nodes visited during CSPF";
               }
               enum "cspf-link" {
                 description "Trace links visited during CSPF";
               }
               enum "cspf-abstract" {
                 description "Trace abstract hop based CSPF details";
               }
               enum "state" {
                 description "Trace state transitions";
               }
               enum "all" {
                 description "Trace everything";
               }
             }
           }
         }
       }
       leaf no-install-to-address {
         description "Don't install host route 'to' address into routing tables";
         type empty;
       }
       leaf backup {
         description "Use LSP for IGP backup";
         type empty;
       }
       leaf from {
         description "Address of ingress router";
         type jt:ipv4addr;
       }
       container pop-and-forward {
         presence "enable pop-and-forward";
         junos:must "(!(\".. lsp-external-controller\"))";
         junos:must-message "lsp-external-controller unsupported for pop-and-forward LSP";
         junos:must "(!(\".. lsp-attributes\"))";
         junos:must-message "lsp-attributes unsupported for pop-and-forward LSP";
         junos:must "(!(\".. single-sided-associated-bidirectional\"))";
         junos:must-message "single-sided-associated-bidirectional unsupported for pop-and-forward LSP";
         junos:must "(!(\".. associate-lsp\"))";
         junos:must-message "associate-lsp unsupported for pop-and-forward LSP";
         junos:must "(!(\".. corouted-bidirectional-passive\"))";
         junos:must-message "corouted-bidirectional-passive unsupported for pop-and-forward LSP";
         junos:must "(!(\".. corouted-bidirectional\"))";
         junos:must-message "corouted-bidirectional unsupported for pop-and-forward LSP";
         junos:must "(!(\".. backup\"))";
         junos:must-message "backup unsupported for pop-and-forward LSP";
         junos:must "(!(\".. no-cspf\"))";
         junos:must-message "no-cspf unsupported for pop-and-forward LSP";
         junos:must "(!((\".. ultimate-hop-popping\" || \".. .. ultimate-hop-popping\")))";
         junos:must-message "ultimate hop popping unsupported for pop-and-forward LSP";
         junos:must "(!(\".. p2mp\"))";
         junos:must-message "p2mp unsupported for pop-and-forward LSP";
         junos:must "(!(\".. node-link-protection\"))";
         junos:must-message "link/node protection unsupported for pop-and-forward LSP";
         junos:must "(!(\".. fast-reroute\"))";
         junos:must-message "fast-reroute unsupported for pop-and-forward LSP";
         description "Enable LSP as pop-and-forward with auto-delegation";
       }
       choice label-switched-path-or-template {
         case case_1 {
           leaf to {
             description "Address of egress router";
             type jt:ipv4addr;
           }
         }
         case case_2 {
           leaf template {
             description "Template for dynamic lsp paramaters";
             junos:must "(!(\".. associate-lsp\"))";
             junos:must-message "Template cannot have associate-lsp";
             junos:must "(!(\".. corouted-bidirectional-passive\"))";
             junos:must-message "Template cannot be passive bidirectional";
             junos:must "(!(\".. corouted-bidirectional\"))";
             junos:must-message "Template cannot be active bidirectional";
             junos:must "(!(\".. lsp-external-controller\"))";
             junos:must-message "Can't configure external controller in template";
             junos:must "(!(\".. disable\"))";
             junos:must-message "Not applicable for template";
             junos:must "(!((\".. primary\" || \".. secondary\")))";
             junos:must-message "Template cannot include 'path' statement";
             type empty;
           }
         }
       }
       leaf corouted-bidirectional {
         description "Setup the LSP as a corouted bidirectional LSP";
         junos:must "(!(\".. p2mp\"))";
         junos:must-message "p2mp unsupported for bidirectional LSP";
         junos:must "(!(\".. auto-bandwidth\"))";
         junos:must-message "auto-bandwidth unsupported for bidirectional LSP";
         junos:must "(!((\".. link-protection\" || \".. node-link-protection\")))";
         junos:must-message "link/node protection unsupported for bidirectional LSP";
         junos:must "(!(\".. fast-reroute\"))";
         junos:must-message "fast-reroute unsupported for bidirectional LSP";
         junos:must "(!(\".. corouted-bidirectional-passive\"))";
         junos:must-message "Passive and active bidirectional attributes cannot coexist";
         type empty;
       }
       leaf corouted-bidirectional-passive {
         description "Associate LSP with incoming corouted bidirectional LSP";
         junos:must "(!(\".. p2mp\"))";
         junos:must-message "p2mp unsupported for bidirectional LSP";
         junos:must "(!(\".. auto-bandwidth\"))";
         junos:must-message "auto-bandwidth unsupported for bidirectional LSP";
         junos:must "(!((\".. link-protection\" || \".. node-link-protection\")))";
         junos:must-message "link/node protection unsupported for bidirectional LSP";
         junos:must "(!(\".. fast-reroute\"))";
         junos:must-message "fast-reroute unsupported for bidirectional LSP";
         junos:must "(!((\".. standby\" || \".. .. standby\")))";
         junos:must-message "standby unsupported for passive bidirectional LSP";
         junos:must "(!(\".. soft-preemption\"))";
         junos:must-message "soft-preemption unsupported for passive bidirectional LSP";
         junos:must "(!((\".. oam bfd-liveness-detection\" || \".. .. oam bfd-liveness-detection\")))";
         junos:must-message "oam bfd-liveness-detection unsupported for passive bidirectional LSP";
         junos:must "(!((\".. no-decrement-ttl\" || \".. .. no-decrement-ttl\")))";
         junos:must-message "no-decrement-ttl unsupported for passive bidirectional LSP";
         junos:must "(!((\".. exclude-srlg\" || \".. .. exclude-srlg\")))";
         junos:must-message "exclude-srlg unsupported for passive bidirectional LSP";
         junos:must "(!((\".. bandwidth\" || \".. .. bandwidth\")))";
         junos:must-message "bandwidth unsupported for passive bidirectional LSP";
         junos:must "(!((\".. admin-group-extended\" || \".. .. admin-group-extended\")))";
         junos:must-message "admin-group-extended unsupported for passive bidirectional LSP";
         junos:must "(!((\".. admin-group\" || \".. .. admin-group\")))";
         junos:must-message "admin-group unsupported for passive bidirectional LSP";
         junos:must "(!(\".. adaptive\"))";
         junos:must-message "adaptive unsupported for passive bidirectional LSP";
         junos:must "(!(\".. lsp-attributes\"))";
         junos:must-message "Passive bidirectional LSP cannot include 'lsp-attributes' statement";
         junos:must "(!((\".. primary\" || \".. secondary\")))";
         junos:must-message "Passive bidirectional LSP cannot include 'path' statement";
         type empty;
       }
       leaf metric {
         description "Metric value";
         type union {
           type string {
             pattern "<.*>|$.*";
           }
           type uint32 {
             range "1 .. 16777215";
           }
         }
       }
       container conditional-metric {
         junos:must "(!(\".. metric\"))";
         junos:must-message "Static metric cannot be configured with Conditional metric";
         description "Set a conditional metric value for the LSP";
         uses apply-advanced;
         list igp-metric-threshold {
           key name;
           description "Set conditional LSP metric based on IGP metric, up to 4 conditions";
           max-elements 4;
           leaf name {
             description "Conditional IGP metric threshold";
             type union {
               type string {
                 pattern "<.*>|$.*";
               }
               type uint32 {
                 range "1 .. 16777215";
               }
             }
           }
           leaf conditional-metric-value {
             description "Conditional LSP metric value";
             type union {
               type string {
                 pattern "<.*>|$.*";
               }
               type uint32 {
                 range "1 .. 16777215";
               }
             }
           }
         }
       }
       leaf ldp-tunneling {
         description "Allow LDP to use this LSP for tunneling";
         type empty;
       }
       leaf soft-preemption {
         description "Attempt make-before-break service while preempting this LSP";
         junos:must "(!(\".. fast-reroute\"))";
         junos:must-message "soft-preemption is unsupported when fast-reroute is desired";
         type empty;
       }
       list install {
         key name;
         ordered-by user;
         description "Install prefix";
         leaf name {
           description "Destination prefix";
           type jt:ipprefix;
         }
         leaf active {
           description "Install prefix into forwarding table";
           type empty;
         }
       }
       leaf retry-timer {
         description "Time before retrying the primary path";
         units "seconds";
         type union {
           type string {
             pattern "<.*>|$.*";
           }
           type uint32 {
             range "1 .. 600";
           }
         }
       }
       leaf retry-limit {
         description "Maximum number of times to retry primary path";
         type union {
           type string {
             pattern "<.*>|$.*";
           }
           type uint32 {
             range "0 .. 10000";
           }
         }
       }
       container lsp-attributes {
         description "Attributes for generalized LSP";
         uses apply-advanced;
         leaf signal-bandwidth {
           description "Signal bandwidth for the LSP";
           junos:must "(!((\".. switching-type l2sc\" || (\".. switching-type psc-1\" || \".. switching-type ethernet-vlan\"))))";
           junos:must-message "signal-bandwidth invalid for VLAN LSP and Packet LSP";
           type enumeration {
             enum "ds1" {
               description "1.544 Mbps";
             }
             enum "vt1-5" {
               description "1.728 Mbps";
             }
             enum "e1" {
               description "2.048 Mbps";
             }
             enum "vt2" {
               description "2.304 Mbps";
             }
             enum "ethernet" {
               description "10 Mbps";
             }
             enum "e3" {
               description "34.368 Mbps";
             }
             enum "ds3" {
               description "44.736 Mbps";
             }
             enum "sts-1" {
               description "51.84 Mbps";
             }
             enum "fastether" {
               description "100.00 Mbps";
             }
             enum "stm-1" {
               description "155.52 Mbps";
             }
             enum "stm-4" {
               description "622.08 Mbps";
             }
             enum "gigether" {
               description "1000.00 Mbps";
             }
             enum "stm-16" {
               description "2488.32 Mbps";
             }
             enum "stm-64" {
               description "9953.28 Mbps";
             }
             enum "10gigether" {
               description "10000.00 Mbps";
             }
             enum "stm-256" {
               description "39813.12 Mbps";
             }
             enum "100gige" {
               description "100000.00 Mbps";
             }
           }
         }
         leaf switching-type {
           description "LSP switching type desired";
           type enumeration {
             enum "psc-1" {
               description "Packet switching";
             }
             enum "lambda" {
               description "Lambda switching";
             }
             enum "fiber" {
               description "Fiber switching";
             }
             enum "tdm" {
               description "TDM switching";
             }
             enum "ethernet-vlan" {
               description "Ethernet VLAN switching";
               junos:must "((!(\".. encoding-type\") || \".. encoding-type ethernet\"))";
               junos:must-message "Only ethernet encoding supported for VLAN LSP";
             }
           }
         }
         leaf encoding-type {
           description "LSP encoding type desired";
           type enumeration {
             enum "packet" {
               description "Packet encoding";
             }
             enum "ethernet" {
               description "Ethernet encoding";
             }
             enum "pdh" {
               description "PDH encoding";
             }
             enum "sonet-sdh" {
               description "SONET-SDH encoding";
             }
           }
         }
         leaf gpid {
           description "Generalized PID";
           type enumeration {
             enum "ipv4" {
             }
             enum "ethernet" {
             }
             enum "ppp" {
             }
             enum "hdlc" {
             }
             enum "pos-no-scrambling-crc-16" {
             }
             enum "pos-no-scrambling-crc-32" {
             }
             enum "pos-scrambling-crc-16" {
             }
             enum "pos-scrambling-crc-32" {
             }
           }
         }
         container upstream-label {
           description "Upstream Label for the bidirectional label-switched path";
           uses apply-advanced;
           leaf vlan-id {
             description "VLAN ID label for the label-switched path";
             junos:must "(\".. .. switching-type ethernet-vlan\")";
             junos:must-message "VLAN label is valid only for VLAN LSP";
             type union {
               type string {
                 pattern "<.*>|$.*";
               }
               type uint32 {
                 range "1 .. 4094";
               }
             }
           }
         }
       }
       leaf revert-timer {
         description "Hold-down window before reverting back to primary path, 0 means disable";
         units "seconds";
         type union {
           type string {
             pattern "<.*>|$.*";
           }
           type int32 {
             range "0 .. 65535";
           }
         }
       }
       leaf optimize-hold-dead-delay {
         description "Delay before tearing down the old optimized path";
         units "seconds";
         type union {
           type string {
             pattern "<.*>|$.*";
           }
           type int32 {
             range "0 .. 65535";
           }
         }
       }
       leaf cspf-backoff-time {
         description "Delay before CSPF, when there is PathErr on backup path";
         units "seconds";
         type union {
           type string {
             pattern "<.*>|$.*";
           }
           type int32 {
             range "0 .. 65535";
           }
         }
       }
       container bandwidth {
         description "Bandwidth to reserve (bps)";
         uses bandwidth-type;
       }
       container admin-group {
         description "Administrative group policy";
         uses admin_group_include_exclude;
       }
       container admin-group-extended {
         description "Extended administrative group policy";
         uses admin_group_include_exclude;
       }
       container priority {
         presence "enable priority";
         description "Preemption priorities";
       }
       leaf setup-priority {
         description "Set-up priority";
         type union {
           type string {
             pattern "<.*>|$.*";
           }
           type uint32 {
             range "0 .. 7";
           }
         }
       }
       leaf reservation-priority {
         description "Reservation priority";
         type union {
           type string {
             pattern "<.*>|$.*";
           }
           type uint32 {
             range "0 .. 7";
           }
         }
       }
       container oam {
         description "Periodic OAM";
         uses periodic_oam;
       }
       leaf class-of-service {
         description "Class-of-service value";
         type union {
           type string {
             pattern "<.*>|$.*";
           }
           type int32 {
             range "0 .. 7";
           }
         }
       }
       leaf no-decrement-ttl {
         description "Do not decrement the TTL within an LSP";
         type empty;
       }
       leaf hop-limit {
         description "Maximum allowed router hops";
         type union {
           type string {
             pattern "<.*>|$.*";
           }
           type int32 {
             range "2 .. 255";
           }
         }
       }
       leaf no-cspf {
         description "Disable automatic path computation";
         type empty;
       }
       leaf admin-down {
         description "Set GMPLS LSP to administrative down state";
         type empty;
       }
       leaf optimize-timer {
         description "Periodical path reoptimizations";
         units "seconds";
         type union {
           type string {
             pattern "<.*>|$.*";
           }
           type int32 {
             range "0 .. 65535";
           }
         }
       }
       leaf preference {
         description "Preference value";
         type union {
           type uint32;
           type string {
             pattern "<.*>|$.*";
           }
         }
       }
       choice record-choice {
         leaf record {
           description "Record transit routers";
           type empty;
         }
         leaf no-record {
           description "Don't record transit routers";
           type empty;
         }
       }
       leaf standby {
         description "Keep backup paths in continuous standby";
         type empty;
       }
       leaf exclude-srlg {
         description "Exclude SRLG links for secondary path";
         type empty;
       }
       leaf ultimate-hop-popping {
         description "Request ultimate hop popping from egress";
         type empty;
       }
       leaf sync-active-path-bandwidth {
         description "Signal standby path with bandwidth obtained from active path";
         type empty;
       }
       leaf cross-credibility-cspf {
         description "Compute paths across multi-protocol links and nodes";
         type empty;
       }
       leaf entropy-label {
         description "Enable entropy label";
         type empty;
       }
       leaf self-ping-duration {
         description "Duration over which to run self-ping (65535 = until success). Default = 1800s";
         units "seconds";
         type union {
           type string {
             pattern "<.*>|$.*";
           }
           type int32 {
             range "1 .. 65535";
           }
         }
       }
       leaf no-self-ping {
         description "Do not run self-ping for this LSP";
         type empty;
       }
       choice cspf-attribute {
         case case_1 {
           leaf random {
             description "Randomly select among equal-cost paths";
             type empty;
           }
         }
         case case_2 {
           leaf least-fill {
             description "Select the least filled among equal-cost paths";
             type empty;
           }
         }
         case case_3 {
           leaf most-fill {
             description "Select the most filled among equal-cost paths";
             type empty;
           }
         }
       }
       leaf description {
         description "Text description of label-switched path";
         type string {
           length "1 .. 80";
         }
       }
       choice lp-type {
         case case_1 {
           leaf link-protection {
             description "Protect LSP from link faults only";
             type empty;
           }
         }
         case case_2 {
           leaf node-link-protection {
             description "Protect LSP from both link and node faults";
             type empty;
           }
         }
       }
       leaf intra-domain {
         description "Intra-domain LSP";
         status deprecated;
         type empty;
       }
       leaf inter-domain {
         description "Inter-domain LSP";
         type empty;
       }
       leaf adaptive {
         description "Have the LSP smoothly cut over to new routes";
         type empty;
       }
       container in-place-lsp-bandwidth-update {
         presence "enable in-place-lsp-bandwidth-update";
         junos:must "(!(\".. fast-reroute\"))";
         junos:must-message "In-place update unsupported for LSPs requesting detour protection";
         junos:must "(!(\".. lsp-external-controller\"))";
         junos:must-message "In-place update unsupported for externally controlled LSPs";
         junos:must "(!(\".. single-sided-associated-bidirectional\"))";
         junos:must-message "In-place update unsupported for single-sided-associated-bidirectional LSPs";
         junos:must "(!(\".. corouted-bidirectional-passive\"))";
         junos:must-message "In-place update unsupported for corouted-bidirectional-passive LSPs";
         junos:must "(!(\".. corouted-bidirectional\"))";
         junos:must-message "In-place update unsupported for corouted-bidirectional LSPs";
         junos:must "(!((\".. no-cspf\" || \".. .. no-cspf\")))";
         junos:must-message "In-place update unsupported for no-cspf LSPs";
         junos:must "(!(\".. p2mp\"))";
         junos:must-message "In-place update unsupported for p2mp sub-LSPs";
         description "Update LSP in-place re-using the same LSP identifier";
       }
       container fast-reroute {
         presence "enable fast-reroute";
         description "Fast reroute";
         uses apply-advanced;
         leaf hop-limit {
           description "Maximum allowed router hops";
           type union {
             type string {
               pattern "<.*>|$.*";
             }
             type int32 {
               range "0 .. 255";
             }
           }
         }
         choice bw-attribute {
           case case_1 {
             leaf bandwidth {
               description "Bandwidth to reserve (bps)";
               type string;
             }
           }
           case case_2 {
             leaf bandwidth-percent {
               description "Percentage of main path bandwidth to reserve";
               type union {
                 type string {
                   pattern "<.*>|$.*";
                 }
                 type int32 {
                   range "1 .. 100";
                 }
               }
             }
           }
         }
         choice include_any_or_no_include_any {
           case case_1 {
             leaf no-include-any {
               description "Disable include-any checking";
               type empty;
             }
           }
           case case_2 {
             leaf-list include-any {
               ordered-by user;
               description "Groups, one or more of which must be present";
               type string;
             }
           }
         }
         choice include_all_or_no_include_all {
           case case_1 {
             leaf no-include-all {
               description "Disable include-all checking";
               type empty;
             }
           }
           case case_2 {
             leaf-list include-all {
               ordered-by user;
               description "Groups, all of which must be present";
               type string;
             }
           }
         }
         choice exclude_or_no_exclude {
           case case_1 {
             leaf no-exclude {
               description "Disable exclude checking";
               type empty;
             }
           }
           case case_2 {
             leaf-list exclude {
               ordered-by user;
               description "Groups, all of which must be absent";
               type string;
             }
           }
         }
       }
       container p2mp {
         presence "enable p2mp";
         junos:must "(!(\".. associate-backup-pe-groups\"))";
         junos:must-message "backup-pe-group cannot be associated with P2MP LSP";
         junos:must "(!(\".. egress-protection\"))";
         junos:must-message "egress-protection unsupported for P2MP LSP branch";
         junos:must "(!(any \".. primary <*> adaptive\"))";
         junos:must-message "adaptive unsupported for P2MP LSP branch path";
         junos:must "(!(\".. adaptive\"))";
         junos:must-message "adaptive unsupported for P2MP LSP branch";
         junos:must "(!(\".. install\"))";
         junos:must-message "install prefixes invalid for P2MP LSP branch";
         junos:must "(!(\".. ldp-tunneling\"))";
         junos:must-message "ldp-tunneling unsupported for P2MP LSP branch";
         junos:must "(!(\".. backup\"))";
         junos:must-message "backup invalid for P2MP LSP branch";
         junos:must "(!(\".. no-install-to-address\"))";
         junos:must-message "no-install-to-address invalid for P2MP LSP branch";
         junos:must "(!(\".. node-link-protection\"))";
         junos:must-message "node protection unsupported for P2MP LSP branch";
         junos:must "(!(\".. fast-reroute\"))";
         junos:must-message "fast-reroute unsupported for P2MP LSP branch";
         junos:must "(!(\".. secondary\"))";
         junos:must-message "secondary paths unsupported for P2MP LSP branch";
         junos:must "(!(\".. ultimate-hop-popping\"))";
         junos:must-message "For point-to-multipoint LSP, ultimate hop popping cannot be configured";
         junos:must "(!(\".. lsp-external-controller\"))";
         junos:must-message "Can't configure lsp-external-controller knob in p2mp LSPs";
         junos:must "((!(\".. .. .. .. .. logical-systems\") || !(\".. .. ipv6-tunneling\")))";
         junos:must-message "In logical systems, IPv6 tunneling cannot be configured with P2MP LSPs";
         junos:must "((any \".. p2mp <*>\" || \".. template\"))";
         junos:must-message "For S2L point-to-multipoint LSP, parent point-to-multipoint LSP name must be configured";
         description "Point-to-multipoint label-switched path";
         leaf path_name {
           description "Name of point-to-multipoint LSP";
           junos:must "(!(\".. .. .. label-switched-path $$\"))";
           junos:must-message "The P2MP name is the same as an existing LSP name";
           junos:must "(!(\".. .. template\"))";
           junos:must-message "Name not applicable for point-to-multipoint template";
           type string {
             junos:posix-pattern "^.{1,64}$";
             junos:pattern-message "Must be a string of less than 64 characters";
           }
         }
       }
       container auto-bandwidth {
         presence "enable auto-bandwidth";
         junos:must "(!(\".. p2mp\"))";
         junos:must-message "Cannot do auto-bandwidth for P2MP LSP branch";
         junos:must "((!(\".. lsp-attributes\") || (\".. lsp-attributes switching-type psc-1\" && (!(\".. lsp-attributes encoding-type\") || \".. lsp-attributes encoding-type packet\"))))";
         junos:must-message "Cannot do auto-bandwidth for non-packet LSP";
         description "Do auto bandwidth allocation for this LSP";
         uses apply-advanced;
         leaf adjust-interval {
           description "Time to adjust LSP bandwidth";
           default "86400";
           units "seconds";
           type union {
             type string {
               pattern "<.*>|$.*";
             }
             type uint32 {
               range "300 .. 315360000";
             }
           }
         }
         leaf adjust-threshold {
           description "Percentage change in average LSP utilization to trigger auto-adjustment";
           default "0";
           units "percent";
           type union {
             type string {
               pattern "<.*>|$.*";
             }
             type uint32 {
               range "0 .. 50";
             }
           }
         }
         leaf adjust-threshold-absolute {
           description "Change in average LSP utilization to trigger auto-adjustment";
           default "0";
           units "bps";
           type string;
         }
         leaf adjust-threshold-activate-bandwidth {
           description "Adjusts signaled bw if greater than this value";
           units "bps";
           type string;
         }
         leaf minimum-bandwidth {
           description "Minimum LSP bandwidth";
           units "bps";
           type string;
         }
         leaf maximum-bandwidth {
           description "Maximum LSP bandwidth";
           units "bps";
           type string;
         }
         leaf minimum-bandwidth-adjust-interval {
           description "Duration for which minimum bandwidth will be frozen";
           units "seconds";
           type union {
             type string {
               pattern "<.*>|$.*";
             }
             type uint32 {
               range "300 .. 31536000";
             }
           }
         }
         leaf minimum-bandwidth-adjust-threshold-change {
           description "Change in max average bandwidth to freeze min bandwidth";
           units "percent";
           junos:must "(\".. minimum-bandwidth-adjust-interval\")";
           junos:must-message "minimum-bandwidth-adjust-interval must be configured";
           type union {
             type string {
               pattern "<.*>|$.*";
             }
             type uint32 {
               range "0 .. 100";
             }
           }
         }
         leaf minimum-bandwidth-adjust-threshold-value {
           description "Freeze min bandwidth if max average bandwidth falls below this bw";
           status deprecated;
           units "bps";
           junos:must "(!(\".. minimum-bandwidth-adjust-threshold-change\"))";
           junos:must-message "minimum-bandwidth-adjust-threshold-change cannot be configured with minimum-bandwidth-adjust-threshold-value";
           junos:must "(\".. minimum-bandwidth-adjust-interval\")";
           junos:must-message "minimum-bandwidth-adjust-interval must be configured";
           type string;
         }
         leaf monitor-bandwidth {
           description "Monitor LSP bandwidth without adjustments";
           type empty;
         }
         leaf adjust-threshold-overflow-limit {
           description "Number of consecutive overflow samples to trigger auto-adjustment";
           junos:must "(((\".. adjust-threshold\" && \".. maximum-bandwidth\") && (!(\".. adjust-threshold $$={0}\") && !(\".. maximum-bandwidth $$={0}\"))))";
           junos:must-message "Non-zero adjust-threshold and maximum-bandwidth MUST be configured";
           junos:must "(!(\".. monitor-bandwidth\"))";
           junos:must-message "adjust-threshold-overflow-limit cannot be used with monitor-bandwidth";
           type union {
             type string {
               pattern "<.*>|$.*";
             }
             type uint32 {
               range "1 .. 65535";
             }
           }
         }
         leaf adjust-threshold-underflow-limit {
           description "Number of consecutive underflow samples to trigger auto-adjustment";
           junos:must "((\".. adjust-threshold\" && !(\".. adjust-threshold 0\")))";
           junos:must-message "Non-zero adjust-threshold must be configured";
           junos:must "(!(\".. monitor-bandwidth\"))";
           junos:must-message "adjust-threshold-underflow-limit cannot be used with monitor-bandwidth";
           type union {
             type string {
               pattern "<.*>|$.*";
             }
             type uint32 {
               range "1 .. 65535";
             }
           }
         }
         leaf resignal-minimum-bandwidth {
           description "Resignal the LSP using minimum-bandwidth";
           type empty;
         }
         leaf sync-active-path-bandwidth {
           description "Signal standby path with bandwidth obtained from active path";
           type empty;
         }
       }
       container optimize-on-change {
         description "Specify additional re-optimization triggers for this LSP";
         uses apply-advanced;
         leaf link-congestion {
           description "Optimize when a link becomes congested";
           type empty;
         }
       }
       container deselect-on-bandwidth-failure {
         presence "enable deselect-on-bandwidth-failure";
         description "Deselect active path if it cannot meet the bandwidth constraint";
         uses apply-advanced;
         leaf tear-lsp {
           description "Bring down active path when all paths fail to reserve required bandwidth";
           type empty;
         }
       }
       container track-igp-metric {
         description "Track IGP metric for LSP install prefixes";
         uses apply-advanced;
         leaf install-v4-prefixes {
           description "Track IGP metric for IPV4 prefixes";
           type empty;
         }
         leaf install-v6-prefixes {
           description "Track IGP metric for IPV6 prefixes";
           type empty;
         }
       }
       container associate-lsp {
         junos:must "((\".. oam mpls-tp-mode\" || \".. .. oam mpls-tp-mode\"))";
         junos:must-message "mpls-tp-mode must be configured for associate-lsp";
         description "Associate the LSP for OAM";
         uses apply-advanced;
         leaf lsp-name {
           description "Name of assocation LSP";
           type string {
             junos:posix-pattern "^.{1,64}$";
             junos:pattern-message "Must be a string of 64 characters or less";
           }
         }
         leaf from {
           description "Address of ingress router of associated LSP";
           type jt:ipv4addr;
         }
       }
       list primary {
         key name;
         ordered-by user;
         description "Preferred path";
         leaf name {
           description "Name of path";
           type string {
             length "1 .. 64";
           }
         }
         uses apply-advanced;
         container bandwidth {
           description "Bandwidth to reserve (bps)";
           uses bandwidth-type;
         }
         container admin-group {
           description "Administrative group policy";
           uses admin_group_include_exclude;
         }
         container admin-group-extended {
           description "Extended administrative group policy";
           uses admin_group_include_exclude;
         }
         container priority {
           presence "enable priority";
           description "Preemption priorities";
         }
         leaf setup-priority {
           description "Set-up priority";
           type union {
             type string {
               pattern "<.*>|$.*";
             }
             type uint32 {
               range "0 .. 7";
             }
           }
         }
         leaf reservation-priority {
           description "Reservation priority";
           type union {
             type string {
               pattern "<.*>|$.*";
             }
             type uint32 {
               range "0 .. 7";
             }
           }
         }
         container oam {
           description "Periodic OAM";
           uses periodic_oam;
         }
         leaf class-of-service {
           description "Class-of-service value";
           type union {
             type string {
               pattern "<.*>|$.*";
             }
             type int32 {
               range "0 .. 7";
             }
           }
         }
         leaf no-decrement-ttl {
           description "Do not decrement the TTL within an LSP";
           type empty;
         }
         leaf hop-limit {
           description "Maximum allowed router hops";
           type union {
             type string {
               pattern "<.*>|$.*";
             }
             type int32 {
               range "2 .. 255";
             }
           }
         }
         leaf no-cspf {
           description "Disable automatic path computation";
           type empty;
         }
         leaf admin-down {
           description "Set GMPLS LSP to administrative down state";
           type empty;
         }
         leaf optimize-timer {
           description "Periodical path reoptimizations";
           units "seconds";
           type union {
             type string {
               pattern "<.*>|$.*";
             }
             type int32 {
               range "0 .. 65535";
             }
           }
         }
         leaf preference {
           description "Preference value";
           type union {
             type uint32;
             type string {
               pattern "<.*>|$.*";
             }
           }
         }
         choice record-choice {
           leaf record {
             description "Record transit routers";
             type empty;
           }
           leaf no-record {
             description "Don't record transit routers";
             type empty;
           }
         }
         leaf standby {
           description "Keep backup paths in continuous standby";
           type empty;
         }
         leaf exclude-srlg {
           description "Exclude SRLG links for secondary path";
           type empty;
         }
         leaf ultimate-hop-popping {
           description "Request ultimate hop popping from egress";
           type empty;
         }
         leaf sync-active-path-bandwidth {
           description "Signal standby path with bandwidth obtained from active path";
           type empty;
         }
         leaf cross-credibility-cspf {
           description "Compute paths across multi-protocol links and nodes";
           type empty;
         }
         leaf adaptive {
           description "Have the LSP smoothly cut over to new routes";
           type empty;
         }
         leaf select {
           type enumeration {
             enum "manual" {
               description "Manual override as preferred active path, if up and stable";
             }
             enum "unconditional" {
               description "Unconditional override as preferred active path, regardless of up/down status";
             }
           }
         }
         container upstream-label {
           description "Upstream Label for the bidirectional label-switched path";
           uses apply-advanced;
           leaf vlan-id {
             description "VLAN ID label for the label-switched path";
             junos:must "(\".. .. .. lsp-attributes switching-type ethernet-vlan\")";
             junos:must-message "VLAN label is valid only for VLAN LSP";
             type union {
               type string {
                 pattern "<.*>|$.*";
               }
               type uint32 {
                 range "1 .. 4094";
               }
             }
           }
         }
         container optimize-on-change {
           junos:must "(!(\"protocols mpls label-switched-path $$ optimize-on-change\"))";
           junos:must-message "LSP already has optimize-on-change";
           description "Specify additional re-optimization triggers for this path";
           uses apply-advanced;
           leaf link-congestion {
             description "Optimize when a link becomes congested";
             type empty;
           }
         }
       }
       list secondary {
         key name;
         ordered-by user;
         description "Backup path";
         leaf name {
           description "Name of path";
           type string {
             length "1 .. 64";
           }
         }
         uses apply-advanced;
         container bandwidth {
           description "Bandwidth to reserve (bps)";
           uses bandwidth-type;
         }
         container admin-group {
           description "Administrative group policy";
           uses admin_group_include_exclude;
         }
         container admin-group-extended {
           description "Extended administrative group policy";
           uses admin_group_include_exclude;
         }
         container priority {
           presence "enable priority";
           description "Preemption priorities";
         }
         leaf setup-priority {
           description "Set-up priority";
           type union {
             type string {
               pattern "<.*>|$.*";
             }
             type uint32 {
               range "0 .. 7";
             }
           }
         }
         leaf reservation-priority {
           description "Reservation priority";
           type union {
             type string {
               pattern "<.*>|$.*";
             }
             type uint32 {
               range "0 .. 7";
             }
           }
         }
         container oam {
           description "Periodic OAM";
           uses periodic_oam;
         }
         leaf class-of-service {
           description "Class-of-service value";
           type union {
             type string {
               pattern "<.*>|$.*";
             }
             type int32 {
               range "0 .. 7";
             }
           }
         }
         leaf no-decrement-ttl {
           description "Do not decrement the TTL within an LSP";
           type empty;
         }
         leaf hop-limit {
           description "Maximum allowed router hops";
           type union {
             type string {
               pattern "<.*>|$.*";
             }
             type int32 {
               range "2 .. 255";
             }
           }
         }
         leaf no-cspf {
           description "Disable automatic path computation";
           type empty;
         }
         leaf admin-down {
           description "Set GMPLS LSP to administrative down state";
           type empty;
         }
         leaf optimize-timer {
           description "Periodical path reoptimizations";
           units "seconds";
           type union {
             type string {
               pattern "<.*>|$.*";
             }
             type int32 {
               range "0 .. 65535";
             }
           }
         }
         leaf preference {
           description "Preference value";
           type union {
             type uint32;
             type string {
               pattern "<.*>|$.*";
             }
           }
         }
         choice record-choice {
           leaf record {
             description "Record transit routers";
             type empty;
           }
           leaf no-record {
             description "Don't record transit routers";
             type empty;
           }
         }
         leaf standby {
           description "Keep backup paths in continuous standby";
           type empty;
         }
         leaf exclude-srlg {
           description "Exclude SRLG links for secondary path";
           type empty;
         }
         leaf ultimate-hop-popping {
           description "Request ultimate hop popping from egress";
           type empty;
         }
         leaf sync-active-path-bandwidth {
           description "Signal standby path with bandwidth obtained from active path";
           type empty;
         }
         leaf cross-credibility-cspf {
           description "Compute paths across multi-protocol links and nodes";
           type empty;
         }
         leaf adaptive {
           description "Have the LSP smoothly cut over to new routes";
           type empty;
         }
         leaf select {
           type enumeration {
             enum "manual" {
               description "Manual override as preferred active path, if up and stable";
             }
             enum "unconditional" {
               description "Unconditional override as preferred active path, regardless of up/down status";
             }
           }
         }
         container upstream-label {
           description "Upstream Label for the bidirectional label-switched path";
           uses apply-advanced;
           leaf vlan-id {
             description "VLAN ID label for the label-switched path";
             junos:must "(\".. .. .. lsp-attributes switching-type ethernet-vlan\")";
             junos:must-message "VLAN label is valid only for VLAN LSP";
             type union {
               type string {
                 pattern "<.*>|$.*";
               }
               type uint32 {
                 range "1 .. 4094";
               }
             }
           }
         }
         container optimize-on-change {
           junos:must "(!(\"protocols mpls label-switched-path $$ optimize-on-change\"))";
           junos:must-message "LSP already has optimize-on-change";
           description "Specify additional re-optimization triggers for this path";
           uses apply-advanced;
           leaf link-congestion {
             description "Optimize when a link becomes congested";
             type empty;
           }
         }
         container non-active-hold-priority {
           description "Non-active hold priority";
           leaf non-active-hold-prio-value {
             description "Non-active hold priority value";
             junos:must "(!((\".. .. no-cspf\" || (\".. .. .. no-cspf\" || \".. .. .. .. no-cspf\"))))";
             junos:must-message "Non-active hold priority unsupported for no-cspf LSPs";
             junos:must "((\".. .. standby\" || (\".. .. .. standby\" || \".. .. .. .. standby\")))";
             junos:must-message "Non-active hold priority supported only for standby path";
             type union {
               type string {
                 pattern "<.*>|$.*";
               }
               type uint32 {
                 range "0 .. 7";
               }
             }
           }
         }
       }
       container policing {
         description "Traffic policing for this LSP";
         leaf filter {
           description "Name of filter to use for policing LSP traffic";
           junos:must "(!(\".. .. p2mp\"))";
           junos:must-message "Manual policing not supported for P2MP LSPs";
           junos:must "(!(\"firewall family any filter $$ interface-specific\"))";
           junos:must-message "LSP policing filter must not be interface-specific";
           junos:must "((\"firewall family any filter $$\" || (!(\"firewall\") && \".. .. .. .. .. .. .. .. firewall family any filter $$\")))";
           junos:must-message "referenced filter must be defined under firewall family any";
           type string {
             junos:posix-pattern "!^((__.*)|(.{65,}))$";
             junos:pattern-message "Must be a non-reserved string of 64 characters or less";
           }
         }
         leaf no-auto-policing {
           description "Turn off automatic policing for this LSP";
           type empty;
         }
       }
       leaf lsp-external-controller {
         description "Name of the external path computing entity";
         junos:must "(!(\".. single-sided-associated-bidirectional\"))";
         junos:must-message "Single-sided associated bidir LSP cannot be externally controlled";
         junos:must "(!(\".. corouted-bidirectional\"))";
         junos:must-message "Externally controlled LSP cannot be corouted bidirectional";
         junos:must "(!(\".. corouted-bidirectional-passive\"))";
         junos:must-message "Externally controlled LSP cannot be corouted bidirectional";
         junos:must "(\"protocols mpls lsp-external-controller $$\")";
         junos:must-message "Referenced lsp-external-controller is not defined";
         type string {
           junos:posix-pattern "^.{1,64}$";
           junos:pattern-message "Must be a string of less than 64 characters";
         }
       }
       leaf associate-backup-pe-groups {
         description "Associate this LSP with backup-pe groups";
         junos:must "(\".. oam bfd-liveness-detection\")";
         junos:must-message "bfd-liveness-detection must be configured for this feature.";
         type empty;
       }
       leaf egress-protection {
         description "Use this LSP for egress protection data transport";
         junos:must "(!(\".. install\"))";
         junos:must-message "Cannot install routes for an egress protection LSP";
         type empty;
       }
       leaf transport-class {
         description "Transport class this LSP belongs to";
         junos:must "(\"routing-options transport-class name $$\")";
         junos:must-message "Referenced transport class is not defined";
         type string {
           junos:posix-pattern "^.{1,64}$";
           junos:pattern-message "Must be a string of less than 64 characters";
         }
       }
     }
     container deselect-on-bandwidth-failure {
       presence "enable deselect-on-bandwidth-failure";
       description "Deselect active path if it cannot meet the bandwidth constraint";
       uses apply-advanced;
       leaf tear-lsp {
         description "Bring down active path when all paths fail to reserve required bandwidth";
         type empty;
       }
     }
     container track-igp-metric {
       description "Track IGP metric for LSP install prefixes";
       uses apply-advanced;
       leaf install-v4-prefixes {
         description "Track IGP metric for IPV4 prefixes";
         type empty;
       }
       leaf install-v6-prefixes {
         description "Track IGP metric for IPV6 prefixes";
         type empty;
       }
     }
     list container-label-switched-path {
       key name;
       ordered-by user;
       leaf name {
         description "Name of container-lsp";
         junos:must "(!(\".. .. label-switched-path $$\"))";
         junos:must-message "The Container LSP name is the same as an existing LSP name";
         type string {
           junos:posix-pattern "^.{1,64}$";
           junos:pattern-message "Must be a string of 64 characters or less";
         }
       }
       uses apply-advanced;
       choice enable-disable {
         case case_1 {
           leaf disable {
             description "Disable MPLS container-label-switched path";
             type empty;
           }
         }
       }
       leaf description {
         description "Text description of label-switched path";
         type string {
           length "1 .. 80";
         }
       }
       container label-switched-path-template {
         description "Template for dynamic point-to-point LSP parameters";
         uses apply-advanced;
         choice dynamic-template {
           case case_1 {
             leaf template-name {
               description "Name of point-to-point LSP template";
               junos:must "(!(\"protocols mpls label-switched-path $$ egress-protection\"))";
               junos:must-message "Referenced point-to-point LSP template cannot have egress-protection";
               junos:must "(!(\"protocols mpls label-switched-path $$ p2mp\"))";
               junos:must-message "Referenced point-to-point LSP template cannot be p2mp sub LSP";
               junos:must "(!(\"protocols mpls label-switched-path $$ bandwidth\"))";
               junos:must-message "Referenced point-to-point LSP template cannot have static bandwidth";
               junos:must "(!(\"protocols mpls label-swithced-path $$ policing\"))";
               junos:must-message "Referenced point-to-point LSP template cannot have policing";
               junos:must "((\"protocols mpls label-switched-path $$\" && (\"protocols mpls label-switched-path $$ template\" && !(\"protocols mpls label-switched-path $$ no-cspf\"))))";
               junos:must-message "Referenced point-to-point LSP template cannot have no-cspf";
               junos:must "((\"protocols mpls label-switched-path $$\" && \"protocols mpls label-switched-path $$ template\"))";
               junos:must-message "Referenced point-to-point LSP template does not exist";
               type string {
                 length "1 .. 64";
                 junos:posix-pattern "![*<>]";
                 junos:pattern-message "Template name should not contain '*' and angle brackets";
               }
             }
           }
           case case_2 {
             leaf default-template {
               description "Use default parameters";
               type empty;
             }
           }
         }
       }
       leaf to {
         description "Address of egress router";
         type jt:ipv4addr;
       }
       leaf suffix {
         description "Suffix to generate names of members of container LSP";
         type string {
           length "1 .. 64";
         }
       }
       container splitting-merging {
         description "Do splitting and merging";
         uses apply-advanced;
         leaf maximum-member-lsps {
           description "Maximum number of LSPs";
           type union {
             type string {
               pattern "<.*>|$.*";
             }
             type int32 {
               range "1 .. 64";
             }
           }
         }
         leaf minimum-member-lsps {
           description "Minimum number of LSPs";
           type union {
             type string {
               pattern "<.*>|$.*";
             }
             type int32 {
               range "1 .. 64";
             }
           }
         }
         leaf splitting-bandwidth {
           description "Maximum bandwidth threshold for splitting";
           units "bps";
           type string;
         }
         leaf merging-bandwidth {
           description "Minimum bandwidth threshold for merging";
           units "bps";
           type string;
         }
         leaf maximum-signaling-bandwidth {
           description "Maximum bandwidth for signaling during normalization";
           units "bps";
           type string;
         }
         leaf minimum-signaling-bandwidth {
           description "Minimum bandwidth for signaling during normalization";
           units "bps";
           type string;
         }
         leaf splitting-merging-threshold {
           description "Change in aggregate LSP utilization to trigger splitting or merging";
           default "10";
           units "percent";
           type union {
             type string {
               pattern "<.*>|$.*";
             }
             type uint32 {
               range "0 .. 100";
             }
           }
         }
         container normalization {
           description "Do normalization";
           uses apply-advanced;
           leaf normalize-interval {
             description "Time to normalize container LSP";
             default "86400";
             units "seconds";
             type union {
               type string {
                 pattern "<.*>|$.*";
               }
               type uint32 {
                 range "300 .. 315360000";
               }
             }
           }
           leaf failover-normalization {
             description "Do pre-mature normalization in case some LSPs go down before next normalization";
             type empty;
           }
           leaf no-incremental-normalize {
             description "Do not normalize unless all LSPs are successfully signaled";
             type empty;
           }
           leaf normalization-retry-duration {
             description "Time before retrying the container LSP normalization";
             units "seconds";
             type union {
               type string {
                 pattern "<.*>|$.*";
               }
               type uint32 {
                 range "1 .. 86400";
               }
             }
           }
           leaf normalization-retry-limits {
             description "Maximum number of times to retry container LSP normalization";
             type union {
               type string {
                 pattern "<.*>|$.*";
               }
               type uint32 {
                 range "1 .. 1000";
               }
             }
           }
           leaf no-normalize-same-members {
             description "Do not normalize when we are not splitting or merging member LSPs";
             type empty;
           }
         }
         container sampling {
           description "Sampling information";
           uses apply-advanced;
           leaf cut-off-threshold {
             description "Cut-off percentile to remove outliers from aggregate samples";
             default "0";
             type union {
               type string {
                 pattern "<.*>|$.*";
               }
               type uint32 {
                 range "0 .. 100";
               }
             }
           }
           choice sampling-mode {
             case case_1 {
               leaf use-average-aggregate {
                 description "Use average of the samples";
                 type empty;
               }
             }
             case case_2 {
               leaf use-percentile {
                 description "Use a percentile of the samples";
                 default "100";
                 type union {
                   type string {
                     pattern "<.*>|$.*";
                   }
                   type uint32 {
                     range "0 .. 100";
                   }
                 }
               }
             }
           }
         }
       }
       leaf lsp-external-controller {
         description "Name of the external path computing entity";
         junos:must "(\"protocols mpls lsp-external-controller $$\")";
         junos:must-message "Referenced lsp-external-controller is not defined";
         type string {
           junos:posix-pattern "^.{1,64}$";
           junos:pattern-message "Must be a string of less than 64 characters";
         }
       }
     }
     list transit-lsp-association {
       key name;
       ordered-by user;
       description "Transit label switch path assoication";
       leaf name {
         description "Name of transit assocation LSP group";
         type string {
           junos:posix-pattern "^.{1,64}$";
           junos:pattern-message "Must be a string of 64 characters or less";
         }
       }
       uses apply-advanced;
       leaf lsp-name-1 {
         description "Name of assocation LSP 1";
         type string {
           junos:posix-pattern "^.{1,64}$";
           junos:pattern-message "Must be a string of 64 characters or less";
         }
       }
       leaf from-1 {
         description "Address of associated LSP 1";
         type jt:ipv4addr;
       }
       leaf lsp-name-2 {
         description "Name of assocation LSP 2";
         type string {
           junos:posix-pattern "^.{1,64}$";
           junos:pattern-message "Must be a string of 64 characters or less";
         }
       }
       leaf from-2 {
         description "Address of associated LSP 2";
         type jt:ipv4addr;
       }
     }
     list path {
       key name;
       ordered-by user;
       description "Route of a label-switched path";
       leaf name {
         description "Name of label-switched path";
         type string {
           junos:posix-pattern "^.{1,64}$";
           junos:pattern-message "Must be a string of less than 64 characters";
         }
       }
       uses apply-advanced;
       list path-list {
         key name;
         ordered-by user;
         description "List of routers in the label-switched path";
         leaf name {
           description "Address of next system in path";
           type string {
             junos:posix-pattern "^.{1,64}$";
             junos:pattern-message "Must be a string of less than 64 characters";
           }
         }
         leaf abstract {
           description "Next system in path is abstract";
           junos:must "(\".. .. .. abstract-hop ${path-list}\")";
           junos:must-message "Referenced abstart hop must be configured";
           type empty;
         }
         choice loose_strict_none {
           case case_1 {
             leaf loose {
               description "Next hop might not be adjacent";
               type empty;
             }
           }
           case case_2 {
             leaf loose-link {
               description "Next hop link might not be adjacent";
               type empty;
             }
           }
           case case_3 {
             leaf strict {
               description "Next hop must be adjacent";
               type empty;
             }
           }
         }
       }
     }
     list constituent-list {
       key name;
       ordered-by user;
       description "MPLS constituent list for abstract hops";
       leaf name {
         description "Constituent list name";
         type string {
           junos:posix-pattern "^.{1,64}$";
           junos:pattern-message "Must be a string of 64 characters or less";
         }
       }
       uses apply-advanced;
       leaf-list srlg {
         ordered-by user;
         description "SRLG Name";
         type string;
         max-elements 16;
       }
       leaf-list admin-group {
         ordered-by user;
         description "Administrative groups";
         type string;
         max-elements 16;
       }
       leaf-list admin-group-extended {
         ordered-by user;
         description "Extended administrative groups";
         type string;
         max-elements 16;
       }
     }
     list abstract-hop {
       key name;
       ordered-by user;
       description "MPLS abstract hop";
       leaf name {
         description "Abstract hop name";
         type string {
           junos:posix-pattern "^.{1,64}$";
           junos:pattern-message "Must be a string of 64 characters or less";
         }
       }
       uses apply-advanced;
       leaf operator {
         description "Operation among constituent lists";
         type enumeration {
           enum "AND" {
             description "AND";
           }
           enum "OR" {
             description "OR";
           }
         }
       }
       list constituent-list {
         key name;
         ordered-by user;
         description "Building abstract hop using constituent lists";
         leaf name {
           description "Constituent list name";
           junos:must "(\"protocols mpls constituent-list $$\")";
           junos:must-message "Referenced constituent list does not exist";
           type string {
             length "1 .. 64";
           }
         }
         uses apply-advanced;
         choice list-type {
           case case_1 {
             leaf include-any-list {
               description "Include any";
               type empty;
             }
           }
           case case_2 {
             leaf include-all-list {
               description "Include all";
               type empty;
             }
           }
           case case_3 {
             leaf exclude-any-list {
               description "Exclude any";
               type empty;
             }
           }
           case case_4 {
             leaf exclude-all-list {
               description "Exclude all";
               type empty;
             }
           }
         }
       }
     }
     container egress-protection {
       description "Egress router protection";
       uses apply-advanced;
       list context-identifier {
         key name;
         description "Context identifier";
         leaf name {
           description "IP address";
           type jt:ipv4addr;
         }
         uses apply-advanced;
         choice context-type {
           case case_1 {
             leaf primary {
               description "Primary";
               type empty;
             }
           }
           case case_2 {
             leaf protector {
               description "Protector";
               type empty;
             }
           }
         }
         leaf metric {
           description "IGP metric";
           junos:must "(!(\" .. advertise-mode stub-alias\"))";
           junos:must-message "Metric configuration is not supported with stub-alias mode";
           junos:must "(\".. protector\")";
           junos:must-message "Configurable only for protector context identifiers";
           type union {
             type string {
               pattern "<.*>|$.*";
             }
             type uint32 {
               range "2 .. 16777215";
             }
           }
         }
         leaf advertise-mode {
           description "Advertise mode";
           type enumeration {
             enum "stub-proxy" {
               description "Proxy";
             }
             enum "stub-alias" {
               description "Alias";
             }
           }
         }
         leaf-list admin-group {
           ordered-by user;
           description "Administrative groups";
           junos:must "((\".. protector\" && \".. advertise-mode stub-proxy\"))";
           junos:must-message "Configurable only for protector with proxy mode";
           type string;
         }
       }
       container traceoptions {
         description "Trace options for egress-protection";
         uses apply-advanced;
         container file {
           description "Trace file options";
           leaf filename {
             description "Name of file in which to write trace information";
             type string {
               length "1 .. 1024";
               junos:posix-pattern "![/ %]";
               junos:pattern-message "Must not contain '/', % or a space";
             }
           }
           leaf replace {
             description "Replace trace file rather than appending to it";
             status deprecated;
             type empty;
           }
           leaf size {
             description "Maximum trace file size";
             type string;
           }
           leaf files {
             description "Maximum number of trace files";
             default "10";
             type union {
               type string {
                 pattern "<.*>|$.*";
               }
               type uint32 {
                 range "2 .. 1000";
               }
             }
           }
           leaf no-stamp {
             description "Do not timestamp trace file";
             status deprecated;
             type empty;
           }
           choice world-readable-choice {
             leaf world-readable {
               description "Allow any user to read the log file";
               type empty;
             }
             leaf no-world-readable {
               description "Don't allow any user to read the log file";
               type empty;
             }
           }
         }
         list flag {
           key name;
           ordered-by user;
           description "Tracing parameters";
           leaf name {
             type enumeration {
               enum "state" {
                 description "Trace state transitions";
               }
               enum "route" {
                 description "Trace route transitions";
               }
               enum "error" {
                 description "Trace error conditions";
               }
               enum "all" {
                 description "Trace everything";
               }
             }
           }
         }
       }
     }
     container label-range {
       description "MPLS labels ranges";
       uses apply-advanced;
       list lsi-label-range {
         key name;
         ordered-by user;
         description "LSI-label-range";
         leaf name {
           description "Label_range_start";
           type union {
             type string {
               pattern "<.*>|$.*";
             }
             type uint32 {
               range "16 .. 1048575";
             }
           }
         }
         leaf range-end {
           description "Label_range_end";
           type union {
             type string {
               pattern "<.*>|$.*";
             }
             type uint32 {
               range "16 .. 1048575";
             }
           }
         }
       }
       list dynamic-label-range {
         key name;
         ordered-by user;
         description "Dynamic-label-range";
         leaf name {
           description "Label_range_start";
           type union {
             type string {
               pattern "<.*>|$.*";
             }
             type uint32 {
               range "16 .. 1048575";
             }
           }
         }
         leaf range-end {
           description "Label_range_end";
           type union {
             type string {
               pattern "<.*>|$.*";
             }
             type uint32 {
               range "16 .. 1048575";
             }
           }
         }
       }
       list block-label-range {
         key name;
         ordered-by user;
         description "Block-label-range";
         leaf name {
           description "Label_range_start";
           type union {
             type string {
               pattern "<.*>|$.*";
             }
             type uint32 {
               range "16 .. 1048575";
             }
           }
         }
         leaf range-end {
           description "Label_range_end";
           type union {
             type string {
               pattern "<.*>|$.*";
             }
             type uint32 {
               range "16 .. 1048575";
             }
           }
         }
       }
       list srgb-label-range {
         key name;
         ordered-by user;
         description "SRGB-label-range";
         max-elements 1;
         leaf name {
           description "Label_range_start";
           type union {
             type string {
               pattern "<.*>|$.*";
             }
             type uint32 {
               range "16 .. 1048575";
             }
           }
         }
         leaf range-end {
           description "Label_range_end";
           type union {
             type string {
               pattern "<.*>|$.*";
             }
             type uint32 {
               range "16 .. 1048575";
             }
           }
         }
       }
       leaf label-limit {
         description "Limit for the number of concurrent active labels";
         type union {
           type string {
             pattern "<.*>|$.*";
           }
           type uint32;
         }
       }
       list static-label-range {
         key name;
         ordered-by user;
         description "Static-label-range";
         leaf name {
           description "Label_range_start";
           type union {
             type string {
               pattern "<.*>|$.*";
             }
             type uint32 {
               range "16 .. 1048575";
             }
           }
         }
         leaf range-end {
           description "Label_range_end";
           type union {
             type string {
               pattern "<.*>|$.*";
             }
             type uint32 {
               range "16 .. 1048575";
             }
           }
         }
       }
     }
     choice enable-disable {
       case case_1 {
         leaf disable {
           description "Disable MPLS";
           type empty;
         }
       }
     }
     container label-history {
       presence "enable label-history";
       description "MPLS label history recording";
       uses apply-advanced;
       leaf max-entries {
         description "Limit for the number of history entry per label";
         type union {
           type string {
             pattern "<.*>|$.*";
           }
           type uint32;
         }
       }
     }
     container traceoptions {
       description "Trace options for MPLS";
       uses apply-advanced;
       container file {
         description "Trace file options";
         leaf filename {
           description "Name of file in which to write trace information";
           type string {
             length "1 .. 1024";
             junos:posix-pattern "![/ %]";
             junos:pattern-message "Must not contain '/', % or a space";
           }
         }
         leaf replace {
           description "Replace trace file rather than appending to it";
           status deprecated;
           type empty;
         }
         leaf size {
           description "Maximum trace file size";
           type string;
         }
         leaf files {
           description "Maximum number of trace files";
           default "10";
           type union {
             type string {
               pattern "<.*>|$.*";
             }
             type uint32 {
               range "2 .. 1000";
             }
           }
         }
         leaf no-stamp {
           description "Do not timestamp trace file";
           status deprecated;
           type empty;
         }
         choice world-readable-choice {
           leaf world-readable {
             description "Allow any user to read the log file";
             type empty;
           }
           leaf no-world-readable {
             description "Don't allow any user to read the log file";
             type empty;
           }
         }
       }
       list flag {
         key name;
         ordered-by user;
         description "Tracing parameters";
         leaf name {
           type enumeration {
             enum "connection" {
               description "Trace CCC activity";
             }
             enum "connection-detail" {
               description "Trace CCC activity in detail";
             }
             enum "cspf" {
               description "Trace CSPF computation";
             }
             enum "cspf-node" {
               description "Trace nodes visited during CSPF";
             }
             enum "cspf-link" {
               description "Trace links visited during CSPF";
             }
             enum "cspf-abstract" {
               description "Trace abstract hop based CSPF details";
             }
             enum "state" {
               description "Trace state transitions";
             }
             enum "error" {
               description "Trace error conditions";
             }
             enum "lsping" {
               description "Trace LSP ping packets received";
             }
             enum "graceful-restart" {
               description "Trace graceful-restart-related events";
             }
             enum "nsr-synchronization" {
               description "Trace NSR synchronization events";
             }
             enum "nsr-synchronization-detail" {
               description "Trace NSR synchronization events in detail";
             }
             enum "static" {
               description "Trace static label-switched path";
             }
             enum "egress-protection" {
               description "Trace egress protection events";
             }
             enum "all" {
               description "Trace everything";
             }
             enum "autobw-state" {
               description "Trace autobandwidth events in mpls trace";
             }
             enum "externally-controlled-lsp" {
               description "Trace externally controlled LSP events in mpls trace";
             }
             enum "ted-import" {
               description "Trace leaking TED entries into lsdist.0 table";
             }
             enum "ted-export" {
               description "Trace leaking of entries from lsdist.0 table into TED";
             }
             enum "lsp-history" {
               description "Trace LSP history events";
             }
             enum "abstract-hop" {
               description "Trace abstract hop related events";
             }
           }
         }
       }
     }
     leaf ipv6-tunneling {
       description "Allow MPLS LSPs to be used for tunneling IPv6 traffic";
       type empty;
     }
     list interface {
       key name;
       ordered-by user;
       description "MPLS interface options";
       uses juniper-protocols-mpls-interface;
     }
     list static-label-switched-path {
       key name;
       ordered-by user;
       description "Static label-switched path";
       leaf name {
         description "Name of path";
         type string {
           length "1 .. 64";
         }
       }
       uses apply-advanced;
       choice lsp-type {
         case case_1 {
           container bypass {
             description "Bypass ingress label-switched path";
             uses apply-advanced;
             leaf bandwidth {
               description "Bandwidth to reserve";
               units "bps";
               type string;
             }
             leaf description {
               description "Text description of label-switched path";
               type string {
                 length "1 .. 80";
               }
             }
             leaf next-hop {
               description "IPv4 or IPv6 address or interface of next-hop router";
               type union {
                 type jt:ipaddr-or-interface;
                 type string {
                   pattern "<.*>|$.*";
                 }
               }
             }
             leaf next-table {
               description "Next-table for lookup";
               type string;
             }
             leaf push {
               description "Label to push";
               type union {
                 type string {
                   pattern "<.*>|$.*";
                 }
                 type uint32 {
                   range "0 .. 1048575";
                 }
               }
             }
             leaf to {
               description "Address of egress router";
               type jt:ipaddr;
             }
           }
         }
         case case_2 {
           list transit {
             key name;
             ordered-by user;
             description "Transit label-switched path";
             leaf name {
               description "Incoming label value";
               type union {
                 type string {
                   pattern "<.*>|$.*";
                 }
                 type uint32 {
                   range "16 .. 1048575";
                 }
               }
             }
             uses apply-advanced;
             leaf bandwidth {
               description "Bandwidth to reserve";
               units "bps";
               type string;
             }
             leaf description {
               description "Text description of label-switched path";
               type string {
                 length "1 .. 80";
               }
             }
             container link-protection {
               description "Bypass link protection";
               leaf bypass-name {
                 description "Bypass label-switched path name";
                 type string {
                   length "1 .. 64";
                 }
               }
             }
             leaf next-hop {
               description "IPv4 or IPv6 address or interface of next-hop router";
               type union {
                 type jt:ipaddr-or-interface;
                 type string {
                   pattern "<.*>|$.*";
                 }
               }
             }
             leaf member-interface {
               description "AE member interface name";
               type union {
                 type jt:interface-unit;
                 type string {
                   pattern "<.*>|$.*";
                 }
               }
             }
             container node-protection {
               description "Bypass node protection";
               leaf bypass-name {
                 description "Bypass label-switched path name";
                 type string {
                   length "1 .. 64";
                 }
               }
               leaf next-next-label {
                 description "Label expected by next-next-hop";
                 type union {
                   type string {
                     pattern "<.*>|$.*";
                   }
                   type uint32 {
                     range "0 .. 1048575";
                   }
                 }
               }
             }
             choice label-action {
               case case_1 {
                 leaf swap {
                   description "Swap top label with this label";
                   type union {
                     type string {
                       pattern "<.*>|$.*";
                     }
                     type uint32 {
                       range "0 .. 1048575";
                     }
                   }
                 }
               }
               case case_2 {
                 leaf pop {
                   description "Pop the top label";
                   type empty;
                 }
               }
               case case_3 {
                 leaf stitch {
                   description "Swap top label with the resolved LSP";
                   junos:must "(!((\".. link-protection\" || \".. node-protection\")))";
                   junos:must-message "Link-protection and node-protection are invalid for LSP stitching";
                   type empty;
                 }
               }
             }
           }
         }
         case case_3 {
           container ingress {
             description "Ingress LSR configuration for a static LSP";
             uses apply-advanced;
             leaf bandwidth {
               description "Bandwidth to reserve";
               units "bps";
               type string;
             }
             leaf class-of-service {
               description "Class-of-service value";
               type union {
                 type string {
                   pattern "<.*>|$.*";
                 }
                 type int32 {
                   range "0 .. 7";
                 }
               }
             }
             leaf description {
               description "Text description of label-switched path";
               type string {
                 length "1 .. 80";
               }
             }
             list install {
               key name;
               ordered-by user;
               description "Install prefix";
               leaf name {
                 description "Destination prefix";
                 type jt:ipv4prefix;
               }
               leaf active {
                 description "Install prefix into forwarding table";
                 type empty;
               }
             }
             leaf metric {
               description "Metric value";
               type union {
                 type string {
                   pattern "<.*>|$.*";
                 }
                 type uint32 {
                   range "1 .. 16777215";
                 }
               }
             }
             leaf next-hop {
               description "IPv4 address or interface of next-hop router";
               type union {
                 type jt:ipv4addr-or-interface;
                 type string {
                   pattern "<.*>|$.*";
                 }
               }
             }
             container link-protection {
               description "Bypass link protection";
               leaf bypass-name {
                 description "Bypass label-switched path name";
                 type string {
                   length "1 .. 64";
                 }
               }
             }
             container node-protection {
               description "Bypass node protection";
               leaf bypass-name {
                 description "Bypass label-switched path name";
                 type string {
                   length "1 .. 64";
                 }
               }
               leaf next-next-label {
                 description "Label expected by next-next-hop";
                 type union {
                   type string {
                     pattern "<.*>|$.*";
                   }
                   type uint32 {
                     range "0 .. 1048575";
                   }
                 }
               }
             }
             leaf no-install-to-address {
               description "Don't install host route 'to' address into routing tables";
               type empty;
             }
             container policing {
               description "Traffic policing for this LSP";
               leaf filter {
                 description "Name of filter to use for policing LSP traffic";
                 junos:must "(!(\"firewall family any filter $$ interface-specific\"))";
                 junos:must-message "LSP policing filter must not be interface-specific";
                 junos:must "((\"firewall family any filter $$\" || (!(\"firewall\") && \".. .. .. .. .. .. .. .. firewall family any filter $$\")))";
                 junos:must-message "referenced filter must be defined under firewall family any";
                 type string {
                   junos:posix-pattern "!^((__.*)|(.{65,}))$";
                   junos:pattern-message "Must be a non-reserved string of 64 characters or less";
                 }
               }
               leaf no-auto-policing {
                 description "Turn off automatic policing for this LSP";
                 type empty;
               }
             }
             leaf preference {
               description "Preference value";
               type union {
                 type uint32;
                 type string {
                   pattern "<.*>|$.*";
                 }
               }
             }
             leaf to {
               description "Address of egress router";
               type jt:ipv4addr;
             }
             leaf push {
               description "Label to push";
               type union {
                 type string {
                   pattern "<.*>|$.*";
                 }
                 type uint32 {
                   range "0 .. 1048575";
                 }
               }
             }
             leaf entropy-label {
               description "Enable entropy label";
               type empty;
             }
           }
         }
         case case_4 {
           container segment {
             description "Segment for segment routing";
             uses apply-advanced;
             leaf sid-label {
               description "Segment identifier (SID) label";
               type union {
                 type string {
                   pattern "<.*>|$.*";
                 }
                 type uint32 {
                   range "16 .. 1048575";
                 }
               }
             }
             leaf description {
               description "Text description of label-switched path";
               type string {
                 length "1 .. 80";
               }
             }
             leaf next-hop {
               description "IPv4 address or interface of next-hop router";
               type union {
                 type jt:ipv4addr-or-interface;
                 type string {
                   pattern "<.*>|$.*";
                 }
               }
             }
             choice label-action {
               case case_1 {
                 leaf swap {
                   description "Swap the SID label to this label";
                   type union {
                     type string {
                       pattern "<.*>|$.*";
                     }
                     type uint32 {
                       range "0 .. 1048575";
                     }
                   }
                 }
               }
               case case_2 {
                 leaf pop {
                   description "Pop the SID label";
                   type empty;
                 }
               }
             }
           }
         }
       }
     }
   }
   grouping admin_group_include_exclude {
     uses apply-advanced;
     choice include-any-choice {
       case case_1 {
         leaf-list include-any {
           ordered-by user;
           description "Groups, one or more of which must be present";
           type string;
         }
       }
     }
     choice include-all-choice {
       case case_1 {
         leaf-list include-all {
           ordered-by user;
           description "Groups, all of which must be present";
           type string;
         }
       }
     }
     choice exclude-choice {
       case case_1 {
         leaf-list exclude {
           ordered-by user;
           description "Groups, all of which must be absent";
           type string;
         }
       }
     }
   }
   grouping bandwidth-type {
     uses apply-advanced;
     leaf per-traffic-class-bandwidth {
       description "Bandwidth to reserve";
       units "bps";
       type string;
     }
     leaf ct0 {
       description "Bandwidth from traffic class 0";
       units "bps";
       type string;
     }
     leaf ct1 {
       description "Bandwidth from traffic class 1";
       units "bps";
       type string;
     }
     leaf ct2 {
       description "Bandwidth from traffic class 2";
       units "bps";
       type string;
     }
     leaf ct3 {
       description "Bandwidth from traffic class 3";
       units "bps";
       type string;
     }
   }
   grouping juniper-protocols-mpls-interface {
     leaf name {
       description "Interface name";
       type union {
         type jt:interface-name;
         type string {
           pattern "<.*>|$.*";
         }
       }
     }
     uses apply-advanced;
     choice enable-disable {
       case case_1 {
         leaf disable {
           description "Disable MPLS on this interface";
           type empty;
         }
       }
     }
     leaf-list srlg {
       ordered-by user;
       description "SRLG Name";
       type string;
       max-elements 64;
     }
     leaf always-mark-connection-protection-tlv {
       description "Mark connection protection tlv on this interface";
       type empty;
     }
     leaf switch-away-lsps {
       description "Switch away protected LSPs to their bypass LSPs";
       type empty;
     }
     leaf-list admin-group {
       ordered-by user;
       description "Administrative groups";
       type string;
     }
     leaf-list admin-group-extended {
       ordered-by user;
       description "Extended administrative groups";
       type string;
     }
     container static {
       description "Static label-switch path related configurations";
       uses apply-advanced;
       leaf protection-revert-time {
         description "FRR revert wait time, 0 means disable";
         units "seconds";
         type union {
           type string {
             pattern "<.*>|$.*";
           }
           type uint32 {
             range "0 .. 65535";
           }
         }
       }
     }
   }
   grouping juniper-protocols-msdp {
     uses apply-advanced;
     leaf data-encapsulation {
       description "Set encapsulation of data packets";
       type enumeration {
         enum "disable" {
           description "Disable data encapsulation";
         }
         enum "enable" {
           description "Enable data encapsulation";
         }
       }
     }
     container rib-group {
       description "Routing table group";
       uses rib_group_inet_type;
     }
     container active-source-limit {
       description "Limit the number of active sources accepted";
       uses apply-advanced;
       leaf maximum {
         description "Maximum number of active sources accepted";
         default "25000";
         type union {
           type string {
             pattern "<.*>|$.*";
           }
           type uint32 {
             range "1 .. 1000000";
           }
         }
       }
       leaf threshold {
         description "RED threshold for active source acceptance";
         default "24000";
         type union {
           type string {
             pattern "<.*>|$.*";
           }
           type uint32 {
             range "1 .. 1000000";
           }
         }
       }
       leaf log-warning {
         description "Percentage of maximum at which to start generating warnings";
         default "100";
         junos:must "(\".. maximum\")";
         junos:must-message "Maximum must be configured to configure log-warning";
         type union {
           type string {
             pattern "<.*>|$.*";
           }
           type uint32 {
             range "1 .. 100";
           }
         }
       }
       leaf log-interval {
         description "Time between log messages";
         junos:must "(\".. maximum\")";
         junos:must-message "Maximum must be configured to configure log-interval";
         type union {
           type string {
             pattern "<.*>|$.*";
           }
           type uint32 {
             range "6 .. 32767";
           }
         }
       }
     }
     choice enable-disable {
       case case_1 {
         leaf disable {
           description "Disable MSDP";
           type empty;
         }
       }
     }
     leaf-list export {
       ordered-by user;
       description "Export policy";
       type jt:policy-algebra;
     }
     leaf-list import {
       ordered-by user;
       description "Import policy";
       type jt:policy-algebra;
     }
     leaf local-address {
       description "Local address";
       type jt:ipv4addr;
     }
     container traceoptions {
       description "Trace options for MSDP";
       uses apply-advanced;
       container file {
         description "Trace file options";
         leaf filename {
           description "Name of file in which to write trace information";
           type string {
             length "1 .. 1024";
             junos:posix-pattern "![/ %]";
             junos:pattern-message "Must not contain '/', % or a space";
           }
         }
         leaf replace {
           description "Replace trace file rather than appending to it";
           status deprecated;
           type empty;
         }
         leaf size {
           description "Maximum trace file size";
           type string;
         }
         leaf files {
           description "Maximum number of trace files";
           default "10";
           type union {
             type string {
               pattern "<.*>|$.*";
             }
             type uint32 {
               range "2 .. 1000";
             }
           }
         }
         leaf no-stamp {
           description "Do not timestamp trace file";
           status deprecated;
           type empty;
         }
         choice world-readable-choice {
           leaf world-readable {
             description "Allow any user to read the log file";
             type empty;
           }
           leaf no-world-readable {
             description "Don't allow any user to read the log file";
             type empty;
           }
         }
       }
       list flag {
         key name;
         ordered-by user;
         description "Tracing parameters";
         leaf name {
           type enumeration {
             enum "packets" {
               description "Trace all MSDP packets";
             }
             enum "route" {
               description "Trace routing information";
             }
             enum "nsr-synchronization" {
               description "Trace NSR synchronization events";
             }
             enum "source-active" {
               description "Trace source-active messages";
             }
             enum "source-active-request" {
               description "Trace source-active request messages";
             }
             enum "source-active-response" {
               description "Trace source-active response messages";
             }
             enum "keepalive" {
               description "Trace keepalive messages";
             }
             enum "normal" {
               description "Trace normal events";
             }
             enum "general" {
               description "Trace general events";
             }
             enum "state" {
               description "Trace state transitions";
             }
             enum "policy" {
               description "Trace policy processing";
             }
             enum "task" {
               description "Trace routing protocol task processing";
             }
             enum "timer" {
               description "Trace routing protocol timer processing";
             }
             enum "all" {
               description "Trace everything";
             }
           }
         }
         leaf send {
           description "Trace transmitted packets";
           type empty;
         }
         leaf receive {
           description "Trace received packets";
           type empty;
         }
         leaf detail {
           description "Trace detailed information";
           type empty;
         }
         leaf disable {
           description "Disable this trace flag";
           type empty;
         }
       }
     }
     list peer {
       key name;
       ordered-by user;
       description "Configure an MSDP peer";
       leaf name {
         description "Peer address";
         type jt:ipv4addr;
       }
       uses apply-advanced;
       choice enable-disable {
         case case_1 {
           leaf disable {
             description "Disable MSDP";
             type empty;
           }
         }
       }
       leaf-list export {
         ordered-by user;
         description "Export policy";
         type jt:policy-algebra;
       }
       leaf-list import {
         ordered-by user;
         description "Import policy";
         type jt:policy-algebra;
       }
       leaf local-address {
         description "Local address";
         type jt:ipv4addr;
       }
       container traceoptions {
         description "Trace options for MSDP";
         uses apply-advanced;
         container file {
           description "Trace file options";
           leaf filename {
             description "Name of file in which to write trace information";
             type string {
               length "1 .. 1024";
               junos:posix-pattern "![/ %]";
               junos:pattern-message "Must not contain '/', % or a space";
             }
           }
           leaf replace {
             description "Replace trace file rather than appending to it";
             status deprecated;
             type empty;
           }
           leaf size {
             description "Maximum trace file size";
             type string;
           }
           leaf files {
             description "Maximum number of trace files";
             default "10";
             type union {
               type string {
                 pattern "<.*>|$.*";
               }
               type uint32 {
                 range "2 .. 1000";
               }
             }
           }
           leaf no-stamp {
             description "Do not timestamp trace file";
             status deprecated;
             type empty;
           }
           choice world-readable-choice {
             leaf world-readable {
               description "Allow any user to read the log file";
               type empty;
             }
             leaf no-world-readable {
               description "Don't allow any user to read the log file";
               type empty;
             }
           }
         }
         list flag {
           key name;
           ordered-by user;
           description "Tracing parameters";
           leaf name {
             type enumeration {
               enum "packets" {
                 description "Trace all MSDP packets";
               }
               enum "route" {
                 description "Trace routing information";
               }
               enum "nsr-synchronization" {
                 description "Trace NSR synchronization events";
               }
               enum "source-active" {
                 description "Trace source-active messages";
               }
               enum "source-active-request" {
                 description "Trace source-active request messages";
               }
               enum "source-active-response" {
                 description "Trace source-active response messages";
               }
               enum "keepalive" {
                 description "Trace keepalive messages";
               }
               enum "normal" {
                 description "Trace normal events";
               }
               enum "general" {
                 description "Trace general events";
               }
               enum "state" {
                 description "Trace state transitions";
               }
               enum "policy" {
                 description "Trace policy processing";
               }
               enum "task" {
                 description "Trace routing protocol task processing";
               }
               enum "timer" {
                 description "Trace routing protocol timer processing";
               }
               enum "all" {
                 description "Trace everything";
               }
             }
           }
           leaf send {
             description "Trace transmitted packets";
             type empty;
           }
           leaf receive {
             description "Trace received packets";
             type empty;
           }
           leaf detail {
             description "Trace detailed information";
             type empty;
           }
           leaf disable {
             description "Disable this trace flag";
             type empty;
           }
         }
       }
       container active-source-limit {
         description "Limit the number of active sources accepted";
         uses apply-advanced;
         leaf maximum {
           description "Maximum number of active sources accepted";
           default "25000";
           type union {
             type string {
               pattern "<.*>|$.*";
             }
             type uint32 {
               range "1 .. 1000000";
             }
           }
         }
         leaf threshold {
           description "RED threshold for active source acceptance";
           default "24000";
           type union {
             type string {
               pattern "<.*>|$.*";
             }
             type uint32 {
               range "1 .. 1000000";
             }
           }
         }
         leaf log-warning {
           description "Percentage of maximum at which to start generating warnings";
           default "100";
           junos:must "(\".. maximum\")";
           junos:must-message "Maximum must be configured to configure log-warning";
           type union {
             type string {
               pattern "<.*>|$.*";
             }
             type uint32 {
               range "1 .. 100";
             }
           }
         }
         leaf log-interval {
           description "Time between log messages";
           junos:must "(\".. maximum\")";
           junos:must-message "Maximum must be configured to configure log-interval";
           type union {
             type string {
               pattern "<.*>|$.*";
             }
             type uint32 {
               range "6 .. 32767";
             }
           }
         }
       }
       leaf keep-alive {
         description "Time limit for sending out periodic keep alive to peer";
         units "seconds";
         type union {
           type string {
             pattern "<.*>|$.*";
           }
           type uint32 {
             range "10 .. 60";
           }
         }
       }
       leaf hold-time {
         description "Max time to terminating a peer for having not received any message from ";
         units "seconds";
         type union {
           type string {
             pattern "<.*>|$.*";
           }
           type uint32 {
             range "15 .. 150";
           }
         }
       }
       leaf sa-hold-time {
         description "Max time for holding a sa message before timing out";
         units "seconds";
         type union {
           type string {
             pattern "<.*>|$.*";
           }
           type uint32 {
             range "75 .. 300";
           }
         }
       }
       leaf default-peer {
         description "Default RPF peer";
         type empty;
       }
       leaf authentication-key {
         description "MD5 authentication key";
         type string {
           length "1 .. 126";
         }
       }
     }
     leaf keep-alive {
       description "Time limit for sending out periodic keep alive to peer";
       units "seconds";
       type union {
         type string {
           pattern "<.*>|$.*";
         }
         type uint32 {
           range "10 .. 60";
         }
       }
     }
     leaf hold-time {
       description "Max time to terminating a peer for having not received any message from ";
       units "seconds";
       type union {
         type string {
           pattern "<.*>|$.*";
         }
         type uint32 {
           range "15 .. 150";
         }
       }
     }
     leaf sa-hold-time {
       description "Max time for holding a sa message before timing out";
       units "seconds";
       type union {
         type string {
           pattern "<.*>|$.*";
         }
         type uint32 {
           range "75 .. 300";
         }
       }
     }
     list source {
       key name;
       ordered-by user;
       description "Configure parameters for each source";
       leaf name {
         description "Source address or prefix";
         type jt:ipprefix;
       }
       uses apply-advanced;
       container active-source-limit {
         description "Limit the number of active sources accepted";
         uses apply-advanced;
         leaf maximum {
           description "Maximum number of active sources accepted";
           default "25000";
           type union {
             type string {
               pattern "<.*>|$.*";
             }
             type uint32 {
               range "1 .. 1000000";
             }
           }
         }
         leaf threshold {
           description "RED threshold for active source acceptance";
           default "24000";
           type union {
             type string {
               pattern "<.*>|$.*";
             }
             type uint32 {
               range "1 .. 1000000";
             }
           }
         }
         leaf log-warning {
           description "Percentage of maximum at which to start generating warnings";
           default "100";
           junos:must "(\".. maximum\")";
           junos:must-message "Maximum must be configured to configure log-warning";
           type union {
             type string {
               pattern "<.*>|$.*";
             }
             type uint32 {
               range "1 .. 100";
             }
           }
         }
         leaf log-interval {
           description "Time between log messages";
           junos:must "(\".. maximum\")";
           junos:must-message "Maximum must be configured to configure log-interval";
           type union {
             type string {
               pattern "<.*>|$.*";
             }
             type uint32 {
               range "6 .. 32767";
             }
           }
         }
       }
     }
     list group {
       key name;
       ordered-by user;
       description "Configure MSDP peer groups";
       leaf name {
         description "MSDP peer group name";
         type string;
       }
       uses apply-advanced;
       leaf mode {
         description "MSDP group source-active flooding mode";
         default "standard";
         type enumeration {
           enum "standard" {
             description "Use standard MSDP source-active flooding rules";
           }
           enum "mesh-group" {
             description "Group peers are mesh group members";
           }
         }
       }
       choice enable-disable {
         case case_1 {
           leaf disable {
             description "Disable MSDP";
             type empty;
           }
         }
       }
       leaf-list export {
         ordered-by user;
         description "Export policy";
         type jt:policy-algebra;
       }
       leaf-list import {
         ordered-by user;
         description "Import policy";
         type jt:policy-algebra;
       }
       leaf local-address {
         description "Local address";
         type jt:ipv4addr;
       }
       container traceoptions {
         description "Trace options for MSDP";
         uses apply-advanced;
         container file {
           description "Trace file options";
           leaf filename {
             description "Name of file in which to write trace information";
             type string {
               length "1 .. 1024";
               junos:posix-pattern "![/ %]";
               junos:pattern-message "Must not contain '/', % or a space";
             }
           }
           leaf replace {
             description "Replace trace file rather than appending to it";
             status deprecated;
             type empty;
           }
           leaf size {
             description "Maximum trace file size";
             type string;
           }
           leaf files {
             description "Maximum number of trace files";
             default "10";
             type union {
               type string {
                 pattern "<.*>|$.*";
               }
               type uint32 {
                 range "2 .. 1000";
               }
             }
           }
           leaf no-stamp {
             description "Do not timestamp trace file";
             status deprecated;
             type empty;
           }
           choice world-readable-choice {
             leaf world-readable {
               description "Allow any user to read the log file";
               type empty;
             }
             leaf no-world-readable {
               description "Don't allow any user to read the log file";
               type empty;
             }
           }
         }
         list flag {
           key name;
           ordered-by user;
           description "Tracing parameters";
           leaf name {
             type enumeration {
               enum "packets" {
                 description "Trace all MSDP packets";
               }
               enum "route" {
                 description "Trace routing information";
               }
               enum "nsr-synchronization" {
                 description "Trace NSR synchronization events";
               }
               enum "source-active" {
                 description "Trace source-active messages";
               }
               enum "source-active-request" {
                 description "Trace source-active request messages";
               }
               enum "source-active-response" {
                 description "Trace source-active response messages";
               }
               enum "keepalive" {
                 description "Trace keepalive messages";
               }
               enum "normal" {
                 description "Trace normal events";
               }
               enum "general" {
                 description "Trace general events";
               }
               enum "state" {
                 description "Trace state transitions";
               }
               enum "policy" {
                 description "Trace policy processing";
               }
               enum "task" {
                 description "Trace routing protocol task processing";
               }
               enum "timer" {
                 description "Trace routing protocol timer processing";
               }
               enum "all" {
                 description "Trace everything";
               }
             }
           }
           leaf send {
             description "Trace transmitted packets";
             type empty;
           }
           leaf receive {
             description "Trace received packets";
             type empty;
           }
           leaf detail {
             description "Trace detailed information";
             type empty;
           }
           leaf disable {
             description "Disable this trace flag";
             type empty;
           }
         }
       }
       list peer {
         key name;
         ordered-by user;
         description "Configure an MSDP peer";
         leaf name {
           description "Peer address";
           type jt:ipv4addr;
         }
         uses apply-advanced;
         choice enable-disable {
           case case_1 {
             leaf disable {
               description "Disable MSDP";
               type empty;
             }
           }
         }
         leaf-list export {
           ordered-by user;
           description "Export policy";
           type jt:policy-algebra;
         }
         leaf-list import {
           ordered-by user;
           description "Import policy";
           type jt:policy-algebra;
         }
         leaf local-address {
           description "Local address";
           type jt:ipv4addr;
         }
         container traceoptions {
           description "Trace options for MSDP";
           uses apply-advanced;
           container file {
             description "Trace file options";
             leaf filename {
               description "Name of file in which to write trace information";
               type string {
                 length "1 .. 1024";
                 junos:posix-pattern "![/ %]";
                 junos:pattern-message "Must not contain '/', % or a space";
               }
             }
             leaf replace {
               description "Replace trace file rather than appending to it";
               status deprecated;
               type empty;
             }
             leaf size {
               description "Maximum trace file size";
               type string;
             }
             leaf files {
               description "Maximum number of trace files";
               default "10";
               type union {
                 type string {
                   pattern "<.*>|$.*";
                 }
                 type uint32 {
                   range "2 .. 1000";
                 }
               }
             }
             leaf no-stamp {
               description "Do not timestamp trace file";
               status deprecated;
               type empty;
             }
             choice world-readable-choice {
               leaf world-readable {
                 description "Allow any user to read the log file";
                 type empty;
               }
               leaf no-world-readable {
                 description "Don't allow any user to read the log file";
                 type empty;
               }
             }
           }
           list flag {
             key name;
             ordered-by user;
             description "Tracing parameters";
             leaf name {
               type enumeration {
                 enum "packets" {
                   description "Trace all MSDP packets";
                 }
                 enum "route" {
                   description "Trace routing information";
                 }
                 enum "nsr-synchronization" {
                   description "Trace NSR synchronization events";
                 }
                 enum "source-active" {
                   description "Trace source-active messages";
                 }
                 enum "source-active-request" {
                   description "Trace source-active request messages";
                 }
                 enum "source-active-response" {
                   description "Trace source-active response messages";
                 }
                 enum "keepalive" {
                   description "Trace keepalive messages";
                 }
                 enum "normal" {
                   description "Trace normal events";
                 }
                 enum "general" {
                   description "Trace general events";
                 }
                 enum "state" {
                   description "Trace state transitions";
                 }
                 enum "policy" {
                   description "Trace policy processing";
                 }
                 enum "task" {
                   description "Trace routing protocol task processing";
                 }
                 enum "timer" {
                   description "Trace routing protocol timer processing";
                 }
                 enum "all" {
                   description "Trace everything";
                 }
               }
             }
             leaf send {
               description "Trace transmitted packets";
               type empty;
             }
             leaf receive {
               description "Trace received packets";
               type empty;
             }
             leaf detail {
               description "Trace detailed information";
               type empty;
             }
             leaf disable {
               description "Disable this trace flag";
               type empty;
             }
           }
         }
         container active-source-limit {
           description "Limit the number of active sources accepted";
           uses apply-advanced;
           leaf maximum {
             description "Maximum number of active sources accepted";
             default "25000";
             type union {
               type string {
                 pattern "<.*>|$.*";
               }
               type uint32 {
                 range "1 .. 1000000";
               }
             }
           }
           leaf threshold {
             description "RED threshold for active source acceptance";
             default "24000";
             type union {
               type string {
                 pattern "<.*>|$.*";
               }
               type uint32 {
                 range "1 .. 1000000";
               }
             }
           }
           leaf log-warning {
             description "Percentage of maximum at which to start generating warnings";
             default "100";
             junos:must "(\".. maximum\")";
             junos:must-message "Maximum must be configured to configure log-warning";
             type union {
               type string {
                 pattern "<.*>|$.*";
               }
               type uint32 {
                 range "1 .. 100";
               }
             }
           }
           leaf log-interval {
             description "Time between log messages";
             junos:must "(\".. maximum\")";
             junos:must-message "Maximum must be configured to configure log-interval";
             type union {
               type string {
                 pattern "<.*>|$.*";
               }
               type uint32 {
                 range "6 .. 32767";
               }
             }
           }
         }
         leaf keep-alive {
           description "Time limit for sending out periodic keep alive to peer";
           units "seconds";
           type union {
             type string {
               pattern "<.*>|$.*";
             }
             type uint32 {
               range "10 .. 60";
             }
           }
         }
         leaf hold-time {
           description "Max time to terminating a peer for having not received any message from ";
           units "seconds";
           type union {
             type string {
               pattern "<.*>|$.*";
             }
             type uint32 {
               range "15 .. 150";
             }
           }
         }
         leaf sa-hold-time {
           description "Max time for holding a sa message before timing out";
           units "seconds";
           type union {
             type string {
               pattern "<.*>|$.*";
             }
             type uint32 {
               range "75 .. 300";
             }
           }
         }
         leaf default-peer {
           description "Default RPF peer";
           type empty;
         }
         leaf authentication-key {
           description "MD5 authentication key";
           type string {
             length "1 .. 126";
           }
         }
       }
     }
   }
   grouping juniper-protocols-mstp {
     uses apply-advanced;
     choice enable-disable {
       case case_1 {
         leaf disable {
           description "Disable MSTP";
           type empty;
         }
       }
     }
     leaf bpdu-destination-mac-address {
       description "Destination MAC address in the spanning tree BPDUs";
       type enumeration {
         enum "provider-bridge-group" {
           description "802.1ad provider bridge group address";
         }
       }
     }
     leaf configuration-name {
       description "Configuration name (part of MST configuration identifier)";
       type string {
         length "1 .. 32";
       }
     }
     leaf revision-level {
       description "Revision level (part of MST configuration identifier)";
       type union {
         type uint16;
         type string {
           pattern "<.*>|$.*";
         }
       }
     }
     leaf max-hops {
       description "Maximum number of hops";
       type union {
         type string {
           pattern "<.*>|$.*";
         }
         type uint16 {
           range "1 .. 255";
         }
       }
     }
     leaf max-age {
       description "Maximum age of received protocol bpdu";
       units "seconds";
       type union {
         type string {
           pattern "<.*>|$.*";
         }
         type uint16 {
           range "6 .. 40";
         }
       }
     }
     leaf hello-time {
       description "Time interval between configuration BPDUs";
       units "seconds";
       type union {
         type string {
           pattern "<.*>|$.*";
         }
         type uint16 {
           range "1 .. 10";
         }
       }
     }
     leaf forward-delay {
       description "Time spent in listening or learning state";
       units "seconds";
       type union {
         type string {
           pattern "<.*>|$.*";
         }
         type uint16 {
           range "4 .. 30";
         }
       }
     }
     leaf system-identifier {
       description "Sytem identifier to represent this node";
       type jt:mac-unicast;
     }
     container traceoptions {
       description "Tracing options for debugging protocol operation";
       uses stp-trace-options;
     }
     leaf bridge-priority {
       description "Priority of the bridge (in increments of 4k - 0,4k,8k,..60k)";
       type string {
         junos:posix-pattern "^(0|4k|4096|8k|8192|12k|12288|16k|16384|20k|20480|24k|24576|28k|28672|32k|32768|36k|36864|40k|40960|44k|45056|48k|49512|52k|53248|56k|57344|60k|61440)$";
         junos:pattern-message "Must be a multiple of 4096";
       }
     }
     leaf backup-bridge-priority {
       description "Priority of the bridge (in increments of 4k - 4k,8k,..60k)";
       type string {
         junos:posix-pattern "^(4k|4096|8k|8192|12k|12288|16k|16384|20k|20480|24k|24576|28k|28672|32k|32768|36k|36864|40k|40960|44k|45056|48k|49512|52k|53248|56k|57344|60k|61440)$";
         junos:pattern-message "Must be a multiple of 4096";
       }
     }
     leaf bpdu-block-on-edge {
       description "Block BPDU on all interfaces configured as edge (BPDU Protect)";
       type empty;
     }
     leaf vpls-flush-on-topology-change {
       description "Enable VPLS MAC flush on root protected CE interface receving topology change";
       type empty;
     }
     leaf priority-hold-time {
       description "Hold time before switching to primary priority when core domain becomes up";
       units "seconds";
       type union {
         type string {
           pattern "<.*>|$.*";
         }
         type uint16 {
           range "1 .. 255";
         }
       }
     }
     list system-id {
       key name;
       ordered-by user;
       description "System ID to IP mapping";
       uses system-id-ip-map;
     }
     list interface {
       key name;
       description "Interface options";
       uses mstp-interface;
     }
     list msti {
       key name;
       description "Per-MSTI options";
       leaf name {
         type union {
           type string {
             pattern "<.*>|$.*";
           }
           type int32 {
             range "1 .. 4094";
           }
         }
       }
       uses apply-advanced;
       leaf bridge-priority {
         description "Priority of the bridge (in increments of 4k - 0,4k,8k,..60k)";
         type string {
           junos:posix-pattern "^(0|4k|4096|8k|8192|12k|12288|16k|16384|20k|20480|24k|24576|28k|28672|32k|32768|36k|36864|40k|40960|44k|45056|48k|49512|52k|53248|56k|57344|60k|61440)$";
           junos:pattern-message "Must be a multiple of 4096";
         }
       }
       leaf backup-bridge-priority {
         description "Priority of the bridge (in increments of 4k - 4k,8k,..60k)";
         type string {
           junos:posix-pattern "^(4k|4096|8k|8192|12k|12288|16k|16384|20k|20480|24k|24576|28k|28672|32k|32768|36k|36864|40k|40960|44k|45056|48k|49512|52k|53248|56k|57344|60k|61440)$";
           junos:pattern-message "Must be a multiple of 4096";
         }
       }
       leaf-list vlan {
         ordered-by user;
         description "VLAN ID or VLAN ID range [1..4094]";
         type string;
       }
       list interface {
         key name;
         description "Interface options";
         uses mstp-interface;
       }
     }
   }
   grouping juniper-protocols-mvpn {
     description "BGP-MVPN configuration";
     uses apply-advanced;
     container traceoptions {
       description "Trace options for BGP-MVPN";
       uses apply-advanced;
       container file {
         description "Trace file options";
         leaf filename {
           description "Name of file in which to write trace information";
           type string {
             length "1 .. 1024";
             junos:posix-pattern "![/ %]";
             junos:pattern-message "Must not contain '/', % or a space";
           }
         }
         leaf replace {
           description "Replace trace file rather than appending to it";
           status deprecated;
           type empty;
         }
         leaf size {
           description "Maximum trace file size";
           type string;
         }
         leaf files {
           description "Maximum number of trace files";
           default "10";
           type union {
             type string {
               pattern "<.*>|$.*";
             }
             type uint32 {
               range "2 .. 1000";
             }
           }
         }
         leaf no-stamp {
           description "Do not timestamp trace file";
           status deprecated;
           type empty;
         }
         choice world-readable-choice {
           leaf world-readable {
             description "Allow any user to read the log file";
             type empty;
           }
           leaf no-world-readable {
             description "Don't allow any user to read the log file";
             type empty;
           }
         }
       }
       list flag {
         key name;
         ordered-by user;
         description "Tracing parameters";
         leaf name {
           type enumeration {
             enum "error" {
               description "Trace errors";
             }
             enum "nlri" {
               description "Trace MVPN advertisements";
             }
             enum "topology" {
               description "Trace MVPN topology changes";
             }
             enum "tunnel" {
               description "Trace provider tunnel events";
             }
             enum "umh" {
               description "Trace Upstream Multicast Hop (UMH) events";
             }
             enum "intra-as-ad" {
               description "Trace MVPN intra-AS auto discovery routes";
             }
             enum "inter-as-ad" {
               description "Trace MVPN inter-AS auto discovery routes";
             }
             enum "spmsi-ad" {
               description "Trace MVPN SPMSI auto discovery routes";
             }
             enum "leaf-ad" {
               description "Trace MVPN leaf auto discovery routes";
             }
             enum "source-active" {
               description "Trace MVPN source active routes";
             }
             enum "cmcast-join" {
               description "Trace MVPN c-multicast join routes";
             }
             enum "mdt-safi-ad" {
               description "Trace MVPN MDT SAFI auto discovery routes";
             }
             enum "mvpn-limit" {
               description "Trace MVPN spmsi and cmcast limit events";
             }
             enum "nsr-synchronization" {
               description "Trace NSR synchronization events";
             }
             enum "route" {
               description "Trace routing information";
             }
             enum "normal" {
               description "Trace normal events";
             }
             enum "general" {
               description "Trace general events";
             }
             enum "state" {
               description "Trace state transitions";
             }
             enum "policy" {
               description "Trace policy processing";
             }
             enum "task" {
               description "Trace routing protocol task processing";
             }
             enum "timer" {
               description "Trace routing protocol timer processing";
             }
             enum "all" {
               description "Trace everything";
             }
           }
         }
         leaf send {
           description "Trace transmitted packets";
           type empty;
         }
         leaf receive {
           description "Trace received packets";
           type empty;
         }
         leaf detail {
           description "Trace detailed information";
           type empty;
         }
         leaf disable {
           description "Disable this trace flag";
           type empty;
         }
       }
     }
     container autodiscovery-only {
       junos:must "(!(\".. route-target\"))";
       junos:must-message "MVPN autodiscovery-only mode cannot be used with route-target";
       junos:must "(!(\".. sender-site\"))";
       junos:must-message "MVPN autodiscovery-only mode cannot be used with sender-site";
       junos:must "(!(\".. receiver-site\"))";
       junos:must-message "MVPN autodiscovery-only mode cannot be used with receiver-site";
       junos:must "(\".. .. .. protocols pim mvpn\")";
       junos:must-message "MVPN autodiscovery-only mode requires protocols pim mvpn configuration for the instance.";
       junos:must "(!(\".. .. .. provider-tunnel family inet pim-asm\"))";
       junos:must-message "MVPN autodiscovery-only mode requires a PIM-SSM provider-tunnel root address.";
       junos:must "((\".. .. .. provider-tunnel pim-ssm\" || \".. .. .. provider-tunnel family inet pim-ssm\"))";
       junos:must-message "MVPN autodiscovery-only mode requires a PIM-SSM provider-tunnel root address.";
       description "Use MVPN exclusively for PE router autodiscovery";
       status deprecated;
       uses apply-advanced;
       container intra-as {
         description "Intra-AS autodiscovery options";
         uses apply-advanced;
         leaf inclusive {
           description "Inclusive provider tunnel autodiscovery";
           type empty;
         }
       }
     }
     container family {
       description "BGP-MVPN address family";
       uses apply-advanced;
       container any {
         presence "enable any";
         description "BGP-MVPN properties for all families";
         uses apply-advanced;
         leaf disable {
           description "Disable all families";
           type empty;
         }
       }
       container inet {
         description "IPv4 BGP-MVPN properties";
         uses apply-advanced;
         container autodiscovery-only {
           junos:must "(!(\".. .. .. route-target\"))";
           junos:must-message "MVPN autodiscovery-only mode cannot be used with route-target";
           junos:must "(!(\".. .. .. sender-site\"))";
           junos:must-message "MVPN autodiscovery-only mode cannot be used with sender-site";
           junos:must "(!(\".. .. .. receiver-site\"))";
           junos:must-message "MVPN autodiscovery-only mode cannot be used with receiver-site";
           junos:must "(\".. .. .. .. .. protocols pim mvpn\")";
           junos:must-message "MVPN autodiscovery-only mode requires protocols pim mvpn configuration for the instance.";
           junos:must "(!(\".. .. .. .. .. provider-tunnel family inet pim-asm\"))";
           junos:must-message "MVPN autodiscovery-only mode requires a PIM-SSM provider-tunnel root address.";
           junos:must "((\".. .. .. .. .. provider-tunnel pim-ssm\" || \".. .. .. .. .. provider-tunnel family inet pim-ssm\"))";
           junos:must-message "MVPN autodiscovery-only mode requires a PIM-SSM provider-tunnel root address.";
           description "Use MVPN exclusively for PE router autodiscovery";
           uses apply-advanced;
           container intra-as {
             description "Intra-AS autodiscovery options";
             uses apply-advanced;
             leaf inclusive {
               description "Inclusive provider tunnel autodiscovery";
               type empty;
             }
           }
         }
         leaf disable {
           description "Disable family IPv4";
           type empty;
         }
       }
       container inet6 {
         presence "enable inet6";
         description "IPv6 BGP-MVPN properties";
         uses apply-advanced;
         container autodiscovery-only {
           junos:must "(!(\".. .. .. route-target\"))";
           junos:must-message "MVPN autodiscovery-only mode cannot be used with route-target";
           junos:must "(!(\".. .. .. sender-site\"))";
           junos:must-message "MVPN autodiscovery-only mode cannot be used with sender-site";
           junos:must "(!(\".. .. .. receiver-site\"))";
           junos:must-message "MVPN autodiscovery-only mode cannot be used with receiver-site";
           junos:must "(\".. .. .. .. .. protocols pim mvpn\")";
           junos:must-message "MVPN autodiscovery-only mode requires protocols pim mvpn configuration for the instance.";
           junos:must "(!(\".. .. .. .. .. provider-tunnel family inet pim-asm\"))";
           junos:must-message "MVPN autodiscovery-only mode requires a PIM-SSM provider-tunnel root address.";
           junos:must "((\".. .. .. .. .. provider-tunnel pim-ssm\" || \".. .. .. .. .. provider-tunnel family inet pim-ssm\"))";
           junos:must-message "MVPN autodiscovery-only mode requires a PIM-SSM provider-tunnel root address.";
           description "Use MVPN exclusively for PE router autodiscovery";
           uses apply-advanced;
           container intra-as {
             description "Intra-AS autodiscovery options";
             uses apply-advanced;
             leaf inclusive {
               description "Inclusive provider tunnel autodiscovery";
               type empty;
             }
           }
         }
         leaf disable {
           description "Disable family IPv6";
           type empty;
         }
       }
     }
     choice sender-receiver-site-choice {
       case case_1 {
         leaf receiver-site {
           description "MVPN instance has sites only with multicast receivers";
           junos:must "(!(\".. .. .. provider-tunnel\"))";
           junos:must-message "MVPN instance with only receiver sites cannot be the root of a provider-tunnel";
           type empty;
         }
       }
       case case_2 {
         leaf sender-site {
           description "MVPN instance has sites only with multicast sources";
           junos:must "(\".. .. .. provider-tunnel\")";
           junos:must-message "MVPN instance with sources must be the root of a provider-tunnel";
           type empty;
         }
       }
     }
     leaf unicast-umh-election {
       description "Upstream Multicast Hop election based on unicast route preference";
       junos:must "(!(\".. mvpn-join-load-balance\"))";
       junos:must-message "UMH election based on unicast route cannot be configured with mvpn-join-load-balance";
       junos:must "(!(\".. .. .. .. .. protocols bgp path-selection cisco-non-deterministic\"))";
       junos:must-message "Upstream Multicast Hop election cannot be used with 'protocols bgp path-selection cisco-non-deterministic'";
       type empty;
     }
     container static-umh {
       description "Upstream Multicast Hop election based on static configuration";
       uses apply-advanced;
       leaf primary {
         description "Primary Upstream Multicast Hop";
         type jt:ipv4addr;
       }
       leaf backup {
         description "Secondary Upstream Multicast Hop";
         type jt:ipv4addr;
       }
       choice source-tree_choice {
         case case_1 {
           leaf source-tree {
             description "Mandatory attribute - static-umh applies only to MVPN source-tree c-multicast joins";
             type empty;
           }
         }
       }
     }
     leaf cmcast-joins-limit-inet {
       description "Maximum number of cmcast entries for v4";
       junos:must "(\".. mvpn-mode rpt-spt\")";
       junos:must-message "Cmcast limit can only be configured for MVPN rpt-spt mode";
       type union {
         type string {
           pattern "<.*>|$.*";
         }
         type uint32 {
           range "0 .. 15000";
         }
       }
     }
     leaf cmcast-joins-limit-inet6 {
       description "Maximum number of cmcast entries for v6";
       junos:must "(\".. mvpn-mode rpt-spt\")";
       junos:must-message "Cmcastv6 limit can only be configured for MVPN rpt-spt mode";
       type union {
         type string {
           pattern "<.*>|$.*";
         }
         type uint32 {
           range "0 .. 15000";
         }
       }
     }
     container mvpn-mode {
       description "MVPN mode of operation";
       uses apply-advanced;
       choice mode {
         case case_1 {
           container rpt-spt {
             presence "enable rpt-spt";
             description "MVPN works in multicast RPT and SPT mode";
             uses apply-advanced;
             leaf spt-switch-timer {
               description "Timeout before a PE router switches between RPT and SPT";
               units "seconds";
               type union {
                 type string {
                   pattern "<.*>|$.*";
                 }
                 type uint32 {
                   range "0 .. 60";
                 }
               }
             }
           }
         }
         case case_2 {
           container spt-only {
             presence "enable spt-only";
             description "MVPN works in multicast SPT only mode (default mode)";
             uses apply-advanced;
             container source-active-advertisement {
               description "Attributes associated with advertising Source-Active A-D routes";
               uses apply-advanced;
               leaf dampen {
                 description "Time to wait before re-advertising source-active route";
                 units "minutes";
                 type union {
                   type string {
                     pattern "<.*>|$.*";
                   }
                   type uint32 {
                     range "1 .. 30";
                   }
                 }
               }
               leaf min-rate {
                 description "Minimum traffic rate required to advertise Source-Active route";
                 units "bits per second";
                 type string;
               }
             }
             leaf convert-sa-to-msdp {
               description "Turn on MVPN SA route to MSDP SA conversion";
               type empty;
             }
           }
         }
       }
     }
     container route-target {
       description "Configure route-targets for MVPN routes";
       uses apply-advanced;
       container import-target {
         description "Target communities used when importing routes";
         uses apply-advanced;
         container unicast {
           presence "enable unicast";
           description "Use the same target community as configured for unicast";
           choice receiver-sender-target-choice {
             case case_1 {
               leaf receiver {
                 description "Target community used when importing receiver site routes";
                 junos:must "(!(\".. .. .. .. receiver-site\"))";
                 junos:must-message "MVPN instance with only receivers must not import routes from other receiver only sites";
                 type empty;
               }
             }
             case case_2 {
               leaf sender {
                 description "Target community used when importing sender site routes";
                 junos:must "(!(\".. .. .. .. sender-site\"))";
                 junos:must-message "MVPN instance with only sources must not import routes from other sender only sites";
                 type empty;
               }
             }
           }
         }
         container target {
           presence "enable target";
           description "Target community";
           leaf target-value {
             type string {
               junos:posix-pattern "^[a-z]+:[0-9.]+L?:[0-9]+$";
               junos:pattern-message "Use format 'target:x:y' where 'x' is an AS number followed by an optional 'L' (To indicate 4 byte AS), or an IP address and 'y' is a number. e.g. target:123456L:100";
             }
           }
           choice receiver-sender-target-choice {
             case case_1 {
               leaf receiver {
                 description "Target community used when importing receiver site routes";
                 junos:must "(!(\".. .. .. .. receiver-site\"))";
                 junos:must-message "MVPN instance with only receivers must not import routes from other receiver only sites";
                 type empty;
               }
             }
             case case_2 {
               leaf sender {
                 description "Target community used when importing sender site routes";
                 junos:must "(!(\".. .. .. .. sender-site\"))";
                 junos:must-message "MVPN instance with only sources must not import routes from other sender only sites";
                 type empty;
               }
             }
           }
         }
       }
       container export-target {
         description "Target communities used when exporting routes";
         uses apply-advanced;
         leaf unicast {
           description "Use the same target community as configured for unicast";
           type empty;
         }
         leaf target {
           description "Target community";
           type string {
             junos:posix-pattern "^[a-z]+:[0-9.]+L?:[0-9]+$";
             junos:pattern-message "Use format 'target:x:y' where 'x' is an AS number followed by an optional 'L' (To indicate 4 byte AS), or an IP address and 'y' is a number. e.g. target:123456L:100";
           }
         }
       }
     }
     container mvpn-join-load-balance {
       junos:must "(!(\".. unicast-umh-election\"))";
       junos:must-message "MVPN join load balancing cannot be configured with unicast-umh-election";
       description "MVPN Join Load Balancing Algorithm";
       uses apply-advanced;
       choice algorithm {
         case case_1 {
           container bytewise-xor-hash {
             presence "enable bytewise-xor-hash";
             description "Upstream selection using bytewise XOR hash";
           }
         }
       }
     }
     leaf install-discard {
       description "Install MVPN discard forwarding entries";
       type empty;
     }
     leaf sender-based-rpf {
       description "Forward multicast traffic only from a selected sender PE";
       type empty;
     }
     container hot-root-standby {
       junos:must "(!(\".. .. .. instance-type mpls-internet-multicast\"))";
       junos:must-message "MVPN live-live - hot-root-standby cannot be configured in mpls-internet-multicast vrf";
       junos:must "(\".. sender-based-rpf\")";
       junos:must-message "MVPN live-live - hot-root-standby configuration needs sender-based-rpf configuration";
       description "MVPN live-live - hot root standby";
       uses apply-advanced;
       choice tree {
         case case_1 {
           container source-tree {
             presence "enable source-tree";
             description "MVPN live-live - hot root standby for source tree";
           }
         }
       }
       container min-rate {
         junos:must "(\".. .. hot-root-standby source-tree\")";
         junos:must-message "MVPN live-live - min-rate can be configured only if hot-root-standby source-tree is configured";
         description "Minimum traffic rate for the provider tunnel below which switchover is initiated (in bps)";
         uses apply-advanced;
         leaf rate {
           description "Minium traffic rate for the provider tunnel below which switchover is initiated (in bps)";
           units "bits per second";
           type string;
         }
         leaf revert-delay {
           description "Time to delay updating of multicast routes to allow for multicast convergence";
           units "seconds";
           type union {
             type string {
               pattern "<.*>|$.*";
             }
             type uint32 {
               range "0 .. 20";
             }
           }
         }
       }
     }
     leaf hierarchical-nexthop {
       description "Enable hierarchical nexthop usage";
       type empty;
     }
     leaf no-nexthop-sharing-for-selective-tunnel {
       description "Disable Tunnel nexthops from getting shared for selective tunnel";
       junos:must "(\"hierarchical-nexthop\")";
       junos:must-message "Disable tunnel nexthop sharing can be configured only when hierarchical-nexthop is set";
       junos:must "((\".. .. .. provider-tunnel ingress-replication\" || (\".. .. .. provider-tunnel inter-as\" || \".. .. .. provider-tunnel inter-region\")))";
       junos:must-message "Disable tunnel nexthop sharing can be configured only for ingress-replication provider tunnels";
       type empty;
     }
     container inter-region-template {
       description "MVPN inter-region tunnel mapping template";
       uses apply-advanced;
       list template {
         key name;
         ordered-by user;
         description "Define a inter-region template";
         leaf name {
           description "MVPN Template Name";
           type string;
         }
         uses apply-advanced;
         list region {
           key name;
           ordered-by user;
           description "BGP peer group names used as region";
           leaf name {
             description "Region name";
             junos:must "(\"protocols bgp group $$\")";
             junos:must-message "BGP group must be present";
             type string;
           }
           uses apply-advanced;
           choice tunnel-type {
             case case_1 {
               container rsvp-te {
                 junos:must "(\"protocols rsvp\")";
                 junos:must-message "RSVP must be configured in the master instance";
                 description "RSVP-TE point-to-multipoint LSP for flooding";
                 uses apply-advanced;
                 choice static-or-dynamic {
                   case case_1 {
                     leaf static-lsp {
                       description "Name of point-to-multipoint LSP";
                       type string {
                         junos:posix-pattern "^.{1,32}$";
                         junos:pattern-message "Must be a string of 32 characters or less";
                       }
                     }
                   }
                   case case_2 {
                     container label-switched-path-template {
                       description "Template for dynamic point-to-multipoint LSP parameters";
                       uses apply-advanced;
                       choice dynamic-template {
                         case case_1 {
                           leaf template-name {
                             description "Name of point-to-multipoint LSP template";
                             junos:must "((\"protocols mpls label-switched-path $$\" && (\"protocols mpls label-switched-path $$ template\" && \"protocols mpls label-switched-path $$ p2mp\")))";
                             junos:must-message "Referenced point-to-multipoint LSP template does not exist";
                             type string {
                               junos:posix-pattern "^.{1,32}$";
                               junos:pattern-message "Must be a string of 32 characters or less";
                             }
                           }
                         }
                         case case_2 {
                           leaf default-template {
                             description "Use default parameters";
                             type empty;
                           }
                         }
                       }
                     }
                   }
                 }
               }
             }
             case case_2 {
               container ldp-p2mp {
                 presence "enable ldp-p2mp";
                 junos:must "(\"protocols ldp p2mp\")";
                 junos:must-message "LDP P2MP must be configured in the master instance";
                 description "LDP point-to-multipoint LSP for flooding";
               }
             }
             case case_3 {
               container ingress-replication {
                 description "Ingress replication tunnel";
                 uses apply-advanced;
                 leaf create-new-ucast-tunnel {
                   description "Create new unicast tunnel for ingress replication";
                   junos:must "(\".. label-switched-path label-switched-path-template\")";
                   junos:must-message "label-switched-path-template must be defined";
                   type empty;
                 }
                 container label-switched-path {
                   presence "enable label-switched-path";
                   description "Point-to-point LSP unicast tunnel";
                   uses apply-advanced;
                   container label-switched-path-template {
                     junos:must "(\".. .. create-new-ucast-tunnel\")";
                     junos:must-message "Templates must be specified when and only when create-new-ucast-tunnel is defined";
                     description "Template for dynamic point-to-point LSP parameters";
                     uses apply-advanced;
                     choice dynamic-template {
                       case case_1 {
                         leaf template-name {
                           description "Name of point-to-point LSP template";
                           junos:must "((\"protocols mpls label-switched-path $$\" && (\"protocols mpls label-switched-path $$ template\" && !(\"protocols mpls label-switched-path $$ p2mp\"))))";
                           junos:must-message "Referenced point-to-point LSP template does not exist";
                           type string {
                             junos:posix-pattern "^.{1,32}$";
                             junos:pattern-message "Must be a string of 32 characters or less";
                           }
                         }
                       }
                       case case_2 {
                         leaf default-template {
                           description "Use default parameters";
                           type empty;
                         }
                       }
                     }
                   }
                 }
               }
             }
             case case_4 {
               leaf incoming {
                 description "Same as incoming provider tunnel";
                 type empty;
               }
             }
           }
         }
         container all-regions {
           description "Used for all regions not specified";
           uses apply-advanced;
           choice tunnel-type {
             case case_1 {
               container rsvp-te {
                 junos:must "(\"protocols rsvp\")";
                 junos:must-message "RSVP must be configured in the master instance";
                 description "RSVP-TE point-to-multipoint LSP for flooding";
                 uses apply-advanced;
                 choice static-or-dynamic {
                   case case_1 {
                     leaf static-lsp {
                       description "Name of point-to-multipoint LSP";
                       type string {
                         junos:posix-pattern "^.{1,32}$";
                         junos:pattern-message "Must be a string of 32 characters or less";
                       }
                     }
                   }
                   case case_2 {
                     container label-switched-path-template {
                       description "Template for dynamic point-to-multipoint LSP parameters";
                       uses apply-advanced;
                       choice dynamic-template {
                         case case_1 {
                           leaf template-name {
                             description "Name of point-to-multipoint LSP template";
                             junos:must "((\"protocols mpls label-switched-path $$\" && (\"protocols mpls label-switched-path $$ template\" && \"protocols mpls label-switched-path $$ p2mp\")))";
                             junos:must-message "Referenced point-to-multipoint LSP template does not exist";
                             type string {
                               junos:posix-pattern "^.{1,32}$";
                               junos:pattern-message "Must be a string of 32 characters or less";
                             }
                           }
                         }
                         case case_2 {
                           leaf default-template {
                             description "Use default parameters";
                             type empty;
                           }
                         }
                       }
                     }
                   }
                 }
               }
             }
             case case_2 {
               container ldp-p2mp {
                 presence "enable ldp-p2mp";
                 junos:must "(\"protocols ldp p2mp\")";
                 junos:must-message "LDP P2MP must be configured in the master instance";
                 description "LDP point-to-multipoint LSP for flooding";
               }
             }
             case case_3 {
               container ingress-replication {
                 description "Ingress replication tunnel";
                 uses apply-advanced;
                 leaf create-new-ucast-tunnel {
                   description "Create new unicast tunnel for ingress replication";
                   junos:must "(\".. label-switched-path label-switched-path-template\")";
                   junos:must-message "label-switched-path-template must be defined";
                   type empty;
                 }
                 container label-switched-path {
                   presence "enable label-switched-path";
                   description "Point-to-point LSP unicast tunnel";
                   uses apply-advanced;
                   container label-switched-path-template {
                     junos:must "(\".. .. create-new-ucast-tunnel\")";
                     junos:must-message "Templates must be specified when and only when create-new-ucast-tunnel is defined";
                     description "Template for dynamic point-to-point LSP parameters";
                     uses apply-advanced;
                     choice dynamic-template {
                       case case_1 {
                         leaf template-name {
                           description "Name of point-to-point LSP template";
                           junos:must "((\"protocols mpls label-switched-path $$\" && (\"protocols mpls label-switched-path $$ template\" && !(\"protocols mpls label-switched-path $$ p2mp\"))))";
                           junos:must-message "Referenced point-to-point LSP template does not exist";
                           type string {
                             junos:posix-pattern "^.{1,32}$";
                             junos:pattern-message "Must be a string of 32 characters or less";
                           }
                         }
                       }
                       case case_2 {
                         leaf default-template {
                           description "Use default parameters";
                           type empty;
                         }
                       }
                     }
                   }
                 }
               }
             }
             case case_4 {
               leaf incoming {
                 description "Same as incoming provider tunnel";
                 type empty;
               }
             }
           }
         }
       }
     }
     leaf source-redundancy {
       description "Assume all the sources for a particular group is sending same data";
       type empty;
     }
     container umh-selection-additional-input {
       description "Additional parameters to consider during UMH";
       uses apply-advanced;
       leaf source-active-preference {
         description "Use the preference set in the source active route";
         junos:must "(!(\".. .. mvpn-mode rpt-spt\"))";
         junos:must-message "Source active preference can be configured only for spt only mode";
         type empty;
       }
       leaf tunnel-status {
         description "Use the RSVP tunnel status";
         type empty;
       }
     }
   }
   grouping juniper-protocols-mvrp {
     description "MVRP Configuration";
     uses apply-advanced;
     container traceoptions {
       description "Tracing options for MVRP";
       uses mrp-trace-options;
     }
     leaf join-timer {
       description "Join timer interval";
       default "200";
       units "milliseconds";
       type union {
         type string {
           pattern "<.*>|$.*";
         }
         type uint16 {
           range "100 .. 500";
         }
       }
     }
     leaf leave-timer {
       description "Leave timer interval";
       default "800";
       units "milliseconds";
       type union {
         type string {
           pattern "<.*>|$.*";
         }
         type uint16 {
           range "300 .. 1000";
         }
       }
     }
     leaf leaveall-timer {
       description "Leaveall timer interval";
       default "10";
       units "seconds";
       type union {
         type string {
           pattern "<.*>|$.*";
         }
         type uint16 {
           range "10 .. 60";
         }
       }
     }
     leaf no-dynamic-vlan {
       description "Disable dynamic VLAN creation";
       type empty;
     }
     leaf no-attribute-length-in-pdu {
       description "No attribute length while sending pdu ";
       type empty;
     }
     leaf bpdu-destination-mac-address {
       description "Destination MAC address in the MVRP BPDUs";
       type enumeration {
         enum "provider-bridge-group" {
           description "802.1ad provider bridge group address";
         }
       }
     }
     list interface {
       key name;
       ordered-by user;
       description "Configure interface options";
       leaf name {
         description "Interface name";
         junos:must "((((\".. .. .. rstp interface $$\" || \".. .. .. rstp interface all\") && !(\".. .. .. rstp interface $$ disable\")) || ((\".. .. .. mstp interface $$\" || \".. .. .. mstp interface all\") && !(\".. .. .. mstp interface $$ disable\"))))";
         junos:must-message "rstp/mstp is not enabled on the interface, mvrp is not allowed";
         junos:must "((!(\"interfaces $$ flexible-vlan-tagging\") && (!(\"interfaces $$ vlan-tagging\") && !(\"interfaces $$ stacked-vlan-tagging\"))))";
         junos:must-message "mvrp is not supported on interfaces if flexible-vlan-tagging/vlan-tagging/stacked-vlan-tagging enabled";
         junos:must "((\"interfaces $$ unit $$={0} family ethernet-switching interface-mode trunk\" || \"interfaces $$ unit $$={0} family bridge interface-mode trunk\"))";
         junos:must-message "mvrp can be enabled only on interfaces with interface-mode trunk";
         type union {
           type jt:interface-device;
           type string {
             pattern "<.*>|$.*";
           }
         }
       }
       uses apply-advanced;
       leaf join-timer {
         description "Join timer interval";
         units "milliseconds";
         type union {
           type string {
             pattern "<.*>|$.*";
           }
           type uint16 {
             range "100 .. 500";
           }
         }
       }
       leaf leave-timer {
         description "Leave timer interval";
         units "milliseconds";
         type union {
           type string {
             pattern "<.*>|$.*";
           }
           type uint16 {
             range "300 .. 1000";
           }
         }
       }
       leaf leaveall-timer {
         description "Leaveall timer interval";
         units "seconds";
         type union {
           type string {
             pattern "<.*>|$.*";
           }
           type uint16 {
             range "10 .. 60";
           }
         }
       }
       leaf point-to-point {
         description "Port is point to point";
         type empty;
       }
       leaf registration {
         description "Registration mode";
         default "normal";
         type enumeration {
           enum "normal" {
             description "Normal registration mode";
           }
           enum "restricted" {
             description "Restricted registration mode";
           }
           enum "forbidden" {
             description "Forbidden registration mode";
           }
         }
       }
     }
   }
   grouping juniper-protocols-ospf {
     uses apply-advanced;
     list topology {
       key name;
       ordered-by user;
       description "Topology parameters";
       leaf name {
         description "Topology name";
         type string;
       }
       uses apply-advanced;
       leaf disable {
         description "Disable this topology";
         type empty;
       }
       leaf topology-id {
         description "Topology identifier";
         type union {
           type string {
             pattern "<.*>|$.*";
           }
           type uint8 {
             range "32 .. 127";
           }
         }
       }
       leaf overload {
         description "Set the overload mode (repel transit traffic)";
         type empty;
       }
       leaf rib-group {
         description "Routing table group for importing routes";
         junos:must "(\"routing-options rib-groups $$\")";
         junos:must-message "Referenced rib-group must be defined";
         type string;
       }
       container spf-options {
         description "Configure options for SPF";
         uses apply-advanced;
         leaf delay {
           description "Time to wait before running an SPF";
           units "milliseconds";
           type union {
             type string {
               pattern "<.*>|$.*";
             }
             type uint32 {
               range "50 .. 8000";
             }
           }
         }
         leaf holddown {
           description "Time to hold down before running an SPF";
           units "milliseconds";
           type union {
             type string {
               pattern "<.*>|$.*";
             }
             type uint32 {
               range "2000 .. 20000";
             }
           }
         }
         leaf rapid-runs {
           description "Number of maximum rapid SPF runs before holddown";
           type union {
             type string {
               pattern "<.*>|$.*";
             }
             type uint32 {
               range "1 .. 10";
             }
           }
         }
         leaf no-ignore-our-externals {
           description "Do not ignore self-generated external and NSSA LSAs";
           type empty;
         }
       }
       container backup-spf-options {
         description "Configure options for backup SPF";
         uses apply-advanced;
         container remote-backup-calculation {
           presence "enable remote-backup-calculation";
           junos:must "(!(\"protocols ospf backup-spf-options use-post-convergence-lfa\"))";
           junos:must-message "Not allowed with 'protocols ospf backup-spf-options use-post-convergence-lfa'";
           description "Calculate Remote LFA backup nexthops";
           uses apply-advanced;
           container pq-nodes-nearest-to-source {
             description "PQ nodes selection based upon nearest to source";
             uses apply-advanced;
             leaf percent {
               description "Selection percentage for nearest to source";
               type union {
                 type string {
                   pattern "<.*>|$.*";
                 }
                 type uint32 {
                   range "10 .. 100";
                 }
               }
             }
           }
         }
         container use-post-convergence-lfa {
           presence "enable use-post-convergence-lfa";
           junos:must "(\"protocols ospf source-packet-routing\")";
           junos:must-message "Configuration of 'protocols ospf source-packet-routing' is required";
           description "Calculate post-convergence backup paths";
           uses apply-advanced;
           leaf maximum-labels {
             description "Maximum number of labels installed for post-convergence paths";
             type union {
               type string {
                 pattern "<.*>|$.*";
               }
               type uint32 {
                 range "2 .. 8";
               }
             }
           }
           leaf maximum-backup-paths {
             description "Maximum number of equal-cost post-convergence paths installed";
             type union {
               type string {
                 pattern "<.*>|$.*";
               }
               type uint32 {
                 range "1 .. 8";
               }
             }
           }
         }
         leaf use-source-packet-routing {
           description "Use spring backup paths for inet.0 routes";
           junos:must "(\".. .. source-packet-routing\")";
           junos:must-message "Configuration of 'protocols ospf source-packet-routing' is required";
           junos:must "(!(\".. remote-backup-calculation\"))";
           junos:must-message "Not allowed with 'protocols ospf backup-spf-options remote-backup-calculation'";
           type empty;
         }
         leaf disable {
           description "Do not run backup SPF";
           junos:must "(!(\"protocols ospf backup-spf-options use-post-convergence-lfa\"))";
           junos:must-message "Not allowed with 'protocols ospf backup-spf-options use-post-convergence-lfa'";
           type empty;
         }
         leaf no-install {
           description "Do not install backup nexthops into the RIB";
           type empty;
         }
         leaf downstream-paths-only {
           description "Use only downstream backup paths";
           junos:must "(!(\"protocols ospf backup-spf-options use-post-convergence-lfa\"))";
           junos:must-message "Not allowed with 'protocols ospf backup-spf-options use-post-convergence-lfa'";
           type empty;
         }
         container per-prefix-calculation {
           junos:must "(!(\"protocols ospf backup-spf-options use-post-convergence-lfa\"))";
           junos:must-message "Not allowed with 'protocols ospf backup-spf-options use-post-convergence-lfa'";
           description "Calculate backup nexthops for non-best prefix originators";
           uses apply-advanced;
           leaf stubs {
             description "Per prefix calculation for stubs only";
             type empty;
           }
           leaf summary {
             description "Per prefix calculation for summary originators only";
             type empty;
           }
           leaf externals {
             description "Per prefix calculation for externals";
             type empty;
           }
           leaf all {
             description "Per prefix calculation for all";
             type empty;
           }
         }
         leaf node-link-degradation {
           description "Degrade to link protection when nodelink protection not available";
           junos:must "(!(\"protocols ospf backup-spf-options use-post-convergence-lfa\"))";
           junos:must-message "Not allowed with 'protocols ospf backup-spf-options use-post-convergence-lfa'";
           type empty;
         }
       }
       leaf prefix-export-limit {
         description "Maximum number of prefixes that can be exported";
         type union {
           type string {
             pattern "<.*>|$.*";
           }
           type uint32 {
             range "0 .. 4294967295";
           }
         }
       }
     }
     container backup-spf-options {
       description "Configure options for backup SPF";
       uses apply-advanced;
       container remote-backup-calculation {
         presence "enable remote-backup-calculation";
         junos:must "(!(\"protocols ospf backup-spf-options use-post-convergence-lfa\"))";
         junos:must-message "Not allowed with 'protocols ospf backup-spf-options use-post-convergence-lfa'";
         description "Calculate Remote LFA backup nexthops";
         uses apply-advanced;
         container pq-nodes-nearest-to-source {
           description "PQ nodes selection based upon nearest to source";
           uses apply-advanced;
           leaf percent {
             description "Selection percentage for nearest to source";
             type union {
               type string {
                 pattern "<.*>|$.*";
               }
               type uint32 {
                 range "10 .. 100";
               }
             }
           }
         }
       }
       container use-post-convergence-lfa {
         presence "enable use-post-convergence-lfa";
         junos:must "(\"protocols ospf source-packet-routing\")";
         junos:must-message "Configuration of 'protocols ospf source-packet-routing' is required";
         description "Calculate post-convergence backup paths";
         uses apply-advanced;
         leaf maximum-labels {
           description "Maximum number of labels installed for post-convergence paths";
           type union {
             type string {
               pattern "<.*>|$.*";
             }
             type uint32 {
               range "2 .. 8";
             }
           }
         }
         leaf maximum-backup-paths {
           description "Maximum number of equal-cost post-convergence paths installed";
           type union {
             type string {
               pattern "<.*>|$.*";
             }
             type uint32 {
               range "1 .. 8";
             }
           }
         }
       }
       leaf use-source-packet-routing {
         description "Use spring backup paths for inet.0 routes";
         junos:must "(\".. .. source-packet-routing\")";
         junos:must-message "Configuration of 'protocols ospf source-packet-routing' is required";
         junos:must "(!(\".. remote-backup-calculation\"))";
         junos:must-message "Not allowed with 'protocols ospf backup-spf-options remote-backup-calculation'";
         type empty;
       }
       leaf disable {
         description "Do not run backup SPF";
         junos:must "(!(\"protocols ospf backup-spf-options use-post-convergence-lfa\"))";
         junos:must-message "Not allowed with 'protocols ospf backup-spf-options use-post-convergence-lfa'";
         type empty;
       }
       leaf no-install {
         description "Do not install backup nexthops into the RIB";
         type empty;
       }
       leaf downstream-paths-only {
         description "Use only downstream backup paths";
         junos:must "(!(\"protocols ospf backup-spf-options use-post-convergence-lfa\"))";
         junos:must-message "Not allowed with 'protocols ospf backup-spf-options use-post-convergence-lfa'";
         type empty;
       }
       container per-prefix-calculation {
         junos:must "(!(\"protocols ospf backup-spf-options use-post-convergence-lfa\"))";
         junos:must-message "Not allowed with 'protocols ospf backup-spf-options use-post-convergence-lfa'";
         description "Calculate backup nexthops for non-best prefix originators";
         uses apply-advanced;
         leaf stubs {
           description "Per prefix calculation for stubs only";
           type empty;
         }
         leaf summary {
           description "Per prefix calculation for summary originators only";
           type empty;
         }
         leaf externals {
           description "Per prefix calculation for externals";
           type empty;
         }
         leaf all {
           description "Per prefix calculation for all";
           type empty;
         }
       }
       leaf node-link-degradation {
         description "Degrade to link protection when nodelink protection not available";
         junos:must "(!(\"protocols ospf backup-spf-options use-post-convergence-lfa\"))";
         junos:must-message "Not allowed with 'protocols ospf backup-spf-options use-post-convergence-lfa'";
         type empty;
       }
     }
     container traffic-engineering {
       presence "enable traffic-engineering";
       description "Configure traffic engineering attributes";
       uses apply-advanced;
       leaf no-topology {
         description "Disable dissemination of TE link-state topology information";
         type empty;
       }
       leaf multicast-rpf-routes {
         description "Install routes for multicast RPF checks into inet.2";
         junos:must "(!(\".. .. topology $$={ipv4-multicast}\"))";
         junos:must-message "multicast-rpf-routes cannot be used with topology ipv4-multicast";
         junos:must "(\".. shortcuts\")";
         junos:must-message "multicast-rpf-routes cannot be used without shortcuts";
         type empty;
       }
       leaf l3-unicast-topology {
         description "Download IGP topology into TED";
         type empty;
       }
       container ignore-lsp-metrics {
         presence "enable ignore-lsp-metrics";
         description "Ignore label-switched path metrics when doing shortcuts";
         uses apply-advanced;
         leaf unconfigured-only {
           description "Ignore lsp metrics for unconfigured only";
           type empty;
         }
       }
       container shortcuts {
         presence "enable shortcuts";
         description "Use label-switched paths as next hops, if possible";
         uses apply-advanced;
         leaf ignore-lsp-metrics {
           description "Ignore label-switched path metrics when doing shortcuts";
           status deprecated;
           type empty;
         }
         leaf lsp-metric-into-summary {
           description "Advertise LSP metric into summary LSAs";
           type empty;
         }
         list family {
           key name;
           ordered-by user;
           description "Address family specific traffic-engineering attributes";
           leaf name {
             type enumeration {
               enum "inet" {
                 description "IPv4 family";
               }
               enum "inet-mpls" {
                 description "IPv4-MPLS family";
               }
             }
           }
           uses apply-advanced;
         }
       }
       leaf advertise-unnumbered-interfaces {
         description "Advertise unnumbered interfaces";
         type empty;
       }
       leaf credibility-protocol-preference {
         description "TED protocol credibility follows protocol preference";
         type empty;
       }
       container advertisement {
         description "Advertise TE parameters even if RSVP is not turned on";
         uses apply-advanced;
         leaf always {
           description "Advertise TE parameters in TE LSAs";
           type empty;
         }
       }
     }
     container source-packet-routing {
       presence "enable source-packet-routing";
       junos:must "(!(\".. .. .. protocols mpls disable\"))";
       junos:must-message "SPRING configuration is not allowed with 'protocols mpls disable'";
       junos:must "(\".. .. .. protocols mpls \")";
       junos:must-message "SPRING configuration is not allowed without 'protocols mpls'";
       description "Enable source packet routing (SPRING)";
       uses apply-advanced;
       container adjacency-segment {
         description "Attributes for adjacency segments in spring";
         uses apply-advanced;
         leaf hold-time {
           description "Retain time of Adjacency segment after isolating from an interface";
           type union {
             type string {
               pattern "<.*>|$.*";
             }
             type uint32 {
               range "180000 .. 900000";
             }
           }
         }
       }
       leaf-list prefix-segment {
         ordered-by user;
         description "Prefix Segment policy";
         type jt:policy-algebra;
       }
       leaf explicit-null {
         description "Set E and P bits in all Prefix SID advertisements";
         type empty;
       }
       container node-segment {
         presence "enable node-segment";
         description "Enable support for Node segments in SPRING";
         uses apply-advanced;
         leaf ipv4-index {
           description "Set ipv4 node segment index";
           type union {
             type string {
               pattern "<.*>|$.*";
             }
             type uint32 {
               range "0 .. 199999";
             }
           }
         }
         leaf index-range {
           description "Set range of node segment indices allowed";
           type union {
             type string {
               pattern "<.*>|$.*";
             }
             type uint32 {
               range "32 .. 16385";
             }
           }
         }
       }
       container srgb {
         junos:must "(!(\".. node-segment index-range\"))";
         junos:must-message "Can not be configured with node-segment index-range";
         description "Set the SRGB global block in SPRING";
         leaf start-label {
           description "Start range for SRGB label block";
           type union {
             type string {
               pattern "<.*>|$.*";
             }
             type uint32;
           }
         }
         leaf index-range {
           description "Index to the SRGB start label block";
           type union {
             type string {
               pattern "<.*>|$.*";
             }
             type uint32;
           }
         }
       }
       leaf mapping-server {
         description "Mapping server name";
         junos:must "(\".. node-segment\")";
         junos:must-message "protocols ospf source-packet-routing node-segment must be defined";
         junos:must "(\"routing-options source-packet-routing mapping-server-entry $$\")";
         junos:must-message "Referenced source-packet-routing mapping-server-entry must be defined";
         type string;
       }
       leaf install-prefix-sid-for-best-route {
         description "For best route install a exact prefix sid route";
         type empty;
       }
       leaf ldp-stitching {
         description "Enable SR to LDP stitching";
         type empty;
       }
       leaf-list flex-algorithm {
         description "Flex-algorithms we would like to participate in";
         type union {
           type string {
             pattern "<.*>|$.*";
           }
           type uint32 {
             range "128 .. 255";
           }
         }
         max-elements 16;
       }
     }
     list area {
       key name;
       ordered-by user;
       description "Configure an OSPF area";
       leaf name {
         description "Area ID";
         type jt:areaid;
       }
       uses apply-advanced;
       choice stub-option {
         case case_1 {
           container stub {
             presence "enable stub";
             description "Configure a stub area";
             leaf default-metric {
               description "Metric for the default route in this stub area";
               type union {
                 type string {
                   pattern "<.*>|$.*";
                 }
                 type uint32 {
                   range "1 .. 16777215";
                 }
               }
             }
             choice summaries-choice {
               leaf summaries {
                 description "Flood summary LSAs into this stub area";
                 type empty;
               }
               leaf no-summaries {
                 description "Don't flood summary LSAs into this stub area";
                 type empty;
               }
             }
           }
         }
         case case_2 {
           container nssa {
             presence "enable nssa";
             description "Configure a not-so-stubby area";
             uses apply-advanced;
             container default-lsa {
               presence "enable default-lsa";
               description "Configure a default LSA";
               uses apply-advanced;
               leaf default-metric {
                 description "Metric for the default route in this area";
                 type union {
                   type string {
                     pattern "<.*>|$.*";
                   }
                   type uint32 {
                     range "1 .. 16777215";
                   }
                 }
               }
               leaf metric-type {
                 description "External metric type for the default type 7 LSA";
                 type union {
                   type string {
                     pattern "<.*>|$.*";
                   }
                   type uint32 {
                     range "1 .. 2";
                   }
                 }
               }
               leaf type-7 {
                 description "Flood type 7 default LSA if no-summaries is configured";
                 type empty;
               }
             }
             leaf default-metric {
               description "Metric for the default route in this area";
               status deprecated;
               type union {
                 type string {
                   pattern "<.*>|$.*";
                 }
                 type uint32 {
                   range "1 .. 16777215";
                 }
               }
             }
             leaf metric-type {
               description "External metric type for the default type 7 LSA";
               status deprecated;
               type union {
                 type string {
                   pattern "<.*>|$.*";
                 }
                 type uint32 {
                   range "1 .. 2";
                 }
               }
             }
             choice summaries-choice {
               leaf summaries {
                 description "Flood summary LSAs into this NSSA area";
                 type empty;
               }
               leaf no-summaries {
                 description "Don't flood summary LSAs into this NSSA area";
                 type empty;
               }
             }
             list area-range {
               key name;
               ordered-by user;
               description "Configure NSSA area ranges";
               leaf name {
                 description "Range to summarize NSSA routes in this area";
                 type jt:ipprefix;
               }
               uses apply-advanced;
               leaf restrict {
                 description "Restrict advertisement of this area range";
                 type empty;
               }
               leaf exact {
                 description "Enforce exact match for advertisement of this area range";
                 type empty;
               }
               container override-metric {
                 presence "enable override-metric";
                 description "Override the dynamic metric for this area-range";
                 uses apply-advanced;
                 leaf metric {
                   description "Metric value";
                   type union {
                     type string {
                       pattern "<.*>|$.*";
                     }
                     type uint32 {
                       range "1 .. 16777215";
                     }
                   }
                 }
                 leaf metric-type {
                   description "Set the metric type for the override metric";
                   default "1";
                   type union {
                     type string {
                       pattern "<.*>|$.*";
                     }
                     type uint32 {
                       range "1 .. 2";
                     }
                   }
                 }
               }
             }
           }
         }
       }
       list area-range {
         key name;
         ordered-by user;
         description "Configure area ranges";
         leaf name {
           description "Range to summarize routes in this area";
           type jt:ipprefix;
         }
         uses apply-advanced;
         leaf restrict {
           description "Restrict advertisement of this area range";
           type empty;
         }
         leaf exact {
           description "Enforce exact match for advertisement of this area range";
           type empty;
         }
         leaf override-metric {
           description "Override the dynamic metric for this area-range";
           type union {
             type string {
               pattern "<.*>|$.*";
             }
             type uint32 {
               range "1 .. 16777215";
             }
           }
         }
       }
       leaf-list network-summary-export {
         ordered-by user;
         description "Export policy for Type 3 Summary LSAs";
         type jt:policy-algebra;
       }
       leaf-list network-summary-import {
         ordered-by user;
         description "Import policy for Type 3 Summary LSAs";
         type jt:policy-algebra;
       }
       leaf-list inter-area-prefix-export {
         ordered-by user;
         description "Export policy for Inter Area Prefix LSAs";
         type jt:policy-algebra;
       }
       leaf-list inter-area-prefix-import {
         ordered-by user;
         description "Import policy for Inter Area Prefix LSAs";
         type jt:policy-algebra;
       }
       leaf authentication-type {
         description "Authentication type";
         status deprecated;
         type enumeration {
           enum "none" {
             description "No authentication";
             status deprecated;
           }
           enum "simple" {
             description "Simple password authentication";
             status deprecated;
           }
           enum "md5" {
             description "MD5 authentication";
             status deprecated;
           }
         }
       }
       list virtual-link {
         key "neighbor-id transit-area";
         ordered-by user;
         description "Configure virtual links";
         junos:must "(\".. .. area $$={0.0.0.0}\")";
         junos:must-message "virtual link can be configured only under backbone area";
         leaf neighbor-id {
           description "Router ID of a virtual neighbor";
           type jt:ipv4addr;
         }
         leaf transit-area {
           description "Transit area in common with virtual neighbor";
           type jt:areaid;
         }
         uses apply-advanced;
         choice enable-disable {
           case case_1 {
             leaf disable {
               description "Disable this virtual link";
               type empty;
             }
           }
         }
         leaf retransmit-interval {
           description "Retransmission interval (seconds)";
           type union {
             type string {
               pattern "<.*>|$.*";
             }
             type uint32 {
               range "1 .. 65535";
             }
           }
         }
         leaf transit-delay {
           description "Transit delay (seconds)";
           type union {
             type string {
               pattern "<.*>|$.*";
             }
             type uint32 {
               range "1 .. 65535";
             }
           }
         }
         leaf hello-interval {
           description "Hello interval (seconds)";
           type union {
             type string {
               pattern "<.*>|$.*";
             }
             type uint32 {
               range "1 .. 255";
             }
           }
         }
         leaf dead-interval {
           description "Dead interval (seconds)";
           type union {
             type string {
               pattern "<.*>|$.*";
             }
             type uint32 {
               range "1 .. 65535";
             }
           }
         }
         leaf mtu {
           description "Maximum OSPF packet size";
           type union {
             type string {
               pattern "<.*>|$.*";
             }
             type uint32 {
               range "128 .. 65535";
             }
           }
         }
         choice auth {
           case case_1 {
             container authentication {
               uses juniper-ospf-authentication;
             }
           }
           case case_2 {
             container authentication-key {
               description "Authentication key";
               status deprecated;
               leaf keyname {
                 description "Authentication key value";
                 type jt:unreadable;
               }
               leaf key-id {
                 description "Key ID for MD5 authentication";
                 type union {
                   type string {
                     pattern "<.*>|$.*";
                   }
                   type uint32 {
                     range "0 .. 255";
                   }
                 }
               }
             }
           }
         }
         leaf demand-circuit {
           description "Interface functions as a demand circuit";
           type empty;
         }
         leaf flood-reduction {
           description "Enable flood reduction";
           type empty;
         }
         leaf no-neighbor-down-notification {
           description "Don't inform other protocols about neighbor down events";
           type empty;
         }
         leaf ipsec-sa {
           description "IPSec security association name";
           junos:must "(!(any \".. .. interface <st*> ipsec-sa $$\"))";
           junos:must-message "Must not configure ipsec-sa for st0 interface";
           junos:must "(\"security ipsec security-association $$ manual\")";
           junos:must-message "Referenced IPSec security association must be a manual SA";
           junos:must "(\"security ipsec security-association $$ mode transport\")";
           junos:must-message "Referenced IPSec security association must be in transport mode";
           junos:must "(\"security ipsec security-association $$\")";
           junos:must-message "Referenced IPSec security association must be defined";
           type string {
             length "1 .. 32";
           }
         }
         list topology {
           key name;
           ordered-by user;
           description "Topology specific attributes";
           leaf name {
             description "Topology name";
             type string;
           }
           uses apply-advanced;
           leaf disable {
             description "Disable this topology";
             type empty;
           }
           leaf metric {
             description "Topology metric";
             type union {
               type string {
                 pattern "<.*>|$.*";
               }
               type uint16 {
                 range "1 .. 65535";
               }
             }
           }
           container bandwidth-based-metrics {
             junos:must "(\".. metric\")";
             junos:must-message "Metric must be configured";
             description "Configure bandwidth based metrics";
             uses apply-advanced;
             list bandwidth {
               key name;
               description "Bandwidth threshold";
               leaf name {
                 type string;
               }
               leaf metric {
                 description "Metric associated with specified bandwidth";
                 type union {
                   type string {
                     pattern "<.*>|$.*";
                   }
                   type uint16 {
                     range "1 .. 65535";
                   }
                 }
               }
             }
           }
         }
       }
       list sham-link-remote {
         key name;
         ordered-by user;
         description "Configure parameters for remote sham link endpoint";
         leaf name {
           description "Remote sham link endpoint address";
           junos:must "(!(\".. .. .. sham-link local $$\"))";
           junos:must-message "Local and remote sham link endpoint addresses must be different";
           junos:must "(\".. .. .. sham-link local\")";
           junos:must-message "Local sham link endpoint must be configured";
           type jt:ipaddr;
         }
         uses apply-advanced;
         leaf metric {
           description "Sham link metric";
           type union {
             type string {
               pattern "<.*>|$.*";
             }
             type uint16 {
               range "1 .. 65535";
             }
           }
         }
         leaf ipsec-sa {
           description "IPSec security association name";
           junos:must "(!(any \".. .. interface <st*> ipsec-sa $$\"))";
           junos:must-message "Must not configure ipsec-sa for st0 interface";
           junos:must "(\"security ipsec security-association $$ manual\")";
           junos:must-message "Referenced IPSec security association must be a manual SA";
           junos:must "(\"security ipsec security-association $$ mode transport\")";
           junos:must-message "Referenced IPSec security association must be in transport mode";
           junos:must "(\"security ipsec security-association $$\")";
           junos:must-message "Referenced IPSec security association must be defined";
           type string {
             length "1 .. 32";
           }
         }
         leaf demand-circuit {
           description "Interface functions as a demand circuit";
           type empty;
         }
         leaf flood-reduction {
           description "Enable flood reduction";
           type empty;
         }
         list topology {
           key name;
           ordered-by user;
           description "Topology specific attributes";
           leaf name {
             description "Topology name";
             type string;
           }
           uses apply-advanced;
           leaf disable {
             description "Disable this topology";
             type empty;
           }
           leaf metric {
             description "Topology metric";
             type union {
               type string {
                 pattern "<.*>|$.*";
               }
               type uint16 {
                 range "1 .. 65535";
               }
             }
           }
           container bandwidth-based-metrics {
             junos:must "(\".. metric\")";
             junos:must-message "Metric must be configured";
             description "Configure bandwidth based metrics";
             uses apply-advanced;
             list bandwidth {
               key name;
               description "Bandwidth threshold";
               leaf name {
                 type string;
               }
               leaf metric {
                 description "Metric associated with specified bandwidth";
                 type union {
                   type string {
                     pattern "<.*>|$.*";
                   }
                   type uint16 {
                     range "1 .. 65535";
                   }
                 }
               }
             }
           }
         }
       }
       list interface {
         key name;
         ordered-by user;
         description "Include an interface in this area";
         leaf name {
           description "Interface name";
           junos:must "((!(\".. interface-type nbma\") || (!((\"interfaces $$\" || any \"logical-systems <*> interfaces $$\")) || (any \"interfaces $$-IFL family inet address <*>\" || any \"logical-systems <*> interfaces $$-IFL family inet address <*>\"))))";
           junos:must-message "IPv4 address must be configured on the interface for nbma mode";
           type union {
             type jt:ipv4addr-or-interface;
             type string {
               pattern "<.*>|$.*";
             }
           }
         }
         uses apply-advanced;
         choice enable-disable {
           case case_1 {
             leaf disable {
               description "Disable OSPF on this interface";
               type empty;
             }
           }
         }
         leaf interface-type {
           description "Type of interface";
           type enumeration {
             enum "nbma" {
               description "Nonbroadcast multiaccess";
             }
             enum "p2mp" {
               description "Point-to-multipoint NBMA";
             }
             enum "p2p" {
               description "Point-to-point";
             }
             enum "p2mp-over-lan" {
               description "Point-to-multipoint over LAN mode";
             }
           }
         }
         choice protection-type {
           case case_1 {
             leaf link-protection {
               description "Protect interface from link faults only";
               type empty;
             }
           }
           case case_2 {
             leaf node-link-protection {
               description "Protect interface from both link and node faults";
               type empty;
             }
           }
         }
         leaf no-eligible-backup {
           description "Not eligible to backup traffic from protected interfaces";
           type empty;
         }
         leaf no-eligible-remote-backup {
           description "Not eligible for Remote-LFA backup traffic from protected interfaces";
           type empty;
         }
         container passive {
           presence "enable passive";
           description "Do not run OSPF, but advertise it";
           uses apply-advanced;
           container traffic-engineering {
             description "Advertise TE link information";
             uses apply-advanced;
             leaf remote-node-id {
               description "Remote address of the link";
               type jt:ipaddr;
             }
             leaf remote-node-router-id {
               description "TE Router-ID of the remote node";
               junos:must "(\".. remote-node-id\")";
               junos:must-message "remote-node-id must be configured";
               type jt:ipv4addr;
             }
           }
         }
         leaf secondary {
           description "Treat interface as secondary";
           junos:must "(!(\" .. ipsec-sa\"))";
           junos:must-message "secondary interface cannot have ipsec-sa configured";
           junos:must "(!(\" .. dynamic-neighbors\"))";
           junos:must-message "secondary interface cannot have dynamic-neighbors configured";
           junos:must "(!(\" .. neighbor\"))";
           junos:must-message "secondary interface cannot have configured neighbors";
           junos:must "(!(\" .. interface-type p2mp\"))";
           junos:must-message "secondary interface cannot be set as type p2mp";
           junos:must "(!(\" .. interface-type nbma\"))";
           junos:must-message "secondary interface cannot be set as type nbma";
           junos:must "(!(\" .. passive\"))";
           junos:must-message "secondary interface cannot be configured passive";
           type empty;
         }
         leaf own-router-lsa {
           description "Generate a separate router LSA for this interface";
           type empty;
         }
         container bandwidth-based-metrics {
           junos:must "(\".. metric\")";
           junos:must-message "Metric must be configured";
           description "Configure bandwidth based metrics";
           uses apply-advanced;
           list bandwidth {
             key name;
             description "Bandwidth threshold";
             leaf name {
               type string;
             }
             leaf metric {
               description "Metric associated with specified bandwidth";
               type union {
                 type string {
                   pattern "<.*>|$.*";
                 }
                 type uint16 {
                   range "1 .. 65535";
                 }
               }
             }
           }
         }
         leaf metric {
           description "Interface metric";
           type union {
             type string {
               pattern "<.*>|$.*";
             }
             type uint16 {
               range "1 .. 65535";
             }
           }
         }
         leaf priority {
           description "Designated router priority";
           type union {
             type string {
               pattern "<.*>|$.*";
             }
             type uint32 {
               range "0 .. 255";
             }
           }
         }
         leaf retransmit-interval {
           description "Retransmission interval (seconds)";
           type union {
             type string {
               pattern "<.*>|$.*";
             }
             type uint32 {
               range "1 .. 65535";
             }
           }
         }
         leaf transit-delay {
           description "Transit delay (seconds)";
           type union {
             type string {
               pattern "<.*>|$.*";
             }
             type uint32 {
               range "1 .. 65535";
             }
           }
         }
         leaf hello-interval {
           description "Hello interval (seconds)";
           type union {
             type string {
               pattern "<.*>|$.*";
             }
             type uint32 {
               range "1 .. 255";
             }
           }
         }
         leaf dead-interval {
           description "Dead interval (seconds)";
           type union {
             type string {
               pattern "<.*>|$.*";
             }
             type uint32 {
               range "1 .. 65535";
             }
           }
         }
         leaf mtu {
           description "Maximum OSPF packet size";
           type union {
             type string {
               pattern "<.*>|$.*";
             }
             type uint32 {
               range "128 .. 65535";
             }
           }
         }
         choice auth {
           case case_1 {
             container authentication {
               uses juniper-ospf-authentication;
             }
           }
           case case_2 {
             container authentication-key {
               description "Authentication key";
               status deprecated;
               leaf keyname {
                 description "Authentication key value";
                 type jt:unreadable;
               }
               leaf key-id {
                 description "Key ID for MD5 authentication";
                 type union {
                   type string {
                     pattern "<.*>|$.*";
                   }
                   type uint32 {
                     range "0 .. 255";
                   }
                 }
               }
             }
           }
         }
         leaf demand-circuit {
           description "Interface functions as a demand circuit";
           type empty;
         }
         leaf flood-reduction {
           description "Enable flood reduction";
           type empty;
         }
         leaf no-neighbor-down-notification {
           description "Don't inform other protocols about neighbor down events";
           type empty;
         }
         leaf ipsec-sa {
           description "IPSec security association name";
           junos:must "(!(any \".. .. interface <st*> ipsec-sa $$\"))";
           junos:must-message "Must not configure ipsec-sa for st0 interface";
           junos:must "(\"security ipsec security-association $$ manual\")";
           junos:must-message "Referenced IPSec security association must be a manual SA";
           junos:must "(\"security ipsec security-association $$ mode transport\")";
           junos:must-message "Referenced IPSec security association must be in transport mode";
           junos:must "(\"security ipsec security-association $$\")";
           junos:must-message "Referenced IPSec security association must be defined";
           type string {
             length "1 .. 32";
           }
         }
         list topology {
           key name;
           ordered-by user;
           description "Topology specific attributes";
           leaf name {
             description "Topology name";
             type string;
           }
           uses apply-advanced;
           leaf disable {
             description "Disable this topology";
             type empty;
           }
           leaf metric {
             description "Topology metric";
             type union {
               type string {
                 pattern "<.*>|$.*";
               }
               type uint16 {
                 range "1 .. 65535";
               }
             }
           }
           container bandwidth-based-metrics {
             junos:must "(\".. metric\")";
             junos:must-message "Metric must be configured";
             description "Configure bandwidth based metrics";
             uses apply-advanced;
             list bandwidth {
               key name;
               description "Bandwidth threshold";
               leaf name {
                 type string;
               }
               leaf metric {
                 description "Metric associated with specified bandwidth";
                 type union {
                   type string {
                     pattern "<.*>|$.*";
                   }
                   type uint16 {
                     range "1 .. 65535";
                   }
                 }
               }
             }
           }
         }
         leaf transmit-interval {
           description "OSPF packet transmit interval (milliseconds)";
           status deprecated;
           type union {
             type string {
               pattern "<.*>|$.*";
             }
             type uint32 {
               range "1 .. 4294967295";
             }
           }
         }
         container bfd-liveness-detection {
           description "Bidirectional Forwarding Detection options";
           uses apply-advanced;
           leaf version {
             description "BFD protocol version number";
             default "automatic";
             type enumeration {
               enum "0" {
                 description "BFD version 0 (deprecated)";
               }
               enum "1" {
                 description "BFD version 1";
               }
               enum "automatic" {
                 description "Choose BFD version automatically";
               }
             }
           }
           leaf minimum-interval {
             description "Minimum transmit and receive interval";
             units "milliseconds";
             type union {
               type string {
                 pattern "<.*>|$.*";
               }
               type uint32 {
                 range "1 .. 255000";
               }
             }
           }
           leaf minimum-transmit-interval {
             description "Minimum transmit interval";
             status deprecated;
             units "milliseconds";
             type union {
               type string {
                 pattern "<.*>|$.*";
               }
               type uint32 {
                 range "1 .. 255000";
               }
             }
           }
           leaf minimum-receive-interval {
             description "Minimum receive interval";
             units "milliseconds";
             type union {
               type string {
                 pattern "<.*>|$.*";
               }
               type uint32 {
                 range "1 .. 255000";
               }
             }
           }
           leaf multiplier {
             description "Detection time multiplier";
             default "3";
             type union {
               type string {
                 pattern "<.*>|$.*";
               }
               type uint32 {
                 range "1 .. 255";
               }
             }
           }
           choice adaptation-choice {
             case case_1 {
               leaf no-adaptation {
                 description "Disable adaptation";
                 type empty;
               }
             }
           }
           container transmit-interval {
             description "Transmit-interval options";
             uses apply-advanced;
             leaf minimum-interval {
               description "Minimum transmit interval";
               units "milliseconds";
               type union {
                 type string {
                   pattern "<.*>|$.*";
                 }
                 type uint32 {
                   range "1 .. 255000";
                 }
               }
             }
             leaf threshold {
               description "High transmit interval triggering a trap";
               units "milliseconds";
               type union {
                 type uint32;
                 type string {
                   pattern "<.*>|$.*";
                 }
               }
             }
           }
           container detection-time {
             description "Detection-time options";
             uses apply-advanced;
             leaf threshold {
               description "High detection-time triggering a trap";
               units "milliseconds";
               type union {
                 type uint32;
                 type string {
                   pattern "<.*>|$.*";
                 }
               }
             }
           }
           container authentication {
             description "Authentication options";
             uses apply-advanced;
             leaf key-chain {
               description "Key chain name";
               junos:must "(\".. algorithm\")";
               junos:must-message "May not be configured without algorithm";
               junos:must "(\"security authentication-key-chains key-chain $$\")";
               junos:must-message "Referenced key-chain must be defined";
               type string;
             }
             leaf algorithm {
               description "Algorithm name";
               junos:must "(\".. key-chain\")";
               junos:must-message "May not be configured without key-chain";
               type enumeration {
                 enum "simple-password" {
                   description "Simple password";
                 }
                 enum "keyed-md5" {
                   description "Keyed message Digest 5";
                 }
                 enum "meticulous-keyed-md5" {
                   description "Meticulous keyed message Digest 5";
                 }
                 enum "keyed-sha-1" {
                   description "Keyed secure hash algorithm (SHA1) ";
                 }
                 enum "meticulous-keyed-sha-1" {
                   description "Meticulous keyed secure hash algorithm (SHA1) ";
                 }
               }
             }
             leaf loose-check {
               description "Verify authentication only if authentication is negotiated";
               type empty;
             }
           }
           leaf full-neighbors-only {
             description "Setup BFD sessions only to Full neighbors";
             type empty;
           }
           leaf holddown-interval {
             description "Time to hold the session-UP notification to the client";
             units "milliseconds";
             type union {
               type string {
                 pattern "<.*>|$.*";
               }
               type uint32 {
                 range "0 .. 255000";
               }
             }
           }
         }
         leaf dynamic-neighbors {
           description "Learn neighbors dynamically on a p2mp interface";
           junos:must "(\" .. interface-type p2mp\")";
           junos:must-message "dynamic-neighbors option can be set only if the interface type is p2mp";
           type empty;
         }
         leaf no-advertise-adjacency-segment {
           description "Do not advertise an adjacency segment for this interface";
           type empty;
         }
         list neighbor {
           key name;
           ordered-by user;
           description "NBMA neighbor";
           junos:must "(!(\" .. dynamic-neighbors\"))";
           junos:must-message "Neighbors cannot be specified manually if dynamic-neighbors is set";
           leaf name {
             description "Address of neighbor";
             type jt:ipaddr;
           }
           leaf eligible {
             description "Eligible to be DR on an NBMA network";
             type empty;
           }
         }
         leaf poll-interval {
           description "Poll interval for NBMA interfaces";
           type union {
             type string {
               pattern "<.*>|$.*";
             }
             type uint32 {
               range "1 .. 65535";
             }
           }
         }
         leaf no-interface-state-traps {
           description "Do not send interface state change traps";
           type empty;
         }
         leaf strict-bfd {
           description "Enable strict bfd over this interface";
           junos:must "(\" .. bfd-liveness-detection\")";
           junos:must-message "strict bfd cannot be configured without bfd.";
           junos:must "(!(\" .. bfd-liveness-detection full-neighbors-only\"))";
           junos:must-message "full-neighbors-only and strict-bfd cannot be configured together";
           type empty;
         }
         container post-convergence-lfa {
           presence "enable post-convergence-lfa";
           junos:must "(\"protocols ospf backup-spf-options use-post-convergence-lfa\")";
           junos:must-message "Not allowed without 'protocols ospf backup-spf-options use-post-convergence-lfa'";
           description "Protect interface using post-convergence backup path";
           uses apply-advanced;
           container node-protection {
             presence "enable node-protection";
             description "Compute backup path assuming node failure";
             uses apply-advanced;
             leaf cost {
               description "Cost for node protection";
               type union {
                 type string {
                   pattern "<.*>|$.*";
                 }
                 type uint16 {
                   range "1 .. 65535";
                 }
               }
             }
           }
           leaf srlg-protection {
             description "Compute backup path assuming SRLG failure";
             type empty;
           }
           leaf fate-sharing-protection {
             description "Compute backup path assuming fate-sharing group failure";
             type empty;
           }
         }
         leaf te-metric {
           description "Traffic engineering metric";
           type union {
             type string {
               pattern "<.*>|$.*";
             }
             type uint32 {
               range "1 .. 4294967295";
             }
           }
         }
         container ldp-synchronization {
           description "Advertise maximum metric until LDP is operational";
           presence "enable ldp-synchronization";
           uses ldp-sync-obj;
         }
         container ipv4-adjacency-segment {
           junos:must "(!(\".. no-advertise-adjacency-segment\"))";
           junos:must-message "ipv4-adjacency-segment can't be configured if no-advertise-adjacency-segment is configured in the same interface";
           description "Configure ipv4 adjacency segment";
           uses apply-advanced;
           container protected {
             description "Adjacency SID is eligible for protection";
             choice adjsid-type {
               case case_1 {
                 container index {
                   description "Adjacency SID indexed from SRGB";
                   leaf index-number {
                     type union {
                       type string {
                         pattern "<.*>|$.*";
                       }
                       type uint32 {
                         range "0 .. 199999";
                       }
                     }
                   }
                 }
               }
               case case_2 {
                 leaf label {
                   description "Adjacency SID from static label pool";
                   type union {
                     type string {
                       pattern "<.*>|$.*";
                     }
                     type uint32 {
                       range "16 .. 1048575";
                     }
                   }
                 }
               }
               case case_3 {
                 leaf dynamic {
                   description "Dynamically allocate an adjacency segment";
                   type empty;
                 }
               }
             }
           }
           container unprotected {
             description "Adjacency SID uneligible for protection";
             choice adjsid-type {
               case case_1 {
                 container index {
                   description "Adjacency SID indexed from SRGB";
                   leaf index-number {
                     type union {
                       type string {
                         pattern "<.*>|$.*";
                       }
                       type uint32 {
                         range "0 .. 199999";
                       }
                     }
                   }
                 }
               }
               case case_2 {
                 leaf label {
                   description "Adjacency SID from static label pool";
                   type union {
                     type string {
                       pattern "<.*>|$.*";
                     }
                     type uint32 {
                       range "16 .. 1048575";
                     }
                   }
                 }
               }
               case case_3 {
                 leaf dynamic {
                   description "Dynamically allocate an adjacency segment";
                   type empty;
                 }
               }
             }
           }
         }
         list lan-neighbor {
           key name;
           ordered-by user;
           description "Configuration specific to a LAN neighbor";
           junos:must "(!(\".. ipv4-adjacency-segment\"))";
           junos:must-message "lan-neighbor can't be configured if ipv4-adjacency-segment is configured in the same interface";
           junos:must "(!(\".. no-advertise-adjacency-segment\"))";
           junos:must-message "lan-neighbor can't be configured if no-advertise-adjacency-segment is configured in the same interface ";
           junos:must "(!(\".. interface-type p2p\"))";
           junos:must-message "lan-neighbor can't be configured for point-to-point interfaces";
           leaf name {
             description "Address of neighbor";
             type jt:ipaddr;
           }
           uses apply-advanced;
           container ipv4-adjacency-segment {
             junos:must "(!(\".. no-advertise-adjacency-segment\"))";
             junos:must-message "ipv4-adjacency-segment can't be configured if no-advertise-adjacency-segment is configured in the same interface";
             description "Configure ipv4 adjacency segment";
             uses apply-advanced;
             container protected {
               description "Adjacency SID is eligible for protection";
               choice adjsid-type {
                 case case_1 {
                   container index {
                     description "Adjacency SID indexed from SRGB";
                     leaf index-number {
                       type union {
                         type string {
                           pattern "<.*>|$.*";
                         }
                         type uint32 {
                           range "0 .. 199999";
                         }
                       }
                     }
                   }
                 }
                 case case_2 {
                   leaf label {
                     description "Adjacency SID from static label pool";
                     type union {
                       type string {
                         pattern "<.*>|$.*";
                       }
                       type uint32 {
                         range "16 .. 1048575";
                       }
                     }
                   }
                 }
                 case case_3 {
                   leaf dynamic {
                     description "Dynamically allocate an adjacency segment";
                     type empty;
                   }
                 }
               }
             }
             container unprotected {
               description "Adjacency SID uneligible for protection";
               choice adjsid-type {
                 case case_1 {
                   container index {
                     description "Adjacency SID indexed from SRGB";
                     leaf index-number {
                       type union {
                         type string {
                           pattern "<.*>|$.*";
                         }
                         type uint32 {
                           range "0 .. 199999";
                         }
                       }
                     }
                   }
                 }
                 case case_2 {
                   leaf label {
                     description "Adjacency SID from static label pool";
                     type union {
                       type string {
                         pattern "<.*>|$.*";
                       }
                       type uint32 {
                         range "16 .. 1048575";
                       }
                     }
                   }
                 }
                 case case_3 {
                   leaf dynamic {
                     description "Dynamically allocate an adjacency segment";
                     type empty;
                   }
                 }
               }
             }
           }
         }
         leaf delay-metric {
           description "Delay metric";
           units "microseconds";
           type union {
             type string {
               pattern "<.*>|$.*";
             }
             type uint32 {
               range "0 .. 16777215";
             }
           }
         }
         container delay-measurement {
           presence "enable delay-measurement";
           description "Enable delay measurement";
           uses apply-advanced;
           leaf probe-interval {
             description "Probe interval";
             units "seconds";
             type union {
               type string {
                 pattern "<.*>|$.*";
               }
               type uint32 {
                 range "1 .. 255";
               }
             }
           }
           leaf probe-count {
             description "Probe count";
             type union {
               type string {
                 pattern "<.*>|$.*";
               }
               type uint32 {
                 range "1 .. 15";
               }
             }
           }
           container advertisement {
             description "Delay advertisement";
             uses apply-advanced;
             container periodic {
               description "Periodic advertisement parameters";
               uses apply-advanced;
               leaf threshold {
                 description "Threshold";
                 units "percentage";
                 type union {
                   type string {
                     pattern "<.*>|$.*";
                   }
                   type uint32 {
                     range "0 .. 100";
                   }
                 }
               }
               leaf interval {
                 description "Interval";
                 units "seconds";
                 type union {
                   type string {
                     pattern "<.*>|$.*";
                   }
                   type uint32 {
                     range "30 .. 3600";
                   }
                 }
               }
             }
             container accelerated {
               presence "enable accelerated";
               description "Accelerated advertisement parameters";
               uses apply-advanced;
               leaf threshold {
                 description "Threshold";
                 units "percentage";
                 type union {
                   type string {
                     pattern "<.*>|$.*";
                   }
                   type uint32 {
                     range "0 .. 100";
                   }
                 }
               }
             }
           }
         }
       }
       leaf no-context-identifier-advertisement {
         description "Disable context identifier advertisments in this area";
         junos:must "(!(\".. context-identifier\"))";
         junos:must-message "no-context-identifier-advertisement and context-identifier attributes are mutually exclusive";
         type empty;
       }
       list peer-interface {
         key name;
         ordered-by user;
         description "Configuration for peer interface";
         leaf name {
           description "Name of peer interface";
           type string;
         }
         uses apply-advanced;
         choice enable-disable {
           case case_1 {
             leaf disable {
               description "Disable OSPF on this control peer";
               type empty;
             }
           }
         }
         leaf retransmit-interval {
           description "Retransmission interval (seconds)";
           type union {
             type string {
               pattern "<.*>|$.*";
             }
             type uint32 {
               range "1 .. 65535";
             }
           }
         }
         leaf transit-delay {
           description "Transit delay (seconds)";
           type union {
             type string {
               pattern "<.*>|$.*";
             }
             type uint32 {
               range "1 .. 65535";
             }
           }
         }
         leaf hello-interval {
           description "Hello interval (seconds)";
           type union {
             type string {
               pattern "<.*>|$.*";
             }
             type uint32 {
               range "1 .. 255";
             }
           }
         }
         leaf dead-interval {
           description "Dead interval (seconds)";
           type union {
             type string {
               pattern "<.*>|$.*";
             }
             type uint32 {
               range "1 .. 65535";
             }
           }
         }
         leaf mtu {
           description "Maximum OSPF packet size";
           type union {
             type string {
               pattern "<.*>|$.*";
             }
             type uint32 {
               range "128 .. 65535";
             }
           }
         }
         choice auth {
           case case_1 {
             container authentication {
               uses juniper-ospf-authentication;
             }
           }
           case case_2 {
             container authentication-key {
               description "Authentication key";
               status deprecated;
               leaf keyname {
                 description "Authentication key value";
                 type jt:unreadable;
               }
               leaf key-id {
                 description "Key ID for MD5 authentication";
                 type union {
                   type string {
                     pattern "<.*>|$.*";
                   }
                   type uint32 {
                     range "0 .. 255";
                   }
                 }
               }
             }
           }
         }
         leaf demand-circuit {
           description "Interface functions as a demand circuit";
           type empty;
         }
         leaf flood-reduction {
           description "Enable flood reduction";
           type empty;
         }
         leaf no-neighbor-down-notification {
           description "Don't inform other protocols about neighbor down events";
           type empty;
         }
       }
       leaf no-source-packet-routing {
         description "Disable SPRING in this area";
         type empty;
       }
       list context-identifier {
         key name;
         ordered-by user;
         description "Configure context identifier in support of edge protection";
         junos:must "(!(\".. no-context-identifier-advertisement\"))";
         junos:must-message "no-context-identifier-advertisement and context-identifier attributes are mutually exclusive";
         leaf name {
           description "Context identifier";
           type jt:ipv4addr;
         }
         uses apply-advanced;
       }
       list label-switched-path {
         key name;
         ordered-by user;
         description "Configuration for advertisement of a label-switched path";
         junos:must "(!(\".. .. traffic-engineering multicast-rpf-routes\"))";
         junos:must-message "cannot advertise LSPs when using multicast-rpf-routes";
         leaf name {
           description "Name of label-switched path to be advertised";
           type string {
             length "1 .. 64";
           }
         }
         uses apply-advanced;
         choice enable-disable {
           case case_1 {
             leaf disable {
               description "Disable OSPF on this label-switched path";
               type empty;
             }
           }
         }
         leaf metric {
           description "Interface metric";
           type union {
             type string {
               pattern "<.*>|$.*";
             }
             type uint16 {
               range "1 .. 65535";
             }
           }
         }
         list topology {
           key name;
           ordered-by user;
           description "Topology specific attributes";
           leaf name {
             description "Topology name";
             type string;
           }
           uses apply-advanced;
           leaf disable {
             description "Disable this topology";
             type empty;
           }
           leaf metric {
             description "Topology metric";
             type union {
               type string {
                 pattern "<.*>|$.*";
               }
               type uint16 {
                 range "1 .. 65535";
               }
             }
           }
           container bandwidth-based-metrics {
             junos:must "(\".. metric\")";
             junos:must-message "Metric must be configured";
             description "Configure bandwidth based metrics";
             uses apply-advanced;
             list bandwidth {
               key name;
               description "Bandwidth threshold";
               leaf name {
                 type string;
               }
               leaf metric {
                 description "Metric associated with specified bandwidth";
                 type union {
                   type string {
                     pattern "<.*>|$.*";
                   }
                   type uint16 {
                     range "1 .. 65535";
                   }
                 }
               }
             }
           }
         }
       }
     }
     choice enable-disable {
       case case_1 {
         leaf disable {
           description "Disable OSPF";
           type empty;
         }
       }
     }
     container traceoptions {
       description "Trace options for OSPF";
       uses apply-advanced;
       container file {
         description "Trace file options";
         leaf filename {
           description "Name of file in which to write trace information";
           type string {
             length "1 .. 1024";
             junos:posix-pattern "![/ %]";
             junos:pattern-message "Must not contain '/', % or a space";
           }
         }
         leaf replace {
           description "Replace trace file rather than appending to it";
           status deprecated;
           type empty;
         }
         leaf size {
           description "Maximum trace file size";
           type string;
         }
         leaf files {
           description "Maximum number of trace files";
           default "10";
           type union {
             type string {
               pattern "<.*>|$.*";
             }
             type uint32 {
               range "2 .. 1000";
             }
           }
         }
         leaf no-stamp {
           description "Do not timestamp trace file";
           status deprecated;
           type empty;
         }
         choice world-readable-choice {
           leaf world-readable {
             description "Allow any user to read the log file";
             type empty;
           }
           leaf no-world-readable {
             description "Don't allow any user to read the log file";
             type empty;
           }
         }
       }
       list flag {
         key name;
         ordered-by user;
         description "Tracing parameters";
         leaf name {
           type enumeration {
             enum "spf" {
               description "Trace SPF calculations";
             }
             enum "error" {
               description "Trace errored packets";
             }
             enum "event" {
               description "Trace OSPF state machine events";
             }
             enum "packet-dump" {
               description "Dump the contents of selected packet types";
             }
             enum "flooding" {
               description "Trace LSA flooding";
             }
             enum "lsa-analysis" {
               description "Trace LSA analysis";
             }
             enum "packets" {
               description "Trace all OSPF packets";
             }
             enum "hello" {
               description "Trace hello packets";
             }
             enum "database-description" {
               description "Trace database description packets";
             }
             enum "lsa-request" {
               description "Trace LSA request packets";
             }
             enum "lsa-update" {
               description "Trace LSA update packets";
             }
             enum "lsa-ack" {
               description "Trace LSA acknowledgment packets";
             }
             enum "ldp-synchronization" {
               description "Trace synchronization between OSPF and LDP";
             }
             enum "on-demand" {
               description "Trace demand circuit extensions";
             }
             enum "nsr-synchronization" {
               description "Trace NSR synchronization events";
             }
             enum "graceful-restart" {
               description "Trace graceful restart";
             }
             enum "restart-signaling" {
               description "Trace restart signaling";
             }
             enum "backup-spf" {
               description "Trace backup SPF (LFA) specific events";
             }
             enum "source-packet-routing" {
               description "Trace source packet routing (SPRING) events";
             }
             enum "post-convergence-lfa" {
               description "Trace post-convergence-lfa related events";
             }
             enum "flex-algorithm" {
               description "Trace flex-algorithm related events";
             }
             enum "rmopd" {
               description "Trace rmopd interactions";
             }
             enum "route" {
               description "Trace routing information";
             }
             enum "normal" {
               description "Trace normal events";
             }
             enum "general" {
               description "Trace general events";
             }
             enum "state" {
               description "Trace state transitions";
             }
             enum "policy" {
               description "Trace policy processing";
             }
             enum "task" {
               description "Trace routing protocol task processing";
             }
             enum "timer" {
               description "Trace routing protocol timer processing";
             }
             enum "all" {
               description "Trace everything";
             }
           }
         }
         leaf send {
           description "Trace transmitted packets";
           type empty;
         }
         leaf receive {
           description "Trace received packets";
           type empty;
         }
         leaf detail {
           description "Trace detailed information";
           type empty;
         }
         leaf disable {
           description "Disable this trace flag";
           type empty;
         }
       }
     }
     container spf-options {
       description "Configure options for SPF";
       uses apply-advanced;
       leaf delay {
         description "Time to wait before running an SPF";
         units "milliseconds";
         type union {
           type string {
             pattern "<.*>|$.*";
           }
           type uint32 {
             range "50 .. 8000";
           }
         }
       }
       leaf holddown {
         description "Time to hold down before running an SPF";
         units "milliseconds";
         type union {
           type string {
             pattern "<.*>|$.*";
           }
           type uint32 {
             range "2000 .. 20000";
           }
         }
       }
       leaf rapid-runs {
         description "Number of maximum rapid SPF runs before holddown";
         type union {
           type string {
             pattern "<.*>|$.*";
           }
           type uint32 {
             range "1 .. 10";
           }
         }
       }
       leaf no-ignore-our-externals {
         description "Do not ignore self-generated external and NSSA LSAs";
         type empty;
       }
     }
     leaf prefix-export-limit {
       description "Maximum number of prefixes that can be exported";
       type union {
         type string {
           pattern "<.*>|$.*";
         }
         type uint32 {
           range "0 .. 4294967295";
         }
       }
     }
     container rib-groups {
       description "Routing table groups for importing OSPF routes";
       uses apply-advanced;
       leaf inet {
         description "Name of the IPv4/v6 routing table group";
         junos:must "(\"routing-options rib-groups $$\")";
         junos:must-message "Referenced rib-groups must be defined";
         junos:must "(!(\".. topology $$={default} rib-group\"))";
         junos:must-message "rib-group cannot be used with topology default rib-group";
         type string;
       }
       leaf inet3 {
         description "Name of the IPv4/v6 inet.3 routing table group";
         junos:must "(\"routing-options rib-groups $$\")";
         junos:must-message "Referenced rib-groups must be defined";
         junos:must "(!(\".. topology $$={default} rib-group\"))";
         junos:must-message "rib-group cannot be used with topology default rib-group";
         type string;
       }
     }
     leaf job-stats {
       description "Collect job statistics";
       type empty;
     }
     container overload {
       presence "enable overload";
       description "Set the overload mode (repel transit traffic)";
       uses apply-advanced;
       leaf timeout {
         description "Time after which overload mode is reset";
         units "seconds";
         type union {
           type string {
             pattern "<.*>|$.*";
           }
           type uint32 {
             range "60 .. 3600";
           }
         }
       }
       leaf allow-route-leaking {
         description "Allow routes to be leaked when overload is configured";
         type empty;
       }
       leaf stub-network {
         description "Advertise Stub Network with maximum metric";
         type empty;
       }
       leaf intra-area-prefix {
         description "Advertise Intra Area Prefix with maximum metric";
         type empty;
       }
       leaf as-external {
         description "Advertise As External with maximum usable metric";
         type empty;
       }
     }
     container database-protection {
       presence "enable database-protection";
       description "Configure database protection attributes";
       uses apply-advanced;
       leaf maximum-lsa {
         description "Maximum allowed non self-generated LSAs";
         type union {
           type string {
             pattern "<.*>|$.*";
           }
           type uint32 {
             range "1 .. 1000000";
           }
         }
       }
       leaf warning-only {
         description "Emit only a warning when LSA maximum limit is exceeded";
         type empty;
       }
       leaf warning-threshold {
         description "Percentage of LSA maximum above which to trigger warning";
         units "percent";
         type union {
           type string {
             pattern "<.*>|$.*";
           }
           type uint8 {
             range "30 .. 100";
           }
         }
       }
       leaf ignore-count {
         description "Maximum number of times to go into ignore state";
         type union {
           type string {
             pattern "<.*>|$.*";
           }
           type uint8 {
             range "1 .. 32";
           }
         }
       }
       leaf ignore-time {
         description "Time to stay in ignore state and ignore all neighbors";
         units "seconds";
         type union {
           type string {
             pattern "<.*>|$.*";
           }
           type uint16 {
             range "30 .. 3600";
           }
         }
       }
       leaf reset-time {
         description "Time after which the ignore count gets reset to zero";
         units "seconds";
         type union {
           type string {
             pattern "<.*>|$.*";
           }
           type uint32 {
             range "60 .. 86400";
           }
         }
       }
     }
     container graceful-restart {
       description "Configure graceful restart attributes";
       uses apply-advanced;
       choice enable-disable {
         case case_1 {
           leaf disable {
             description "Disable OSPF graceful restart capability";
             type empty;
           }
         }
       }
       leaf restart-duration {
         description "Time for all neighbors to become full";
         units "seconds";
         type union {
           type string {
             pattern "<.*>|$.*";
           }
           type uint32 {
             range "1 .. 3600";
           }
         }
       }
       leaf notify-duration {
         description "Time to send all max-aged grace LSAs";
         units "seconds";
         type union {
           type string {
             pattern "<.*>|$.*";
           }
           type uint32 {
             range "1 .. 3600";
           }
         }
       }
       container helper-disable {
         presence "enable helper-disable";
         description "Disable graceful restart helper capability";
         uses apply-advanced;
         choice disable-choices {
           case case_1 {
             leaf standard {
               description "Disable helper-mode for rfc3623 based GR";
               type empty;
             }
           }
           case case_2 {
             leaf restart-signaling {
               description "Disable helper mode for restart-signaling ";
               type empty;
             }
           }
           case case_3 {
             leaf both {
               description "Disable helper mode for both the types of GR";
               type empty;
             }
           }
         }
       }
       leaf no-strict-lsa-checking {
         description "Do not abort graceful helper mode upon LSA changes";
         junos:must "(!(\".. helper-disable\"))";
         junos:must-message "To configure no-strict-lsa-checking, helper-disable must not be set";
         type empty;
       }
     }
     leaf route-type-community {
       description "Specify BGP extended community value to encode OSPF route type";
       type enumeration {
         enum "iana" {
           description "BGP extended community value used is 0x0306";
         }
         enum "vendor" {
           description "Vendor BGP extended community value used is 0x8000";
         }
       }
     }
     container domain-id {
       description "Configure domain ID";
       choice domain_id_or_disable {
         case case_1 {
           leaf domain-id {
             description "Domain ID";
             type string;
           }
         }
         case case_2 {
           leaf disable {
             description "Disable domain ID";
             type empty;
           }
         }
       }
     }
     choice domain_vpn_tag_or_disable {
       case case_1 {
         leaf domain-vpn-tag {
           description "Domain VPN tag for external LSA";
           type union {
             type string {
               pattern "<.*>|$.*";
             }
             type uint32 {
               range "0 .. 4294967295";
             }
           }
         }
       }
       case case_2 {
         leaf no-domain-vpn-tag {
           description "Disable domain VPN tag";
           type empty;
         }
       }
     }
     leaf preference {
       description "Preference of internal routes";
       type union {
         type uint32;
         type string {
           pattern "<.*>|$.*";
         }
       }
     }
     leaf external-preference {
       description "Preference of external routes";
       type union {
         type uint32;
         type string {
           pattern "<.*>|$.*";
         }
       }
     }
     leaf labeled-preference {
       description "Preference of labeled routes";
       type union {
         type uint32;
         type string {
           pattern "<.*>|$.*";
         }
       }
     }
     leaf-list export {
       ordered-by user;
       description "Export policy";
       type jt:policy-algebra;
     }
     leaf-list import {
       ordered-by user;
       description "Import policy (for external routes or setting priority)";
       type jt:policy-algebra;
     }
     leaf reference-bandwidth {
       description "Bandwidth for calculating metric defaults";
       type string;
     }
     leaf lsa-refresh-interval {
       description "LSA refresh interval (minutes)";
       default "50";
       type union {
         type string {
           pattern "<.*>|$.*";
         }
         type uint32 {
           range "25 .. 50";
         }
       }
     }
     leaf spf-delay {
       description "Time to wait before running an SPF";
       status deprecated;
       units "milliseconds";
       junos:must "(!(\".. spf-options delay\"))";
       junos:must-message "You can only configure either spf-delay or delay under spf-options";
       type union {
         type string {
           pattern "<.*>|$.*";
         }
         type uint32 {
           range "50 .. 8000";
         }
       }
     }
     leaf no-rfc-1583 {
       description "Disable RFC1583 compatibility";
       type empty;
     }
     leaf forwarding-address-to-broadcast {
       description "Set forwarding address in Type 5 LSA in broadcast network";
       type empty;
     }
     choice nssa-abr-option {
       case case_1 {
         leaf no-nssa-abr {
           description "Disable full NSSA functionality at ABR";
           type empty;
         }
       }
     }
     container sham-link {
       presence "enable sham-link";
       description "Configure parameters for sham links";
       uses apply-advanced;
       leaf local {
         description "Local sham link endpoint address";
         type jt:ipaddr;
       }
       leaf no-advertise-local {
         description "Don't advertise local sham link endpoint as stub in router LSA";
         status deprecated;
         type empty;
       }
     }
   }
   grouping juniper-ospf-authentication {
     description "Authentication information";
     uses apply-advanced;
     choice authentication-type {
       case case_1 {
         leaf simple-password {
           description "Authentication key";
           type jt:unreadable;
         }
       }
       case case_2 {
         list md5 {
           key name;
           ordered-by user;
           description "MD5 authentication key";
           leaf name {
             description "Key ID for MD5 authentication";
             type union {
               type string {
                 pattern "<.*>|$.*";
               }
               type uint32 {
                 range "0 .. 255";
               }
             }
           }
           leaf key {
             description "MD5 authentication key value";
             type jt:unreadable;
           }
           leaf start-time {
             description "Start time for key transmission (YYYY-MM-DD.HH:MM)";
             type jt:time;
           }
         }
       }
     }
   }
   grouping juniper-protocols-ospf3 {
     list realm {
       key name;
       ordered-by user;
       description "OSPFv3 realm configuration";
       leaf name {
         description "OSPFv3 realm name";
         type enumeration {
           enum "ipv6-unicast" {
             description "IPv6 unicast realm";
           }
           enum "ipv6-multicast" {
             description "IPv6 multicast realm";
           }
           enum "ipv4-unicast" {
             description "IPv4 unicast realm";
           }
           enum "ipv4-multicast" {
             description "IPv4 multicast realm";
           }
         }
       }
       uses apply-advanced;
       list topology {
         key name;
         ordered-by user;
         description "Topology parameters";
         leaf name {
           description "Topology name";
           type string;
         }
         uses apply-advanced;
         leaf disable {
           description "Disable this topology";
           type empty;
         }
         leaf topology-id {
           description "Topology identifier";
           type union {
             type string {
               pattern "<.*>|$.*";
             }
             type uint8 {
               range "32 .. 127";
             }
           }
         }
         leaf overload {
           description "Set the overload mode (repel transit traffic)";
           type empty;
         }
         leaf rib-group {
           description "Routing table group for importing routes";
           junos:must "(\"routing-options rib-groups $$\")";
           junos:must-message "Referenced rib-group must be defined";
           type string;
         }
         container spf-options {
           description "Configure options for SPF";
           uses apply-advanced;
           leaf delay {
             description "Time to wait before running an SPF";
             units "milliseconds";
             type union {
               type string {
                 pattern "<.*>|$.*";
               }
               type uint32 {
                 range "50 .. 8000";
               }
             }
           }
           leaf holddown {
             description "Time to hold down before running an SPF";
             units "milliseconds";
             type union {
               type string {
                 pattern "<.*>|$.*";
               }
               type uint32 {
                 range "2000 .. 20000";
               }
             }
           }
           leaf rapid-runs {
             description "Number of maximum rapid SPF runs before holddown";
             type union {
               type string {
                 pattern "<.*>|$.*";
               }
               type uint32 {
                 range "1 .. 10";
               }
             }
           }
           leaf no-ignore-our-externals {
             description "Do not ignore self-generated external and NSSA LSAs";
             type empty;
           }
         }
         container backup-spf-options {
           description "Configure options for backup SPF";
           uses apply-advanced;
           container remote-backup-calculation {
             presence "enable remote-backup-calculation";
             junos:must "(!(\"protocols ospf backup-spf-options use-post-convergence-lfa\"))";
             junos:must-message "Not allowed with 'protocols ospf backup-spf-options use-post-convergence-lfa'";
             description "Calculate Remote LFA backup nexthops";
             uses apply-advanced;
             container pq-nodes-nearest-to-source {
               description "PQ nodes selection based upon nearest to source";
               uses apply-advanced;
               leaf percent {
                 description "Selection percentage for nearest to source";
                 type union {
                   type string {
                     pattern "<.*>|$.*";
                   }
                   type uint32 {
                     range "10 .. 100";
                   }
                 }
               }
             }
           }
           container use-post-convergence-lfa {
             presence "enable use-post-convergence-lfa";
             junos:must "(\"protocols ospf source-packet-routing\")";
             junos:must-message "Configuration of 'protocols ospf source-packet-routing' is required";
             description "Calculate post-convergence backup paths";
             uses apply-advanced;
             leaf maximum-labels {
               description "Maximum number of labels installed for post-convergence paths";
               type union {
                 type string {
                   pattern "<.*>|$.*";
                 }
                 type uint32 {
                   range "2 .. 8";
                 }
               }
             }
             leaf maximum-backup-paths {
               description "Maximum number of equal-cost post-convergence paths installed";
               type union {
                 type string {
                   pattern "<.*>|$.*";
                 }
                 type uint32 {
                   range "1 .. 8";
                 }
               }
             }
           }
           leaf use-source-packet-routing {
             description "Use spring backup paths for inet.0 routes";
             junos:must "(\".. .. source-packet-routing\")";
             junos:must-message "Configuration of 'protocols ospf source-packet-routing' is required";
             junos:must "(!(\".. remote-backup-calculation\"))";
             junos:must-message "Not allowed with 'protocols ospf backup-spf-options remote-backup-calculation'";
             type empty;
           }
           leaf disable {
             description "Do not run backup SPF";
             junos:must "(!(\"protocols ospf backup-spf-options use-post-convergence-lfa\"))";
             junos:must-message "Not allowed with 'protocols ospf backup-spf-options use-post-convergence-lfa'";
             type empty;
           }
           leaf no-install {
             description "Do not install backup nexthops into the RIB";
             type empty;
           }
           leaf downstream-paths-only {
             description "Use only downstream backup paths";
             junos:must "(!(\"protocols ospf backup-spf-options use-post-convergence-lfa\"))";
             junos:must-message "Not allowed with 'protocols ospf backup-spf-options use-post-convergence-lfa'";
             type empty;
           }
           container per-prefix-calculation {
             junos:must "(!(\"protocols ospf backup-spf-options use-post-convergence-lfa\"))";
             junos:must-message "Not allowed with 'protocols ospf backup-spf-options use-post-convergence-lfa'";
             description "Calculate backup nexthops for non-best prefix originators";
             uses apply-advanced;
             leaf stubs {
               description "Per prefix calculation for stubs only";
               type empty;
             }
             leaf summary {
               description "Per prefix calculation for summary originators only";
               type empty;
             }
             leaf externals {
               description "Per prefix calculation for externals";
               type empty;
             }
             leaf all {
               description "Per prefix calculation for all";
               type empty;
             }
           }
           leaf node-link-degradation {
             description "Degrade to link protection when nodelink protection not available";
             junos:must "(!(\"protocols ospf backup-spf-options use-post-convergence-lfa\"))";
             junos:must-message "Not allowed with 'protocols ospf backup-spf-options use-post-convergence-lfa'";
             type empty;
           }
         }
         leaf prefix-export-limit {
           description "Maximum number of prefixes that can be exported";
           type union {
             type string {
               pattern "<.*>|$.*";
             }
             type uint32 {
               range "0 .. 4294967295";
             }
           }
         }
       }
       container backup-spf-options {
         description "Configure options for backup SPF";
         uses apply-advanced;
         container remote-backup-calculation {
           presence "enable remote-backup-calculation";
           junos:must "(!(\"protocols ospf backup-spf-options use-post-convergence-lfa\"))";
           junos:must-message "Not allowed with 'protocols ospf backup-spf-options use-post-convergence-lfa'";
           description "Calculate Remote LFA backup nexthops";
           uses apply-advanced;
           container pq-nodes-nearest-to-source {
             description "PQ nodes selection based upon nearest to source";
             uses apply-advanced;
             leaf percent {
               description "Selection percentage for nearest to source";
               type union {
                 type string {
                   pattern "<.*>|$.*";
                 }
                 type uint32 {
                   range "10 .. 100";
                 }
               }
             }
           }
         }
         container use-post-convergence-lfa {
           presence "enable use-post-convergence-lfa";
           junos:must "(\"protocols ospf source-packet-routing\")";
           junos:must-message "Configuration of 'protocols ospf source-packet-routing' is required";
           description "Calculate post-convergence backup paths";
           uses apply-advanced;
           leaf maximum-labels {
             description "Maximum number of labels installed for post-convergence paths";
             type union {
               type string {
                 pattern "<.*>|$.*";
               }
               type uint32 {
                 range "2 .. 8";
               }
             }
           }
           leaf maximum-backup-paths {
             description "Maximum number of equal-cost post-convergence paths installed";
             type union {
               type string {
                 pattern "<.*>|$.*";
               }
               type uint32 {
                 range "1 .. 8";
               }
             }
           }
         }
         leaf use-source-packet-routing {
           description "Use spring backup paths for inet.0 routes";
           junos:must "(\".. .. source-packet-routing\")";
           junos:must-message "Configuration of 'protocols ospf source-packet-routing' is required";
           junos:must "(!(\".. remote-backup-calculation\"))";
           junos:must-message "Not allowed with 'protocols ospf backup-spf-options remote-backup-calculation'";
           type empty;
         }
         leaf disable {
           description "Do not run backup SPF";
           junos:must "(!(\"protocols ospf backup-spf-options use-post-convergence-lfa\"))";
           junos:must-message "Not allowed with 'protocols ospf backup-spf-options use-post-convergence-lfa'";
           type empty;
         }
         leaf no-install {
           description "Do not install backup nexthops into the RIB";
           type empty;
         }
         leaf downstream-paths-only {
           description "Use only downstream backup paths";
           junos:must "(!(\"protocols ospf backup-spf-options use-post-convergence-lfa\"))";
           junos:must-message "Not allowed with 'protocols ospf backup-spf-options use-post-convergence-lfa'";
           type empty;
         }
         container per-prefix-calculation {
           junos:must "(!(\"protocols ospf backup-spf-options use-post-convergence-lfa\"))";
           junos:must-message "Not allowed with 'protocols ospf backup-spf-options use-post-convergence-lfa'";
           description "Calculate backup nexthops for non-best prefix originators";
           uses apply-advanced;
           leaf stubs {
             description "Per prefix calculation for stubs only";
             type empty;
           }
           leaf summary {
             description "Per prefix calculation for summary originators only";
             type empty;
           }
           leaf externals {
             description "Per prefix calculation for externals";
             type empty;
           }
           leaf all {
             description "Per prefix calculation for all";
             type empty;
           }
         }
         leaf node-link-degradation {
           description "Degrade to link protection when nodelink protection not available";
           junos:must "(!(\"protocols ospf backup-spf-options use-post-convergence-lfa\"))";
           junos:must-message "Not allowed with 'protocols ospf backup-spf-options use-post-convergence-lfa'";
           type empty;
         }
       }
       container traffic-engineering {
         presence "enable traffic-engineering";
         description "Configure traffic engineering attributes";
         uses apply-advanced;
         leaf no-topology {
           description "Disable dissemination of TE link-state topology information";
           type empty;
         }
         leaf multicast-rpf-routes {
           description "Install routes for multicast RPF checks into inet.2";
           junos:must "(!(\".. .. topology $$={ipv4-multicast}\"))";
           junos:must-message "multicast-rpf-routes cannot be used with topology ipv4-multicast";
           junos:must "(\".. shortcuts\")";
           junos:must-message "multicast-rpf-routes cannot be used without shortcuts";
           type empty;
         }
         leaf l3-unicast-topology {
           description "Download IGP topology into TED";
           type empty;
         }
         container ignore-lsp-metrics {
           presence "enable ignore-lsp-metrics";
           description "Ignore label-switched path metrics when doing shortcuts";
           uses apply-advanced;
           leaf unconfigured-only {
             description "Ignore lsp metrics for unconfigured only";
             type empty;
           }
         }
         container shortcuts {
           presence "enable shortcuts";
           description "Use label-switched paths as next hops, if possible";
           uses apply-advanced;
           leaf ignore-lsp-metrics {
             description "Ignore label-switched path metrics when doing shortcuts";
             status deprecated;
             type empty;
           }
           leaf lsp-metric-into-summary {
             description "Advertise LSP metric into summary LSAs";
             type empty;
           }
           list family {
             key name;
             ordered-by user;
             description "Address family specific traffic-engineering attributes";
             leaf name {
               type enumeration {
                 enum "inet" {
                   description "IPv4 family";
                 }
                 enum "inet-mpls" {
                   description "IPv4-MPLS family";
                 }
               }
             }
             uses apply-advanced;
           }
         }
         leaf advertise-unnumbered-interfaces {
           description "Advertise unnumbered interfaces";
           type empty;
         }
         leaf credibility-protocol-preference {
           description "TED protocol credibility follows protocol preference";
           type empty;
         }
         container advertisement {
           description "Advertise TE parameters even if RSVP is not turned on";
           uses apply-advanced;
           leaf always {
             description "Advertise TE parameters in TE LSAs";
             type empty;
           }
         }
       }
       container source-packet-routing {
         presence "enable source-packet-routing";
         junos:must "(!(\".. .. .. protocols mpls disable\"))";
         junos:must-message "SPRING configuration is not allowed with 'protocols mpls disable'";
         junos:must "(\".. .. .. protocols mpls \")";
         junos:must-message "SPRING configuration is not allowed without 'protocols mpls'";
         description "Enable source packet routing (SPRING)";
         uses apply-advanced;
         container adjacency-segment {
           description "Attributes for adjacency segments in spring";
           uses apply-advanced;
           leaf hold-time {
             description "Retain time of Adjacency segment after isolating from an interface";
             type union {
               type string {
                 pattern "<.*>|$.*";
               }
               type uint32 {
                 range "180000 .. 900000";
               }
             }
           }
         }
         leaf-list prefix-segment {
           ordered-by user;
           description "Prefix Segment policy";
           type jt:policy-algebra;
         }
         leaf explicit-null {
           description "Set E and P bits in all Prefix SID advertisements";
           type empty;
         }
         container node-segment {
           presence "enable node-segment";
           description "Enable support for Node segments in SPRING";
           uses apply-advanced;
           leaf ipv4-index {
             description "Set ipv4 node segment index";
             type union {
               type string {
                 pattern "<.*>|$.*";
               }
               type uint32 {
                 range "0 .. 199999";
               }
             }
           }
           leaf index-range {
             description "Set range of node segment indices allowed";
             type union {
               type string {
                 pattern "<.*>|$.*";
               }
               type uint32 {
                 range "32 .. 16385";
               }
             }
           }
         }
         container srgb {
           junos:must "(!(\".. node-segment index-range\"))";
           junos:must-message "Can not be configured with node-segment index-range";
           description "Set the SRGB global block in SPRING";
           leaf start-label {
             description "Start range for SRGB label block";
             type union {
               type string {
                 pattern "<.*>|$.*";
               }
               type uint32;
             }
           }
           leaf index-range {
             description "Index to the SRGB start label block";
             type union {
               type string {
                 pattern "<.*>|$.*";
               }
               type uint32;
             }
           }
         }
         leaf mapping-server {
           description "Mapping server name";
           junos:must "(\".. node-segment\")";
           junos:must-message "protocols ospf source-packet-routing node-segment must be defined";
           junos:must "(\"routing-options source-packet-routing mapping-server-entry $$\")";
           junos:must-message "Referenced source-packet-routing mapping-server-entry must be defined";
           type string;
         }
         leaf install-prefix-sid-for-best-route {
           description "For best route install a exact prefix sid route";
           type empty;
         }
         leaf ldp-stitching {
           description "Enable SR to LDP stitching";
           type empty;
         }
         leaf-list flex-algorithm {
           description "Flex-algorithms we would like to participate in";
           type union {
             type string {
               pattern "<.*>|$.*";
             }
             type uint32 {
               range "128 .. 255";
             }
           }
           max-elements 16;
         }
       }
       list area {
         key name;
         ordered-by user;
         description "Configure an OSPF area";
         leaf name {
           description "Area ID";
           type jt:areaid;
         }
         uses apply-advanced;
         choice stub-option {
           case case_1 {
             container stub {
               presence "enable stub";
               description "Configure a stub area";
               leaf default-metric {
                 description "Metric for the default route in this stub area";
                 type union {
                   type string {
                     pattern "<.*>|$.*";
                   }
                   type uint32 {
                     range "1 .. 16777215";
                   }
                 }
               }
               choice summaries-choice {
                 leaf summaries {
                   description "Flood summary LSAs into this stub area";
                   type empty;
                 }
                 leaf no-summaries {
                   description "Don't flood summary LSAs into this stub area";
                   type empty;
                 }
               }
             }
           }
           case case_2 {
             container nssa {
               presence "enable nssa";
               description "Configure a not-so-stubby area";
               uses apply-advanced;
               container default-lsa {
                 presence "enable default-lsa";
                 description "Configure a default LSA";
                 uses apply-advanced;
                 leaf default-metric {
                   description "Metric for the default route in this area";
                   type union {
                     type string {
                       pattern "<.*>|$.*";
                     }
                     type uint32 {
                       range "1 .. 16777215";
                     }
                   }
                 }
                 leaf metric-type {
                   description "External metric type for the default type 7 LSA";
                   type union {
                     type string {
                       pattern "<.*>|$.*";
                     }
                     type uint32 {
                       range "1 .. 2";
                     }
                   }
                 }
                 leaf type-7 {
                   description "Flood type 7 default LSA if no-summaries is configured";
                   type empty;
                 }
               }
               leaf default-metric {
                 description "Metric for the default route in this area";
                 status deprecated;
                 type union {
                   type string {
                     pattern "<.*>|$.*";
                   }
                   type uint32 {
                     range "1 .. 16777215";
                   }
                 }
               }
               leaf metric-type {
                 description "External metric type for the default type 7 LSA";
                 status deprecated;
                 type union {
                   type string {
                     pattern "<.*>|$.*";
                   }
                   type uint32 {
                     range "1 .. 2";
                   }
                 }
               }
               choice summaries-choice {
                 leaf summaries {
                   description "Flood summary LSAs into this NSSA area";
                   type empty;
                 }
                 leaf no-summaries {
                   description "Don't flood summary LSAs into this NSSA area";
                   type empty;
                 }
               }
               list area-range {
                 key name;
                 ordered-by user;
                 description "Configure NSSA area ranges";
                 leaf name {
                   description "Range to summarize NSSA routes in this area";
                   type jt:ipprefix;
                 }
                 uses apply-advanced;
                 leaf restrict {
                   description "Restrict advertisement of this area range";
                   type empty;
                 }
                 leaf exact {
                   description "Enforce exact match for advertisement of this area range";
                   type empty;
                 }
                 container override-metric {
                   presence "enable override-metric";
                   description "Override the dynamic metric for this area-range";
                   uses apply-advanced;
                   leaf metric {
                     description "Metric value";
                     type union {
                       type string {
                         pattern "<.*>|$.*";
                       }
                       type uint32 {
                         range "1 .. 16777215";
                       }
                     }
                   }
                   leaf metric-type {
                     description "Set the metric type for the override metric";
                     default "1";
                     type union {
                       type string {
                         pattern "<.*>|$.*";
                       }
                       type uint32 {
                         range "1 .. 2";
                       }
                     }
                   }
                 }
               }
             }
           }
         }
         list area-range {
           key name;
           ordered-by user;
           description "Configure area ranges";
           leaf name {
             description "Range to summarize routes in this area";
             type jt:ipprefix;
           }
           uses apply-advanced;
           leaf restrict {
             description "Restrict advertisement of this area range";
             type empty;
           }
           leaf exact {
             description "Enforce exact match for advertisement of this area range";
             type empty;
           }
           leaf override-metric {
             description "Override the dynamic metric for this area-range";
             type union {
               type string {
                 pattern "<.*>|$.*";
               }
               type uint32 {
                 range "1 .. 16777215";
               }
             }
           }
         }
         leaf-list network-summary-export {
           ordered-by user;
           description "Export policy for Type 3 Summary LSAs";
           type jt:policy-algebra;
         }
         leaf-list network-summary-import {
           ordered-by user;
           description "Import policy for Type 3 Summary LSAs";
           type jt:policy-algebra;
         }
         leaf-list inter-area-prefix-export {
           ordered-by user;
           description "Export policy for Inter Area Prefix LSAs";
           type jt:policy-algebra;
         }
         leaf-list inter-area-prefix-import {
           ordered-by user;
           description "Import policy for Inter Area Prefix LSAs";
           type jt:policy-algebra;
         }
         leaf authentication-type {
           description "Authentication type";
           status deprecated;
           type enumeration {
             enum "none" {
               description "No authentication";
               status deprecated;
             }
             enum "simple" {
               description "Simple password authentication";
               status deprecated;
             }
             enum "md5" {
               description "MD5 authentication";
               status deprecated;
             }
           }
         }
         list virtual-link {
           key "neighbor-id transit-area";
           ordered-by user;
           description "Configure virtual links";
           junos:must "(\".. .. area $$={0.0.0.0}\")";
           junos:must-message "virtual link can be configured only under backbone area";
           leaf neighbor-id {
             description "Router ID of a virtual neighbor";
             type jt:ipv4addr;
           }
           leaf transit-area {
             description "Transit area in common with virtual neighbor";
             type jt:areaid;
           }
           uses apply-advanced;
           choice enable-disable {
             case case_1 {
               leaf disable {
                 description "Disable this virtual link";
                 type empty;
               }
             }
           }
           leaf retransmit-interval {
             description "Retransmission interval (seconds)";
             type union {
               type string {
                 pattern "<.*>|$.*";
               }
               type uint32 {
                 range "1 .. 65535";
               }
             }
           }
           leaf transit-delay {
             description "Transit delay (seconds)";
             type union {
               type string {
                 pattern "<.*>|$.*";
               }
               type uint32 {
                 range "1 .. 65535";
               }
             }
           }
           leaf hello-interval {
             description "Hello interval (seconds)";
             type union {
               type string {
                 pattern "<.*>|$.*";
               }
               type uint32 {
                 range "1 .. 255";
               }
             }
           }
           leaf dead-interval {
             description "Dead interval (seconds)";
             type union {
               type string {
                 pattern "<.*>|$.*";
               }
               type uint32 {
                 range "1 .. 65535";
               }
             }
           }
           leaf mtu {
             description "Maximum OSPF packet size";
             type union {
               type string {
                 pattern "<.*>|$.*";
               }
               type uint32 {
                 range "128 .. 65535";
               }
             }
           }
           choice auth {
             case case_1 {
               container authentication {
                 uses juniper-ospf-authentication;
               }
             }
             case case_2 {
               container authentication-key {
                 description "Authentication key";
                 status deprecated;
                 leaf keyname {
                   description "Authentication key value";
                   type jt:unreadable;
                 }
                 leaf key-id {
                   description "Key ID for MD5 authentication";
                   type union {
                     type string {
                       pattern "<.*>|$.*";
                     }
                     type uint32 {
                       range "0 .. 255";
                     }
                   }
                 }
               }
             }
           }
           leaf demand-circuit {
             description "Interface functions as a demand circuit";
             type empty;
           }
           leaf flood-reduction {
             description "Enable flood reduction";
             type empty;
           }
           leaf no-neighbor-down-notification {
             description "Don't inform other protocols about neighbor down events";
             type empty;
           }
           leaf ipsec-sa {
             description "IPSec security association name";
             junos:must "(!(any \".. .. interface <st*> ipsec-sa $$\"))";
             junos:must-message "Must not configure ipsec-sa for st0 interface";
             junos:must "(\"security ipsec security-association $$ manual\")";
             junos:must-message "Referenced IPSec security association must be a manual SA";
             junos:must "(\"security ipsec security-association $$ mode transport\")";
             junos:must-message "Referenced IPSec security association must be in transport mode";
             junos:must "(\"security ipsec security-association $$\")";
             junos:must-message "Referenced IPSec security association must be defined";
             type string {
               length "1 .. 32";
             }
           }
           list topology {
             key name;
             ordered-by user;
             description "Topology specific attributes";
             leaf name {
               description "Topology name";
               type string;
             }
             uses apply-advanced;
             leaf disable {
               description "Disable this topology";
               type empty;
             }
             leaf metric {
               description "Topology metric";
               type union {
                 type string {
                   pattern "<.*>|$.*";
                 }
                 type uint16 {
                   range "1 .. 65535";
                 }
               }
             }
             container bandwidth-based-metrics {
               junos:must "(\".. metric\")";
               junos:must-message "Metric must be configured";
               description "Configure bandwidth based metrics";
               uses apply-advanced;
               list bandwidth {
                 key name;
                 description "Bandwidth threshold";
                 leaf name {
                   type string;
                 }
                 leaf metric {
                   description "Metric associated with specified bandwidth";
                   type union {
                     type string {
                       pattern "<.*>|$.*";
                     }
                     type uint16 {
                       range "1 .. 65535";
                     }
                   }
                 }
               }
             }
           }
         }
         list sham-link-remote {
           key name;
           ordered-by user;
           description "Configure parameters for remote sham link endpoint";
           leaf name {
             description "Remote sham link endpoint address";
             junos:must "(!(\".. .. .. sham-link local $$\"))";
             junos:must-message "Local and remote sham link endpoint addresses must be different";
             junos:must "(\".. .. .. sham-link local\")";
             junos:must-message "Local sham link endpoint must be configured";
             type jt:ipaddr;
           }
           uses apply-advanced;
           leaf metric {
             description "Sham link metric";
             type union {
               type string {
                 pattern "<.*>|$.*";
               }
               type uint16 {
                 range "1 .. 65535";
               }
             }
           }
           leaf ipsec-sa {
             description "IPSec security association name";
             junos:must "(!(any \".. .. interface <st*> ipsec-sa $$\"))";
             junos:must-message "Must not configure ipsec-sa for st0 interface";
             junos:must "(\"security ipsec security-association $$ manual\")";
             junos:must-message "Referenced IPSec security association must be a manual SA";
             junos:must "(\"security ipsec security-association $$ mode transport\")";
             junos:must-message "Referenced IPSec security association must be in transport mode";
             junos:must "(\"security ipsec security-association $$\")";
             junos:must-message "Referenced IPSec security association must be defined";
             type string {
               length "1 .. 32";
             }
           }
           leaf demand-circuit {
             description "Interface functions as a demand circuit";
             type empty;
           }
           leaf flood-reduction {
             description "Enable flood reduction";
             type empty;
           }
           list topology {
             key name;
             ordered-by user;
             description "Topology specific attributes";
             leaf name {
               description "Topology name";
               type string;
             }
             uses apply-advanced;
             leaf disable {
               description "Disable this topology";
               type empty;
             }
             leaf metric {
               description "Topology metric";
               type union {
                 type string {
                   pattern "<.*>|$.*";
                 }
                 type uint16 {
                   range "1 .. 65535";
                 }
               }
             }
             container bandwidth-based-metrics {
               junos:must "(\".. metric\")";
               junos:must-message "Metric must be configured";
               description "Configure bandwidth based metrics";
               uses apply-advanced;
               list bandwidth {
                 key name;
                 description "Bandwidth threshold";
                 leaf name {
                   type string;
                 }
                 leaf metric {
                   description "Metric associated with specified bandwidth";
                   type union {
                     type string {
                       pattern "<.*>|$.*";
                     }
                     type uint16 {
                       range "1 .. 65535";
                     }
                   }
                 }
               }
             }
           }
         }
         list interface {
           key name;
           ordered-by user;
           description "Include an interface in this area";
           leaf name {
             description "Interface name";
             junos:must "((!(\".. interface-type nbma\") || (!((\"interfaces $$\" || any \"logical-systems <*> interfaces $$\")) || (any \"interfaces $$-IFL family inet address <*>\" || any \"logical-systems <*> interfaces $$-IFL family inet address <*>\"))))";
             junos:must-message "IPv4 address must be configured on the interface for nbma mode";
             type union {
               type jt:ipv4addr-or-interface;
               type string {
                 pattern "<.*>|$.*";
               }
             }
           }
           uses apply-advanced;
           choice enable-disable {
             case case_1 {
               leaf disable {
                 description "Disable OSPF on this interface";
                 type empty;
               }
             }
           }
           leaf interface-type {
             description "Type of interface";
             type enumeration {
               enum "nbma" {
                 description "Nonbroadcast multiaccess";
               }
               enum "p2mp" {
                 description "Point-to-multipoint NBMA";
               }
               enum "p2p" {
                 description "Point-to-point";
               }
               enum "p2mp-over-lan" {
                 description "Point-to-multipoint over LAN mode";
               }
             }
           }
           choice protection-type {
             case case_1 {
               leaf link-protection {
                 description "Protect interface from link faults only";
                 type empty;
               }
             }
             case case_2 {
               leaf node-link-protection {
                 description "Protect interface from both link and node faults";
                 type empty;
               }
             }
           }
           leaf no-eligible-backup {
             description "Not eligible to backup traffic from protected interfaces";
             type empty;
           }
           leaf no-eligible-remote-backup {
             description "Not eligible for Remote-LFA backup traffic from protected interfaces";
             type empty;
           }
           container passive {
             presence "enable passive";
             description "Do not run OSPF, but advertise it";
             uses apply-advanced;
             container traffic-engineering {
               description "Advertise TE link information";
               uses apply-advanced;
               leaf remote-node-id {
                 description "Remote address of the link";
                 type jt:ipaddr;
               }
               leaf remote-node-router-id {
                 description "TE Router-ID of the remote node";
                 junos:must "(\".. remote-node-id\")";
                 junos:must-message "remote-node-id must be configured";
                 type jt:ipv4addr;
               }
             }
           }
           leaf secondary {
             description "Treat interface as secondary";
             junos:must "(!(\" .. ipsec-sa\"))";
             junos:must-message "secondary interface cannot have ipsec-sa configured";
             junos:must "(!(\" .. dynamic-neighbors\"))";
             junos:must-message "secondary interface cannot have dynamic-neighbors configured";
             junos:must "(!(\" .. neighbor\"))";
             junos:must-message "secondary interface cannot have configured neighbors";
             junos:must "(!(\" .. interface-type p2mp\"))";
             junos:must-message "secondary interface cannot be set as type p2mp";
             junos:must "(!(\" .. interface-type nbma\"))";
             junos:must-message "secondary interface cannot be set as type nbma";
             junos:must "(!(\" .. passive\"))";
             junos:must-message "secondary interface cannot be configured passive";
             type empty;
           }
           leaf own-router-lsa {
             description "Generate a separate router LSA for this interface";
             type empty;
           }
           container bandwidth-based-metrics {
             junos:must "(\".. metric\")";
             junos:must-message "Metric must be configured";
             description "Configure bandwidth based metrics";
             uses apply-advanced;
             list bandwidth {
               key name;
               description "Bandwidth threshold";
               leaf name {
                 type string;
               }
               leaf metric {
                 description "Metric associated with specified bandwidth";
                 type union {
                   type string {
                     pattern "<.*>|$.*";
                   }
                   type uint16 {
                     range "1 .. 65535";
                   }
                 }
               }
             }
           }
           leaf metric {
             description "Interface metric";
             type union {
               type string {
                 pattern "<.*>|$.*";
               }
               type uint16 {
                 range "1 .. 65535";
               }
             }
           }
           leaf priority {
             description "Designated router priority";
             type union {
               type string {
                 pattern "<.*>|$.*";
               }
               type uint32 {
                 range "0 .. 255";
               }
             }
           }
           leaf retransmit-interval {
             description "Retransmission interval (seconds)";
             type union {
               type string {
                 pattern "<.*>|$.*";
               }
               type uint32 {
                 range "1 .. 65535";
               }
             }
           }
           leaf transit-delay {
             description "Transit delay (seconds)";
             type union {
               type string {
                 pattern "<.*>|$.*";
               }
               type uint32 {
                 range "1 .. 65535";
               }
             }
           }
           leaf hello-interval {
             description "Hello interval (seconds)";
             type union {
               type string {
                 pattern "<.*>|$.*";
               }
               type uint32 {
                 range "1 .. 255";
               }
             }
           }
           leaf dead-interval {
             description "Dead interval (seconds)";
             type union {
               type string {
                 pattern "<.*>|$.*";
               }
               type uint32 {
                 range "1 .. 65535";
               }
             }
           }
           leaf mtu {
             description "Maximum OSPF packet size";
             type union {
               type string {
                 pattern "<.*>|$.*";
               }
               type uint32 {
                 range "128 .. 65535";
               }
             }
           }
           choice auth {
             case case_1 {
               container authentication {
                 uses juniper-ospf-authentication;
               }
             }
             case case_2 {
               container authentication-key {
                 description "Authentication key";
                 status deprecated;
                 leaf keyname {
                   description "Authentication key value";
                   type jt:unreadable;
                 }
                 leaf key-id {
                   description "Key ID for MD5 authentication";
                   type union {
                     type string {
                       pattern "<.*>|$.*";
                     }
                     type uint32 {
                       range "0 .. 255";
                     }
                   }
                 }
               }
             }
           }
           leaf demand-circuit {
             description "Interface functions as a demand circuit";
             type empty;
           }
           leaf flood-reduction {
             description "Enable flood reduction";
             type empty;
           }
           leaf no-neighbor-down-notification {
             description "Don't inform other protocols about neighbor down events";
             type empty;
           }
           leaf ipsec-sa {
             description "IPSec security association name";
             junos:must "(!(any \".. .. interface <st*> ipsec-sa $$\"))";
             junos:must-message "Must not configure ipsec-sa for st0 interface";
             junos:must "(\"security ipsec security-association $$ manual\")";
             junos:must-message "Referenced IPSec security association must be a manual SA";
             junos:must "(\"security ipsec security-association $$ mode transport\")";
             junos:must-message "Referenced IPSec security association must be in transport mode";
             junos:must "(\"security ipsec security-association $$\")";
             junos:must-message "Referenced IPSec security association must be defined";
             type string {
               length "1 .. 32";
             }
           }
           list topology {
             key name;
             ordered-by user;
             description "Topology specific attributes";
             leaf name {
               description "Topology name";
               type string;
             }
             uses apply-advanced;
             leaf disable {
               description "Disable this topology";
               type empty;
             }
             leaf metric {
               description "Topology metric";
               type union {
                 type string {
                   pattern "<.*>|$.*";
                 }
                 type uint16 {
                   range "1 .. 65535";
                 }
               }
             }
             container bandwidth-based-metrics {
               junos:must "(\".. metric\")";
               junos:must-message "Metric must be configured";
               description "Configure bandwidth based metrics";
               uses apply-advanced;
               list bandwidth {
                 key name;
                 description "Bandwidth threshold";
                 leaf name {
                   type string;
                 }
                 leaf metric {
                   description "Metric associated with specified bandwidth";
                   type union {
                     type string {
                       pattern "<.*>|$.*";
                     }
                     type uint16 {
                       range "1 .. 65535";
                     }
                   }
                 }
               }
             }
           }
           leaf transmit-interval {
             description "OSPF packet transmit interval (milliseconds)";
             status deprecated;
             type union {
               type string {
                 pattern "<.*>|$.*";
               }
               type uint32 {
                 range "1 .. 4294967295";
               }
             }
           }
           container bfd-liveness-detection {
             description "Bidirectional Forwarding Detection options";
             uses apply-advanced;
             leaf version {
               description "BFD protocol version number";
               default "automatic";
               type enumeration {
                 enum "0" {
                   description "BFD version 0 (deprecated)";
                 }
                 enum "1" {
                   description "BFD version 1";
                 }
                 enum "automatic" {
                   description "Choose BFD version automatically";
                 }
               }
             }
             leaf minimum-interval {
               description "Minimum transmit and receive interval";
               units "milliseconds";
               type union {
                 type string {
                   pattern "<.*>|$.*";
                 }
                 type uint32 {
                   range "1 .. 255000";
                 }
               }
             }
             leaf minimum-transmit-interval {
               description "Minimum transmit interval";
               status deprecated;
               units "milliseconds";
               type union {
                 type string {
                   pattern "<.*>|$.*";
                 }
                 type uint32 {
                   range "1 .. 255000";
                 }
               }
             }
             leaf minimum-receive-interval {
               description "Minimum receive interval";
               units "milliseconds";
               type union {
                 type string {
                   pattern "<.*>|$.*";
                 }
                 type uint32 {
                   range "1 .. 255000";
                 }
               }
             }
             leaf multiplier {
               description "Detection time multiplier";
               default "3";
               type union {
                 type string {
                   pattern "<.*>|$.*";
                 }
                 type uint32 {
                   range "1 .. 255";
                 }
               }
             }
             choice adaptation-choice {
               case case_1 {
                 leaf no-adaptation {
                   description "Disable adaptation";
                   type empty;
                 }
               }
             }
             container transmit-interval {
               description "Transmit-interval options";
               uses apply-advanced;
               leaf minimum-interval {
                 description "Minimum transmit interval";
                 units "milliseconds";
                 type union {
                   type string {
                     pattern "<.*>|$.*";
                   }
                   type uint32 {
                     range "1 .. 255000";
                   }
                 }
               }
               leaf threshold {
                 description "High transmit interval triggering a trap";
                 units "milliseconds";
                 type union {
                   type uint32;
                   type string {
                     pattern "<.*>|$.*";
                   }
                 }
               }
             }
             container detection-time {
               description "Detection-time options";
               uses apply-advanced;
               leaf threshold {
                 description "High detection-time triggering a trap";
                 units "milliseconds";
                 type union {
                   type uint32;
                   type string {
                     pattern "<.*>|$.*";
                   }
                 }
               }
             }
             container authentication {
               description "Authentication options";
               uses apply-advanced;
               leaf key-chain {
                 description "Key chain name";
                 junos:must "(\".. algorithm\")";
                 junos:must-message "May not be configured without algorithm";
                 junos:must "(\"security authentication-key-chains key-chain $$\")";
                 junos:must-message "Referenced key-chain must be defined";
                 type string;
               }
               leaf algorithm {
                 description "Algorithm name";
                 junos:must "(\".. key-chain\")";
                 junos:must-message "May not be configured without key-chain";
                 type enumeration {
                   enum "simple-password" {
                     description "Simple password";
                   }
                   enum "keyed-md5" {
                     description "Keyed message Digest 5";
                   }
                   enum "meticulous-keyed-md5" {
                     description "Meticulous keyed message Digest 5";
                   }
                   enum "keyed-sha-1" {
                     description "Keyed secure hash algorithm (SHA1) ";
                   }
                   enum "meticulous-keyed-sha-1" {
                     description "Meticulous keyed secure hash algorithm (SHA1) ";
                   }
                 }
               }
               leaf loose-check {
                 description "Verify authentication only if authentication is negotiated";
                 type empty;
               }
             }
             leaf full-neighbors-only {
               description "Setup BFD sessions only to Full neighbors";
               type empty;
             }
             leaf holddown-interval {
               description "Time to hold the session-UP notification to the client";
               units "milliseconds";
               type union {
                 type string {
                   pattern "<.*>|$.*";
                 }
                 type uint32 {
                   range "0 .. 255000";
                 }
               }
             }
           }
           leaf dynamic-neighbors {
             description "Learn neighbors dynamically on a p2mp interface";
             junos:must "(\" .. interface-type p2mp\")";
             junos:must-message "dynamic-neighbors option can be set only if the interface type is p2mp";
             type empty;
           }
           leaf no-advertise-adjacency-segment {
             description "Do not advertise an adjacency segment for this interface";
             type empty;
           }
           list neighbor {
             key name;
             ordered-by user;
             description "NBMA neighbor";
             junos:must "(!(\" .. dynamic-neighbors\"))";
             junos:must-message "Neighbors cannot be specified manually if dynamic-neighbors is set";
             leaf name {
               description "Address of neighbor";
               type jt:ipaddr;
             }
             leaf eligible {
               description "Eligible to be DR on an NBMA network";
               type empty;
             }
           }
           leaf poll-interval {
             description "Poll interval for NBMA interfaces";
             type union {
               type string {
                 pattern "<.*>|$.*";
               }
               type uint32 {
                 range "1 .. 65535";
               }
             }
           }
           leaf no-interface-state-traps {
             description "Do not send interface state change traps";
             type empty;
           }
           leaf strict-bfd {
             description "Enable strict bfd over this interface";
             junos:must "(\" .. bfd-liveness-detection\")";
             junos:must-message "strict bfd cannot be configured without bfd.";
             junos:must "(!(\" .. bfd-liveness-detection full-neighbors-only\"))";
             junos:must-message "full-neighbors-only and strict-bfd cannot be configured together";
             type empty;
           }
           container post-convergence-lfa {
             presence "enable post-convergence-lfa";
             junos:must "(\"protocols ospf backup-spf-options use-post-convergence-lfa\")";
             junos:must-message "Not allowed without 'protocols ospf backup-spf-options use-post-convergence-lfa'";
             description "Protect interface using post-convergence backup path";
             uses apply-advanced;
             container node-protection {
               presence "enable node-protection";
               description "Compute backup path assuming node failure";
               uses apply-advanced;
               leaf cost {
                 description "Cost for node protection";
                 type union {
                   type string {
                     pattern "<.*>|$.*";
                   }
                   type uint16 {
                     range "1 .. 65535";
                   }
                 }
               }
             }
             leaf srlg-protection {
               description "Compute backup path assuming SRLG failure";
               type empty;
             }
             leaf fate-sharing-protection {
               description "Compute backup path assuming fate-sharing group failure";
               type empty;
             }
           }
           leaf te-metric {
             description "Traffic engineering metric";
             type union {
               type string {
                 pattern "<.*>|$.*";
               }
               type uint32 {
                 range "1 .. 4294967295";
               }
             }
           }
           container ldp-synchronization {
             description "Advertise maximum metric until LDP is operational";
             presence "enable ldp-synchronization";
             uses ldp-sync-obj;
           }
           container ipv4-adjacency-segment {
             junos:must "(!(\".. no-advertise-adjacency-segment\"))";
             junos:must-message "ipv4-adjacency-segment can't be configured if no-advertise-adjacency-segment is configured in the same interface";
             description "Configure ipv4 adjacency segment";
             uses apply-advanced;
             container protected {
               description "Adjacency SID is eligible for protection";
               choice adjsid-type {
                 case case_1 {
                   container index {
                     description "Adjacency SID indexed from SRGB";
                     leaf index-number {
                       type union {
                         type string {
                           pattern "<.*>|$.*";
                         }
                         type uint32 {
                           range "0 .. 199999";
                         }
                       }
                     }
                   }
                 }
                 case case_2 {
                   leaf label {
                     description "Adjacency SID from static label pool";
                     type union {
                       type string {
                         pattern "<.*>|$.*";
                       }
                       type uint32 {
                         range "16 .. 1048575";
                       }
                     }
                   }
                 }
                 case case_3 {
                   leaf dynamic {
                     description "Dynamically allocate an adjacency segment";
                     type empty;
                   }
                 }
               }
             }
             container unprotected {
               description "Adjacency SID uneligible for protection";
               choice adjsid-type {
                 case case_1 {
                   container index {
                     description "Adjacency SID indexed from SRGB";
                     leaf index-number {
                       type union {
                         type string {
                           pattern "<.*>|$.*";
                         }
                         type uint32 {
                           range "0 .. 199999";
                         }
                       }
                     }
                   }
                 }
                 case case_2 {
                   leaf label {
                     description "Adjacency SID from static label pool";
                     type union {
                       type string {
                         pattern "<.*>|$.*";
                       }
                       type uint32 {
                         range "16 .. 1048575";
                       }
                     }
                   }
                 }
                 case case_3 {
                   leaf dynamic {
                     description "Dynamically allocate an adjacency segment";
                     type empty;
                   }
                 }
               }
             }
           }
           list lan-neighbor {
             key name;
             ordered-by user;
             description "Configuration specific to a LAN neighbor";
             junos:must "(!(\".. ipv4-adjacency-segment\"))";
             junos:must-message "lan-neighbor can't be configured if ipv4-adjacency-segment is configured in the same interface";
             junos:must "(!(\".. no-advertise-adjacency-segment\"))";
             junos:must-message "lan-neighbor can't be configured if no-advertise-adjacency-segment is configured in the same interface ";
             junos:must "(!(\".. interface-type p2p\"))";
             junos:must-message "lan-neighbor can't be configured for point-to-point interfaces";
             leaf name {
               description "Address of neighbor";
               type jt:ipaddr;
             }
             uses apply-advanced;
             container ipv4-adjacency-segment {
               junos:must "(!(\".. no-advertise-adjacency-segment\"))";
               junos:must-message "ipv4-adjacency-segment can't be configured if no-advertise-adjacency-segment is configured in the same interface";
               description "Configure ipv4 adjacency segment";
               uses apply-advanced;
               container protected {
                 description "Adjacency SID is eligible for protection";
                 choice adjsid-type {
                   case case_1 {
                     container index {
                       description "Adjacency SID indexed from SRGB";
                       leaf index-number {
                         type union {
                           type string {
                             pattern "<.*>|$.*";
                           }
                           type uint32 {
                             range "0 .. 199999";
                           }
                         }
                       }
                     }
                   }
                   case case_2 {
                     leaf label {
                       description "Adjacency SID from static label pool";
                       type union {
                         type string {
                           pattern "<.*>|$.*";
                         }
                         type uint32 {
                           range "16 .. 1048575";
                         }
                       }
                     }
                   }
                   case case_3 {
                     leaf dynamic {
                       description "Dynamically allocate an adjacency segment";
                       type empty;
                     }
                   }
                 }
               }
               container unprotected {
                 description "Adjacency SID uneligible for protection";
                 choice adjsid-type {
                   case case_1 {
                     container index {
                       description "Adjacency SID indexed from SRGB";
                       leaf index-number {
                         type union {
                           type string {
                             pattern "<.*>|$.*";
                           }
                           type uint32 {
                             range "0 .. 199999";
                           }
                         }
                       }
                     }
                   }
                   case case_2 {
                     leaf label {
                       description "Adjacency SID from static label pool";
                       type union {
                         type string {
                           pattern "<.*>|$.*";
                         }
                         type uint32 {
                           range "16 .. 1048575";
                         }
                       }
                     }
                   }
                   case case_3 {
                     leaf dynamic {
                       description "Dynamically allocate an adjacency segment";
                       type empty;
                     }
                   }
                 }
               }
             }
           }
           leaf delay-metric {
             description "Delay metric";
             units "microseconds";
             type union {
               type string {
                 pattern "<.*>|$.*";
               }
               type uint32 {
                 range "0 .. 16777215";
               }
             }
           }
           container delay-measurement {
             presence "enable delay-measurement";
             description "Enable delay measurement";
             uses apply-advanced;
             leaf probe-interval {
               description "Probe interval";
               units "seconds";
               type union {
                 type string {
                   pattern "<.*>|$.*";
                 }
                 type uint32 {
                   range "1 .. 255";
                 }
               }
             }
             leaf probe-count {
               description "Probe count";
               type union {
                 type string {
                   pattern "<.*>|$.*";
                 }
                 type uint32 {
                   range "1 .. 15";
                 }
               }
             }
             container advertisement {
               description "Delay advertisement";
               uses apply-advanced;
               container periodic {
                 description "Periodic advertisement parameters";
                 uses apply-advanced;
                 leaf threshold {
                   description "Threshold";
                   units "percentage";
                   type union {
                     type string {
                       pattern "<.*>|$.*";
                     }
                     type uint32 {
                       range "0 .. 100";
                     }
                   }
                 }
                 leaf interval {
                   description "Interval";
                   units "seconds";
                   type union {
                     type string {
                       pattern "<.*>|$.*";
                     }
                     type uint32 {
                       range "30 .. 3600";
                     }
                   }
                 }
               }
               container accelerated {
                 presence "enable accelerated";
                 description "Accelerated advertisement parameters";
                 uses apply-advanced;
                 leaf threshold {
                   description "Threshold";
                   units "percentage";
                   type union {
                     type string {
                       pattern "<.*>|$.*";
                     }
                     type uint32 {
                       range "0 .. 100";
                     }
                   }
                 }
               }
             }
           }
         }
         leaf no-context-identifier-advertisement {
           description "Disable context identifier advertisments in this area";
           junos:must "(!(\".. context-identifier\"))";
           junos:must-message "no-context-identifier-advertisement and context-identifier attributes are mutually exclusive";
           type empty;
         }
         list peer-interface {
           key name;
           ordered-by user;
           description "Configuration for peer interface";
           leaf name {
             description "Name of peer interface";
             type string;
           }
           uses apply-advanced;
           choice enable-disable {
             case case_1 {
               leaf disable {
                 description "Disable OSPF on this control peer";
                 type empty;
               }
             }
           }
           leaf retransmit-interval {
             description "Retransmission interval (seconds)";
             type union {
               type string {
                 pattern "<.*>|$.*";
               }
               type uint32 {
                 range "1 .. 65535";
               }
             }
           }
           leaf transit-delay {
             description "Transit delay (seconds)";
             type union {
               type string {
                 pattern "<.*>|$.*";
               }
               type uint32 {
                 range "1 .. 65535";
               }
             }
           }
           leaf hello-interval {
             description "Hello interval (seconds)";
             type union {
               type string {
                 pattern "<.*>|$.*";
               }
               type uint32 {
                 range "1 .. 255";
               }
             }
           }
           leaf dead-interval {
             description "Dead interval (seconds)";
             type union {
               type string {
                 pattern "<.*>|$.*";
               }
               type uint32 {
                 range "1 .. 65535";
               }
             }
           }
           leaf mtu {
             description "Maximum OSPF packet size";
             type union {
               type string {
                 pattern "<.*>|$.*";
               }
               type uint32 {
                 range "128 .. 65535";
               }
             }
           }
           choice auth {
             case case_1 {
               container authentication {
                 uses juniper-ospf-authentication;
               }
             }
             case case_2 {
               container authentication-key {
                 description "Authentication key";
                 status deprecated;
                 leaf keyname {
                   description "Authentication key value";
                   type jt:unreadable;
                 }
                 leaf key-id {
                   description "Key ID for MD5 authentication";
                   type union {
                     type string {
                       pattern "<.*>|$.*";
                     }
                     type uint32 {
                       range "0 .. 255";
                     }
                   }
                 }
               }
             }
           }
           leaf demand-circuit {
             description "Interface functions as a demand circuit";
             type empty;
           }
           leaf flood-reduction {
             description "Enable flood reduction";
             type empty;
           }
           leaf no-neighbor-down-notification {
             description "Don't inform other protocols about neighbor down events";
             type empty;
           }
         }
         leaf no-source-packet-routing {
           description "Disable SPRING in this area";
           type empty;
         }
         list context-identifier {
           key name;
           ordered-by user;
           description "Configure context identifier in support of edge protection";
           junos:must "(!(\".. no-context-identifier-advertisement\"))";
           junos:must-message "no-context-identifier-advertisement and context-identifier attributes are mutually exclusive";
           leaf name {
             description "Context identifier";
             type jt:ipv4addr;
           }
           uses apply-advanced;
         }
         list label-switched-path {
           key name;
           ordered-by user;
           description "Configuration for advertisement of a label-switched path";
           junos:must "(!(\".. .. traffic-engineering multicast-rpf-routes\"))";
           junos:must-message "cannot advertise LSPs when using multicast-rpf-routes";
           leaf name {
             description "Name of label-switched path to be advertised";
             type string {
               length "1 .. 64";
             }
           }
           uses apply-advanced;
           choice enable-disable {
             case case_1 {
               leaf disable {
                 description "Disable OSPF on this label-switched path";
                 type empty;
               }
             }
           }
           leaf metric {
             description "Interface metric";
             type union {
               type string {
                 pattern "<.*>|$.*";
               }
               type uint16 {
                 range "1 .. 65535";
               }
             }
           }
           list topology {
             key name;
             ordered-by user;
             description "Topology specific attributes";
             leaf name {
               description "Topology name";
               type string;
             }
             uses apply-advanced;
             leaf disable {
               description "Disable this topology";
               type empty;
             }
             leaf metric {
               description "Topology metric";
               type union {
                 type string {
                   pattern "<.*>|$.*";
                 }
                 type uint16 {
                   range "1 .. 65535";
                 }
               }
             }
             container bandwidth-based-metrics {
               junos:must "(\".. metric\")";
               junos:must-message "Metric must be configured";
               description "Configure bandwidth based metrics";
               uses apply-advanced;
               list bandwidth {
                 key name;
                 description "Bandwidth threshold";
                 leaf name {
                   type string;
                 }
                 leaf metric {
                   description "Metric associated with specified bandwidth";
                   type union {
                     type string {
                       pattern "<.*>|$.*";
                     }
                     type uint16 {
                       range "1 .. 65535";
                     }
                   }
                 }
               }
             }
           }
         }
       }
       choice enable-disable {
         case case_1 {
           leaf disable {
             description "Disable OSPF";
             type empty;
           }
         }
       }
       container traceoptions {
         description "Trace options for OSPF";
         uses apply-advanced;
         container file {
           description "Trace file options";
           leaf filename {
             description "Name of file in which to write trace information";
             type string {
               length "1 .. 1024";
               junos:posix-pattern "![/ %]";
               junos:pattern-message "Must not contain '/', % or a space";
             }
           }
           leaf replace {
             description "Replace trace file rather than appending to it";
             status deprecated;
             type empty;
           }
           leaf size {
             description "Maximum trace file size";
             type string;
           }
           leaf files {
             description "Maximum number of trace files";
             default "10";
             type union {
               type string {
                 pattern "<.*>|$.*";
               }
               type uint32 {
                 range "2 .. 1000";
               }
             }
           }
           leaf no-stamp {
             description "Do not timestamp trace file";
             status deprecated;
             type empty;
           }
           choice world-readable-choice {
             leaf world-readable {
               description "Allow any user to read the log file";
               type empty;
             }
             leaf no-world-readable {
               description "Don't allow any user to read the log file";
               type empty;
             }
           }
         }
         list flag {
           key name;
           ordered-by user;
           description "Tracing parameters";
           leaf name {
             type enumeration {
               enum "spf" {
                 description "Trace SPF calculations";
               }
               enum "error" {
                 description "Trace errored packets";
               }
               enum "event" {
                 description "Trace OSPF state machine events";
               }
               enum "packet-dump" {
                 description "Dump the contents of selected packet types";
               }
               enum "flooding" {
                 description "Trace LSA flooding";
               }
               enum "lsa-analysis" {
                 description "Trace LSA analysis";
               }
               enum "packets" {
                 description "Trace all OSPF packets";
               }
               enum "hello" {
                 description "Trace hello packets";
               }
               enum "database-description" {
                 description "Trace database description packets";
               }
               enum "lsa-request" {
                 description "Trace LSA request packets";
               }
               enum "lsa-update" {
                 description "Trace LSA update packets";
               }
               enum "lsa-ack" {
                 description "Trace LSA acknowledgment packets";
               }
               enum "ldp-synchronization" {
                 description "Trace synchronization between OSPF and LDP";
               }
               enum "on-demand" {
                 description "Trace demand circuit extensions";
               }
               enum "nsr-synchronization" {
                 description "Trace NSR synchronization events";
               }
               enum "graceful-restart" {
                 description "Trace graceful restart";
               }
               enum "restart-signaling" {
                 description "Trace restart signaling";
               }
               enum "backup-spf" {
                 description "Trace backup SPF (LFA) specific events";
               }
               enum "source-packet-routing" {
                 description "Trace source packet routing (SPRING) events";
               }
               enum "post-convergence-lfa" {
                 description "Trace post-convergence-lfa related events";
               }
               enum "flex-algorithm" {
                 description "Trace flex-algorithm related events";
               }
               enum "rmopd" {
                 description "Trace rmopd interactions";
               }
               enum "route" {
                 description "Trace routing information";
               }
               enum "normal" {
                 description "Trace normal events";
               }
               enum "general" {
                 description "Trace general events";
               }
               enum "state" {
                 description "Trace state transitions";
               }
               enum "policy" {
                 description "Trace policy processing";
               }
               enum "task" {
                 description "Trace routing protocol task processing";
               }
               enum "timer" {
                 description "Trace routing protocol timer processing";
               }
               enum "all" {
                 description "Trace everything";
               }
             }
           }
           leaf send {
             description "Trace transmitted packets";
             type empty;
           }
           leaf receive {
             description "Trace received packets";
             type empty;
           }
           leaf detail {
             description "Trace detailed information";
             type empty;
           }
           leaf disable {
             description "Disable this trace flag";
             type empty;
           }
         }
       }
       container spf-options {
         description "Configure options for SPF";
         uses apply-advanced;
         leaf delay {
           description "Time to wait before running an SPF";
           units "milliseconds";
           type union {
             type string {
               pattern "<.*>|$.*";
             }
             type uint32 {
               range "50 .. 8000";
             }
           }
         }
         leaf holddown {
           description "Time to hold down before running an SPF";
           units "milliseconds";
           type union {
             type string {
               pattern "<.*>|$.*";
             }
             type uint32 {
               range "2000 .. 20000";
             }
           }
         }
         leaf rapid-runs {
           description "Number of maximum rapid SPF runs before holddown";
           type union {
             type string {
               pattern "<.*>|$.*";
             }
             type uint32 {
               range "1 .. 10";
             }
           }
         }
         leaf no-ignore-our-externals {
           description "Do not ignore self-generated external and NSSA LSAs";
           type empty;
         }
       }
       leaf prefix-export-limit {
         description "Maximum number of prefixes that can be exported";
         type union {
           type string {
             pattern "<.*>|$.*";
           }
           type uint32 {
             range "0 .. 4294967295";
           }
         }
       }
       container rib-groups {
         description "Routing table groups for importing OSPF routes";
         uses apply-advanced;
         leaf inet {
           description "Name of the IPv4/v6 routing table group";
           junos:must "(\"routing-options rib-groups $$\")";
           junos:must-message "Referenced rib-groups must be defined";
           junos:must "(!(\".. topology $$={default} rib-group\"))";
           junos:must-message "rib-group cannot be used with topology default rib-group";
           type string;
         }
         leaf inet3 {
           description "Name of the IPv4/v6 inet.3 routing table group";
           junos:must "(\"routing-options rib-groups $$\")";
           junos:must-message "Referenced rib-groups must be defined";
           junos:must "(!(\".. topology $$={default} rib-group\"))";
           junos:must-message "rib-group cannot be used with topology default rib-group";
           type string;
         }
       }
       leaf job-stats {
         description "Collect job statistics";
         type empty;
       }
       container overload {
         presence "enable overload";
         description "Set the overload mode (repel transit traffic)";
         uses apply-advanced;
         leaf timeout {
           description "Time after which overload mode is reset";
           units "seconds";
           type union {
             type string {
               pattern "<.*>|$.*";
             }
             type uint32 {
               range "60 .. 3600";
             }
           }
         }
         leaf allow-route-leaking {
           description "Allow routes to be leaked when overload is configured";
           type empty;
         }
         leaf stub-network {
           description "Advertise Stub Network with maximum metric";
           type empty;
         }
         leaf intra-area-prefix {
           description "Advertise Intra Area Prefix with maximum metric";
           type empty;
         }
         leaf as-external {
           description "Advertise As External with maximum usable metric";
           type empty;
         }
       }
       container database-protection {
         presence "enable database-protection";
         description "Configure database protection attributes";
         uses apply-advanced;
         leaf maximum-lsa {
           description "Maximum allowed non self-generated LSAs";
           type union {
             type string {
               pattern "<.*>|$.*";
             }
             type uint32 {
               range "1 .. 1000000";
             }
           }
         }
         leaf warning-only {
           description "Emit only a warning when LSA maximum limit is exceeded";
           type empty;
         }
         leaf warning-threshold {
           description "Percentage of LSA maximum above which to trigger warning";
           units "percent";
           type union {
             type string {
               pattern "<.*>|$.*";
             }
             type uint8 {
               range "30 .. 100";
             }
           }
         }
         leaf ignore-count {
           description "Maximum number of times to go into ignore state";
           type union {
             type string {
               pattern "<.*>|$.*";
             }
             type uint8 {
               range "1 .. 32";
             }
           }
         }
         leaf ignore-time {
           description "Time to stay in ignore state and ignore all neighbors";
           units "seconds";
           type union {
             type string {
               pattern "<.*>|$.*";
             }
             type uint16 {
               range "30 .. 3600";
             }
           }
         }
         leaf reset-time {
           description "Time after which the ignore count gets reset to zero";
           units "seconds";
           type union {
             type string {
               pattern "<.*>|$.*";
             }
             type uint32 {
               range "60 .. 86400";
             }
           }
         }
       }
       container graceful-restart {
         description "Configure graceful restart attributes";
         uses apply-advanced;
         choice enable-disable {
           case case_1 {
             leaf disable {
               description "Disable OSPF graceful restart capability";
               type empty;
             }
           }
         }
         leaf restart-duration {
           description "Time for all neighbors to become full";
           units "seconds";
           type union {
             type string {
               pattern "<.*>|$.*";
             }
             type uint32 {
               range "1 .. 3600";
             }
           }
         }
         leaf notify-duration {
           description "Time to send all max-aged grace LSAs";
           units "seconds";
           type union {
             type string {
               pattern "<.*>|$.*";
             }
             type uint32 {
               range "1 .. 3600";
             }
           }
         }
         container helper-disable {
           presence "enable helper-disable";
           description "Disable graceful restart helper capability";
           uses apply-advanced;
           choice disable-choices {
             case case_1 {
               leaf standard {
                 description "Disable helper-mode for rfc3623 based GR";
                 type empty;
               }
             }
             case case_2 {
               leaf restart-signaling {
                 description "Disable helper mode for restart-signaling ";
                 type empty;
               }
             }
             case case_3 {
               leaf both {
                 description "Disable helper mode for both the types of GR";
                 type empty;
               }
             }
           }
         }
         leaf no-strict-lsa-checking {
           description "Do not abort graceful helper mode upon LSA changes";
           junos:must "(!(\".. helper-disable\"))";
           junos:must-message "To configure no-strict-lsa-checking, helper-disable must not be set";
           type empty;
         }
       }
       leaf route-type-community {
         description "Specify BGP extended community value to encode OSPF route type";
         type enumeration {
           enum "iana" {
             description "BGP extended community value used is 0x0306";
           }
           enum "vendor" {
             description "Vendor BGP extended community value used is 0x8000";
           }
         }
       }
       container domain-id {
         description "Configure domain ID";
         choice domain_id_or_disable {
           case case_1 {
             leaf domain-id {
               description "Domain ID";
               type string;
             }
           }
           case case_2 {
             leaf disable {
               description "Disable domain ID";
               type empty;
             }
           }
         }
       }
       choice domain_vpn_tag_or_disable {
         case case_1 {
           leaf domain-vpn-tag {
             description "Domain VPN tag for external LSA";
             type union {
               type string {
                 pattern "<.*>|$.*";
               }
               type uint32 {
                 range "0 .. 4294967295";
               }
             }
           }
         }
         case case_2 {
           leaf no-domain-vpn-tag {
             description "Disable domain VPN tag";
             type empty;
           }
         }
       }
       leaf preference {
         description "Preference of internal routes";
         type union {
           type uint32;
           type string {
             pattern "<.*>|$.*";
           }
         }
       }
       leaf external-preference {
         description "Preference of external routes";
         type union {
           type uint32;
           type string {
             pattern "<.*>|$.*";
           }
         }
       }
       leaf labeled-preference {
         description "Preference of labeled routes";
         type union {
           type uint32;
           type string {
             pattern "<.*>|$.*";
           }
         }
       }
       leaf-list export {
         ordered-by user;
         description "Export policy";
         type jt:policy-algebra;
       }
       leaf-list import {
         ordered-by user;
         description "Import policy (for external routes or setting priority)";
         type jt:policy-algebra;
       }
       leaf reference-bandwidth {
         description "Bandwidth for calculating metric defaults";
         type string;
       }
       leaf lsa-refresh-interval {
         description "LSA refresh interval (minutes)";
         default "50";
         type union {
           type string {
             pattern "<.*>|$.*";
           }
           type uint32 {
             range "25 .. 50";
           }
         }
       }
       leaf spf-delay {
         description "Time to wait before running an SPF";
         status deprecated;
         units "milliseconds";
         junos:must "(!(\".. spf-options delay\"))";
         junos:must-message "You can only configure either spf-delay or delay under spf-options";
         type union {
           type string {
             pattern "<.*>|$.*";
           }
           type uint32 {
             range "50 .. 8000";
           }
         }
       }
       leaf no-rfc-1583 {
         description "Disable RFC1583 compatibility";
         type empty;
       }
       leaf forwarding-address-to-broadcast {
         description "Set forwarding address in Type 5 LSA in broadcast network";
         type empty;
       }
       choice nssa-abr-option {
         case case_1 {
           leaf no-nssa-abr {
             description "Disable full NSSA functionality at ABR";
             type empty;
           }
         }
       }
       container sham-link {
         presence "enable sham-link";
         description "Configure parameters for sham links";
         uses apply-advanced;
         leaf local {
           description "Local sham link endpoint address";
           type jt:ipaddr;
         }
         leaf no-advertise-local {
           description "Don't advertise local sham link endpoint as stub in router LSA";
           status deprecated;
           type empty;
         }
       }
     }
     uses apply-advanced;
     list topology {
       key name;
       ordered-by user;
       description "Topology parameters";
       leaf name {
         description "Topology name";
         type string;
       }
       uses apply-advanced;
       leaf disable {
         description "Disable this topology";
         type empty;
       }
       leaf topology-id {
         description "Topology identifier";
         type union {
           type string {
             pattern "<.*>|$.*";
           }
           type uint8 {
             range "32 .. 127";
           }
         }
       }
       leaf overload {
         description "Set the overload mode (repel transit traffic)";
         type empty;
       }
       leaf rib-group {
         description "Routing table group for importing routes";
         junos:must "(\"routing-options rib-groups $$\")";
         junos:must-message "Referenced rib-group must be defined";
         type string;
       }
       container spf-options {
         description "Configure options for SPF";
         uses apply-advanced;
         leaf delay {
           description "Time to wait before running an SPF";
           units "milliseconds";
           type union {
             type string {
               pattern "<.*>|$.*";
             }
             type uint32 {
               range "50 .. 8000";
             }
           }
         }
         leaf holddown {
           description "Time to hold down before running an SPF";
           units "milliseconds";
           type union {
             type string {
               pattern "<.*>|$.*";
             }
             type uint32 {
               range "2000 .. 20000";
             }
           }
         }
         leaf rapid-runs {
           description "Number of maximum rapid SPF runs before holddown";
           type union {
             type string {
               pattern "<.*>|$.*";
             }
             type uint32 {
               range "1 .. 10";
             }
           }
         }
         leaf no-ignore-our-externals {
           description "Do not ignore self-generated external and NSSA LSAs";
           type empty;
         }
       }
       container backup-spf-options {
         description "Configure options for backup SPF";
         uses apply-advanced;
         container remote-backup-calculation {
           presence "enable remote-backup-calculation";
           junos:must "(!(\"protocols ospf backup-spf-options use-post-convergence-lfa\"))";
           junos:must-message "Not allowed with 'protocols ospf backup-spf-options use-post-convergence-lfa'";
           description "Calculate Remote LFA backup nexthops";
           uses apply-advanced;
           container pq-nodes-nearest-to-source {
             description "PQ nodes selection based upon nearest to source";
             uses apply-advanced;
             leaf percent {
               description "Selection percentage for nearest to source";
               type union {
                 type string {
                   pattern "<.*>|$.*";
                 }
                 type uint32 {
                   range "10 .. 100";
                 }
               }
             }
           }
         }
         container use-post-convergence-lfa {
           presence "enable use-post-convergence-lfa";
           junos:must "(\"protocols ospf source-packet-routing\")";
           junos:must-message "Configuration of 'protocols ospf source-packet-routing' is required";
           description "Calculate post-convergence backup paths";
           uses apply-advanced;
           leaf maximum-labels {
             description "Maximum number of labels installed for post-convergence paths";
             type union {
               type string {
                 pattern "<.*>|$.*";
               }
               type uint32 {
                 range "2 .. 8";
               }
             }
           }
           leaf maximum-backup-paths {
             description "Maximum number of equal-cost post-convergence paths installed";
             type union {
               type string {
                 pattern "<.*>|$.*";
               }
               type uint32 {
                 range "1 .. 8";
               }
             }
           }
         }
         leaf use-source-packet-routing {
           description "Use spring backup paths for inet.0 routes";
           junos:must "(\".. .. source-packet-routing\")";
           junos:must-message "Configuration of 'protocols ospf source-packet-routing' is required";
           junos:must "(!(\".. remote-backup-calculation\"))";
           junos:must-message "Not allowed with 'protocols ospf backup-spf-options remote-backup-calculation'";
           type empty;
         }
         leaf disable {
           description "Do not run backup SPF";
           junos:must "(!(\"protocols ospf backup-spf-options use-post-convergence-lfa\"))";
           junos:must-message "Not allowed with 'protocols ospf backup-spf-options use-post-convergence-lfa'";
           type empty;
         }
         leaf no-install {
           description "Do not install backup nexthops into the RIB";
           type empty;
         }
         leaf downstream-paths-only {
           description "Use only downstream backup paths";
           junos:must "(!(\"protocols ospf backup-spf-options use-post-convergence-lfa\"))";
           junos:must-message "Not allowed with 'protocols ospf backup-spf-options use-post-convergence-lfa'";
           type empty;
         }
         container per-prefix-calculation {
           junos:must "(!(\"protocols ospf backup-spf-options use-post-convergence-lfa\"))";
           junos:must-message "Not allowed with 'protocols ospf backup-spf-options use-post-convergence-lfa'";
           description "Calculate backup nexthops for non-best prefix originators";
           uses apply-advanced;
           leaf stubs {
             description "Per prefix calculation for stubs only";
             type empty;
           }
           leaf summary {
             description "Per prefix calculation for summary originators only";
             type empty;
           }
           leaf externals {
             description "Per prefix calculation for externals";
             type empty;
           }
           leaf all {
             description "Per prefix calculation for all";
             type empty;
           }
         }
         leaf node-link-degradation {
           description "Degrade to link protection when nodelink protection not available";
           junos:must "(!(\"protocols ospf backup-spf-options use-post-convergence-lfa\"))";
           junos:must-message "Not allowed with 'protocols ospf backup-spf-options use-post-convergence-lfa'";
           type empty;
         }
       }
       leaf prefix-export-limit {
         description "Maximum number of prefixes that can be exported";
         type union {
           type string {
             pattern "<.*>|$.*";
           }
           type uint32 {
             range "0 .. 4294967295";
           }
         }
       }
     }
     container backup-spf-options {
       description "Configure options for backup SPF";
       uses apply-advanced;
       container remote-backup-calculation {
         presence "enable remote-backup-calculation";
         junos:must "(!(\"protocols ospf backup-spf-options use-post-convergence-lfa\"))";
         junos:must-message "Not allowed with 'protocols ospf backup-spf-options use-post-convergence-lfa'";
         description "Calculate Remote LFA backup nexthops";
         uses apply-advanced;
         container pq-nodes-nearest-to-source {
           description "PQ nodes selection based upon nearest to source";
           uses apply-advanced;
           leaf percent {
             description "Selection percentage for nearest to source";
             type union {
               type string {
                 pattern "<.*>|$.*";
               }
               type uint32 {
                 range "10 .. 100";
               }
             }
           }
         }
       }
       container use-post-convergence-lfa {
         presence "enable use-post-convergence-lfa";
         junos:must "(\"protocols ospf source-packet-routing\")";
         junos:must-message "Configuration of 'protocols ospf source-packet-routing' is required";
         description "Calculate post-convergence backup paths";
         uses apply-advanced;
         leaf maximum-labels {
           description "Maximum number of labels installed for post-convergence paths";
           type union {
             type string {
               pattern "<.*>|$.*";
             }
             type uint32 {
               range "2 .. 8";
             }
           }
         }
         leaf maximum-backup-paths {
           description "Maximum number of equal-cost post-convergence paths installed";
           type union {
             type string {
               pattern "<.*>|$.*";
             }
             type uint32 {
               range "1 .. 8";
             }
           }
         }
       }
       leaf use-source-packet-routing {
         description "Use spring backup paths for inet.0 routes";
         junos:must "(\".. .. source-packet-routing\")";
         junos:must-message "Configuration of 'protocols ospf source-packet-routing' is required";
         junos:must "(!(\".. remote-backup-calculation\"))";
         junos:must-message "Not allowed with 'protocols ospf backup-spf-options remote-backup-calculation'";
         type empty;
       }
       leaf disable {
         description "Do not run backup SPF";
         junos:must "(!(\"protocols ospf backup-spf-options use-post-convergence-lfa\"))";
         junos:must-message "Not allowed with 'protocols ospf backup-spf-options use-post-convergence-lfa'";
         type empty;
       }
       leaf no-install {
         description "Do not install backup nexthops into the RIB";
         type empty;
       }
       leaf downstream-paths-only {
         description "Use only downstream backup paths";
         junos:must "(!(\"protocols ospf backup-spf-options use-post-convergence-lfa\"))";
         junos:must-message "Not allowed with 'protocols ospf backup-spf-options use-post-convergence-lfa'";
         type empty;
       }
       container per-prefix-calculation {
         junos:must "(!(\"protocols ospf backup-spf-options use-post-convergence-lfa\"))";
         junos:must-message "Not allowed with 'protocols ospf backup-spf-options use-post-convergence-lfa'";
         description "Calculate backup nexthops for non-best prefix originators";
         uses apply-advanced;
         leaf stubs {
           description "Per prefix calculation for stubs only";
           type empty;
         }
         leaf summary {
           description "Per prefix calculation for summary originators only";
           type empty;
         }
         leaf externals {
           description "Per prefix calculation for externals";
           type empty;
         }
         leaf all {
           description "Per prefix calculation for all";
           type empty;
         }
       }
       leaf node-link-degradation {
         description "Degrade to link protection when nodelink protection not available";
         junos:must "(!(\"protocols ospf backup-spf-options use-post-convergence-lfa\"))";
         junos:must-message "Not allowed with 'protocols ospf backup-spf-options use-post-convergence-lfa'";
         type empty;
       }
     }
     container traffic-engineering {
       presence "enable traffic-engineering";
       description "Configure traffic engineering attributes";
       uses apply-advanced;
       leaf no-topology {
         description "Disable dissemination of TE link-state topology information";
         type empty;
       }
       leaf multicast-rpf-routes {
         description "Install routes for multicast RPF checks into inet.2";
         junos:must "(!(\".. .. topology $$={ipv4-multicast}\"))";
         junos:must-message "multicast-rpf-routes cannot be used with topology ipv4-multicast";
         junos:must "(\".. shortcuts\")";
         junos:must-message "multicast-rpf-routes cannot be used without shortcuts";
         type empty;
       }
       leaf l3-unicast-topology {
         description "Download IGP topology into TED";
         type empty;
       }
       container ignore-lsp-metrics {
         presence "enable ignore-lsp-metrics";
         description "Ignore label-switched path metrics when doing shortcuts";
         uses apply-advanced;
         leaf unconfigured-only {
           description "Ignore lsp metrics for unconfigured only";
           type empty;
         }
       }
       container shortcuts {
         presence "enable shortcuts";
         description "Use label-switched paths as next hops, if possible";
         uses apply-advanced;
         leaf ignore-lsp-metrics {
           description "Ignore label-switched path metrics when doing shortcuts";
           status deprecated;
           type empty;
         }
         leaf lsp-metric-into-summary {
           description "Advertise LSP metric into summary LSAs";
           type empty;
         }
         list family {
           key name;
           ordered-by user;
           description "Address family specific traffic-engineering attributes";
           leaf name {
             type enumeration {
               enum "inet" {
                 description "IPv4 family";
               }
               enum "inet-mpls" {
                 description "IPv4-MPLS family";
               }
             }
           }
           uses apply-advanced;
         }
       }
       leaf advertise-unnumbered-interfaces {
         description "Advertise unnumbered interfaces";
         type empty;
       }
       leaf credibility-protocol-preference {
         description "TED protocol credibility follows protocol preference";
         type empty;
       }
       container advertisement {
         description "Advertise TE parameters even if RSVP is not turned on";
         uses apply-advanced;
         leaf always {
           description "Advertise TE parameters in TE LSAs";
           type empty;
         }
       }
     }
     container source-packet-routing {
       presence "enable source-packet-routing";
       junos:must "(!(\".. .. .. protocols mpls disable\"))";
       junos:must-message "SPRING configuration is not allowed with 'protocols mpls disable'";
       junos:must "(\".. .. .. protocols mpls \")";
       junos:must-message "SPRING configuration is not allowed without 'protocols mpls'";
       description "Enable source packet routing (SPRING)";
       uses apply-advanced;
       container adjacency-segment {
         description "Attributes for adjacency segments in spring";
         uses apply-advanced;
         leaf hold-time {
           description "Retain time of Adjacency segment after isolating from an interface";
           type union {
             type string {
               pattern "<.*>|$.*";
             }
             type uint32 {
               range "180000 .. 900000";
             }
           }
         }
       }
       leaf-list prefix-segment {
         ordered-by user;
         description "Prefix Segment policy";
         type jt:policy-algebra;
       }
       leaf explicit-null {
         description "Set E and P bits in all Prefix SID advertisements";
         type empty;
       }
       container node-segment {
         presence "enable node-segment";
         description "Enable support for Node segments in SPRING";
         uses apply-advanced;
         leaf ipv4-index {
           description "Set ipv4 node segment index";
           type union {
             type string {
               pattern "<.*>|$.*";
             }
             type uint32 {
               range "0 .. 199999";
             }
           }
         }
         leaf index-range {
           description "Set range of node segment indices allowed";
           type union {
             type string {
               pattern "<.*>|$.*";
             }
             type uint32 {
               range "32 .. 16385";
             }
           }
         }
       }
       container srgb {
         junos:must "(!(\".. node-segment index-range\"))";
         junos:must-message "Can not be configured with node-segment index-range";
         description "Set the SRGB global block in SPRING";
         leaf start-label {
           description "Start range for SRGB label block";
           type union {
             type string {
               pattern "<.*>|$.*";
             }
             type uint32;
           }
         }
         leaf index-range {
           description "Index to the SRGB start label block";
           type union {
             type string {
               pattern "<.*>|$.*";
             }
             type uint32;
           }
         }
       }
       leaf mapping-server {
         description "Mapping server name";
         junos:must "(\".. node-segment\")";
         junos:must-message "protocols ospf source-packet-routing node-segment must be defined";
         junos:must "(\"routing-options source-packet-routing mapping-server-entry $$\")";
         junos:must-message "Referenced source-packet-routing mapping-server-entry must be defined";
         type string;
       }
       leaf install-prefix-sid-for-best-route {
         description "For best route install a exact prefix sid route";
         type empty;
       }
       leaf ldp-stitching {
         description "Enable SR to LDP stitching";
         type empty;
       }
       leaf-list flex-algorithm {
         description "Flex-algorithms we would like to participate in";
         type union {
           type string {
             pattern "<.*>|$.*";
           }
           type uint32 {
             range "128 .. 255";
           }
         }
         max-elements 16;
       }
     }
     list area {
       key name;
       ordered-by user;
       description "Configure an OSPF area";
       leaf name {
         description "Area ID";
         type jt:areaid;
       }
       uses apply-advanced;
       choice stub-option {
         case case_1 {
           container stub {
             presence "enable stub";
             description "Configure a stub area";
             leaf default-metric {
               description "Metric for the default route in this stub area";
               type union {
                 type string {
                   pattern "<.*>|$.*";
                 }
                 type uint32 {
                   range "1 .. 16777215";
                 }
               }
             }
             choice summaries-choice {
               leaf summaries {
                 description "Flood summary LSAs into this stub area";
                 type empty;
               }
               leaf no-summaries {
                 description "Don't flood summary LSAs into this stub area";
                 type empty;
               }
             }
           }
         }
         case case_2 {
           container nssa {
             presence "enable nssa";
             description "Configure a not-so-stubby area";
             uses apply-advanced;
             container default-lsa {
               presence "enable default-lsa";
               description "Configure a default LSA";
               uses apply-advanced;
               leaf default-metric {
                 description "Metric for the default route in this area";
                 type union {
                   type string {
                     pattern "<.*>|$.*";
                   }
                   type uint32 {
                     range "1 .. 16777215";
                   }
                 }
               }
               leaf metric-type {
                 description "External metric type for the default type 7 LSA";
                 type union {
                   type string {
                     pattern "<.*>|$.*";
                   }
                   type uint32 {
                     range "1 .. 2";
                   }
                 }
               }
               leaf type-7 {
                 description "Flood type 7 default LSA if no-summaries is configured";
                 type empty;
               }
             }
             leaf default-metric {
               description "Metric for the default route in this area";
               status deprecated;
               type union {
                 type string {
                   pattern "<.*>|$.*";
                 }
                 type uint32 {
                   range "1 .. 16777215";
                 }
               }
             }
             leaf metric-type {
               description "External metric type for the default type 7 LSA";
               status deprecated;
               type union {
                 type string {
                   pattern "<.*>|$.*";
                 }
                 type uint32 {
                   range "1 .. 2";
                 }
               }
             }
             choice summaries-choice {
               leaf summaries {
                 description "Flood summary LSAs into this NSSA area";
                 type empty;
               }
               leaf no-summaries {
                 description "Don't flood summary LSAs into this NSSA area";
                 type empty;
               }
             }
             list area-range {
               key name;
               ordered-by user;
               description "Configure NSSA area ranges";
               leaf name {
                 description "Range to summarize NSSA routes in this area";
                 type jt:ipprefix;
               }
               uses apply-advanced;
               leaf restrict {
                 description "Restrict advertisement of this area range";
                 type empty;
               }
               leaf exact {
                 description "Enforce exact match for advertisement of this area range";
                 type empty;
               }
               container override-metric {
                 presence "enable override-metric";
                 description "Override the dynamic metric for this area-range";
                 uses apply-advanced;
                 leaf metric {
                   description "Metric value";
                   type union {
                     type string {
                       pattern "<.*>|$.*";
                     }
                     type uint32 {
                       range "1 .. 16777215";
                     }
                   }
                 }
                 leaf metric-type {
                   description "Set the metric type for the override metric";
                   default "1";
                   type union {
                     type string {
                       pattern "<.*>|$.*";
                     }
                     type uint32 {
                       range "1 .. 2";
                     }
                   }
                 }
               }
             }
           }
         }
       }
       list area-range {
         key name;
         ordered-by user;
         description "Configure area ranges";
         leaf name {
           description "Range to summarize routes in this area";
           type jt:ipprefix;
         }
         uses apply-advanced;
         leaf restrict {
           description "Restrict advertisement of this area range";
           type empty;
         }
         leaf exact {
           description "Enforce exact match for advertisement of this area range";
           type empty;
         }
         leaf override-metric {
           description "Override the dynamic metric for this area-range";
           type union {
             type string {
               pattern "<.*>|$.*";
             }
             type uint32 {
               range "1 .. 16777215";
             }
           }
         }
       }
       leaf-list network-summary-export {
         ordered-by user;
         description "Export policy for Type 3 Summary LSAs";
         type jt:policy-algebra;
       }
       leaf-list network-summary-import {
         ordered-by user;
         description "Import policy for Type 3 Summary LSAs";
         type jt:policy-algebra;
       }
       leaf-list inter-area-prefix-export {
         ordered-by user;
         description "Export policy for Inter Area Prefix LSAs";
         type jt:policy-algebra;
       }
       leaf-list inter-area-prefix-import {
         ordered-by user;
         description "Import policy for Inter Area Prefix LSAs";
         type jt:policy-algebra;
       }
       leaf authentication-type {
         description "Authentication type";
         status deprecated;
         type enumeration {
           enum "none" {
             description "No authentication";
             status deprecated;
           }
           enum "simple" {
             description "Simple password authentication";
             status deprecated;
           }
           enum "md5" {
             description "MD5 authentication";
             status deprecated;
           }
         }
       }
       list virtual-link {
         key "neighbor-id transit-area";
         ordered-by user;
         description "Configure virtual links";
         junos:must "(\".. .. area $$={0.0.0.0}\")";
         junos:must-message "virtual link can be configured only under backbone area";
         leaf neighbor-id {
           description "Router ID of a virtual neighbor";
           type jt:ipv4addr;
         }
         leaf transit-area {
           description "Transit area in common with virtual neighbor";
           type jt:areaid;
         }
         uses apply-advanced;
         choice enable-disable {
           case case_1 {
             leaf disable {
               description "Disable this virtual link";
               type empty;
             }
           }
         }
         leaf retransmit-interval {
           description "Retransmission interval (seconds)";
           type union {
             type string {
               pattern "<.*>|$.*";
             }
             type uint32 {
               range "1 .. 65535";
             }
           }
         }
         leaf transit-delay {
           description "Transit delay (seconds)";
           type union {
             type string {
               pattern "<.*>|$.*";
             }
             type uint32 {
               range "1 .. 65535";
             }
           }
         }
         leaf hello-interval {
           description "Hello interval (seconds)";
           type union {
             type string {
               pattern "<.*>|$.*";
             }
             type uint32 {
               range "1 .. 255";
             }
           }
         }
         leaf dead-interval {
           description "Dead interval (seconds)";
           type union {
             type string {
               pattern "<.*>|$.*";
             }
             type uint32 {
               range "1 .. 65535";
             }
           }
         }
         leaf mtu {
           description "Maximum OSPF packet size";
           type union {
             type string {
               pattern "<.*>|$.*";
             }
             type uint32 {
               range "128 .. 65535";
             }
           }
         }
         choice auth {
           case case_1 {
             container authentication {
               uses juniper-ospf-authentication;
             }
           }
           case case_2 {
             container authentication-key {
               description "Authentication key";
               status deprecated;
               leaf keyname {
                 description "Authentication key value";
                 type jt:unreadable;
               }
               leaf key-id {
                 description "Key ID for MD5 authentication";
                 type union {
                   type string {
                     pattern "<.*>|$.*";
                   }
                   type uint32 {
                     range "0 .. 255";
                   }
                 }
               }
             }
           }
         }
         leaf demand-circuit {
           description "Interface functions as a demand circuit";
           type empty;
         }
         leaf flood-reduction {
           description "Enable flood reduction";
           type empty;
         }
         leaf no-neighbor-down-notification {
           description "Don't inform other protocols about neighbor down events";
           type empty;
         }
         leaf ipsec-sa {
           description "IPSec security association name";
           junos:must "(!(any \".. .. interface <st*> ipsec-sa $$\"))";
           junos:must-message "Must not configure ipsec-sa for st0 interface";
           junos:must "(\"security ipsec security-association $$ manual\")";
           junos:must-message "Referenced IPSec security association must be a manual SA";
           junos:must "(\"security ipsec security-association $$ mode transport\")";
           junos:must-message "Referenced IPSec security association must be in transport mode";
           junos:must "(\"security ipsec security-association $$\")";
           junos:must-message "Referenced IPSec security association must be defined";
           type string {
             length "1 .. 32";
           }
         }
         list topology {
           key name;
           ordered-by user;
           description "Topology specific attributes";
           leaf name {
             description "Topology name";
             type string;
           }
           uses apply-advanced;
           leaf disable {
             description "Disable this topology";
             type empty;
           }
           leaf metric {
             description "Topology metric";
             type union {
               type string {
                 pattern "<.*>|$.*";
               }
               type uint16 {
                 range "1 .. 65535";
               }
             }
           }
           container bandwidth-based-metrics {
             junos:must "(\".. metric\")";
             junos:must-message "Metric must be configured";
             description "Configure bandwidth based metrics";
             uses apply-advanced;
             list bandwidth {
               key name;
               description "Bandwidth threshold";
               leaf name {
                 type string;
               }
               leaf metric {
                 description "Metric associated with specified bandwidth";
                 type union {
                   type string {
                     pattern "<.*>|$.*";
                   }
                   type uint16 {
                     range "1 .. 65535";
                   }
                 }
               }
             }
           }
         }
       }
       list sham-link-remote {
         key name;
         ordered-by user;
         description "Configure parameters for remote sham link endpoint";
         leaf name {
           description "Remote sham link endpoint address";
           junos:must "(!(\".. .. .. sham-link local $$\"))";
           junos:must-message "Local and remote sham link endpoint addresses must be different";
           junos:must "(\".. .. .. sham-link local\")";
           junos:must-message "Local sham link endpoint must be configured";
           type jt:ipaddr;
         }
         uses apply-advanced;
         leaf metric {
           description "Sham link metric";
           type union {
             type string {
               pattern "<.*>|$.*";
             }
             type uint16 {
               range "1 .. 65535";
             }
           }
         }
         leaf ipsec-sa {
           description "IPSec security association name";
           junos:must "(!(any \".. .. interface <st*> ipsec-sa $$\"))";
           junos:must-message "Must not configure ipsec-sa for st0 interface";
           junos:must "(\"security ipsec security-association $$ manual\")";
           junos:must-message "Referenced IPSec security association must be a manual SA";
           junos:must "(\"security ipsec security-association $$ mode transport\")";
           junos:must-message "Referenced IPSec security association must be in transport mode";
           junos:must "(\"security ipsec security-association $$\")";
           junos:must-message "Referenced IPSec security association must be defined";
           type string {
             length "1 .. 32";
           }
         }
         leaf demand-circuit {
           description "Interface functions as a demand circuit";
           type empty;
         }
         leaf flood-reduction {
           description "Enable flood reduction";
           type empty;
         }
         list topology {
           key name;
           ordered-by user;
           description "Topology specific attributes";
           leaf name {
             description "Topology name";
             type string;
           }
           uses apply-advanced;
           leaf disable {
             description "Disable this topology";
             type empty;
           }
           leaf metric {
             description "Topology metric";
             type union {
               type string {
                 pattern "<.*>|$.*";
               }
               type uint16 {
                 range "1 .. 65535";
               }
             }
           }
           container bandwidth-based-metrics {
             junos:must "(\".. metric\")";
             junos:must-message "Metric must be configured";
             description "Configure bandwidth based metrics";
             uses apply-advanced;
             list bandwidth {
               key name;
               description "Bandwidth threshold";
               leaf name {
                 type string;
               }
               leaf metric {
                 description "Metric associated with specified bandwidth";
                 type union {
                   type string {
                     pattern "<.*>|$.*";
                   }
                   type uint16 {
                     range "1 .. 65535";
                   }
                 }
               }
             }
           }
         }
       }
       list interface {
         key name;
         ordered-by user;
         description "Include an interface in this area";
         leaf name {
           description "Interface name";
           junos:must "((!(\".. interface-type nbma\") || (!((\"interfaces $$\" || any \"logical-systems <*> interfaces $$\")) || (any \"interfaces $$-IFL family inet address <*>\" || any \"logical-systems <*> interfaces $$-IFL family inet address <*>\"))))";
           junos:must-message "IPv4 address must be configured on the interface for nbma mode";
           type union {
             type jt:ipv4addr-or-interface;
             type string {
               pattern "<.*>|$.*";
             }
           }
         }
         uses apply-advanced;
         choice enable-disable {
           case case_1 {
             leaf disable {
               description "Disable OSPF on this interface";
               type empty;
             }
           }
         }
         leaf interface-type {
           description "Type of interface";
           type enumeration {
             enum "nbma" {
               description "Nonbroadcast multiaccess";
             }
             enum "p2mp" {
               description "Point-to-multipoint NBMA";
             }
             enum "p2p" {
               description "Point-to-point";
             }
             enum "p2mp-over-lan" {
               description "Point-to-multipoint over LAN mode";
             }
           }
         }
         choice protection-type {
           case case_1 {
             leaf link-protection {
               description "Protect interface from link faults only";
               type empty;
             }
           }
           case case_2 {
             leaf node-link-protection {
               description "Protect interface from both link and node faults";
               type empty;
             }
           }
         }
         leaf no-eligible-backup {
           description "Not eligible to backup traffic from protected interfaces";
           type empty;
         }
         leaf no-eligible-remote-backup {
           description "Not eligible for Remote-LFA backup traffic from protected interfaces";
           type empty;
         }
         container passive {
           presence "enable passive";
           description "Do not run OSPF, but advertise it";
           uses apply-advanced;
           container traffic-engineering {
             description "Advertise TE link information";
             uses apply-advanced;
             leaf remote-node-id {
               description "Remote address of the link";
               type jt:ipaddr;
             }
             leaf remote-node-router-id {
               description "TE Router-ID of the remote node";
               junos:must "(\".. remote-node-id\")";
               junos:must-message "remote-node-id must be configured";
               type jt:ipv4addr;
             }
           }
         }
         leaf secondary {
           description "Treat interface as secondary";
           junos:must "(!(\" .. ipsec-sa\"))";
           junos:must-message "secondary interface cannot have ipsec-sa configured";
           junos:must "(!(\" .. dynamic-neighbors\"))";
           junos:must-message "secondary interface cannot have dynamic-neighbors configured";
           junos:must "(!(\" .. neighbor\"))";
           junos:must-message "secondary interface cannot have configured neighbors";
           junos:must "(!(\" .. interface-type p2mp\"))";
           junos:must-message "secondary interface cannot be set as type p2mp";
           junos:must "(!(\" .. interface-type nbma\"))";
           junos:must-message "secondary interface cannot be set as type nbma";
           junos:must "(!(\" .. passive\"))";
           junos:must-message "secondary interface cannot be configured passive";
           type empty;
         }
         leaf own-router-lsa {
           description "Generate a separate router LSA for this interface";
           type empty;
         }
         container bandwidth-based-metrics {
           junos:must "(\".. metric\")";
           junos:must-message "Metric must be configured";
           description "Configure bandwidth based metrics";
           uses apply-advanced;
           list bandwidth {
             key name;
             description "Bandwidth threshold";
             leaf name {
               type string;
             }
             leaf metric {
               description "Metric associated with specified bandwidth";
               type union {
                 type string {
                   pattern "<.*>|$.*";
                 }
                 type uint16 {
                   range "1 .. 65535";
                 }
               }
             }
           }
         }
         leaf metric {
           description "Interface metric";
           type union {
             type string {
               pattern "<.*>|$.*";
             }
             type uint16 {
               range "1 .. 65535";
             }
           }
         }
         leaf priority {
           description "Designated router priority";
           type union {
             type string {
               pattern "<.*>|$.*";
             }
             type uint32 {
               range "0 .. 255";
             }
           }
         }
         leaf retransmit-interval {
           description "Retransmission interval (seconds)";
           type union {
             type string {
               pattern "<.*>|$.*";
             }
             type uint32 {
               range "1 .. 65535";
             }
           }
         }
         leaf transit-delay {
           description "Transit delay (seconds)";
           type union {
             type string {
               pattern "<.*>|$.*";
             }
             type uint32 {
               range "1 .. 65535";
             }
           }
         }
         leaf hello-interval {
           description "Hello interval (seconds)";
           type union {
             type string {
               pattern "<.*>|$.*";
             }
             type uint32 {
               range "1 .. 255";
             }
           }
         }
         leaf dead-interval {
           description "Dead interval (seconds)";
           type union {
             type string {
               pattern "<.*>|$.*";
             }
             type uint32 {
               range "1 .. 65535";
             }
           }
         }
         leaf mtu {
           description "Maximum OSPF packet size";
           type union {
             type string {
               pattern "<.*>|$.*";
             }
             type uint32 {
               range "128 .. 65535";
             }
           }
         }
         choice auth {
           case case_1 {
             container authentication {
               uses juniper-ospf-authentication;
             }
           }
           case case_2 {
             container authentication-key {
               description "Authentication key";
               status deprecated;
               leaf keyname {
                 description "Authentication key value";
                 type jt:unreadable;
               }
               leaf key-id {
                 description "Key ID for MD5 authentication";
                 type union {
                   type string {
                     pattern "<.*>|$.*";
                   }
                   type uint32 {
                     range "0 .. 255";
                   }
                 }
               }
             }
           }
         }
         leaf demand-circuit {
           description "Interface functions as a demand circuit";
           type empty;
         }
         leaf flood-reduction {
           description "Enable flood reduction";
           type empty;
         }
         leaf no-neighbor-down-notification {
           description "Don't inform other protocols about neighbor down events";
           type empty;
         }
         leaf ipsec-sa {
           description "IPSec security association name";
           junos:must "(!(any \".. .. interface <st*> ipsec-sa $$\"))";
           junos:must-message "Must not configure ipsec-sa for st0 interface";
           junos:must "(\"security ipsec security-association $$ manual\")";
           junos:must-message "Referenced IPSec security association must be a manual SA";
           junos:must "(\"security ipsec security-association $$ mode transport\")";
           junos:must-message "Referenced IPSec security association must be in transport mode";
           junos:must "(\"security ipsec security-association $$\")";
           junos:must-message "Referenced IPSec security association must be defined";
           type string {
             length "1 .. 32";
           }
         }
         list topology {
           key name;
           ordered-by user;
           description "Topology specific attributes";
           leaf name {
             description "Topology name";
             type string;
           }
           uses apply-advanced;
           leaf disable {
             description "Disable this topology";
             type empty;
           }
           leaf metric {
             description "Topology metric";
             type union {
               type string {
                 pattern "<.*>|$.*";
               }
               type uint16 {
                 range "1 .. 65535";
               }
             }
           }
           container bandwidth-based-metrics {
             junos:must "(\".. metric\")";
             junos:must-message "Metric must be configured";
             description "Configure bandwidth based metrics";
             uses apply-advanced;
             list bandwidth {
               key name;
               description "Bandwidth threshold";
               leaf name {
                 type string;
               }
               leaf metric {
                 description "Metric associated with specified bandwidth";
                 type union {
                   type string {
                     pattern "<.*>|$.*";
                   }
                   type uint16 {
                     range "1 .. 65535";
                   }
                 }
               }
             }
           }
         }
         leaf transmit-interval {
           description "OSPF packet transmit interval (milliseconds)";
           status deprecated;
           type union {
             type string {
               pattern "<.*>|$.*";
             }
             type uint32 {
               range "1 .. 4294967295";
             }
           }
         }
         container bfd-liveness-detection {
           description "Bidirectional Forwarding Detection options";
           uses apply-advanced;
           leaf version {
             description "BFD protocol version number";
             default "automatic";
             type enumeration {
               enum "0" {
                 description "BFD version 0 (deprecated)";
               }
               enum "1" {
                 description "BFD version 1";
               }
               enum "automatic" {
                 description "Choose BFD version automatically";
               }
             }
           }
           leaf minimum-interval {
             description "Minimum transmit and receive interval";
             units "milliseconds";
             type union {
               type string {
                 pattern "<.*>|$.*";
               }
               type uint32 {
                 range "1 .. 255000";
               }
             }
           }
           leaf minimum-transmit-interval {
             description "Minimum transmit interval";
             status deprecated;
             units "milliseconds";
             type union {
               type string {
                 pattern "<.*>|$.*";
               }
               type uint32 {
                 range "1 .. 255000";
               }
             }
           }
           leaf minimum-receive-interval {
             description "Minimum receive interval";
             units "milliseconds";
             type union {
               type string {
                 pattern "<.*>|$.*";
               }
               type uint32 {
                 range "1 .. 255000";
               }
             }
           }
           leaf multiplier {
             description "Detection time multiplier";
             default "3";
             type union {
               type string {
                 pattern "<.*>|$.*";
               }
               type uint32 {
                 range "1 .. 255";
               }
             }
           }
           choice adaptation-choice {
             case case_1 {
               leaf no-adaptation {
                 description "Disable adaptation";
                 type empty;
               }
             }
           }
           container transmit-interval {
             description "Transmit-interval options";
             uses apply-advanced;
             leaf minimum-interval {
               description "Minimum transmit interval";
               units "milliseconds";
               type union {
                 type string {
                   pattern "<.*>|$.*";
                 }
                 type uint32 {
                   range "1 .. 255000";
                 }
               }
             }
             leaf threshold {
               description "High transmit interval triggering a trap";
               units "milliseconds";
               type union {
                 type uint32;
                 type string {
                   pattern "<.*>|$.*";
                 }
               }
             }
           }
           container detection-time {
             description "Detection-time options";
             uses apply-advanced;
             leaf threshold {
               description "High detection-time triggering a trap";
               units "milliseconds";
               type union {
                 type uint32;
                 type string {
                   pattern "<.*>|$.*";
                 }
               }
             }
           }
           container authentication {
             description "Authentication options";
             uses apply-advanced;
             leaf key-chain {
               description "Key chain name";
               junos:must "(\".. algorithm\")";
               junos:must-message "May not be configured without algorithm";
               junos:must "(\"security authentication-key-chains key-chain $$\")";
               junos:must-message "Referenced key-chain must be defined";
               type string;
             }
             leaf algorithm {
               description "Algorithm name";
               junos:must "(\".. key-chain\")";
               junos:must-message "May not be configured without key-chain";
               type enumeration {
                 enum "simple-password" {
                   description "Simple password";
                 }
                 enum "keyed-md5" {
                   description "Keyed message Digest 5";
                 }
                 enum "meticulous-keyed-md5" {
                   description "Meticulous keyed message Digest 5";
                 }
                 enum "keyed-sha-1" {
                   description "Keyed secure hash algorithm (SHA1) ";
                 }
                 enum "meticulous-keyed-sha-1" {
                   description "Meticulous keyed secure hash algorithm (SHA1) ";
                 }
               }
             }
             leaf loose-check {
               description "Verify authentication only if authentication is negotiated";
               type empty;
             }
           }
           leaf full-neighbors-only {
             description "Setup BFD sessions only to Full neighbors";
             type empty;
           }
           leaf holddown-interval {
             description "Time to hold the session-UP notification to the client";
             units "milliseconds";
             type union {
               type string {
                 pattern "<.*>|$.*";
               }
               type uint32 {
                 range "0 .. 255000";
               }
             }
           }
         }
         leaf dynamic-neighbors {
           description "Learn neighbors dynamically on a p2mp interface";
           junos:must "(\" .. interface-type p2mp\")";
           junos:must-message "dynamic-neighbors option can be set only if the interface type is p2mp";
           type empty;
         }
         leaf no-advertise-adjacency-segment {
           description "Do not advertise an adjacency segment for this interface";
           type empty;
         }
         list neighbor {
           key name;
           ordered-by user;
           description "NBMA neighbor";
           junos:must "(!(\" .. dynamic-neighbors\"))";
           junos:must-message "Neighbors cannot be specified manually if dynamic-neighbors is set";
           leaf name {
             description "Address of neighbor";
             type jt:ipaddr;
           }
           leaf eligible {
             description "Eligible to be DR on an NBMA network";
             type empty;
           }
         }
         leaf poll-interval {
           description "Poll interval for NBMA interfaces";
           type union {
             type string {
               pattern "<.*>|$.*";
             }
             type uint32 {
               range "1 .. 65535";
             }
           }
         }
         leaf no-interface-state-traps {
           description "Do not send interface state change traps";
           type empty;
         }
         leaf strict-bfd {
           description "Enable strict bfd over this interface";
           junos:must "(\" .. bfd-liveness-detection\")";
           junos:must-message "strict bfd cannot be configured without bfd.";
           junos:must "(!(\" .. bfd-liveness-detection full-neighbors-only\"))";
           junos:must-message "full-neighbors-only and strict-bfd cannot be configured together";
           type empty;
         }
         container post-convergence-lfa {
           presence "enable post-convergence-lfa";
           junos:must "(\"protocols ospf backup-spf-options use-post-convergence-lfa\")";
           junos:must-message "Not allowed without 'protocols ospf backup-spf-options use-post-convergence-lfa'";
           description "Protect interface using post-convergence backup path";
           uses apply-advanced;
           container node-protection {
             presence "enable node-protection";
             description "Compute backup path assuming node failure";
             uses apply-advanced;
             leaf cost {
               description "Cost for node protection";
               type union {
                 type string {
                   pattern "<.*>|$.*";
                 }
                 type uint16 {
                   range "1 .. 65535";
                 }
               }
             }
           }
           leaf srlg-protection {
             description "Compute backup path assuming SRLG failure";
             type empty;
           }
           leaf fate-sharing-protection {
             description "Compute backup path assuming fate-sharing group failure";
             type empty;
           }
         }
         leaf te-metric {
           description "Traffic engineering metric";
           type union {
             type string {
               pattern "<.*>|$.*";
             }
             type uint32 {
               range "1 .. 4294967295";
             }
           }
         }
         container ldp-synchronization {
           description "Advertise maximum metric until LDP is operational";
           presence "enable ldp-synchronization";
           uses ldp-sync-obj;
         }
         container ipv4-adjacency-segment {
           junos:must "(!(\".. no-advertise-adjacency-segment\"))";
           junos:must-message "ipv4-adjacency-segment can't be configured if no-advertise-adjacency-segment is configured in the same interface";
           description "Configure ipv4 adjacency segment";
           uses apply-advanced;
           container protected {
             description "Adjacency SID is eligible for protection";
             choice adjsid-type {
               case case_1 {
                 container index {
                   description "Adjacency SID indexed from SRGB";
                   leaf index-number {
                     type union {
                       type string {
                         pattern "<.*>|$.*";
                       }
                       type uint32 {
                         range "0 .. 199999";
                       }
                     }
                   }
                 }
               }
               case case_2 {
                 leaf label {
                   description "Adjacency SID from static label pool";
                   type union {
                     type string {
                       pattern "<.*>|$.*";
                     }
                     type uint32 {
                       range "16 .. 1048575";
                     }
                   }
                 }
               }
               case case_3 {
                 leaf dynamic {
                   description "Dynamically allocate an adjacency segment";
                   type empty;
                 }
               }
             }
           }
           container unprotected {
             description "Adjacency SID uneligible for protection";
             choice adjsid-type {
               case case_1 {
                 container index {
                   description "Adjacency SID indexed from SRGB";
                   leaf index-number {
                     type union {
                       type string {
                         pattern "<.*>|$.*";
                       }
                       type uint32 {
                         range "0 .. 199999";
                       }
                     }
                   }
                 }
               }
               case case_2 {
                 leaf label {
                   description "Adjacency SID from static label pool";
                   type union {
                     type string {
                       pattern "<.*>|$.*";
                     }
                     type uint32 {
                       range "16 .. 1048575";
                     }
                   }
                 }
               }
               case case_3 {
                 leaf dynamic {
                   description "Dynamically allocate an adjacency segment";
                   type empty;
                 }
               }
             }
           }
         }
         list lan-neighbor {
           key name;
           ordered-by user;
           description "Configuration specific to a LAN neighbor";
           junos:must "(!(\".. ipv4-adjacency-segment\"))";
           junos:must-message "lan-neighbor can't be configured if ipv4-adjacency-segment is configured in the same interface";
           junos:must "(!(\".. no-advertise-adjacency-segment\"))";
           junos:must-message "lan-neighbor can't be configured if no-advertise-adjacency-segment is configured in the same interface ";
           junos:must "(!(\".. interface-type p2p\"))";
           junos:must-message "lan-neighbor can't be configured for point-to-point interfaces";
           leaf name {
             description "Address of neighbor";
             type jt:ipaddr;
           }
           uses apply-advanced;
           container ipv4-adjacency-segment {
             junos:must "(!(\".. no-advertise-adjacency-segment\"))";
             junos:must-message "ipv4-adjacency-segment can't be configured if no-advertise-adjacency-segment is configured in the same interface";
             description "Configure ipv4 adjacency segment";
             uses apply-advanced;
             container protected {
               description "Adjacency SID is eligible for protection";
               choice adjsid-type {
                 case case_1 {
                   container index {
                     description "Adjacency SID indexed from SRGB";
                     leaf index-number {
                       type union {
                         type string {
                           pattern "<.*>|$.*";
                         }
                         type uint32 {
                           range "0 .. 199999";
                         }
                       }
                     }
                   }
                 }
                 case case_2 {
                   leaf label {
                     description "Adjacency SID from static label pool";
                     type union {
                       type string {
                         pattern "<.*>|$.*";
                       }
                       type uint32 {
                         range "16 .. 1048575";
                       }
                     }
                   }
                 }
                 case case_3 {
                   leaf dynamic {
                     description "Dynamically allocate an adjacency segment";
                     type empty;
                   }
                 }
               }
             }
             container unprotected {
               description "Adjacency SID uneligible for protection";
               choice adjsid-type {
                 case case_1 {
                   container index {
                     description "Adjacency SID indexed from SRGB";
                     leaf index-number {
                       type union {
                         type string {
                           pattern "<.*>|$.*";
                         }
                         type uint32 {
                           range "0 .. 199999";
                         }
                       }
                     }
                   }
                 }
                 case case_2 {
                   leaf label {
                     description "Adjacency SID from static label pool";
                     type union {
                       type string {
                         pattern "<.*>|$.*";
                       }
                       type uint32 {
                         range "16 .. 1048575";
                       }
                     }
                   }
                 }
                 case case_3 {
                   leaf dynamic {
                     description "Dynamically allocate an adjacency segment";
                     type empty;
                   }
                 }
               }
             }
           }
         }
         leaf delay-metric {
           description "Delay metric";
           units "microseconds";
           type union {
             type string {
               pattern "<.*>|$.*";
             }
             type uint32 {
               range "0 .. 16777215";
             }
           }
         }
         container delay-measurement {
           presence "enable delay-measurement";
           description "Enable delay measurement";
           uses apply-advanced;
           leaf probe-interval {
             description "Probe interval";
             units "seconds";
             type union {
               type string {
                 pattern "<.*>|$.*";
               }
               type uint32 {
                 range "1 .. 255";
               }
             }
           }
           leaf probe-count {
             description "Probe count";
             type union {
               type string {
                 pattern "<.*>|$.*";
               }
               type uint32 {
                 range "1 .. 15";
               }
             }
           }
           container advertisement {
             description "Delay advertisement";
             uses apply-advanced;
             container periodic {
               description "Periodic advertisement parameters";
               uses apply-advanced;
               leaf threshold {
                 description "Threshold";
                 units "percentage";
                 type union {
                   type string {
                     pattern "<.*>|$.*";
                   }
                   type uint32 {
                     range "0 .. 100";
                   }
                 }
               }
               leaf interval {
                 description "Interval";
                 units "seconds";
                 type union {
                   type string {
                     pattern "<.*>|$.*";
                   }
                   type uint32 {
                     range "30 .. 3600";
                   }
                 }
               }
             }
             container accelerated {
               presence "enable accelerated";
               description "Accelerated advertisement parameters";
               uses apply-advanced;
               leaf threshold {
                 description "Threshold";
                 units "percentage";
                 type union {
                   type string {
                     pattern "<.*>|$.*";
                   }
                   type uint32 {
                     range "0 .. 100";
                   }
                 }
               }
             }
           }
         }
       }
       leaf no-context-identifier-advertisement {
         description "Disable context identifier advertisments in this area";
         junos:must "(!(\".. context-identifier\"))";
         junos:must-message "no-context-identifier-advertisement and context-identifier attributes are mutually exclusive";
         type empty;
       }
       list peer-interface {
         key name;
         ordered-by user;
         description "Configuration for peer interface";
         leaf name {
           description "Name of peer interface";
           type string;
         }
         uses apply-advanced;
         choice enable-disable {
           case case_1 {
             leaf disable {
               description "Disable OSPF on this control peer";
               type empty;
             }
           }
         }
         leaf retransmit-interval {
           description "Retransmission interval (seconds)";
           type union {
             type string {
               pattern "<.*>|$.*";
             }
             type uint32 {
               range "1 .. 65535";
             }
           }
         }
         leaf transit-delay {
           description "Transit delay (seconds)";
           type union {
             type string {
               pattern "<.*>|$.*";
             }
             type uint32 {
               range "1 .. 65535";
             }
           }
         }
         leaf hello-interval {
           description "Hello interval (seconds)";
           type union {
             type string {
               pattern "<.*>|$.*";
             }
             type uint32 {
               range "1 .. 255";
             }
           }
         }
         leaf dead-interval {
           description "Dead interval (seconds)";
           type union {
             type string {
               pattern "<.*>|$.*";
             }
             type uint32 {
               range "1 .. 65535";
             }
           }
         }
         leaf mtu {
           description "Maximum OSPF packet size";
           type union {
             type string {
               pattern "<.*>|$.*";
             }
             type uint32 {
               range "128 .. 65535";
             }
           }
         }
         choice auth {
           case case_1 {
             container authentication {
               uses juniper-ospf-authentication;
             }
           }
           case case_2 {
             container authentication-key {
               description "Authentication key";
               status deprecated;
               leaf keyname {
                 description "Authentication key value";
                 type jt:unreadable;
               }
               leaf key-id {
                 description "Key ID for MD5 authentication";
                 type union {
                   type string {
                     pattern "<.*>|$.*";
                   }
                   type uint32 {
                     range "0 .. 255";
                   }
                 }
               }
             }
           }
         }
         leaf demand-circuit {
           description "Interface functions as a demand circuit";
           type empty;
         }
         leaf flood-reduction {
           description "Enable flood reduction";
           type empty;
         }
         leaf no-neighbor-down-notification {
           description "Don't inform other protocols about neighbor down events";
           type empty;
         }
       }
       leaf no-source-packet-routing {
         description "Disable SPRING in this area";
         type empty;
       }
       list context-identifier {
         key name;
         ordered-by user;
         description "Configure context identifier in support of edge protection";
         junos:must "(!(\".. no-context-identifier-advertisement\"))";
         junos:must-message "no-context-identifier-advertisement and context-identifier attributes are mutually exclusive";
         leaf name {
           description "Context identifier";
           type jt:ipv4addr;
         }
         uses apply-advanced;
       }
       list label-switched-path {
         key name;
         ordered-by user;
         description "Configuration for advertisement of a label-switched path";
         junos:must "(!(\".. .. traffic-engineering multicast-rpf-routes\"))";
         junos:must-message "cannot advertise LSPs when using multicast-rpf-routes";
         leaf name {
           description "Name of label-switched path to be advertised";
           type string {
             length "1 .. 64";
           }
         }
         uses apply-advanced;
         choice enable-disable {
           case case_1 {
             leaf disable {
               description "Disable OSPF on this label-switched path";
               type empty;
             }
           }
         }
         leaf metric {
           description "Interface metric";
           type union {
             type string {
               pattern "<.*>|$.*";
             }
             type uint16 {
               range "1 .. 65535";
             }
           }
         }
         list topology {
           key name;
           ordered-by user;
           description "Topology specific attributes";
           leaf name {
             description "Topology name";
             type string;
           }
           uses apply-advanced;
           leaf disable {
             description "Disable this topology";
             type empty;
           }
           leaf metric {
             description "Topology metric";
             type union {
               type string {
                 pattern "<.*>|$.*";
               }
               type uint16 {
                 range "1 .. 65535";
               }
             }
           }
           container bandwidth-based-metrics {
             junos:must "(\".. metric\")";
             junos:must-message "Metric must be configured";
             description "Configure bandwidth based metrics";
             uses apply-advanced;
             list bandwidth {
               key name;
               description "Bandwidth threshold";
               leaf name {
                 type string;
               }
               leaf metric {
                 description "Metric associated with specified bandwidth";
                 type union {
                   type string {
                     pattern "<.*>|$.*";
                   }
                   type uint16 {
                     range "1 .. 65535";
                   }
                 }
               }
             }
           }
         }
       }
     }
     choice enable-disable {
       case case_1 {
         leaf disable {
           description "Disable OSPF";
           type empty;
         }
       }
     }
     container traceoptions {
       description "Trace options for OSPF";
       uses apply-advanced;
       container file {
         description "Trace file options";
         leaf filename {
           description "Name of file in which to write trace information";
           type string {
             length "1 .. 1024";
             junos:posix-pattern "![/ %]";
             junos:pattern-message "Must not contain '/', % or a space";
           }
         }
         leaf replace {
           description "Replace trace file rather than appending to it";
           status deprecated;
           type empty;
         }
         leaf size {
           description "Maximum trace file size";
           type string;
         }
         leaf files {
           description "Maximum number of trace files";
           default "10";
           type union {
             type string {
               pattern "<.*>|$.*";
             }
             type uint32 {
               range "2 .. 1000";
             }
           }
         }
         leaf no-stamp {
           description "Do not timestamp trace file";
           status deprecated;
           type empty;
         }
         choice world-readable-choice {
           leaf world-readable {
             description "Allow any user to read the log file";
             type empty;
           }
           leaf no-world-readable {
             description "Don't allow any user to read the log file";
             type empty;
           }
         }
       }
       list flag {
         key name;
         ordered-by user;
         description "Tracing parameters";
         leaf name {
           type enumeration {
             enum "spf" {
               description "Trace SPF calculations";
             }
             enum "error" {
               description "Trace errored packets";
             }
             enum "event" {
               description "Trace OSPF state machine events";
             }
             enum "packet-dump" {
               description "Dump the contents of selected packet types";
             }
             enum "flooding" {
               description "Trace LSA flooding";
             }
             enum "lsa-analysis" {
               description "Trace LSA analysis";
             }
             enum "packets" {
               description "Trace all OSPF packets";
             }
             enum "hello" {
               description "Trace hello packets";
             }
             enum "database-description" {
               description "Trace database description packets";
             }
             enum "lsa-request" {
               description "Trace LSA request packets";
             }
             enum "lsa-update" {
               description "Trace LSA update packets";
             }
             enum "lsa-ack" {
               description "Trace LSA acknowledgment packets";
             }
             enum "ldp-synchronization" {
               description "Trace synchronization between OSPF and LDP";
             }
             enum "on-demand" {
               description "Trace demand circuit extensions";
             }
             enum "nsr-synchronization" {
               description "Trace NSR synchronization events";
             }
             enum "graceful-restart" {
               description "Trace graceful restart";
             }
             enum "restart-signaling" {
               description "Trace restart signaling";
             }
             enum "backup-spf" {
               description "Trace backup SPF (LFA) specific events";
             }
             enum "source-packet-routing" {
               description "Trace source packet routing (SPRING) events";
             }
             enum "post-convergence-lfa" {
               description "Trace post-convergence-lfa related events";
             }
             enum "flex-algorithm" {
               description "Trace flex-algorithm related events";
             }
             enum "rmopd" {
               description "Trace rmopd interactions";
             }
             enum "route" {
               description "Trace routing information";
             }
             enum "normal" {
               description "Trace normal events";
             }
             enum "general" {
               description "Trace general events";
             }
             enum "state" {
               description "Trace state transitions";
             }
             enum "policy" {
               description "Trace policy processing";
             }
             enum "task" {
               description "Trace routing protocol task processing";
             }
             enum "timer" {
               description "Trace routing protocol timer processing";
             }
             enum "all" {
               description "Trace everything";
             }
           }
         }
         leaf send {
           description "Trace transmitted packets";
           type empty;
         }
         leaf receive {
           description "Trace received packets";
           type empty;
         }
         leaf detail {
           description "Trace detailed information";
           type empty;
         }
         leaf disable {
           description "Disable this trace flag";
           type empty;
         }
       }
     }
     container spf-options {
       description "Configure options for SPF";
       uses apply-advanced;
       leaf delay {
         description "Time to wait before running an SPF";
         units "milliseconds";
         type union {
           type string {
             pattern "<.*>|$.*";
           }
           type uint32 {
             range "50 .. 8000";
           }
         }
       }
       leaf holddown {
         description "Time to hold down before running an SPF";
         units "milliseconds";
         type union {
           type string {
             pattern "<.*>|$.*";
           }
           type uint32 {
             range "2000 .. 20000";
           }
         }
       }
       leaf rapid-runs {
         description "Number of maximum rapid SPF runs before holddown";
         type union {
           type string {
             pattern "<.*>|$.*";
           }
           type uint32 {
             range "1 .. 10";
           }
         }
       }
       leaf no-ignore-our-externals {
         description "Do not ignore self-generated external and NSSA LSAs";
         type empty;
       }
     }
     leaf prefix-export-limit {
       description "Maximum number of prefixes that can be exported";
       type union {
         type string {
           pattern "<.*>|$.*";
         }
         type uint32 {
           range "0 .. 4294967295";
         }
       }
     }
     container rib-groups {
       description "Routing table groups for importing OSPF routes";
       uses apply-advanced;
       leaf inet {
         description "Name of the IPv4/v6 routing table group";
         junos:must "(\"routing-options rib-groups $$\")";
         junos:must-message "Referenced rib-groups must be defined";
         junos:must "(!(\".. topology $$={default} rib-group\"))";
         junos:must-message "rib-group cannot be used with topology default rib-group";
         type string;
       }
       leaf inet3 {
         description "Name of the IPv4/v6 inet.3 routing table group";
         junos:must "(\"routing-options rib-groups $$\")";
         junos:must-message "Referenced rib-groups must be defined";
         junos:must "(!(\".. topology $$={default} rib-group\"))";
         junos:must-message "rib-group cannot be used with topology default rib-group";
         type string;
       }
     }
     leaf job-stats {
       description "Collect job statistics";
       type empty;
     }
     container overload {
       presence "enable overload";
       description "Set the overload mode (repel transit traffic)";
       uses apply-advanced;
       leaf timeout {
         description "Time after which overload mode is reset";
         units "seconds";
         type union {
           type string {
             pattern "<.*>|$.*";
           }
           type uint32 {
             range "60 .. 3600";
           }
         }
       }
       leaf allow-route-leaking {
         description "Allow routes to be leaked when overload is configured";
         type empty;
       }
       leaf stub-network {
         description "Advertise Stub Network with maximum metric";
         type empty;
       }
       leaf intra-area-prefix {
         description "Advertise Intra Area Prefix with maximum metric";
         type empty;
       }
       leaf as-external {
         description "Advertise As External with maximum usable metric";
         type empty;
       }
     }
     container database-protection {
       presence "enable database-protection";
       description "Configure database protection attributes";
       uses apply-advanced;
       leaf maximum-lsa {
         description "Maximum allowed non self-generated LSAs";
         type union {
           type string {
             pattern "<.*>|$.*";
           }
           type uint32 {
             range "1 .. 1000000";
           }
         }
       }
       leaf warning-only {
         description "Emit only a warning when LSA maximum limit is exceeded";
         type empty;
       }
       leaf warning-threshold {
         description "Percentage of LSA maximum above which to trigger warning";
         units "percent";
         type union {
           type string {
             pattern "<.*>|$.*";
           }
           type uint8 {
             range "30 .. 100";
           }
         }
       }
       leaf ignore-count {
         description "Maximum number of times to go into ignore state";
         type union {
           type string {
             pattern "<.*>|$.*";
           }
           type uint8 {
             range "1 .. 32";
           }
         }
       }
       leaf ignore-time {
         description "Time to stay in ignore state and ignore all neighbors";
         units "seconds";
         type union {
           type string {
             pattern "<.*>|$.*";
           }
           type uint16 {
             range "30 .. 3600";
           }
         }
       }
       leaf reset-time {
         description "Time after which the ignore count gets reset to zero";
         units "seconds";
         type union {
           type string {
             pattern "<.*>|$.*";
           }
           type uint32 {
             range "60 .. 86400";
           }
         }
       }
     }
     container graceful-restart {
       description "Configure graceful restart attributes";
       uses apply-advanced;
       choice enable-disable {
         case case_1 {
           leaf disable {
             description "Disable OSPF graceful restart capability";
             type empty;
           }
         }
       }
       leaf restart-duration {
         description "Time for all neighbors to become full";
         units "seconds";
         type union {
           type string {
             pattern "<.*>|$.*";
           }
           type uint32 {
             range "1 .. 3600";
           }
         }
       }
       leaf notify-duration {
         description "Time to send all max-aged grace LSAs";
         units "seconds";
         type union {
           type string {
             pattern "<.*>|$.*";
           }
           type uint32 {
             range "1 .. 3600";
           }
         }
       }
       container helper-disable {
         presence "enable helper-disable";
         description "Disable graceful restart helper capability";
         uses apply-advanced;
         choice disable-choices {
           case case_1 {
             leaf standard {
               description "Disable helper-mode for rfc3623 based GR";
               type empty;
             }
           }
           case case_2 {
             leaf restart-signaling {
               description "Disable helper mode for restart-signaling ";
               type empty;
             }
           }
           case case_3 {
             leaf both {
               description "Disable helper mode for both the types of GR";
               type empty;
             }
           }
         }
       }
       leaf no-strict-lsa-checking {
         description "Do not abort graceful helper mode upon LSA changes";
         junos:must "(!(\".. helper-disable\"))";
         junos:must-message "To configure no-strict-lsa-checking, helper-disable must not be set";
         type empty;
       }
     }
     leaf route-type-community {
       description "Specify BGP extended community value to encode OSPF route type";
       type enumeration {
         enum "iana" {
           description "BGP extended community value used is 0x0306";
         }
         enum "vendor" {
           description "Vendor BGP extended community value used is 0x8000";
         }
       }
     }
     container domain-id {
       description "Configure domain ID";
       choice domain_id_or_disable {
         case case_1 {
           leaf domain-id {
             description "Domain ID";
             type string;
           }
         }
         case case_2 {
           leaf disable {
             description "Disable domain ID";
             type empty;
           }
         }
       }
     }
     choice domain_vpn_tag_or_disable {
       case case_1 {
         leaf domain-vpn-tag {
           description "Domain VPN tag for external LSA";
           type union {
             type string {
               pattern "<.*>|$.*";
             }
             type uint32 {
               range "0 .. 4294967295";
             }
           }
         }
       }
       case case_2 {
         leaf no-domain-vpn-tag {
           description "Disable domain VPN tag";
           type empty;
         }
       }
     }
     leaf preference {
       description "Preference of internal routes";
       type union {
         type uint32;
         type string {
           pattern "<.*>|$.*";
         }
       }
     }
     leaf external-preference {
       description "Preference of external routes";
       type union {
         type uint32;
         type string {
           pattern "<.*>|$.*";
         }
       }
     }
     leaf labeled-preference {
       description "Preference of labeled routes";
       type union {
         type uint32;
         type string {
           pattern "<.*>|$.*";
         }
       }
     }
     leaf-list export {
       ordered-by user;
       description "Export policy";
       type jt:policy-algebra;
     }
     leaf-list import {
       ordered-by user;
       description "Import policy (for external routes or setting priority)";
       type jt:policy-algebra;
     }
     leaf reference-bandwidth {
       description "Bandwidth for calculating metric defaults";
       type string;
     }
     leaf lsa-refresh-interval {
       description "LSA refresh interval (minutes)";
       default "50";
       type union {
         type string {
           pattern "<.*>|$.*";
         }
         type uint32 {
           range "25 .. 50";
         }
       }
     }
     leaf spf-delay {
       description "Time to wait before running an SPF";
       status deprecated;
       units "milliseconds";
       junos:must "(!(\".. spf-options delay\"))";
       junos:must-message "You can only configure either spf-delay or delay under spf-options";
       type union {
         type string {
           pattern "<.*>|$.*";
         }
         type uint32 {
           range "50 .. 8000";
         }
       }
     }
     leaf no-rfc-1583 {
       description "Disable RFC1583 compatibility";
       type empty;
     }
     leaf forwarding-address-to-broadcast {
       description "Set forwarding address in Type 5 LSA in broadcast network";
       type empty;
     }
     choice nssa-abr-option {
       case case_1 {
         leaf no-nssa-abr {
           description "Disable full NSSA functionality at ABR";
           type empty;
         }
       }
     }
     container sham-link {
       presence "enable sham-link";
       description "Configure parameters for sham links";
       uses apply-advanced;
       leaf local {
         description "Local sham link endpoint address";
         type jt:ipaddr;
       }
       leaf no-advertise-local {
         description "Don't advertise local sham link endpoint as stub in router LSA";
         status deprecated;
         type empty;
       }
     }
   }
   grouping juniper-protocols-pim {
     uses apply-advanced;
     container family {
       description "Local address family";
       container any {
         presence "enable any";
         description "Default properties for all address families";
         uses apply-advanced;
         leaf disable {
           description "Disable all families";
           type empty;
         }
       }
       container inet {
         presence "enable inet";
         description "IPv4 specific properties";
         uses apply-advanced;
         choice enable-disable {
           case case_1 {
             leaf disable {
               description "Disable PIMv4 on all interfaces";
               type empty;
             }
           }
         }
       }
       container inet6 {
         presence "enable inet6";
         description "IPv6 specific properties";
         uses apply-advanced;
         choice enable-disable {
           case case_1 {
             leaf disable {
               description "Disable PIMv6 on all interfaces";
               type empty;
             }
           }
         }
       }
     }
     choice enable-disable {
       case case_1 {
         leaf disable {
           description "Disable PIM";
           type empty;
         }
       }
     }
     container nonstop-routing {
       junos:must "(\"routing-options nonstop-routing\")";
       junos:must-message "To disable PIM nonstop-routing, non-stop routing must be globally enabled.";
       description "Configure PIM nonstop-routing attributes";
       uses apply-advanced;
       choice enable-disable {
         case case_1 {
           leaf disable {
             description "Disable non-stop routing for PIM";
             type empty;
           }
         }
       }
     }
     container traceoptions {
       description "Trace options for PIM";
       uses apply-advanced;
       container file {
         description "Trace file options";
         leaf filename {
           description "Name of file in which to write trace information";
           type string {
             length "1 .. 1024";
             junos:posix-pattern "![/ %]";
             junos:pattern-message "Must not contain '/', % or a space";
           }
         }
         leaf replace {
           description "Replace trace file rather than appending to it";
           status deprecated;
           type empty;
         }
         leaf size {
           description "Maximum trace file size";
           type string;
         }
         leaf files {
           description "Maximum number of trace files";
           default "10";
           type union {
             type string {
               pattern "<.*>|$.*";
             }
             type uint32 {
               range "2 .. 1000";
             }
           }
         }
         leaf no-stamp {
           description "Do not timestamp trace file";
           status deprecated;
           type empty;
         }
         choice world-readable-choice {
           leaf world-readable {
             description "Allow any user to read the log file";
             type empty;
           }
           leaf no-world-readable {
             description "Don't allow any user to read the log file";
             type empty;
           }
         }
       }
       list flag {
         key name;
         ordered-by user;
         description "Tracing parameters";
         leaf name {
           type enumeration {
             enum "route" {
               description "Trace routing information";
             }
             enum "packets" {
               description "Trace all PIM packets";
             }
             enum "hello" {
               description "Trace hello packets";
             }
             enum "register" {
               description "Trace register/register-stop messages";
             }
             enum "join" {
               description "Trace join/prune/graft/graft-ack messages";
             }
             enum "prune" {
               description "Trace join/prune/graft/graft-ack messages";
             }
             enum "graft" {
               description "Trace join/prune/graft/graft-ack messages";
             }
             enum "bootstrap" {
               description "Trace bootstrap/RP/auto-RP messages";
             }
             enum "rp" {
               description "Trace bootstrap/RP/auto-RP messages";
             }
             enum "autorp" {
               description "Trace bootstrap/RP/auto-RP messages";
             }
             enum "assert" {
               description "Trace assert messages";
             }
             enum "mdt" {
               description "Trace messages related to multicast data tunnels";
             }
             enum "nsr-synchronization" {
               description "Trace NSR synchronization events";
             }
             enum "bidirectional-df-election" {
               description "Trace bidirectional PIM DF election events";
             }
             enum "mofrr" {
               description "Trace Multicast only Fast Re-Route messages";
             }
             enum "normal" {
               description "Trace normal events";
             }
             enum "general" {
               description "Trace general events";
             }
             enum "state" {
               description "Trace state transitions";
             }
             enum "policy" {
               description "Trace policy processing";
             }
             enum "task" {
               description "Trace routing protocol task processing";
             }
             enum "timer" {
               description "Trace routing protocol timer processing";
             }
             enum "all" {
               description "Trace everything";
             }
           }
         }
         leaf send {
           description "Trace transmitted packets";
           type empty;
         }
         leaf receive {
           description "Trace received packets";
           type empty;
         }
         leaf detail {
           description "Trace detailed information";
           type empty;
         }
         leaf disable {
           description "Disable this trace flag";
           type empty;
         }
         container filter {
           description "Filter to apply to this flag";
           presence "enable filter";
           uses pim_filter_obj;
         }
       }
     }
     container dense-groups {
       description "Dense mode groups for sparse-dense mode";
       uses apply-advanced;
       leaf dynamic-reject {
         description "Reject dynamic autorp negative dense-mode prefixes learnt from network";
         type empty;
       }
       list pim-dense-group-type {
         key name;
         ordered-by user;
         leaf name {
           description "Group address or range to forward in dense mode";
           type jt:ipprefix;
         }
         choice dense-group-flags {
           case case_1 {
             leaf reject {
               description "Do not include prefix as dense mode; force sparse mode";
               type empty;
             }
           }
           case case_2 {
             leaf announce {
               description "Advertise as negative prefix in auto-RP announce messages";
               type empty;
             }
           }
         }
       }
     }
     leaf vpn-tunnel-source {
       description "Source address for the provider space mGRE tunnel";
       status deprecated;
       type jt:ipv4addr;
     }
     leaf vpn-group-address {
       description "Group address for the VPN in provider space";
       status deprecated;
       junos:must "(!(\".. .. .. provider-tunnel pim-ssm\"))";
       junos:must-message "'provider-tunnel pim-ssm' can not be configured with 'pim vpn-group-address'. Please disable one of them.";
       junos:must "((!(\".. .. .. provider-tunnel pim-asm\") || \".. .. .. provider-tunnel pim-asm group-address $$\"))";
       junos:must-message "MVPN inclusive provider-tunnel group-address must be same as 'vpn-group-address'";
       type jt:ipv4addr;
     }
     leaf-list tunnel-devices {
       ordered-by user;
       description "Tunnel devices to be used for creating mt interfaces";
       type union {
         type jt:interface-device;
         type string {
           pattern "<.*>|$.*";
         }
       }
     }
     container rpf-selection {
       description "Select RPF neighbor";
       uses apply-advanced;
       list group {
         key name;
         ordered-by user;
         description "IP prefix of multicast group";
         leaf name {
           description "IP prefix of group";
           type jt:ipprefix;
         }
         uses apply-advanced;
         container wildcard-source {
           presence "enable wildcard-source";
           description "Select RPF for (*,g) and unspecified (s,g) joins";
           uses apply-advanced;
           leaf next-hop {
             description "Next-hop address";
             type jt:ipaddr;
           }
         }
         list source {
           key name;
           ordered-by user;
           description "IP prefix of one or more multicast sources";
           leaf name {
             description "IP prefix of source";
             type jt:ipprefix;
           }
           uses apply-advanced;
           leaf next-hop {
             description "Next-hop address";
             type jt:ipaddr;
           }
         }
       }
       list prefix-list {
         key name;
         ordered-by user;
         description "Multicast group prefix list";
         leaf name {
           description "Name of prefix list to match against";
           junos:must "(\"policy-options prefix-list $$\")";
           junos:must-message "This prefix-list must be configured in policy-options.";
           type string;
         }
         uses apply-advanced;
         container wildcard-source {
           presence "enable wildcard-source";
           description "Select RPF for (*,g) and unspecified (s,g) joins";
           uses apply-advanced;
           leaf next-hop {
             description "Next-hop address";
             type jt:ipaddr;
           }
         }
         list source {
           key name;
           ordered-by user;
           description "IP prefix of one or more multicast sources";
           leaf name {
             description "IP prefix of source";
             type jt:ipprefix;
           }
           uses apply-advanced;
           leaf next-hop {
             description "Next-hop address";
             type jt:ipaddr;
           }
         }
       }
     }
     container mvpn {
       presence "enable mvpn";
       description "PIM MVPN control-plane options";
       uses apply-advanced;
       container autodiscovery {
         junos:must "(!(\".. .. vpn-group-address\"))";
         junos:must-message "PIM MVPN autodiscovery options cannot be configured with 'vpn-group-address'";
         junos:must "(\".. .. .. mvpn\")";
         junos:must-message "Autodiscovery for PIM MVPNs requires 'protocols mvpn'";
         junos:must "(!(\".. .. mdt\"))";
         junos:must-message "PIM MVPN auto-discovery cannot be configured with 'pim mdt'";
         description "PE router autodiscovery options for SSM MDTs";
         status deprecated;
         uses apply-advanced;
         leaf inet-mdt {
           description "MDT-SAFI PE autodiscovery for SSM MDTs";
           type empty;
         }
       }
       container family {
         description "PIM MVPN address family";
         uses apply-advanced;
         container inet {
           description "IPv4 PIM MVPN specific properties";
           uses apply-advanced;
           leaf rosen-mvpn {
             status deprecated;
             type empty;
           }
           leaf ngen-mvpn {
             status deprecated;
             junos:must "(\".. .. .. .. .. mvpn\")";
             junos:must-message "Requires 'protocols mvpn'";
             type empty;
           }
           container autodiscovery {
             junos:must "(!(\".. .. .. .. vpn-group-address\"))";
             junos:must-message "PIM MVPN autodiscovery options cannot be configured with 'vpn-group-address'";
             junos:must "(\".. .. .. .. .. mvpn\")";
             junos:must-message "Autodiscovery for PIM MVPNs requires 'protocols mvpn'";
             junos:must "(!(\".. .. .. .. mdt\"))";
             junos:must-message "PIM MVPN auto-discovery cannot be configured with 'pim mdt'";
             description "PE router autodiscovery options for SSM MDTs";
             uses apply-advanced;
             leaf inet-mdt {
               description "MDT-SAFI PE autodiscovery for SSM MDTs";
               type empty;
             }
           }
           leaf disable {
             description "Disable family IPv4";
             type empty;
           }
         }
         container inet6 {
           description "IPv6 PIM MVPN specific properties";
           uses apply-advanced;
           leaf rosen-mvpn {
             status deprecated;
             type empty;
           }
           leaf ngen-mvpn {
             status deprecated;
             junos:must "(\".. .. .. .. .. mvpn\")";
             junos:must-message "Requires 'protocols mvpn'";
             type empty;
           }
           container autodiscovery {
             junos:must "(!(\".. .. .. .. vpn-group-address\"))";
             junos:must-message "PIM MVPN autodiscovery options cannot be configured with 'vpn-group-address'";
             junos:must "(\".. .. .. .. .. mvpn\")";
             junos:must-message "Autodiscovery for PIM MVPNs requires 'protocols mvpn'";
             junos:must "(!(\".. .. .. .. mdt\"))";
             junos:must-message "PIM MVPN auto-discovery cannot be configured with 'pim mdt'";
             description "PE router autodiscovery options for SSM MDTs";
             uses apply-advanced;
             leaf inet-mdt {
               description "MDT-SAFI PE autodiscovery for SSM MDTs";
               type empty;
             }
           }
           leaf disable {
             description "Disable family IPv6";
             type empty;
           }
         }
       }
     }
     container rib-group {
       description "Routing table group";
       uses rib_group_type;
     }
     leaf-list import {
       ordered-by user;
       description "PIM sparse import join policy";
       type jt:policy-algebra;
     }
     leaf-list export {
       ordered-by user;
       description "PIM sparse export join policy";
       type jt:policy-algebra;
     }
     container mldp-inband-signalling {
       presence "enable mldp-inband-signalling";
       junos:must "(!(\"system processes routing bgp rib-sharding\"))";
       junos:must-message "Can't be configured together with rib-sharding";
       uses apply-advanced;
       leaf-list policy {
         ordered-by user;
         description "PIM MLDP join translation filter policy";
         type jt:policy-algebra;
       }
     }
     container rpf-vector {
       description "RPF vector TLV";
       uses apply-advanced;
       leaf-list policy {
         ordered-by user;
         description "RPF vector TLV include policy";
         type jt:policy-algebra;
       }
     }
     leaf assert-timeout {
       description "Set assert timeout";
       default "180";
       type union {
         type string {
           pattern "<.*>|$.*";
         }
         type uint32 {
           range "5 .. 210";
         }
       }
     }
     leaf assert-robust-count {
       description "Number of assert messages an assert winner sends in one cycle";
       default "2";
       type union {
         type string {
           pattern "<.*>|$.*";
         }
         type uint32 {
           range "1 .. 5";
         }
       }
     }
     leaf join-prune-timeout {
       description "Set join/prune timeout";
       default "210";
       type union {
         type string {
           pattern "<.*>|$.*";
         }
         type uint32 {
           range "210 .. 420";
         }
       }
     }
     container spt-threshold {
       description "Set shortest-path-tree threshold policy";
       uses apply-advanced;
       leaf-list infinity {
         ordered-by user;
         description "Apply policy to always remain on shared tree";
         type jt:policy-algebra;
       }
     }
     container sglimit {
       description "Set limit on number of (S,G) states ";
       uses apply-advanced;
       list family {
         key name;
         ordered-by user;
         description "Protocol family";
         junos:must "(!(\".. maximum\"))";
         junos:must-message "Family wise threshold cannot be configuredif global threshold is already configured";
         leaf name {
           type enumeration {
             enum "inet" {
               description "IPv4 family";
             }
             enum "inet6" {
               description "IPv6 family";
             }
           }
         }
         uses apply-advanced;
         leaf maximum {
           description "Maximum limit above which additional entries are not accepted";
           type union {
             type string {
               pattern "<.*>|$.*";
             }
             type uint32 {
               range "1 .. 65535";
             }
           }
         }
         leaf threshold {
           description "Percentage of maximum at which to start generating warnings";
           junos:must "(\".. maximum\")";
           junos:must-message "To configure threshold, maximum must be configured";
           type union {
             type string {
               pattern "<.*>|$.*";
             }
             type uint32 {
               range "1 .. 100";
             }
           }
         }
         leaf log-interval {
           description "Time between successive log messages";
           junos:must "(\".. maximum\")";
           junos:must-message "To configure log-interval, maximum must be configured";
           type union {
             type string {
               pattern "<.*>|$.*";
             }
             type uint32 {
               range "1 .. 65535";
             }
           }
         }
       }
       leaf maximum {
         description "Maximum limit above which additional entries are not accepted";
         type union {
           type string {
             pattern "<.*>|$.*";
           }
           type uint32 {
             range "1 .. 65535";
           }
         }
       }
       leaf threshold {
         description "Percentage of maximum at which to start generating warnings";
         junos:must "(\".. maximum\")";
         junos:must-message "To configure threshold, maximum must be configured";
         type union {
           type string {
             pattern "<.*>|$.*";
           }
           type uint32 {
             range "1 .. 100";
           }
         }
       }
       leaf log-interval {
         description "Time between successive log messages";
         junos:must "(\".. maximum\")";
         junos:must-message "To configure log-interval, maximum must be configured";
         type union {
           type string {
             pattern "<.*>|$.*";
           }
           type uint32 {
             range "1 .. 65535";
           }
         }
       }
     }
     container rp {
       junos:must "(!(\" .. passive\"))";
       junos:must-message "pim rp cannot be configured with pim passive";
       description "Router's rendezvous point properties";
       uses apply-advanced;
       leaf bootstrap-priority {
         description "Eligibility to be the bootstrap router (IPv4 only)";
         type union {
           type string {
             pattern "<.*>|$.*";
           }
           type uint32 {
             range "0 .. 255";
           }
         }
       }
       leaf-list bootstrap-import {
         ordered-by user;
         description "Bootstrap import policy (IPv4 only)";
         type jt:policy-algebra;
       }
       leaf-list bootstrap-export {
         ordered-by user;
         description "Bootstrap export policy (IPv4 only)";
         type jt:policy-algebra;
       }
       container bootstrap {
         description "Bootstrap properties";
         uses apply-advanced;
         container family {
           description "Bootstrap address family";
           container inet {
             description "IPv4 bootstrap properties";
             junos:must "(!((\".. .. .. bootstrap-priority\" || (\".. .. .. bootstrap-import\" || \".. .. .. bootstrap-export\"))))";
             junos:must-message "Duplicate IPv4 bootstrap configuration";
             uses pim_bootstrap_options_type;
           }
           container inet6 {
             description "IPv6 bootstrap properties";
             uses pim_bootstrap_options_type;
           }
         }
       }
       container register-limit {
         description "Set limit on incoming registers that create (S,G) state";
         uses apply-advanced;
         list family {
           key name;
           ordered-by user;
           description "Protocol family";
           junos:must "(!(\".. maximum\"))";
           junos:must-message "Family wise threshold cannot be configuredif global threshold is already configured";
           leaf name {
             type enumeration {
               enum "inet" {
                 description "IPv4 family";
               }
               enum "inet6" {
                 description "IPv6 family";
               }
             }
           }
           uses apply-advanced;
           leaf maximum {
             description "Maximum limit above which additional entries are not accepted";
             type union {
               type string {
                 pattern "<.*>|$.*";
               }
               type uint32 {
                 range "1 .. 65535";
               }
             }
           }
           leaf threshold {
             description "Percentage of maximum at which to start generating warnings";
             junos:must "(\".. maximum\")";
             junos:must-message "To configure threshold, maximum must be configured";
             type union {
               type string {
                 pattern "<.*>|$.*";
               }
               type uint32 {
                 range "1 .. 100";
               }
             }
           }
           leaf log-interval {
             description "Time between successive log messages";
             junos:must "(\".. maximum\")";
             junos:must-message "To configure log-interval, maximum must be configured";
             type union {
               type string {
                 pattern "<.*>|$.*";
               }
               type uint32 {
                 range "1 .. 65535";
               }
             }
           }
         }
         leaf maximum {
           description "Maximum limit above which additional entries are not accepted";
           type union {
             type string {
               pattern "<.*>|$.*";
             }
             type uint32 {
               range "1 .. 65535";
             }
           }
         }
         leaf threshold {
           description "Percentage of maximum at which to start generating warnings";
           junos:must "(\".. maximum\")";
           junos:must-message "To configure threshold, maximum must be configured";
           type union {
             type string {
               pattern "<.*>|$.*";
             }
             type uint32 {
               range "1 .. 100";
             }
           }
         }
         leaf log-interval {
           description "Time between successive log messages";
           junos:must "(\".. maximum\")";
           junos:must-message "To configure log-interval, maximum must be configured";
           type union {
             type string {
               pattern "<.*>|$.*";
             }
             type uint32 {
               range "1 .. 65535";
             }
           }
         }
       }
       container group-rp-mapping {
         description "Group-rp-mapping";
         uses apply-advanced;
         list family {
           key name;
           ordered-by user;
           description "Protocol family";
           junos:must "(!(\".. maximum\"))";
           junos:must-message "Family wise threshold cannot be configuredif global threshold is already configured";
           leaf name {
             type enumeration {
               enum "inet" {
                 description "IPv4 family";
               }
               enum "inet6" {
                 description "IPv6 family";
               }
             }
           }
           uses apply-advanced;
           leaf maximum {
             description "Maximum limit above which additional entries are not accepted";
             type union {
               type string {
                 pattern "<.*>|$.*";
               }
               type uint32 {
                 range "1 .. 65535";
               }
             }
           }
           leaf threshold {
             description "Percentage of maximum at which to start generating warnings";
             junos:must "(\".. maximum\")";
             junos:must-message "To configure threshold, maximum must be configured";
             type union {
               type string {
                 pattern "<.*>|$.*";
               }
               type uint32 {
                 range "1 .. 100";
               }
             }
           }
           leaf log-interval {
             description "Time between successive log messages";
             junos:must "(\".. maximum\")";
             junos:must-message "To configure log-interval, maximum must be configured";
             type union {
               type string {
                 pattern "<.*>|$.*";
               }
               type uint32 {
                 range "1 .. 65535";
               }
             }
           }
         }
         leaf maximum {
           description "Maximum limit above which additional entries are not accepted";
           type union {
             type string {
               pattern "<.*>|$.*";
             }
             type uint32 {
               range "1 .. 65535";
             }
           }
         }
         leaf threshold {
           description "Percentage of maximum at which to start generating warnings";
           junos:must "(\".. maximum\")";
           junos:must-message "To configure threshold, maximum must be configured";
           type union {
             type string {
               pattern "<.*>|$.*";
             }
             type uint32 {
               range "1 .. 100";
             }
           }
         }
         leaf log-interval {
           description "Time between successive log messages";
           junos:must "(\".. maximum\")";
           junos:must-message "To configure log-interval, maximum must be configured";
           type union {
             type string {
               pattern "<.*>|$.*";
             }
             type uint32 {
               range "1 .. 65535";
             }
           }
         }
       }
       leaf-list rp-register-policy {
         ordered-by user;
         description "RP policy applied to incoming register messages";
         type jt:policy-algebra;
       }
       leaf-list dr-register-policy {
         ordered-by user;
         description "DR policy applied to outgoing register messages";
         type jt:policy-algebra;
       }
       container local {
         description "Router's local RP properties";
         uses apply-advanced;
         leaf address {
           description "Local RP address (IPv4 only)";
           type jt:ipv4addr;
         }
         choice enable-disable {
           case case_1 {
             leaf disable {
               description "Disable this RP (IPv4 only)";
               type empty;
             }
           }
         }
         leaf priority {
           description "Router's priority for becoming an RP (IPv4 only)";
           type union {
             type string {
               pattern "<.*>|$.*";
             }
             type uint32 {
               range "0 .. 255";
             }
           }
         }
         leaf hold-time {
           description "How long neighbor considers this router to be up, in seconds (IPv4 only)";
           type union {
             type string {
               pattern "<.*>|$.*";
             }
             type uint32 {
               range "1 .. 65535";
             }
           }
         }
         list group-ranges {
           key name;
           ordered-by user;
           description "Group address range for which this router can be an RP (IPv4 only)";
           leaf name {
             type jt:ipv4prefix;
           }
           uses apply-advanced;
         }
         leaf override {
           description "Static RP mapping will take precedence over dynamic";
           type empty;
         }
         leaf process-non-null-as-null-register {
           description "Process incoming non null registers as null registers";
           type empty;
         }
         container family {
           description "Local RP address family";
           container inet {
             description "IPv4 local RP properties";
             uses apply-advanced;
             leaf address {
               description "Local RP address";
               type jt:ipv4addr;
             }
             choice enable-disable {
               case case_1 {
                 leaf disable {
                   description "Disable this RP";
                   type empty;
                 }
               }
             }
             leaf priority {
               description "Router's priority for becoming an RP";
               type union {
                 type string {
                   pattern "<.*>|$.*";
                 }
                 type uint32 {
                   range "0 .. 255";
                 }
               }
             }
             leaf hold-time {
               description "How long neighbor considers this router to be up, in seconds";
               type union {
                 type string {
                   pattern "<.*>|$.*";
                 }
                 type uint32 {
                   range "1 .. 65535";
                 }
               }
             }
             list group-ranges {
               key name;
               ordered-by user;
               description "Group address range for which this router can be an RP";
               leaf name {
                 type jt:ipv4prefix;
               }
               uses apply-advanced;
             }
             leaf override {
               description "Static RP mapping will take precedence over dynamic";
               type empty;
             }
             container anycast-pim {
               description "Attributes for IPv4 anycast PIM";
               uses apply-advanced;
               container rp-set {
                 description "Rendezvous points belonging to anycast RP set";
                 uses apply-advanced;
                 list address {
                   key name;
                   ordered-by user;
                   description "IPv4 address of one or more remote anycast RPs";
                   leaf name {
                     description "IPv4 address of remote anycast RP";
                     type jt:ipaddr;
                   }
                   uses apply-advanced;
                   leaf forward-msdp-sa {
                     description "Forward SAs learned from MSDP to this RP";
                     type empty;
                   }
                 }
               }
               leaf local-address {
                 description "Local address for replicating register messages to other RPs";
                 type jt:ipaddr;
               }
             }
           }
           container inet6 {
             description "IPv6 local RP properties";
             uses apply-advanced;
             leaf address {
               description "Local RP address";
               type jt:ipv6addr;
             }
             choice enable-disable {
               case case_1 {
                 leaf disable {
                   description "Disable this RP";
                   type empty;
                 }
               }
             }
             leaf priority {
               description "Router's priority for becoming an RP";
               type union {
                 type string {
                   pattern "<.*>|$.*";
                 }
                 type uint32 {
                   range "0 .. 255";
                 }
               }
             }
             leaf hold-time {
               description "How long neighbor considers this router to be up, in seconds";
               type union {
                 type string {
                   pattern "<.*>|$.*";
                 }
                 type uint32 {
                   range "1 .. 65535";
                 }
               }
             }
             list group-ranges {
               key name;
               ordered-by user;
               description "Group address range for which this router can be an RP";
               leaf name {
                 type jt:ipv6prefix;
               }
               uses apply-advanced;
             }
             leaf override {
               description "Static RP mapping will take precedence over dynamic";
               type empty;
             }
             container anycast-pim {
               description "Attributes for IPv6 anycast PIM";
               uses apply-advanced;
               container rp-set {
                 description "Rendezvous points belonging to anycast RP set";
                 uses apply-advanced;
                 list address {
                   key name;
                   ordered-by user;
                   description "IPv6 address of one or more remote anycast RPs";
                   leaf name {
                     description "IPv6 address of remote anycast RP";
                     type jt:ipv6addr;
                   }
                   uses apply-advanced;
                 }
               }
               leaf local-address {
                 description "Local address for replicating register messages to other RPs";
                 type jt:ipv6addr;
               }
             }
           }
         }
       }
       container embedded-rp {
         presence "enable embedded-rp";
         description "Set embedded-RP mode (IPv6 only)";
         uses apply-advanced;
         list group-ranges {
           key name;
           ordered-by user;
           description "Group address range of RP";
           uses pim_rp_group_range_type;
         }
         leaf maximum-rps {
           description "Maximum number of embedded RPs";
           default "100";
           type union {
             type string {
               pattern "<.*>|$.*";
             }
             type uint32 {
               range "1 .. 500";
             }
           }
         }
       }
       container auto-rp {
         description "Set auto-RP mode (IPv4 only)";
         uses apply-advanced;
         choice autorp-mode {
           case case_1 {
             leaf discovery {
               description "Listen for auto-RP discovery messages";
               type empty;
             }
           }
           case case_2 {
             leaf announce {
               description "Transmit auto-RP announcement messages";
               type empty;
             }
           }
           case case_3 {
             leaf mapping {
               description "Transmit auto-RP mapping messages";
               type empty;
             }
           }
         }
         choice mapping-agent-election-choice {
           leaf mapping-agent-election {
             description "Consider higher-addressed mapping agents as authoritative";
             type empty;
           }
           leaf no-mapping-agent-election {
             description "Don't consider higher-addressed mapping agents as authoritative";
             type empty;
           }
         }
       }
       container static {
         description "Configure static PIM RPs";
         uses apply-advanced;
         list address {
           key name;
           ordered-by user;
           description "RP address";
           leaf name {
             description "IP address of RP";
             type jt:ipaddr;
           }
           uses apply-advanced;
           leaf version {
             description "PIM version of RP";
             status deprecated;
             type union {
               type string {
                 pattern "<.*>|$.*";
               }
               type uint32 {
                 range "1 .. 2";
               }
             }
           }
           list group-ranges {
             key name;
             ordered-by user;
             description "Group address range of RP";
             uses pim_rp_group_range_type;
           }
           leaf override {
             description "Static RP mapping will take precedence over dynamic";
             type empty;
           }
         }
       }
       container bidirectional {
         junos:must "((!(\".. .. .. .. .. .. routing-instances\") || any \".. .. .. .. .. .. routing-instances <*> instance-type virtual-router\"))";
         junos:must-message "Only master instance and routing-instances of type virtual-router support PIM-BIDIR.";
         description "Configure PIM bidirectional-mode RPs";
         uses apply-advanced;
         list address {
           key name;
           ordered-by user;
           description "RP address";
           leaf name {
             description "IP address of RP";
             type jt:ipaddr;
           }
           uses apply-advanced;
           leaf priority {
             description "Router's priority for becoming an RP";
             type union {
               type string {
                 pattern "<.*>|$.*";
               }
               type uint32 {
                 range "0 .. 255";
               }
             }
           }
           leaf hold-time {
             description "How long neighbor considers this router to be up";
             units "seconds";
             type union {
               type string {
                 pattern "<.*>|$.*";
               }
               type uint32 {
                 range "1 .. 65535";
               }
             }
           }
           list group-ranges {
             key name;
             ordered-by user;
             description "Group address range of RP";
             uses pim_rp_group_range_type;
           }
         }
       }
       leaf register-probe-time {
         description "Register probe time";
         default "5";
         units "seconds";
         type union {
           type string {
             pattern "<.*>|$.*";
           }
           type uint32 {
             range "5 .. 60";
           }
         }
       }
     }
     leaf passive {
       description "Configure PIM protocol in passive mode";
       junos:must "(!(any \".. interface <*> distributed-dr\"))";
       junos:must-message "pim passive cannot be configured with pim distributed-dr";
       junos:must "(!(\" .. rp\"))";
       junos:must-message "pim passive cannot be configured with pim rp";
       type empty;
     }
     list interface {
       key name;
       ordered-by user;
       description "PIM interface options";
       leaf name {
         description "Interface name";
         junos:must "((((\"routing-options multicast interface $$ disable\" || (\"routing-options multicast interface $$ maximum-bandwidth\" || (\"routing-options multicast interface $$ nexthop-unicast-address\" || (\"routing-options multicast interface $$ reverse-oif-mapping\" || (\"routing-options multicast interface $$ subscriber-leave-timer\" || \"routing-options multicast interface $$ no-qos-adjust\"))))) && !(\"routing-options multicast interface $$ enable\")) || (\"protocols pim interface $$ disable\" || !((\"routing-options multicast interface $$\" || \"routing-options multicast interface $$ enable\")))))";
         junos:must-message "Multicast cannot be enabled on the same interface in the [edit routing-options] hierarchy";
         type string;
       }
       uses apply-advanced;
       container family {
         description "Local address family";
         container any {
           presence "enable any";
           description "Default properties for all families";
           uses apply-advanced;
           leaf disable {
             description "Disable all families";
             type empty;
           }
         }
         container inet {
           presence "enable inet";
           description "IPv4 specific properties";
           uses apply-advanced;
           container bfd-liveness-detection {
             description "Bidirectional Forwarding Detection options";
             uses apply-advanced;
             leaf version {
               description "BFD protocol version number";
               default "automatic";
               type enumeration {
                 enum "0" {
                   description "BFD version 0 (deprecated)";
                 }
                 enum "1" {
                   description "BFD version 1";
                 }
                 enum "automatic" {
                   description "Choose BFD version automatically";
                 }
               }
             }
             leaf minimum-interval {
               description "Minimum transmit and receive interval";
               units "milliseconds";
               type union {
                 type string {
                   pattern "<.*>|$.*";
                 }
                 type uint32 {
                   range "1 .. 255000";
                 }
               }
             }
             leaf minimum-transmit-interval {
               description "Minimum transmit interval";
               status deprecated;
               units "milliseconds";
               type union {
                 type string {
                   pattern "<.*>|$.*";
                 }
                 type uint32 {
                   range "1 .. 255000";
                 }
               }
             }
             leaf minimum-receive-interval {
               description "Minimum receive interval";
               units "milliseconds";
               type union {
                 type string {
                   pattern "<.*>|$.*";
                 }
                 type uint32 {
                   range "1 .. 255000";
                 }
               }
             }
             leaf multiplier {
               description "Detection time multiplier";
               default "3";
               type union {
                 type string {
                   pattern "<.*>|$.*";
                 }
                 type uint32 {
                   range "1 .. 255";
                 }
               }
             }
             choice adaptation-choice {
               case case_1 {
                 leaf no-adaptation {
                   description "Disable adaptation";
                   type empty;
                 }
               }
             }
             container transmit-interval {
               description "Transmit-interval options";
               uses apply-advanced;
               leaf minimum-interval {
                 description "Minimum transmit interval";
                 units "milliseconds";
                 type union {
                   type string {
                     pattern "<.*>|$.*";
                   }
                   type uint32 {
                     range "1 .. 255000";
                   }
                 }
               }
               leaf threshold {
                 description "High transmit interval triggering a trap";
                 units "milliseconds";
                 type union {
                   type uint32;
                   type string {
                     pattern "<.*>|$.*";
                   }
                 }
               }
             }
             container detection-time {
               description "Detection-time options";
               uses apply-advanced;
               leaf threshold {
                 description "High detection-time triggering a trap";
                 units "milliseconds";
                 type union {
                   type uint32;
                   type string {
                     pattern "<.*>|$.*";
                   }
                 }
               }
             }
             container authentication {
               description "Authentication options";
               uses apply-advanced;
               leaf key-chain {
                 description "Key chain name";
                 junos:must "(\".. algorithm\")";
                 junos:must-message "May not be configured without algorithm";
                 junos:must "(\"security authentication-key-chains key-chain $$\")";
                 junos:must-message "Referenced key-chain must be defined";
                 type string;
               }
               leaf algorithm {
                 description "Algorithm name";
                 junos:must "(\".. key-chain\")";
                 junos:must-message "May not be configured without key-chain";
                 type enumeration {
                   enum "simple-password" {
                     description "Simple password";
                   }
                   enum "keyed-md5" {
                     description "Keyed message Digest 5";
                   }
                   enum "meticulous-keyed-md5" {
                     description "Meticulous keyed message Digest 5";
                   }
                   enum "keyed-sha-1" {
                     description "Keyed secure hash algorithm (SHA1) ";
                   }
                   enum "meticulous-keyed-sha-1" {
                     description "Meticulous keyed secure hash algorithm (SHA1) ";
                   }
                 }
               }
               leaf loose-check {
                 description "Verify authentication only if authentication is negotiated";
                 type empty;
               }
             }
           }
           leaf mcae-mac-synchronize {
             description "Mclag mac synchronization";
             type empty;
           }
           choice enable-disable {
             case case_1 {
               leaf disable {
                 description "Disable PIMv4 on this interface";
                 type empty;
               }
             }
           }
         }
         container inet6 {
           presence "enable inet6";
           description "IPv6 specific properties";
           uses apply-advanced;
           container bfd-liveness-detection {
             description "Bidirectional Forwarding Detection options";
             uses apply-advanced;
             leaf version {
               description "BFD protocol version number";
               default "automatic";
               type enumeration {
                 enum "0" {
                   description "BFD version 0 (deprecated)";
                 }
                 enum "1" {
                   description "BFD version 1";
                 }
                 enum "automatic" {
                   description "Choose BFD version automatically";
                 }
               }
             }
             leaf minimum-interval {
               description "Minimum transmit and receive interval";
               units "milliseconds";
               type union {
                 type string {
                   pattern "<.*>|$.*";
                 }
                 type uint32 {
                   range "1 .. 255000";
                 }
               }
             }
             leaf minimum-transmit-interval {
               description "Minimum transmit interval";
               status deprecated;
               units "milliseconds";
               type union {
                 type string {
                   pattern "<.*>|$.*";
                 }
                 type uint32 {
                   range "1 .. 255000";
                 }
               }
             }
             leaf minimum-receive-interval {
               description "Minimum receive interval";
               units "milliseconds";
               type union {
                 type string {
                   pattern "<.*>|$.*";
                 }
                 type uint32 {
                   range "1 .. 255000";
                 }
               }
             }
             leaf multiplier {
               description "Detection time multiplier";
               default "3";
               type union {
                 type string {
                   pattern "<.*>|$.*";
                 }
                 type uint32 {
                   range "1 .. 255";
                 }
               }
             }
             choice adaptation-choice {
               case case_1 {
                 leaf no-adaptation {
                   description "Disable adaptation";
                   type empty;
                 }
               }
             }
             container transmit-interval {
               description "Transmit-interval options";
               uses apply-advanced;
               leaf minimum-interval {
                 description "Minimum transmit interval";
                 units "milliseconds";
                 type union {
                   type string {
                     pattern "<.*>|$.*";
                   }
                   type uint32 {
                     range "1 .. 255000";
                   }
                 }
               }
               leaf threshold {
                 description "High transmit interval triggering a trap";
                 units "milliseconds";
                 type union {
                   type uint32;
                   type string {
                     pattern "<.*>|$.*";
                   }
                 }
               }
             }
             container detection-time {
               description "Detection-time options";
               uses apply-advanced;
               leaf threshold {
                 description "High detection-time triggering a trap";
                 units "milliseconds";
                 type union {
                   type uint32;
                   type string {
                     pattern "<.*>|$.*";
                   }
                 }
               }
             }
             container authentication {
               description "Authentication options";
               uses apply-advanced;
               leaf key-chain {
                 description "Key chain name";
                 junos:must "(\".. algorithm\")";
                 junos:must-message "May not be configured without algorithm";
                 junos:must "(\"security authentication-key-chains key-chain $$\")";
                 junos:must-message "Referenced key-chain must be defined";
                 type string;
               }
               leaf algorithm {
                 description "Algorithm name";
                 junos:must "(\".. key-chain\")";
                 junos:must-message "May not be configured without key-chain";
                 type enumeration {
                   enum "simple-password" {
                     description "Simple password";
                   }
                   enum "keyed-md5" {
                     description "Keyed message Digest 5";
                   }
                   enum "meticulous-keyed-md5" {
                     description "Meticulous keyed message Digest 5";
                   }
                   enum "keyed-sha-1" {
                     description "Keyed secure hash algorithm (SHA1) ";
                   }
                   enum "meticulous-keyed-sha-1" {
                     description "Meticulous keyed secure hash algorithm (SHA1) ";
                   }
                 }
               }
               leaf loose-check {
                 description "Verify authentication only if authentication is negotiated";
                 type empty;
               }
             }
           }
           choice enable-disable {
             case case_1 {
               leaf disable {
                 description "Disable PIMv6 on this interface";
                 type empty;
               }
             }
           }
         }
       }
       choice enable-disable {
         case case_1 {
           leaf disable {
             description "Disable PIM on this interface";
             type empty;
           }
         }
       }
       container bidirectional {
         junos:must "((!(\".. .. .. .. .. .. routing-instances\") || any \".. .. .. .. .. .. routing-instances <*> instance-type virtual-router\"))";
         junos:must-message "Only master instance and routing-instances of type virtual-router support PIM-BIDIR.";
         description "PIM bidirectional mode properties";
         uses apply-advanced;
         container df-election {
           description "Bidir designated forwarder properties";
           uses apply-advanced;
           leaf robustness-count {
             description "Election robustness count";
             type union {
               type string {
                 pattern "<.*>|$.*";
               }
               type uint32 {
                 range "1 .. 10";
               }
             }
           }
           leaf offer-period {
             description "Election offer message period";
             units "milliseconds";
             type union {
               type string {
                 pattern "<.*>|$.*";
               }
               type uint32 {
                 range "100 .. 10000";
               }
             }
           }
           leaf backoff-period {
             description "Election backoff period";
             units "milliseconds";
             type union {
               type string {
                 pattern "<.*>|$.*";
               }
               type uint32 {
                 range "100 .. 65535";
               }
             }
           }
         }
       }
       leaf mode {
         description "Mode of interface";
         type enumeration {
           enum "dense" {
             description "Dense mode";
           }
           enum "sparse" {
             description "Sparse mode";
           }
           enum "sparse-dense" {
             description "Sparse-dense mode";
           }
           enum "bidirectional-sparse" {
             description "Bidirectional-sparse mode";
             junos:must "((!(\".. .. .. .. .. .. routing-instances\") || any \".. .. .. .. .. .. routing-instances <*> instance-type virtual-router\"))";
             junos:must-message "Only master instance and routing-instances of type virtual-router support PIM-BIDIR.";
             junos:must "(!(\".. version $$={1}\"))";
             junos:must-message "PIM Bidirectional is not supported by PIMv1.";
           }
           enum "bidirectional-sparse-dense" {
             description "Bidirectional-sparse-dense mode";
             junos:must "((!(\".. .. .. .. .. .. routing-instances\") || any \".. .. .. .. .. .. routing-instances <*> instance-type virtual-router\"))";
             junos:must-message "Only master instance and routing-instances of type virtual-router support PIM-BIDIR.";
             junos:must "(!(\".. version $$={1}\"))";
             junos:must-message "PIM Bidirectional is not supported by PIMv1.";
           }
         }
       }
       leaf priority {
         description "Hello option DR priority";
         junos:must "((!(\".. mode dense\") || (\".. mode dense\" && \"protocols igmp interface ${interface} version 1\")))";
         junos:must-message "PIM DR Priority cannot be configured in Dense Mode unless IGMP V1 is configured";
         type union {
           type string {
             pattern "<.*>|$.*";
           }
           type uint32 {
             range "0 .. 4294967295";
           }
         }
       }
       container stickydr {
         presence "enable stickydr";
         description "Make DR sticky";
         uses apply-advanced;
       }
       container multiple-triggered-joins {
         presence "enable multiple-triggered-joins";
         description "Send multiple pim triggered joins in quick intervals";
         uses apply-advanced;
         leaf count {
           description "Set number of triggered joins to be sent";
           default "2";
           type union {
             type string {
               pattern "<.*>|$.*";
             }
             type uint16 {
               range "2 .. 15";
             }
           }
         }
         leaf interval {
           description "Set interval between multiple triggered joins to be sent in milliseconds";
           default "100";
           type union {
             type string {
               pattern "<.*>|$.*";
             }
             type uint16 {
               range "100 .. 1000";
             }
           }
         }
       }
       leaf version {
         description "Force PIM version";
         status deprecated;
         type union {
           type string {
             pattern "<.*>|$.*";
           }
           type uint32 {
             range "1 .. 2";
           }
         }
       }
       leaf hello-interval {
         description "Hello interval";
         units "seconds";
         type union {
           type string {
             pattern "<.*>|$.*";
           }
           type uint32 {
             range "0 .. 255";
           }
         }
       }
       leaf-list neighbor-policy {
         ordered-by user;
         description "PIM neighbor policy applied to incoming hello messages";
         type jt:policy-algebra;
       }
       leaf-list accept-join-always-from {
         ordered-by user;
         description "Accept pim join/prune messages based on the policy configured";
         type jt:policy-algebra;
       }
       leaf accept-remote-source {
         description "Accept traffic from remote source";
         type empty;
       }
       container dual-dr {
         presence "enable dual-dr";
         junos:must "(!(\" .. distributed-dr\"))";
         junos:must-message "pim dual-dr cannot be configured with pim distributed-dr";
         description "Configure PIM Dual DR";
         uses apply-advanced;
         leaf enhanced {
           description "Enable enhanced PIM Dual DR";
           type empty;
         }
       }
       leaf distributed-dr {
         description "PIM Distributed DR";
         junos:must "(!(\".. .. .. passive\"))";
         junos:must-message "pim distributed-dr cannot be configured with pim passive";
         junos:must "(!(\" .. dual-dr\"))";
         junos:must-message "pim distributed-dr cannot be configured with pim dual-dr";
         type empty;
       }
       leaf reset-tracking-bit {
         description "Clear tracking-bit in PIM Hello LAN Prune Delay Option";
         type empty;
       }
       leaf propagation-delay {
         description "Propagation delay value";
         default "500";
         units "milliseconds";
         type union {
           type string {
             pattern "<.*>|$.*";
           }
           type uint32 {
             range "250 .. 2000";
           }
         }
       }
       leaf override-interval {
         description "Override interval value";
         default "2000";
         units "milliseconds";
         type union {
           type string {
             pattern "<.*>|$.*";
           }
           type uint32 {
             range "500 .. 6000";
           }
         }
       }
       container bfd-liveness-detection {
         description "Bidirectional Forwarding Detection options (ipv4 only)";
         status deprecated;
         uses apply-advanced;
         leaf version {
           description "BFD protocol version number";
           default "automatic";
           type enumeration {
             enum "0" {
               description "BFD version 0 (deprecated)";
             }
             enum "1" {
               description "BFD version 1";
             }
             enum "automatic" {
               description "Choose BFD version automatically";
             }
           }
         }
         leaf minimum-interval {
           description "Minimum transmit and receive interval";
           units "milliseconds";
           type union {
             type string {
               pattern "<.*>|$.*";
             }
             type uint32 {
               range "1 .. 255000";
             }
           }
         }
         leaf minimum-transmit-interval {
           description "Minimum transmit interval";
           status deprecated;
           units "milliseconds";
           type union {
             type string {
               pattern "<.*>|$.*";
             }
             type uint32 {
               range "1 .. 255000";
             }
           }
         }
         leaf minimum-receive-interval {
           description "Minimum receive interval";
           units "milliseconds";
           type union {
             type string {
               pattern "<.*>|$.*";
             }
             type uint32 {
               range "1 .. 255000";
             }
           }
         }
         leaf multiplier {
           description "Detection time multiplier";
           default "3";
           type union {
             type string {
               pattern "<.*>|$.*";
             }
             type uint32 {
               range "1 .. 255";
             }
           }
         }
         choice adaptation-choice {
           case case_1 {
             leaf no-adaptation {
               description "Disable adaptation";
               type empty;
             }
           }
         }
         container transmit-interval {
           description "Transmit-interval options";
           uses apply-advanced;
           leaf minimum-interval {
             description "Minimum transmit interval";
             units "milliseconds";
             type union {
               type string {
                 pattern "<.*>|$.*";
               }
               type uint32 {
                 range "1 .. 255000";
               }
             }
           }
           leaf threshold {
             description "High transmit interval triggering a trap";
             units "milliseconds";
             type union {
               type uint32;
               type string {
                 pattern "<.*>|$.*";
               }
             }
           }
         }
         container detection-time {
           description "Detection-time options";
           uses apply-advanced;
           leaf threshold {
             description "High detection-time triggering a trap";
             units "milliseconds";
             type union {
               type uint32;
               type string {
                 pattern "<.*>|$.*";
               }
             }
           }
         }
         container authentication {
           description "Authentication options";
           uses apply-advanced;
           leaf key-chain {
             description "Key chain name";
             junos:must "(\".. algorithm\")";
             junos:must-message "May not be configured without algorithm";
             junos:must "(\"security authentication-key-chains key-chain $$\")";
             junos:must-message "Referenced key-chain must be defined";
             type string;
           }
           leaf algorithm {
             description "Algorithm name";
             junos:must "(\".. key-chain\")";
             junos:must-message "May not be configured without key-chain";
             type enumeration {
               enum "simple-password" {
                 description "Simple password";
               }
               enum "keyed-md5" {
                 description "Keyed message Digest 5";
               }
               enum "meticulous-keyed-md5" {
                 description "Meticulous keyed message Digest 5";
               }
               enum "keyed-sha-1" {
                 description "Keyed secure hash algorithm (SHA1) ";
               }
               enum "meticulous-keyed-sha-1" {
                 description "Meticulous keyed secure hash algorithm (SHA1) ";
               }
             }
           }
           leaf loose-check {
             description "Verify authentication only if authentication is negotiated";
             type empty;
           }
         }
       }
     }
     container mdt {
       junos:must "((!(\" .. .. mvpn\") || \".. mvpn family inet rosen-mvpn\"))";
       junos:must-message "Data tunnels cannot be configured with 'protocols mvpn'";
       description "Configure multicast data tunnel parameters";
       status deprecated;
       uses apply-advanced;
       container threshold {
         description "Threshold for creation of multicast tunnels";
         uses apply-advanced;
         list group {
           key name;
           ordered-by user;
           description "IP prefix of multicast group";
           leaf name {
             description "IP prefix of group";
             type jt:ipprefix;
           }
           uses apply-advanced;
           list source {
             key name;
             ordered-by user;
             description "IP prefix of one or more multicast sources ";
             leaf name {
               description "IP prefix of source";
               type jt:ipprefix;
             }
             uses apply-advanced;
             leaf rate {
               description "Data threshold to create new tunnel";
               units "kilobits";
               type union {
                 type string {
                   pattern "<.*>|$.*";
                 }
                 type uint32 {
                   range "10 .. 1000000";
                 }
               }
             }
           }
         }
       }
       leaf data-mdt-reuse {
         description "Allow multiple customer streams to be transmitted over one data tunnel ";
         type empty;
       }
       leaf tunnel-limit {
         description "Maximum multicast data tunnels";
         type union {
           type string {
             pattern "<.*>|$.*";
           }
           type uint32 {
             range "0 .. 8192";
           }
         }
       }
       leaf group-range {
         description "Group address range for multicast data tunnels";
         type jt:ipprefix;
       }
     }
     container graceful-restart {
       description "Configure graceful restart attributes";
       uses apply-advanced;
       choice enable-disable {
         case case_1 {
           leaf disable {
             description "Disable PIM graceful restart capability";
             type empty;
           }
         }
       }
       leaf restart-duration {
         description "Maximum time for graceful restart to finish (seconds)";
         units "seconds";
         type union {
           type string {
             pattern "<.*>|$.*";
           }
           type uint32 {
             range "30 .. 300";
           }
         }
       }
       leaf no-bidirectional-mode {
         description "Disable PIM graceful restart for bidirectional mode";
         type empty;
       }
       leaf restart-complete-duration {
         description "Maximum time for graceful restart to complete (seconds)";
         units "seconds";
         type union {
           type string {
             pattern "<.*>|$.*";
           }
           type uint32 {
             range "5 .. 300";
           }
         }
       }
     }
     container join-load-balance {
       presence "enable join-load-balance";
       description "Configure PIM join load balancing";
       uses apply-advanced;
       leaf automatic {
         description "Enable automatic PIM join load balancing";
         type empty;
       }
     }
     leaf standby-path-creation-delay {
       description "Amount of time to wait before creating standby path";
       units "seconds";
       type union {
         type string {
           pattern "<.*>|$.*";
         }
         type uint32 {
           range "1 .. 300";
         }
       }
     }
     leaf idle-standby-path-switchover-delay {
       description "Amount of time to wait before switching over to idle standby path";
       units "seconds";
       type union {
         type string {
           pattern "<.*>|$.*";
         }
         type uint32 {
           range "1 .. 300";
         }
       }
     }
     leaf dr-election-on-p2p {
       description "Enable DR election on Point-to-Point Interfaces";
       type empty;
     }
     leaf no-wildcard-register-stop {
       description "Disable sending of wildcard register stop message";
       type empty;
     }
     leaf nexthop-hold-time {
       description "Nexthop hold time in milliseconds";
       units "milliseconds";
       type union {
         type string {
           pattern "<.*>|$.*";
         }
         type uint32 {
           range "1 .. 1000";
         }
       }
     }
     leaf mpls-internet-multicast {
       description "Enable support for Internet Multicast over MPLS";
       junos:must "(any \"routing-instances <*> instance-type mpls-internet-multicast\")";
       junos:must-message "The mpls-internet-multicast instance must be configured to support multicast over MPLS";
       type empty;
     }
     container join-make-before-break {
       description "Enable PIM Join Make-Before-Break during RPF neighbor change";
       uses apply-advanced;
       choice enable-disable {
         case case_1 {
           leaf disable {
             description "Disable Make-Before-Break for PIM RPF neighbor change";
             type empty;
           }
         }
       }
     }
     leaf reset-tracking-bit {
       description "Clear tracking-bit in PIM Hello LAN Prune Delay Option";
       type empty;
     }
     leaf propagation-delay {
       description "Propagation delay value";
       default "500";
       units "milliseconds";
       type union {
         type string {
           pattern "<.*>|$.*";
         }
         type uint32 {
           range "250 .. 2000";
         }
       }
     }
     leaf override-interval {
       description "Override interval value";
       default "2000";
       units "milliseconds";
       type union {
         type string {
           pattern "<.*>|$.*";
         }
         type uint32 {
           range "500 .. 6000";
         }
       }
     }
     container default-vpn-source {
       presence "enable default-vpn-source";
       description "Let all VRFs use master loopback address for mt interfaces";
       uses apply-advanced;
       leaf interface-name {
         description "Master loopback interface name";
         junos:must "(\"interfaces $$-IFL family inet address\")";
         junos:must-message "Family inet address should be configured on this loopback interface";
         type union {
           type jt:interface-unit;
           type string {
             pattern "<.*>|$.*";
           }
         }
       }
     }
   }
   grouping juniper-protocols-pim-snooping {
     description "PIM snooping options";
     uses apply-advanced;
     container traceoptions {
       description "Trace options for PIM Snooping";
       uses apply-advanced;
       container file {
         description "Trace file options";
         leaf filename {
           description "Name of file in which to write trace information";
           type string {
             length "1 .. 1024";
             junos:posix-pattern "![/ %]";
             junos:pattern-message "Must not contain '/', % or a space";
           }
         }
         leaf replace {
           description "Replace trace file rather than appending to it";
           status deprecated;
           type empty;
         }
         leaf size {
           description "Maximum trace file size";
           type string;
         }
         leaf files {
           description "Maximum number of trace files";
           default "10";
           type union {
             type string {
               pattern "<.*>|$.*";
             }
             type uint32 {
               range "2 .. 1000";
             }
           }
         }
         leaf no-stamp {
           description "Do not timestamp trace file";
           status deprecated;
           type empty;
         }
         choice world-readable-choice {
           leaf world-readable {
             description "Allow any user to read the log file";
             type empty;
           }
           leaf no-world-readable {
             description "Don't allow any user to read the log file";
             type empty;
           }
         }
       }
       list flag {
         key name;
         ordered-by user;
         description "Tracing parameters";
         leaf name {
           type enumeration {
             enum "packets" {
               description "Trace all PIM packets";
             }
             enum "hello" {
               description "Trace hello packets";
             }
             enum "join" {
               description "Trace join messages";
             }
             enum "prune" {
               description "Trace prune messages";
             }
             enum "route" {
               description "Trace routing information";
             }
             enum "normal" {
               description "Trace normal events";
             }
             enum "general" {
               description "Trace general events";
             }
             enum "state" {
               description "Trace state transitions";
             }
             enum "policy" {
               description "Trace policy processing";
             }
             enum "task" {
               description "Trace routing protocol task processing";
             }
             enum "timer" {
               description "Trace routing protocol timer processing";
             }
             enum "all" {
               description "Trace everything";
             }
           }
         }
         leaf send {
           description "Trace transmitted packets";
           type empty;
         }
         leaf receive {
           description "Trace received packets";
           type empty;
         }
         leaf detail {
           description "Trace detailed information";
           type empty;
         }
         leaf disable {
           description "Disable this trace flag";
           type empty;
         }
       }
     }
     leaf no-dr-flood {
       description "Disable default flooding of multicast data on the PIM designated router port";
       type empty;
     }
     list vlan {
       key name;
       ordered-by user;
       description "Vlan options";
       leaf name {
         description "Vlan_id of the learning-domain";
         junos:must "(\".. .. .. .. vlan-id all\")";
         junos:must-message "vlan specific configuration is allowed with qualified-learning only";
         type union {
           type string {
             pattern "<.*>|$.*";
           }
           type uint32 {
             range "0 .. 1023";
           }
         }
       }
       uses apply-advanced;
       leaf no-dr-flood {
         description "Disable default flooding of multicast data on the PIM DR port";
         type empty;
       }
     }
   }
   grouping juniper-protocols-rip {
     uses apply-advanced;
     container traceoptions {
       description "Trace options for RIP";
       uses apply-advanced;
       container file {
         description "Trace file options";
         leaf filename {
           description "Name of file in which to write trace information";
           type string {
             length "1 .. 1024";
             junos:posix-pattern "![/ %]";
             junos:pattern-message "Must not contain '/', % or a space";
           }
         }
         leaf replace {
           description "Replace trace file rather than appending to it";
           status deprecated;
           type empty;
         }
         leaf size {
           description "Maximum trace file size";
           type string;
         }
         leaf files {
           description "Maximum number of trace files";
           default "10";
           type union {
             type string {
               pattern "<.*>|$.*";
             }
             type uint32 {
               range "2 .. 1000";
             }
           }
         }
         leaf no-stamp {
           description "Do not timestamp trace file";
           status deprecated;
           type empty;
         }
         choice world-readable-choice {
           leaf world-readable {
             description "Allow any user to read the log file";
             type empty;
           }
           leaf no-world-readable {
             description "Don't allow any user to read the log file";
             type empty;
           }
         }
       }
       list flag {
         key name;
         ordered-by user;
         description "Tracing parameters";
         leaf name {
           type enumeration {
             enum "auth" {
               description "Trace RIP authentication";
             }
             enum "error" {
               description "Trace RIP errors";
             }
             enum "expiration" {
               description "Trace RIP route expiration processing";
             }
             enum "holddown" {
               description "Trace RIP hold-down processing";
             }
             enum "packets" {
               description "Trace all RIP packets";
             }
             enum "request" {
               description "Trace RIP information packets";
             }
             enum "trigger" {
               description "Trace RIP triggered updates";
             }
             enum "update" {
               description "Trace RIP update packets";
             }
             enum "nsr-synchronization" {
               description "Trace NSR synchronization events";
             }
             enum "route" {
               description "Trace routing information";
             }
             enum "normal" {
               description "Trace normal events";
             }
             enum "general" {
               description "Trace general events";
             }
             enum "state" {
               description "Trace state transitions";
             }
             enum "policy" {
               description "Trace policy processing";
             }
             enum "task" {
               description "Trace routing protocol task processing";
             }
             enum "timer" {
               description "Trace routing protocol timer processing";
             }
             enum "all" {
               description "Trace everything";
             }
           }
         }
         leaf send {
           description "Trace transmitted packets";
           type empty;
         }
         leaf receive {
           description "Trace received packets";
           type empty;
         }
         leaf detail {
           description "Trace detailed information";
           type empty;
         }
         leaf disable {
           description "Disable this trace flag";
           type empty;
         }
         container filter {
           description "Filter to apply to this flag";
           presence "enable filter";
           uses rip_filter_obj;
         }
       }
     }
     container rib-group {
       description "Routing table group for importing RIP routes";
       uses rib_group_inet_type;
     }
     leaf metric-in {
       description "Metric value to add to incoming routes";
       type union {
         type string {
           pattern "<.*>|$.*";
         }
         type uint32 {
           range "1 .. 15";
         }
       }
     }
     container send {
       description "Configure RIP send options";
       choice send-opts {
         case case_1 {
           leaf broadcast {
             description "Broadcast RIPv2 packets (RIPv1 compatible)";
             type empty;
           }
         }
         case case_2 {
           leaf multicast {
             description "Multicast RIPv2 packets";
             type empty;
           }
         }
         case case_3 {
           leaf none {
             description "Do not send RIP updates";
             type empty;
           }
         }
         case case_4 {
           leaf version-1 {
             description "Broadcast RIPv1 packets";
             type empty;
           }
         }
       }
     }
     container receive {
       description "Configure RIP receive options";
       choice receive-opts {
         case case_1 {
           leaf both {
             description "Accept both RIPv1 and RIPv2 packets";
             type empty;
           }
         }
         case case_2 {
           leaf none {
             description "Do not receive RIP packets";
             type empty;
           }
         }
         case case_3 {
           leaf version-1 {
             description "Accept RIPv1 packets only";
             type empty;
           }
         }
         case case_4 {
           leaf version-2 {
             description "Accept only RIPv2 packets";
             type empty;
           }
         }
       }
     }
     choice check-zero-choice {
       leaf check-zero {
         description "Check reserved fields on incoming RIPv2 packets";
         type empty;
       }
       leaf no-check-zero {
         description "Don't check reserved fields on incoming RIPv2 packets";
         type empty;
       }
     }
     leaf message-size {
       description "Number of route entries per update message";
       type union {
         type string {
           pattern "<.*>|$.*";
         }
         type uint32 {
           range "25 .. 255";
         }
       }
     }
     leaf-list import {
       ordered-by user;
       description "Import policy";
       type jt:policy-algebra;
     }
     leaf holddown {
       description "Hold-down time";
       units "seconds";
       type union {
         type string {
           pattern "<.*>|$.*";
         }
         type uint32 {
           range "10 .. 180";
         }
       }
     }
     leaf route-timeout {
       description "Delay before routes time out";
       units "seconds";
       type union {
         type string {
           pattern "<.*>|$.*";
         }
         type uint32 {
           range "30 .. 360";
         }
       }
     }
     leaf update-interval {
       description "Interval between regular route updates";
       units "seconds";
       type union {
         type string {
           pattern "<.*>|$.*";
         }
         type uint32 {
           range "10 .. 60";
         }
       }
     }
     choice authentication {
       case case_1 {
         leaf authentication-type {
           type enumeration {
             enum "none" {
               description "No authentication";
             }
             enum "simple" {
               description "Simple password authentication";
             }
             enum "md5" {
               description "MD5 authentication";
             }
           }
         }
       }
       case case_2 {
         list authentication-selective-md5 {
           key name;
           ordered-by user;
           description "MD5 authentication with one or more keys";
           leaf name {
             description "Key ID for MD5 authentication";
             type union {
               type string {
                 pattern "<.*>|$.*";
               }
               type uint32 {
                 range "0 .. 255";
               }
             }
           }
           leaf key {
             description "MD5 authentication key value";
             type jt:unreadable;
           }
           leaf start-time {
             description "Start time for key transmission (YYYY-MM-DD.HH:MM)";
             type jt:time;
           }
         }
       }
     }
     leaf authentication-key {
       description "Authentication key (password)";
       junos:must "(!(\".. authentication-selective-md5\"))";
       junos:must-message "Key already provided for selective-md5";
       type jt:unreadable;
     }
     list group {
       key name;
       ordered-by user;
       description "Instance configuration";
       leaf name {
         description "Group name";
         type string {
           junos:posix-pattern "^.{1,48}$";
           junos:pattern-message "Must be a string of at most 48 characters";
         }
       }
       uses apply-advanced;
       leaf route-timeout {
         description "Delay before routes time out";
         units "seconds";
         type union {
           type string {
             pattern "<.*>|$.*";
           }
           type uint32 {
             range "30 .. 360";
           }
         }
       }
       leaf update-interval {
         description "Interval between regular route updates";
         units "seconds";
         type union {
           type string {
             pattern "<.*>|$.*";
           }
           type uint32 {
             range "10 .. 60";
           }
         }
       }
       leaf preference {
         description "Preference of routes learned by this group";
         type union {
           type uint32;
           type string {
             pattern "<.*>|$.*";
           }
         }
       }
       leaf metric-out {
         description "Default metric of exported routes";
         type union {
           type string {
             pattern "<.*>|$.*";
           }
           type uint32 {
             range "1 .. 15";
           }
         }
       }
       leaf-list export {
         ordered-by user;
         description "Export policy";
         type jt:policy-algebra;
       }
       leaf-list import {
         ordered-by user;
         description "Import policy";
         type jt:policy-algebra;
       }
       leaf demand-circuit {
         description "Enable demand circuit on this interface";
         junos:must "(!(\".. .. authentication-selective-md5\"))";
         junos:must-message "selective-md5 isn't supported with demand-circuit,opt for 'authentication-type md5' instead";
         type empty;
       }
       leaf max-retrans-time {
         description "Maximum time to re-transmit a message in demand-circuit";
         type union {
           type string {
             pattern "<.*>|$.*";
           }
           type uint32 {
             range "5 .. 180";
           }
         }
       }
       container bfd-liveness-detection {
         description "Bidirectional Forwarding Detection options";
         uses apply-advanced;
         leaf version {
           description "BFD protocol version number";
           default "automatic";
           type enumeration {
             enum "0" {
               description "BFD version 0 (deprecated)";
             }
             enum "1" {
               description "BFD version 1";
             }
             enum "automatic" {
               description "Choose BFD version automatically";
             }
           }
         }
         leaf minimum-interval {
           description "Minimum transmit and receive interval";
           units "milliseconds";
           type union {
             type string {
               pattern "<.*>|$.*";
             }
             type uint32 {
               range "1 .. 255000";
             }
           }
         }
         leaf minimum-transmit-interval {
           description "Minimum transmit interval";
           status deprecated;
           units "milliseconds";
           type union {
             type string {
               pattern "<.*>|$.*";
             }
             type uint32 {
               range "1 .. 255000";
             }
           }
         }
         leaf minimum-receive-interval {
           description "Minimum receive interval";
           units "milliseconds";
           type union {
             type string {
               pattern "<.*>|$.*";
             }
             type uint32 {
               range "1 .. 255000";
             }
           }
         }
         leaf multiplier {
           description "Detection time multiplier";
           default "3";
           type union {
             type string {
               pattern "<.*>|$.*";
             }
             type uint32 {
               range "1 .. 255";
             }
           }
         }
         choice adaptation-choice {
           case case_1 {
             leaf no-adaptation {
               description "Disable adaptation";
               type empty;
             }
           }
         }
         container transmit-interval {
           description "Transmit-interval options";
           uses apply-advanced;
           leaf minimum-interval {
             description "Minimum transmit interval";
             units "milliseconds";
             type union {
               type string {
                 pattern "<.*>|$.*";
               }
               type uint32 {
                 range "1 .. 255000";
               }
             }
           }
           leaf threshold {
             description "High transmit interval triggering a trap";
             units "milliseconds";
             type union {
               type uint32;
               type string {
                 pattern "<.*>|$.*";
               }
             }
           }
         }
         container detection-time {
           description "Detection-time options";
           uses apply-advanced;
           leaf threshold {
             description "High detection-time triggering a trap";
             units "milliseconds";
             type union {
               type uint32;
               type string {
                 pattern "<.*>|$.*";
               }
             }
           }
         }
         container authentication {
           description "Authentication options";
           uses apply-advanced;
           leaf key-chain {
             description "Key chain name";
             junos:must "(\".. algorithm\")";
             junos:must-message "May not be configured without algorithm";
             junos:must "(\"security authentication-key-chains key-chain $$\")";
             junos:must-message "Referenced key-chain must be defined";
             type string;
           }
           leaf algorithm {
             description "Algorithm name";
             junos:must "(\".. key-chain\")";
             junos:must-message "May not be configured without key-chain";
             type enumeration {
               enum "simple-password" {
                 description "Simple password";
               }
               enum "keyed-md5" {
                 description "Keyed message Digest 5";
               }
               enum "meticulous-keyed-md5" {
                 description "Meticulous keyed message Digest 5";
               }
               enum "keyed-sha-1" {
                 description "Keyed secure hash algorithm (SHA1) ";
               }
               enum "meticulous-keyed-sha-1" {
                 description "Meticulous keyed secure hash algorithm (SHA1) ";
               }
             }
           }
           leaf loose-check {
             description "Verify authentication only if authentication is negotiated";
             type empty;
           }
         }
       }
       list neighbor {
         key name;
         ordered-by user;
         description "Neighbor configuration";
         leaf name {
           description "Interface name";
           type union {
             type jt:interface-name;
             type string {
               pattern "<.*>|$.*";
             }
           }
         }
         uses apply-advanced;
         leaf route-timeout {
           description "Delay before routes time out";
           units "seconds";
           type union {
             type string {
               pattern "<.*>|$.*";
             }
             type uint32 {
               range "30 .. 360";
             }
           }
         }
         leaf update-interval {
           description "Interval between regular route updates";
           units "seconds";
           type union {
             type string {
               pattern "<.*>|$.*";
             }
             type uint32 {
               range "10 .. 60";
             }
           }
         }
         leaf interface-type {
           description "Interface type for the neighbor";
           type enumeration {
             enum "p2mp" {
               description "Point-to-multipoint link";
               junos:must "(!(\".. .. .. authentication-selective-md5\"))";
               junos:must-message "selective-md5 isn't supported with 'interface-type p2mp', opt for 'authentication-type md5' instead";
             }
           }
         }
         leaf dynamic-peers {
           description "Learn peers dynamically on a p2mp interface";
           junos:must "(\" .. interface-type p2mp\")";
           junos:must-message "dynamic-peers option can be set only if the interface type is p2mp";
           type empty;
         }
         list peer {
           key name;
           ordered-by user;
           description "P2MP peer";
           junos:must "(\" .. interface-type p2mp\")";
           junos:must-message "Peer address can be set only if the interface type is p2mp";
           leaf name {
             description "Address of peer";
             type jt:ipaddr;
           }
         }
         leaf metric-in {
           description "Metric value to add to incoming routes";
           type union {
             type string {
               pattern "<.*>|$.*";
             }
             type uint32 {
               range "1 .. 15";
             }
           }
         }
         container send {
           description "Configure RIP send options";
           choice send-opts {
             case case_1 {
               leaf broadcast {
                 description "Broadcast RIPv2 packets (RIPv1 compatible)";
                 type empty;
               }
             }
             case case_2 {
               leaf multicast {
                 description "Multicast RIPv2 packets";
                 type empty;
               }
             }
             case case_3 {
               leaf none {
                 description "Do not send RIP updates";
                 type empty;
               }
             }
             case case_4 {
               leaf version-1 {
                 description "Broadcast RIPv1 packets";
                 type empty;
               }
             }
           }
         }
         container receive {
           description "Configure RIP receive options";
           choice receive-opts {
             case case_1 {
               leaf both {
                 description "Accept both RIPv1 and RIPv2 packets";
                 type empty;
               }
             }
             case case_2 {
               leaf none {
                 description "Do not receive RIP packets";
                 type empty;
               }
             }
             case case_3 {
               leaf version-1 {
                 description "Accept RIPv1 packets only";
                 type empty;
               }
             }
             case case_4 {
               leaf version-2 {
                 description "Accept only RIPv2 packets";
                 type empty;
               }
             }
           }
         }
         leaf demand-circuit {
           description "Enable demand circuit on this interface";
           junos:must "(!(\".. .. .. authentication-selective-md5\"))";
           junos:must-message "selective-md5 isn't supported with demand-circuit, opt for 'authentication-type md5' instead";
           type empty;
         }
         leaf max-retrans-time {
           description "Maximum time to re-transmit a msg in demand-circuit";
           type union {
             type string {
               pattern "<.*>|$.*";
             }
             type uint32 {
               range "5 .. 180";
             }
           }
         }
         choice check-zero-choice {
           leaf check-zero {
             description "Check reserved fields on incoming RIPv1 packets";
             type empty;
           }
           leaf no-check-zero {
             description "Don't check reserved fields on incoming RIPv1 packets";
             type empty;
           }
         }
         leaf any-sender {
           description "Disable strict checks on sender address";
           type empty;
         }
         leaf message-size {
           description "Number of route entries per update message";
           type union {
             type string {
               pattern "<.*>|$.*";
             }
             type uint32 {
               range "25 .. 255";
             }
           }
         }
         leaf-list import {
           ordered-by user;
           description "Import policy";
           type jt:policy-algebra;
         }
         choice authentication {
           case case_1 {
             leaf authentication-type {
               type enumeration {
                 enum "none" {
                   description "No authentication";
                 }
                 enum "simple" {
                   description "Simple password authentication";
                 }
                 enum "md5" {
                   description "MD5 authentication";
                 }
               }
             }
           }
           case case_2 {
             list authentication-selective-md5 {
               key name;
               ordered-by user;
               description "MD5 authentication with one or more keys";
               junos:must "(!(\"..  interface-type p2mp\"))";
               junos:must-message "selective-md5 isn't supported with '.. neighbor <> interface-type p2mp', opt for 'authentication-type md5' instead";
               junos:must "(!(\"..  demand-circuit\"))";
               junos:must-message "selective-md5 isn't supported with '.. neighbor <> demand-circuit', opt for 'authentication-type md5' instead";
               junos:must "(!(\".. .. demand-circuit\"))";
               junos:must-message "selective-md5 isn't supported with '.. group <> demand-circuit', opt for 'authentication-type md5' instead";
               leaf name {
                 description "Key ID for MD5 authentication";
                 type union {
                   type string {
                     pattern "<.*>|$.*";
                   }
                   type uint32 {
                     range "0 .. 255";
                   }
                 }
               }
               leaf key {
                 description "MD5 authentication key value";
                 type jt:unreadable;
               }
               leaf start-time {
                 description "Start time for key transmission (YYYY-MM-DD.HH:MM)";
                 type jt:time;
               }
             }
           }
         }
         leaf authentication-key {
           description "Authentication key (password)";
           junos:must "(!(\".. authentication-selective-md5\"))";
           junos:must-message "Key already provided for selective-md5";
           type jt:unreadable;
         }
         container bfd-liveness-detection {
           description "Bidirectional Forwarding Detection options";
           uses apply-advanced;
           leaf version {
             description "BFD protocol version number";
             default "automatic";
             type enumeration {
               enum "0" {
                 description "BFD version 0 (deprecated)";
               }
               enum "1" {
                 description "BFD version 1";
               }
               enum "automatic" {
                 description "Choose BFD version automatically";
               }
             }
           }
           leaf minimum-interval {
             description "Minimum transmit and receive interval";
             units "milliseconds";
             type union {
               type string {
                 pattern "<.*>|$.*";
               }
               type uint32 {
                 range "1 .. 255000";
               }
             }
           }
           leaf minimum-transmit-interval {
             description "Minimum transmit interval";
             status deprecated;
             units "milliseconds";
             type union {
               type string {
                 pattern "<.*>|$.*";
               }
               type uint32 {
                 range "1 .. 255000";
               }
             }
           }
           leaf minimum-receive-interval {
             description "Minimum receive interval";
             units "milliseconds";
             type union {
               type string {
                 pattern "<.*>|$.*";
               }
               type uint32 {
                 range "1 .. 255000";
               }
             }
           }
           leaf multiplier {
             description "Detection time multiplier";
             default "3";
             type union {
               type string {
                 pattern "<.*>|$.*";
               }
               type uint32 {
                 range "1 .. 255";
               }
             }
           }
           choice adaptation-choice {
             case case_1 {
               leaf no-adaptation {
                 description "Disable adaptation";
                 type empty;
               }
             }
           }
           container transmit-interval {
             description "Transmit-interval options";
             uses apply-advanced;
             leaf minimum-interval {
               description "Minimum transmit interval";
               units "milliseconds";
               type union {
                 type string {
                   pattern "<.*>|$.*";
                 }
                 type uint32 {
                   range "1 .. 255000";
                 }
               }
             }
             leaf threshold {
               description "High transmit interval triggering a trap";
               units "milliseconds";
               type union {
                 type uint32;
                 type string {
                   pattern "<.*>|$.*";
                 }
               }
             }
           }
           container detection-time {
             description "Detection-time options";
             uses apply-advanced;
             leaf threshold {
               description "High detection-time triggering a trap";
               units "milliseconds";
               type union {
                 type uint32;
                 type string {
                   pattern "<.*>|$.*";
                 }
               }
             }
           }
           container authentication {
             description "Authentication options";
             uses apply-advanced;
             leaf key-chain {
               description "Key chain name";
               junos:must "(\".. algorithm\")";
               junos:must-message "May not be configured without algorithm";
               junos:must "(\"security authentication-key-chains key-chain $$\")";
               junos:must-message "Referenced key-chain must be defined";
               type string;
             }
             leaf algorithm {
               description "Algorithm name";
               junos:must "(\".. key-chain\")";
               junos:must-message "May not be configured without key-chain";
               type enumeration {
                 enum "simple-password" {
                   description "Simple password";
                 }
                 enum "keyed-md5" {
                   description "Keyed message Digest 5";
                 }
                 enum "meticulous-keyed-md5" {
                   description "Meticulous keyed message Digest 5";
                 }
                 enum "keyed-sha-1" {
                   description "Keyed secure hash algorithm (SHA1) ";
                 }
                 enum "meticulous-keyed-sha-1" {
                   description "Meticulous keyed secure hash algorithm (SHA1) ";
                 }
               }
             }
             leaf loose-check {
               description "Verify authentication only if authentication is negotiated";
               type empty;
             }
           }
         }
       }
     }
     container graceful-restart {
       presence "enable graceful-restart";
       description "RIP graceful restart options";
       uses apply-advanced;
       choice enable-disable {
         case case_1 {
           leaf disable {
             description "Disable graceful restart";
             type empty;
           }
         }
       }
       leaf restart-time {
         description "Time after which RIP is declared out of restart";
         type union {
           type string {
             pattern "<.*>|$.*";
           }
           type uint32 {
             range "1 .. 600";
           }
         }
       }
     }
   }
   grouping juniper-protocols-ripng {
     uses apply-advanced;
     container traceoptions {
       description "Trace options for RIPng";
       uses apply-advanced;
       container file {
         description "Trace file options";
         leaf filename {
           description "Name of file in which to write trace information";
           type string {
             length "1 .. 1024";
             junos:posix-pattern "![/ %]";
             junos:pattern-message "Must not contain '/', % or a space";
           }
         }
         leaf replace {
           description "Replace trace file rather than appending to it";
           status deprecated;
           type empty;
         }
         leaf size {
           description "Maximum trace file size";
           type string;
         }
         leaf files {
           description "Maximum number of trace files";
           default "10";
           type union {
             type string {
               pattern "<.*>|$.*";
             }
             type uint32 {
               range "2 .. 1000";
             }
           }
         }
         leaf no-stamp {
           description "Do not timestamp trace file";
           status deprecated;
           type empty;
         }
         choice world-readable-choice {
           leaf world-readable {
             description "Allow any user to read the log file";
             type empty;
           }
           leaf no-world-readable {
             description "Don't allow any user to read the log file";
             type empty;
           }
         }
       }
       list flag {
         key name;
         ordered-by user;
         description "Tracing parameters";
         leaf name {
           type enumeration {
             enum "error" {
               description "Trace RIPng errors";
             }
             enum "expiration" {
               description "Trace RIPng route expiration processing";
             }
             enum "holddown" {
               description "Trace RIPng hold-down processing";
             }
             enum "packets" {
               description "Trace all RIPng packets";
             }
             enum "request" {
               description "Trace RIPng information packets";
             }
             enum "trigger" {
               description "Trace RIPng triggered updates";
             }
             enum "update" {
               description "Trace RIPng update packets";
             }
             enum "nsr-synchronization" {
               description "Trace NSR synchronization events";
             }
             enum "route" {
               description "Trace routing information";
             }
             enum "normal" {
               description "Trace normal events";
             }
             enum "general" {
               description "Trace general events";
             }
             enum "state" {
               description "Trace state transitions";
             }
             enum "policy" {
               description "Trace policy processing";
             }
             enum "task" {
               description "Trace routing protocol task processing";
             }
             enum "timer" {
               description "Trace routing protocol timer processing";
             }
             enum "all" {
               description "Trace everything";
             }
           }
         }
         leaf send {
           description "Trace transmitted packets";
           type empty;
         }
         leaf receive {
           description "Trace received packets";
           type empty;
         }
         leaf detail {
           description "Trace detailed information";
           type empty;
         }
         leaf disable {
           description "Disable this trace flag";
           type empty;
         }
       }
     }
     leaf metric-in {
       description "Metric value to add to incoming routes";
       type union {
         type string {
           pattern "<.*>|$.*";
         }
         type uint32 {
           range "1 .. 15";
         }
       }
     }
     container send {
       description "Configure RIPng send options";
       choice send-opts {
         case case_1 {
           leaf none {
             description "Do not send RIPng updates";
             type empty;
           }
         }
       }
     }
     container receive {
       description "Configure RIPng receive options";
       choice receive-opts {
         case case_1 {
           leaf none {
             description "Do not receive RIPng packets";
             type empty;
           }
         }
       }
     }
     leaf-list import {
       ordered-by user;
       description "Import policy";
       type jt:policy-algebra;
     }
     leaf holddown {
       description "Hold-down time";
       units "seconds";
       type union {
         type string {
           pattern "<.*>|$.*";
         }
         type uint32 {
           range "10 .. 180";
         }
       }
     }
     leaf route-timeout {
       description "Delay before routes time out";
       units "seconds";
       type union {
         type string {
           pattern "<.*>|$.*";
         }
         type uint32 {
           range "30 .. 360";
         }
       }
     }
     leaf update-interval {
       description "Interval between regular route updates";
       units "seconds";
       type union {
         type string {
           pattern "<.*>|$.*";
         }
         type uint32 {
           range "10 .. 60";
         }
       }
     }
     list group {
       key name;
       ordered-by user;
       description "Instance configuration";
       leaf name {
         description "Group name";
         type string {
           junos:posix-pattern "^.{1,48}$";
           junos:pattern-message "Must be a string of at most 48 characters";
         }
       }
       uses apply-advanced;
       leaf route-timeout {
         description "Delay before routes time out";
         units "seconds";
         type union {
           type string {
             pattern "<.*>|$.*";
           }
           type uint32 {
             range "30 .. 360";
           }
         }
       }
       leaf update-interval {
         description "Interval between regular route updates";
         units "seconds";
         type union {
           type string {
             pattern "<.*>|$.*";
           }
           type uint32 {
             range "10 .. 60";
           }
         }
       }
       leaf preference {
         description "Preference of routes learned by this group";
         type union {
           type uint32;
           type string {
             pattern "<.*>|$.*";
           }
         }
       }
       leaf metric-out {
         description "Default metric of exported routes";
         type union {
           type string {
             pattern "<.*>|$.*";
           }
           type uint32 {
             range "1 .. 15";
           }
         }
       }
       leaf-list export {
         ordered-by user;
         description "Export policy";
         type jt:policy-algebra;
       }
       leaf-list import {
         ordered-by user;
         description "Import policy";
         type jt:policy-algebra;
       }
       list neighbor {
         key name;
         ordered-by user;
         description "Neighbor configuration";
         leaf name {
           description "Interface name";
           type union {
             type jt:interface-name;
             type string {
               pattern "<.*>|$.*";
             }
           }
         }
         uses apply-advanced;
         leaf route-timeout {
           description "Delay before routes time out";
           units "seconds";
           type union {
             type string {
               pattern "<.*>|$.*";
             }
             type uint32 {
               range "30 .. 360";
             }
           }
         }
         leaf update-interval {
           description "Interval between regular route updates";
           units "seconds";
           type union {
             type string {
               pattern "<.*>|$.*";
             }
             type uint32 {
               range "10 .. 60";
             }
           }
         }
         leaf metric-in {
           description "Metric value to add to incoming routes";
           type union {
             type string {
               pattern "<.*>|$.*";
             }
             type uint32 {
               range "1 .. 15";
             }
           }
         }
         container send {
           description "Configure RIPng send options";
           choice send-opts {
             case case_1 {
               leaf none {
                 description "Do not send RIPng updates";
                 type empty;
               }
             }
           }
         }
         container receive {
           description "Configure RIPng receive options";
           choice receive-opts {
             case case_1 {
               leaf none {
                 description "Do not receive RIPng packets";
                 type empty;
               }
             }
           }
         }
         leaf-list import {
           ordered-by user;
           description "Import policy";
           type jt:policy-algebra;
         }
       }
     }
     container graceful-restart {
       presence "enable graceful-restart";
       description "RIPng graceful restart options";
       uses apply-advanced;
       choice enable-disable {
         case case_1 {
           leaf disable {
             description "Disable graceful restart";
             type empty;
           }
         }
       }
       leaf restart-time {
         description "Time after which RIPng is declared out of restart";
         type union {
           type string {
             pattern "<.*>|$.*";
           }
           type uint32 {
             range "1 .. 600";
           }
         }
       }
     }
   }
   grouping juniper-protocols-router-discovery {
     uses apply-advanced;
     choice enable-disable {
       case case_1 {
         leaf disable {
           description "Disable router discovery";
           type empty;
         }
       }
     }
     container traceoptions {
       description "Trace options for router discovery";
       uses apply-advanced;
       container file {
         description "Trace file options";
         leaf filename {
           description "Name of file in which to write trace information";
           type string {
             length "1 .. 1024";
             junos:posix-pattern "![/ %]";
             junos:pattern-message "Must not contain '/', % or a space";
           }
         }
         leaf replace {
           description "Replace trace file rather than appending to it";
           status deprecated;
           type empty;
         }
         leaf size {
           description "Maximum trace file size";
           type string;
         }
         leaf files {
           description "Maximum number of trace files";
           default "10";
           type union {
             type string {
               pattern "<.*>|$.*";
             }
             type uint32 {
               range "2 .. 1000";
             }
           }
         }
         leaf no-stamp {
           description "Do not timestamp trace file";
           status deprecated;
           type empty;
         }
         choice world-readable-choice {
           leaf world-readable {
             description "Allow any user to read the log file";
             type empty;
           }
           leaf no-world-readable {
             description "Don't allow any user to read the log file";
             type empty;
           }
         }
       }
       list flag {
         key name;
         ordered-by user;
         description "Tracing parameters";
         leaf name {
           type enumeration {
             enum "route" {
               description "Trace routing information";
             }
             enum "normal" {
               description "Trace normal events";
             }
             enum "general" {
               description "Trace general events";
             }
             enum "state" {
               description "Trace state transitions";
             }
             enum "policy" {
               description "Trace policy processing";
             }
             enum "task" {
               description "Trace routing protocol task processing";
             }
             enum "timer" {
               description "Trace routing protocol timer processing";
             }
             enum "all" {
               description "Trace everything";
             }
           }
         }
       }
     }
     list interface {
       key name;
       ordered-by user;
       description "Interfaces on which to configure router discovery";
       leaf name {
         description "Interface name";
         type union {
           type jt:interface-name;
           type string {
             pattern "<.*>|$.*";
           }
         }
       }
       uses apply-advanced;
       leaf max-advertisement-interval {
         description "Maximum time before sending advertisements";
         units "seconds";
         type union {
           type string {
             pattern "<.*>|$.*";
           }
           type uint32 {
             range "4 .. 1800";
           }
         }
       }
       leaf min-advertisement-interval {
         description "Minimum time before sending advertisements";
         units "seconds";
         type union {
           type string {
             pattern "<.*>|$.*";
           }
           type uint32 {
             range "3 .. 1800";
           }
         }
       }
       leaf lifetime {
         description "How long addresses in advertisements are valid";
         units "seconds";
         type union {
           type string {
             pattern "<.*>|$.*";
           }
           type uint32 {
             range "3 .. 9000";
           }
         }
       }
     }
     list address {
       key name;
       ordered-by user;
       description "IP addresses to include in advertisements";
       leaf name {
         description "IP addresses to include in router advertisements";
         type jt:ipv4addr;
       }
       uses apply-advanced;
       leaf advertise {
         description "Advertise the IP address in advertisements";
         type empty;
       }
       leaf ignore {
         description "Do not advertise the IP address in advertisements";
         type empty;
       }
       leaf broadcast {
         description "Include IP address only in broadcast advertisements";
         type empty;
       }
       leaf multicast {
         description "Include IP address only in multicast advertisements";
         type empty;
       }
       leaf ineligible {
         description "IP address can never become a default router";
         type empty;
       }
       leaf priority {
         description "Preference of the address to become a default router";
         type union {
           type int32;
           type string {
             pattern "<.*>|$.*";
           }
         }
       }
     }
   }
   grouping juniper-protocols-rsvp {
     description "RSVP options";
     uses apply-advanced;
     choice enable-disable {
       case case_1 {
         leaf disable {
           description "Disable RSVP";
           type empty;
         }
       }
     }
     container graceful-restart {
       description "Configure graceful restart attributes";
       uses apply-advanced;
       choice enable-disable {
         case case_1 {
           leaf disable {
             description "Disable RSVP graceful restart capability";
             type empty;
           }
         }
       }
       leaf helper-disable {
         description "Disable graceful restart helper capability";
         type empty;
       }
       leaf maximum-helper-restart-time {
         description "Maximum wait time from down event to neighbor dead";
         default "20";
         units "seconds";
         type union {
           type string {
             pattern "<.*>|$.*";
           }
           type uint32 {
             range "1 .. 1800";
           }
         }
       }
       leaf maximum-helper-recovery-time {
         description "Maximum time restarting neighbor states are kept";
         default "180";
         units "seconds";
         type union {
           type string {
             pattern "<.*>|$.*";
           }
           type uint32 {
             range "1 .. 3600";
           }
         }
       }
     }
     container tunnel-services {
       presence "enable tunnel-services";
       description "Use tunnel services for P2MP LSP ultimate-hop popping";
       uses apply-advanced;
       leaf-list devices {
         ordered-by user;
         description "Tunnel services devices to use for P2MP LSPs";
         type union {
           type jt:interface-device;
           type string {
             pattern "<.*>|$.*";
           }
         }
       }
     }
     leaf no-p2mp-sublsp {
       description "Disable P2MP sub-LSP object generation";
       type empty;
     }
     leaf no-node-id-subobject {
       description "Do not include the node-id sub-object in the RRO";
       type empty;
     }
     leaf no-interface-hello {
       description "Disble interface Hellos on all RSVP interfaces";
       type empty;
     }
     container pop-and-forward {
       description "RSVP pop-and-forward specific global parameters";
       uses apply-advanced;
       container application-label {
         description "Number of application labels under the RSVP transport";
         uses apply-advanced;
         leaf depth {
           description "Application label depth";
           default "1";
           type union {
             type string {
               pattern "<.*>|$.*";
             }
             type uint32 {
               range "0 .. 3";
             }
           }
         }
       }
     }
     leaf hello-acknowledgements {
       description "Acknowledge Hellos on RSVP interfaces not having sessions";
       type empty;
     }
     leaf no-hello-acknowledgements {
       description "Do not ack Hellos on RSVP interfaces not having sessions";
       junos:must "(!(\"protocols rsvp hello-acknowledgements\"))";
       junos:must-message "Config hello-acknowledgements should be removed";
       type empty;
     }
     container node-hello {
       presence "enable node-hello";
       description "Enable node-ID based Hellos on all RSVP interfaces";
       leaf hello-interval {
         description "Hello interval";
         default "9";
         units "seconds";
         type union {
           type string {
             pattern "<.*>|$.*";
           }
           type uint32 {
             range "0 .. 60";
           }
         }
       }
     }
     leaf no-node-hello {
       description "Disable node-ID based Hellos on the router";
       junos:must "(!(\"protocols rsvp node-hello\"))";
       junos:must-message "Config node-hello should be removed";
       type empty;
     }
     leaf allow-bidirectional {
       description "Enable bidirectional support in RSVP";
       status deprecated;
       type empty;
     }
     leaf local-reversion {
       description "Enable local reversion at this Point of Local Repair";
       junos:must "(!(\"protocols rsvp no-local-reversion\"))";
       junos:must-message "Config no-local-reversion should be removed";
       type empty;
     }
     leaf no-local-reversion {
       description "Disable local reversion at this Point of Local Repair";
       type empty;
     }
     leaf rfc6510-lsp-attributes {
       description "Use RFC6510 compliant LSP_ATTRIBUTES";
       type empty;
     }
     container fast-reroute {
       description "One-to-one fast-reroute protection mechanism";
       uses apply-advanced;
       leaf optimize-timer {
         description "Frequency of reoptimization for fast-reroute detour";
         units "seconds";
         type union {
           type string {
             pattern "<.*>|$.*";
           }
           type int32 {
             range "0 .. 65535";
           }
         }
       }
     }
     container load-balance {
       description "Per-packet load-balancing algorithm";
       uses apply-advanced;
       leaf bandwidth {
         description "Per-packet load balancing proportional to LSP bandwidth";
         type empty;
       }
     }
     container traceoptions {
       description "Trace options for RSVP";
       uses apply-advanced;
       container file {
         description "Trace file options";
         leaf filename {
           description "Name of file in which to write trace information";
           type string {
             length "1 .. 1024";
             junos:posix-pattern "![/ %]";
             junos:pattern-message "Must not contain '/', % or a space";
           }
         }
         leaf replace {
           description "Replace trace file rather than appending to it";
           status deprecated;
           type empty;
         }
         leaf size {
           description "Maximum trace file size";
           type string;
         }
         leaf files {
           description "Maximum number of trace files";
           default "10";
           type union {
             type string {
               pattern "<.*>|$.*";
             }
             type uint32 {
               range "2 .. 1000";
             }
           }
         }
         leaf no-stamp {
           description "Do not timestamp trace file";
           status deprecated;
           type empty;
         }
         choice world-readable-choice {
           leaf world-readable {
             description "Allow any user to read the log file";
             type empty;
           }
           leaf no-world-readable {
             description "Don't allow any user to read the log file";
             type empty;
           }
         }
       }
       list flag {
         key name;
         ordered-by user;
         description "Tracing parameters";
         leaf name {
           type enumeration {
             enum "io-event" {
               description "Trace RSVP IO task related events";
             }
             enum "io-packets" {
               description "Trace all RSVP periodic refresh activity";
             }
             enum "packets" {
               description "Trace all RSVP trigger packets";
             }
             enum "path" {
               description "Trace RSVP trigger path messages";
             }
             enum "resv" {
               description "Trace RSVP trigger Resv messages";
             }
             enum "pathtear" {
               description "Trace RSVP PathTear messages";
             }
             enum "resvtear" {
               description "Trace RSVP ResvTear messages";
             }
             enum "state" {
               description "Trace state transitions";
             }
             enum "error" {
               description "Trace error conditions";
             }
             enum "route" {
               description "Trace routing information";
             }
             enum "lmp" {
               description "Trace RSVP-LMP related interactions";
             }
             enum "event" {
               description "Trace RSVP related events";
             }
             enum "nsr-synchronization" {
               description "Trace NSR synchronization events";
             }
             enum "lsp-prefix" {
               description "Prefix the trace messages with LSP information";
             }
             enum "enhanced-frr" {
               description "Enhanced FRR related information";
             }
             enum "all" {
               description "Trace everything";
             }
           }
         }
         leaf send {
           description "Trace transmitted packets";
           type empty;
         }
         leaf receive {
           description "Trace received packets";
           type empty;
         }
         leaf detail {
           description "Trace detailed information";
           type empty;
         }
         leaf disable {
           description "Disable this trace flag";
           type empty;
         }
       }
     }
     leaf refresh-time {
       description "Refresh time in seconds";
       default "1200";
       type union {
         type string {
           pattern "<.*>|$.*";
         }
         type uint32 {
           range "1 .. 65535";
         }
       }
     }
     leaf keep-multiplier {
       description "Keep multiplier";
       default "3";
       type union {
         type string {
           pattern "<.*>|$.*";
         }
         type uint32 {
           range "1 .. 255";
         }
       }
     }
     leaf graceful-deletion-timeout {
       description "Time to complete graceful deletion signaling";
       default "30";
       units "seconds";
       type union {
         type string {
           pattern "<.*>|$.*";
         }
         type uint32 {
           range "1 .. 300";
         }
       }
     }
     leaf setup-protection {
       description "Enable setup protection";
       type empty;
     }
     leaf no-p2mp-re-merge {
       description "Enable p2mp remerge";
       type empty;
     }
     leaf cross-credibility-cspf {
       description "Compute CSPF paths spanning protocols for bypass LSP, detour LSP and loose hop expansion";
       type empty;
     }
     container preemption {
       description "Set RSVP session preemption attributes";
       uses apply-advanced;
       choice preemption-type {
         case case_1 {
           leaf disabled {
             description "No RSVP session preemption";
             type empty;
           }
         }
         case case_2 {
           leaf normal {
             description "Run RSVP session preemption to accommodate new sessions";
             type empty;
           }
         }
         case case_3 {
           leaf aggressive {
             description "Run RSVP session preemption whenever necessary";
             type empty;
           }
         }
       }
       container soft-preemption {
         description "Options for establishing new path before tearing down a preempted LSP";
         uses apply-advanced;
         leaf cleanup-timer {
           description "Time a soft-preempted LSP will be maintained";
           units "seconds";
           type union {
             type string {
               pattern "<.*>|$.*";
             }
             type int32 {
               range "0 .. 10800";
             }
           }
         }
       }
     }
     leaf authentication-key {
       description "Authentication password";
       type jt:unreadable;
     }
     leaf no-authentication-check {
       description "Skip authentication check for received messages";
       type empty;
     }
     container associated-bidirectional-lsp {
       description "Set associated bidirectional LSP attributes";
       uses apply-advanced;
       leaf single-sided-provisioning {
         description "Enable unidirectional reverse LSP setup for single sided provisioned forward LSP";
         type empty;
       }
     }
     leaf no-enhanced-frr-bypass {
       description "Disable enhanced facility backup FRR";
       type empty;
     }
     container expand-flood-reflector-hop {
       presence "enable expand-flood-reflector-hop";
       description "Control expansion of flood reflector ERO strict hops";
     }
     list interface {
       key name;
       ordered-by user;
       description "RSVP interface options";
       leaf name {
         description "Interface name";
         type union {
           type jt:interface-name;
           type string {
             pattern "<.*>|$.*";
           }
         }
       }
       uses apply-advanced;
       choice enable-disable {
         case case_1 {
           leaf disable {
             description "Disable RSVP on this interface";
             type empty;
           }
         }
       }
       leaf authentication-key {
         description "Authentication password";
         type jt:unreadable;
       }
       choice aggregate-choice {
         leaf aggregate {
           description "Permit refresh reduction extensions on the interface";
           status deprecated;
           type empty;
         }
         leaf no-aggregate {
           description "Don't permit refresh reduction extensions on the interface";
           status deprecated;
           type empty;
         }
       }
       choice reliable-choice {
         leaf reliable {
           description "Permit reliable message delivery on the interface";
           type empty;
         }
         leaf no-reliable {
           description "Don't permit reliable message delivery on the interface";
           type empty;
         }
       }
       leaf hello-interval {
         description "Hello interval";
         default "9";
         units "seconds";
         type union {
           type string {
             pattern "<.*>|$.*";
           }
           type uint32 {
             range "0 .. 60";
           }
         }
       }
       container subscription {
         description "Link bandwidth percentage for RSVP reservation";
         uses subscription-type;
       }
       leaf bandwidth {
         description "Available bandwidth for the interface units bps";
         type string;
       }
       container update-threshold {
         description "Change in reserved bandwidth to trigger IGP update";
         uses apply-advanced;
         container adaptive {
           junos:must "(!(\".. threshold-value\"))";
           junos:must-message "Cannot be configured with threshold-value";
           junos:must "(!(\".. threshold-percent\"))";
           junos:must-message "Cannot be configured with threshold-percent";
           description "Tune update-threshold dynamically";
           uses apply-advanced;
           list limit {
             key name;
             description "Available Bandwidth threshold limit";
             leaf name {
               description "Upper limit of Available bandwidth for this range";
               type string;
             }
             leaf threshold-percent {
               description "Percentage change in reserved bandwidth to trigger IGP update";
               default "10.0";
               units "percent";
               junos:must "(!(\".. .. limit $$ threshold-value\"))";
               junos:must-message "Cannot be configured with threshold-value";
               type decimal64 {
                 fraction-digits 9;
                 range "0.001 .. 20";
               }
             }
             leaf threshold-value {
               description "Change in reserved bandwidth to trigger IGP update (will be capped at 20% of link BW)";
               junos:must "(!(\".. .. limit $$ threshold-percent\"))";
               junos:must-message "Cannot be configured with threshold-percent";
               type string;
             }
           }
         }
         leaf threshold-percent {
           description "Percentage change in reserved bandwidth to trigger IGP update";
           default "10.0";
           units "percent";
           junos:must "(!(\".. adaptive\"))";
           junos:must-message "Cannot be configured with adaptive";
           type decimal64 {
             fraction-digits 9;
             range "0.001 .. 20";
           }
         }
         leaf threshold-value {
           description "Change in reserved bandwidth to trigger IGP update (will be capped at 20% of link BW)";
           junos:must "(!(\".. adaptive\"))";
           junos:must-message "Cannot be configured with adaptive";
           type string;
         }
       }
       container update-threshold-max-reservable {
         description "Change in non-rsvp bandwidth to trigger IGP update ";
         uses apply-advanced;
         leaf bandwidth {
           description "Change in non-rsvp bandwidth to trigger IGP update units bps";
           type string;
         }
         leaf percent {
           description "Percentage change in max-reservable bandwidth to trigger IGP update";
           units "percent";
           type union {
             type string {
               pattern "<.*>|$.*";
             }
             type uint32 {
               range "1 .. 100";
             }
           }
         }
       }
       container non-rsvp-bandwdith {
         description "Config knobs relating to non-rsvp bandwidth";
         uses apply-advanced;
         leaf local-bw-override-threshold {
           description "Overide threshold and update local bandwidth with non-rsvp bandwidth usage";
           type empty;
         }
       }
       container link-protection {
         presence "enable link-protection";
         description "Protect traffic with a label-stacked LSP";
         uses apply-advanced;
         choice enable-disable {
           case case_1 {
             leaf disable {
               description "Disable link protection on this interface";
               type empty;
             }
           }
         }
         container bandwidth {
           description "Bandwidth for each bypass";
           uses bandwidth-type;
         }
         leaf max-bypasses {
           description "Max number of bypasses permitted for protecting this interface";
           default "1";
           type union {
             type string {
               pattern "<.*>|$.*";
             }
             type uint32 {
               range "0 .. 99";
             }
           }
         }
         leaf subscription {
           description "Percent of bandwidth guaranteed when admitting protected LSPs into bypasses";
           default "100";
           type union {
             type string {
               pattern "<.*>|$.*";
             }
             type uint32 {
               range "1 .. 65535";
             }
           }
         }
         leaf no-node-protection {
           description "Disallow node protection on this interface";
           type empty;
         }
         leaf optimize-timer {
           description "Interval between bypass reoptimizations";
           default "0";
           units "seconds";
           type union {
             type string {
               pattern "<.*>|$.*";
             }
             type uint32 {
               range "0 .. 65535";
             }
           }
         }
         leaf class-of-service {
           description "Class of service for the bypass LSP";
           type union {
             type string {
               pattern "<.*>|$.*";
             }
             type int32 {
               range "0 .. 7";
             }
           }
         }
         leaf hop-limit {
           description "Maximum allowed router hops for bypass";
           type union {
             type string {
               pattern "<.*>|$.*";
             }
             type uint32 {
               range "2 .. 255";
             }
           }
         }
         leaf no-cspf {
           description "Disable automatic path computation";
           junos:must "(\".. path\")";
           junos:must-message "The path of the bypass must be configured when using no-cspf";
           type empty;
         }
         leaf exclude-srlg {
           description "Exclude SRLG links";
           type empty;
         }
         container priority {
           presence "enable priority";
           description "Preemption priorities for the bypass LSP";
         }
         leaf setup-priority {
           description "Set-up priority";
           type union {
             type string {
               pattern "<.*>|$.*";
             }
             type uint32 {
               range "0 .. 7";
             }
           }
         }
         leaf reservation-priority {
           description "Reservation priority";
           type union {
             type string {
               pattern "<.*>|$.*";
             }
             type uint32 {
               range "0 .. 7";
             }
           }
         }
         list path {
           key name;
           ordered-by user;
           description "Explicit route of bypass path";
           leaf name {
             description "Address of next system in path";
             type jt:ipv4addr;
           }
           choice loose_strict_none {
             case case_1 {
               leaf loose {
                 description "Next hop might not be adjacent";
                 type empty;
               }
             }
             case case_2 {
               leaf strict {
                 description "Next hop must be adjacent";
                 type empty;
               }
             }
           }
         }
         container admin-group {
           description "Administrative group policy";
           uses admin_group_include_exclude;
         }
         list bypass {
           key name;
           ordered-by user;
           description "Bypass with specific constraints";
           leaf name {
             description "Name of bypass";
             type string {
               length "1 .. 64";
             }
           }
           uses apply-advanced;
           leaf to {
             description "Address of egress router";
             type jt:ipv4addr;
           }
           container bandwidth {
             description "Bandwidth for each bypass";
             uses bandwidth-type;
           }
           container subscription {
             description "Bandwidth percent available on bypass for protected LSPs";
             presence "enable subscription";
             uses bypass-subscription-type;
           }
           leaf description {
             description "Text description of bypass";
             type string {
               length "1 .. 80";
             }
           }
           container priority {
             presence "enable priority";
             description "Preemption priorities for bypass";
           }
           leaf setup-priority {
             description "Set-up priority";
             type union {
               type string {
                 pattern "<.*>|$.*";
               }
               type uint32 {
                 range "0 .. 7";
               }
             }
           }
           leaf reservation-priority {
             description "Reservation priority";
             type union {
               type string {
                 pattern "<.*>|$.*";
               }
               type uint32 {
                 range "0 .. 7";
               }
             }
           }
           leaf class-of-service {
             description "Class of service for the bypass LSP";
             type union {
               type string {
                 pattern "<.*>|$.*";
               }
               type int32 {
                 range "0 .. 7";
               }
             }
           }
           leaf hop-limit {
             description "Maximum allowed router hops for bypass";
             type union {
               type string {
                 pattern "<.*>|$.*";
               }
               type uint32 {
                 range "2 .. 255";
               }
             }
           }
           leaf no-cspf {
             description "Disable automatic path computation";
             junos:must "(\".. path\")";
             junos:must-message "The path of the bypass must be configured when using no-cspf";
             type empty;
           }
           leaf exclude-srlg {
             description "Exclude SRLG links";
             type empty;
           }
           list path {
             key name;
             ordered-by user;
             description "Explicit route of bypass path";
             leaf name {
               description "Address of next system in path";
               type jt:ipv4addr;
             }
             choice loose_strict_none {
               case case_1 {
                 leaf loose {
                   description "Next hop might not be adjacent";
                   type empty;
                 }
               }
               case case_2 {
                 leaf strict {
                   description "Next hop must be adjacent";
                   type empty;
                 }
               }
             }
           }
           container admin-group {
             description "Administrative group policy";
             uses admin_group_include_exclude;
           }
         }
       }
     }
     list peer-interface {
       key name;
       ordered-by user;
       description "Configuration for peer interface";
       leaf name {
         description "Name of peer interface";
         type string;
       }
       uses apply-advanced;
       choice enable-disable {
         case case_1 {
           leaf disable {
             description "Disable RSVP on this control peer";
             type empty;
           }
         }
       }
       leaf authentication-key {
         description "Authentication password";
         type jt:unreadable;
       }
       choice aggregate-choice {
         leaf aggregate {
           description "Permit refresh reduction extensions on the interface";
           status deprecated;
           type empty;
         }
         leaf no-aggregate {
           description "Don't permit refresh reduction extensions on the interface";
           status deprecated;
           type empty;
         }
       }
       choice reliable-choice {
         leaf reliable {
           description "Permit reliable message delivery on the interface";
           type empty;
         }
         leaf no-reliable {
           description "Don't permit reliable message delivery on the interface";
           type empty;
         }
       }
       leaf hello-interval {
         description "Hello interval";
         default "9";
         units "seconds";
         type union {
           type string {
             pattern "<.*>|$.*";
           }
           type uint32 {
             range "0 .. 60";
           }
         }
       }
       container dynamic-bidirectional-transport {
         presence "enable dynamic-bidirectional-transport";
         description "Enable dynamic setup of bidirectional packet LSP for transporting non-packet GMPLS LSP";
         uses apply-advanced;
         leaf template {
           description "Template for the dynamic bidirectional packet LSP";
           junos:must "(!(\"protocols mpls label-switched-path $$ p2mp\"))";
           junos:must-message "Referenced template cannot be a p2mp template";
           junos:must "((\"protocols mpls label-switched-path $$\" && \"protocols mpls label-switched-path $$ template\"))";
           junos:must-message "Referenced LSP template does not exist";
           type string {
             junos:posix-pattern "^.{1,64}$";
             junos:pattern-message "Must be a string of 64 characters or less";
           }
         }
       }
     }
     list lsp-set {
       key name;
       ordered-by user;
       description "Configuration for lsp set";
       leaf name {
         description "Name of lsp set";
         type string;
       }
       uses apply-advanced;
       choice enable-disable {
         case case_1 {
           leaf disable {
             description "Disable this lsp set";
             type empty;
           }
         }
       }
       container match-criteria {
         description "Match criteria for this lsp set";
         uses lsp-set-match-type;
       }
       container traceoptions {
         description "Trace options for this lsp set";
         uses apply-advanced;
         container file {
           description "Trace file options";
           leaf filename {
             description "Name of file in which to write trace information";
             type string {
               length "1 .. 1024";
               junos:posix-pattern "![/ %]";
               junos:pattern-message "Must not contain '/', % or a space";
             }
           }
           leaf replace {
             description "Replace trace file rather than appending to it";
             status deprecated;
             type empty;
           }
           leaf size {
             description "Maximum trace file size";
             type string;
           }
           leaf files {
             description "Maximum number of trace files";
             default "10";
             type union {
               type string {
                 pattern "<.*>|$.*";
               }
               type uint32 {
                 range "2 .. 1000";
               }
             }
           }
           leaf no-stamp {
             description "Do not timestamp trace file";
             status deprecated;
             type empty;
           }
           choice world-readable-choice {
             leaf world-readable {
               description "Allow any user to read the log file";
               type empty;
             }
             leaf no-world-readable {
               description "Don't allow any user to read the log file";
               type empty;
             }
           }
         }
         list flag {
           key name;
           ordered-by user;
           description "Tracing parameters";
           leaf name {
             type enumeration {
               enum "io-event" {
                 description "Trace RSVP IO task related events";
               }
               enum "io-packets" {
                 description "Trace all RSVP periodic refresh activity";
               }
               enum "packets" {
                 description "Trace all RSVP packets";
               }
               enum "path" {
                 description "Trace RSVP path messages";
               }
               enum "resv" {
                 description "Trace RSVP Resv messages";
               }
               enum "pathtear" {
                 description "Trace RSVP PathTear messages";
               }
               enum "resvtear" {
                 description "Trace RSVP ResvTear messages";
               }
               enum "state" {
                 description "Trace state transitions";
               }
               enum "error" {
                 description "Trace error conditions";
               }
               enum "route" {
                 description "Trace routing information";
               }
               enum "lmp" {
                 description "Trace RSVP-LMP related interactions";
               }
               enum "event" {
                 description "Trace RSVP related events";
               }
               enum "nsr-synchronization" {
                 description "Trace NSR synchronization events";
               }
               enum "lsp-prefix" {
                 description "Prefix the trace messages with LSP information";
               }
               enum "enhanced-frr" {
                 description "Enhanced FRR related information";
               }
               enum "all" {
                 description "Trace everything";
               }
             }
           }
           leaf send {
             description "Trace transmitted packets";
             type empty;
           }
           leaf receive {
             description "Trace received packets";
             type empty;
           }
           leaf detail {
             description "Trace detailed information";
             type empty;
           }
           leaf disable {
             description "Disable this trace flag";
             type empty;
           }
         }
       }
     }
   }
   grouping bypass-subscription-type {
     uses apply-advanced;
     leaf subscription {
       description "Subscription percentage for bandwidth protection";
       default "100";
       type string;
     }
   }
   grouping juniper-protocols-stp {
     uses apply-advanced;
     choice enable-disable {
       case case_1 {
         leaf disable {
           description "Disable STP";
           type empty;
         }
       }
     }
     leaf bpdu-destination-mac-address {
       description "Destination MAC address in the spanning tree BPDUs";
       type enumeration {
         enum "provider-bridge-group" {
           description "802.1ad provider bridge group address";
         }
       }
     }
     leaf bridge-priority {
       description "Priority of the bridge (in increments of 4k - 0,4k,8k,..60k)";
       type string {
         junos:posix-pattern "^(0|4k|4096|8k|8192|12k|12288|16k|16384|20k|20480|24k|24576|28k|28672|32k|32768|36k|36864|40k|40960|44k|45056|48k|49512|52k|53248|56k|57344|60k|61440)$";
         junos:pattern-message "Must be a multiple of 4096";
       }
     }
     leaf backup-bridge-priority {
       description "Priority of the bridge (in increments of 4k - 4k,8k,..60k)";
       type string {
         junos:posix-pattern "^(4k|4096|8k|8192|12k|12288|16k|16384|20k|20480|24k|24576|28k|28672|32k|32768|36k|36864|40k|40960|44k|45056|48k|49512|52k|53248|56k|57344|60k|61440)$";
         junos:pattern-message "Must be a multiple of 4096";
       }
     }
     leaf max-age {
       description "Maximum age of received protocol bpdu";
       units "seconds";
       type union {
         type string {
           pattern "<.*>|$.*";
         }
         type uint16 {
           range "6 .. 40";
         }
       }
     }
     leaf hello-time {
       description "Time interval between configuration BPDUs";
       units "seconds";
       type union {
         type string {
           pattern "<.*>|$.*";
         }
         type uint16 {
           range "1 .. 10";
         }
       }
     }
     leaf forward-delay {
       description "Time spent in listening or learning state";
       units "seconds";
       type union {
         type string {
           pattern "<.*>|$.*";
         }
         type uint16 {
           range "4 .. 30";
         }
       }
     }
     leaf system-identifier {
       description "Sytem identifier to represent this node";
       type jt:mac-unicast;
     }
     container traceoptions {
       description "Tracing options for debugging protocol operation";
       uses stp-trace-options;
     }
     leaf vpls-flush-on-topology-change {
       description "Enable VPLS MAC flush on root protected CE interface receving topology change";
       type empty;
     }
     leaf priority-hold-time {
       description "Hold time before switching to primary priority when core domain becomes up";
       units "seconds";
       type union {
         type string {
           pattern "<.*>|$.*";
         }
         type uint16 {
           range "1 .. 255";
         }
       }
     }
     list system-id {
       key name;
       ordered-by user;
       description "System ID to IP mapping";
       uses system-id-ip-map;
     }
     list interface {
       key name;
       description "Interface options";
       uses stp-interface;
     }
     leaf extended-system-id {
       description "Extended system identifier";
       type union {
         type string {
           pattern "<.*>|$.*";
         }
         type uint16 {
           range "0 .. 4095";
         }
       }
     }
     leaf force-version {
       description "Force protocol version";
       type enumeration {
         enum "stp" {
           description "Spanning tree protocol";
         }
       }
     }
     leaf bpdu-block-on-edge {
       description "Block BPDU on all interfaces configured as edge (BPDU Protect)";
       type empty;
     }
   }
   grouping juniper-protocols-vstp {
     uses apply-advanced;
     choice enable-disable {
       case case_1 {
         leaf disable {
           description "Disable VSTP";
           type empty;
         }
       }
     }
     leaf force-version {
       description "Force protocol version";
       type enumeration {
         enum "stp" {
           description "Spanning tree protocol";
         }
       }
     }
     leaf bpdu-block-on-edge {
       description "Block BPDU on all interfaces configured as edge (BPDU Protect)";
       type empty;
     }
     leaf vpls-flush-on-topology-change {
       description "Enable VPLS MAC flush on root protected CE interface receving topology change";
       type empty;
     }
     leaf priority-hold-time {
       description "Hold time before switching to primary priority when core domain becomes up";
       units "seconds";
       type union {
         type string {
           pattern "<.*>|$.*";
         }
         type uint16 {
           range "1 .. 255";
         }
       }
     }
     list system-id {
       key name;
       ordered-by user;
       description "System ID to IP mapping";
       uses system-id-ip-map;
     }
     list interface {
       key name;
       description "Interface options";
       uses stp-interface;
     }
     list vlan {
       key name;
       description "VLAN spanning tree options";
       leaf name {
         description "VLAN id or all";
         type string;
       }
       uses apply-advanced;
       leaf bridge-priority {
         description "Priority of the bridge (in increments of 4k - 0,4k,8k,..60k)";
         type string {
           junos:posix-pattern "^(0|4k|4096|8k|8192|12k|12288|16k|16384|20k|20480|24k|24576|28k|28672|32k|32768|36k|36864|40k|40960|44k|45056|48k|49512|52k|53248|56k|57344|60k|61440)$";
           junos:pattern-message "Must be a multiple of 4096";
         }
       }
       leaf backup-bridge-priority {
         description "Priority of the bridge (in increments of 4k - 4k,8k,..60k)";
         type string {
           junos:posix-pattern "^(4k|4096|8k|8192|12k|12288|16k|16384|20k|20480|24k|24576|28k|28672|32k|32768|36k|36864|40k|40960|44k|45056|48k|49512|52k|53248|56k|57344|60k|61440)$";
           junos:pattern-message "Must be a multiple of 4096";
         }
       }
       leaf max-age {
         description "Maximum age of received protocol bpdu";
         units "seconds";
         type union {
           type string {
             pattern "<.*>|$.*";
           }
           type uint16 {
             range "6 .. 40";
           }
         }
       }
       leaf hello-time {
         description "Time interval between configuration BPDUs";
         units "seconds";
         type union {
           type string {
             pattern "<.*>|$.*";
           }
           type uint16 {
             range "1 .. 10";
           }
         }
       }
       leaf forward-delay {
         description "Time spent in listening or learning state";
         units "seconds";
         type union {
           type string {
             pattern "<.*>|$.*";
           }
           type uint16 {
             range "4 .. 30";
           }
         }
       }
       leaf system-identifier {
         description "Sytem identifier to represent this node";
         type jt:mac-unicast;
       }
       container traceoptions {
         description "Tracing options for debugging protocol operation";
         uses stp-trace-options;
       }
       list interface {
         key name;
         description "Interface options";
         uses stp-interface;
       }
     }
     container vlan-group {
       presence "enable vlan-group";
       description "Spanning tree options for group of VLANs";
       uses apply-advanced;
       list group {
         key name;
         ordered-by user;
         description "Name if VLAN group";
         leaf name {
           description "VLAN group name";
           type string {
             length "1 .. 63";
             junos:posix-pattern "^[[:alpha:]][[:alnum:]_-]+$";
             junos:pattern-message "Must be a string beginning with a letter and consisting of letters, numbers, dashes, and underscores";
           }
         }
         uses apply-advanced;
         leaf-list vlan {
           ordered-by user;
           description "VLAN ID or VLAN ID range [1..4094]";
           type string;
         }
         leaf bridge-priority {
           description "Priority of the bridge (in increments of 4k - 0,4k,8k,..60k)";
           type string {
             junos:posix-pattern "^(0|4k|4096|8k|8192|12k|12288|16k|16384|20k|20480|24k|24576|28k|28672|32k|32768|36k|36864|40k|40960|44k|45056|48k|49512|52k|53248|56k|57344|60k|61440)$";
             junos:pattern-message "Must be a multiple of 4096";
           }
         }
         leaf backup-bridge-priority {
           description "Priority of the bridge (in increments of 4k - 4k,8k,..60k)";
           type string {
             junos:posix-pattern "^(4k|4096|8k|8192|12k|12288|16k|16384|20k|20480|24k|24576|28k|28672|32k|32768|36k|36864|40k|40960|44k|45056|48k|49512|52k|53248|56k|57344|60k|61440)$";
             junos:pattern-message "Must be a multiple of 4096";
           }
         }
         leaf max-age {
           description "Maximum age of received protocol bpdu";
           units "seconds";
           type union {
             type string {
               pattern "<.*>|$.*";
             }
             type uint16 {
               range "6 .. 40";
             }
           }
         }
         leaf hello-time {
           description "Time interval between configuration BPDUs";
           units "seconds";
           type union {
             type string {
               pattern "<.*>|$.*";
             }
             type uint16 {
               range "1 .. 10";
             }
           }
         }
         leaf forward-delay {
           description "Time spent in listening or learning state";
           units "seconds";
           type union {
             type string {
               pattern "<.*>|$.*";
             }
             type uint16 {
               range "4 .. 30";
             }
           }
         }
         leaf system-identifier {
           description "Sytem identifier to represent this node";
           type jt:mac-unicast;
         }
         container traceoptions {
           description "Tracing options for debugging protocol operation";
           uses stp-trace-options;
         }
         list interface {
           key name;
           description "Interface options";
           uses stp-interface;
         }
       }
     }
   }
   grouping juniper-ri-protocols-bfd {
     uses apply-advanced;
     container sbfd {
       description "Seamless BFD parameters";
       uses apply-advanced;
       leaf-list pool {
         description "List of seamless BFD endpoints";
         type union {
           type uint32;
           type string {
             pattern "<.*>|$.*";
           }
         }
       }
       list local-discriminator {
         key name;
         ordered-by user;
         description "Local discriminator for seamless BFD responder";
         leaf name {
           description "Local discriminator for seamless BFD responder";
           type union {
             type string {
               pattern "<.*>|$.*";
             }
             type uint32 {
               range "1 .. 4294967295";
             }
           }
         }
         uses apply-advanced;
         leaf minimum-receive-interval {
           description "Minimum receive interval for seamless BFD responder";
           units "milliseconds";
           type union {
             type string {
               pattern "<.*>|$.*";
             }
             type uint32 {
               range "10 .. 255000";
             }
           }
         }
         leaf local-ip-address {
           description "IPv4 source address";
           type jt:ipv4addr;
         }
       }
     }
   }
   grouping juniper-ri-protocols-igmp-snooping {
     description "IGMP snooping options";
     uses apply-advanced;
     container traceoptions {
       description "Trace options for IGMP Snooping";
       uses apply-advanced;
       container file {
         description "Trace file options";
         leaf filename {
           description "Name of file in which to write trace information";
           type string {
             length "1 .. 1024";
             junos:posix-pattern "![/ %]";
             junos:pattern-message "Must not contain '/', % or a space";
           }
         }
         leaf replace {
           description "Replace trace file rather than appending to it";
           status deprecated;
           type empty;
         }
         leaf size {
           description "Maximum trace file size";
           type string;
         }
         leaf files {
           description "Maximum number of trace files";
           default "10";
           type union {
             type string {
               pattern "<.*>|$.*";
             }
             type uint32 {
               range "2 .. 1000";
             }
           }
         }
         leaf no-stamp {
           description "Do not timestamp trace file";
           status deprecated;
           type empty;
         }
         choice world-readable-choice {
           leaf world-readable {
             description "Allow any user to read the log file";
             type empty;
           }
           leaf no-world-readable {
             description "Don't allow any user to read the log file";
             type empty;
           }
         }
       }
       list flag {
         key name;
         ordered-by user;
         description "Tracing parameters";
         leaf name {
           type enumeration {
             enum "packets" {
               description "Trace all IGMP packets";
             }
             enum "query" {
               description "Trace IGMP membership query messages";
             }
             enum "report" {
               description "Trace membership report messages";
             }
             enum "leave" {
               description "Trace leave group messages (IGMPv2 only)";
             }
             enum "group" {
               description "Trace group operations";
             }
             enum "client-notification" {
               description "Trace notifications";
             }
             enum "host-notification" {
               description "Trace host notifications";
             }
             enum "route" {
               description "Trace routing information";
             }
             enum "normal" {
               description "Trace normal events";
             }
             enum "general" {
               description "Trace general events";
             }
             enum "state" {
               description "Trace state transitions";
             }
             enum "policy" {
               description "Trace policy processing";
             }
             enum "task" {
               description "Trace routing protocol task processing";
             }
             enum "timer" {
               description "Trace routing protocol timer processing";
             }
             enum "all" {
               description "Trace everything";
             }
           }
         }
         leaf send {
           description "Trace transmitted packets";
           type empty;
         }
         leaf receive {
           description "Trace received packets";
           type empty;
         }
         leaf detail {
           description "Trace detailed information";
           type empty;
         }
         leaf disable {
           description "Disable this trace flag";
           type empty;
         }
       }
     }
     leaf query-interval {
       description "When to send host query messages";
       default "125";
       units "seconds";
       type union {
         type string {
           pattern "<.*>|$.*";
         }
         type uint32 {
           range "1 .. 1024";
         }
       }
     }
     container l2-querier {
       description "Enable L2 querier mode";
       uses apply-advanced;
       leaf source-address {
         description "Source IP address to use for L2 querier";
         type jt:ipv4addr;
       }
     }
     leaf query-response-interval {
       description "How long to wait for a host query response";
       default "10";
       units "seconds";
       type string {
         junos:posix-pattern "^[0-9]{1,4}(.[0-9])?$";
         junos:pattern-message "Up to 1 digit to right of decimal point";
       }
     }
     leaf query-last-member-interval {
       description "When to send group query messages";
       default "1";
       units "seconds";
       type string {
         junos:posix-pattern "^[0-9]{1,4}(.[0-9])?$";
         junos:pattern-message "Up to 1 digit to right of decimal point";
       }
     }
     leaf robust-count {
       description "Expected packet loss on a subnet";
       default "2";
       type union {
         type string {
           pattern "<.*>|$.*";
         }
         type uint32 {
           range "2 .. 10";
         }
       }
     }
     leaf learn-pim-router {
       description "Learn PIM router interfaces from PIM hellos";
       type empty;
     }
     leaf immediate-leave {
       description "Enable immediate group leave on interfaces";
       type empty;
     }
     leaf evpn-ssm-reports-only {
       description "Accept and process only <s,g> reports of SSM groups";
       type empty;
     }
     container proxy {
       presence "enable proxy";
       description "Enable proxy mode";
       uses apply-advanced;
       leaf source-address {
         description "Source IP address to use for proxy";
         junos:must "(!(\".. .. .. .. vlan-id all\"))";
         junos:must-message "With qualified-learning source-address should be configured under Vlan options";
         type jt:ipv4addr;
       }
       leaf irb {
         description "Proxy IGMP reports to IRB";
         type empty;
       }
     }
     list interface {
       key name;
       ordered-by user;
       description "Interface options for IGMP";
       leaf name {
         description "Interface name";
         junos:must "(!(\"interfaces $$-IFL vlan-tags inner-range\"))";
         junos:must-message "interface with vlan-tags inner-range should be specified in a learning-domain only";
         junos:must "(!(\"interfaces $$-IFL vlan-id-range\"))";
         junos:must-message "interface with vlan-id-range should be specified in a learning-domain only";
         junos:must "(\".. .. .. .. interface $$\")";
         junos:must-message "interface options can be specified for the interfaces in the routing-instance";
         junos:must "(!(\".. .. .. .. vlan-id all\"))";
         junos:must-message "When 'vlan-id all' is configured, interface should be configured only under vlan";
         type union {
           type jt:interface-name;
           type string {
             pattern "<.*>|$.*";
           }
         }
       }
       uses apply-advanced;
       leaf multicast-router-interface {
         description "Enabling multicast-router-interface on the interface";
         type empty;
       }
       leaf immediate-leave {
         description "Enable immediate group leave on interfaces";
         type empty;
       }
       leaf host-only-interface {
         description "Enable interfaces to be treated as host-side interfaces";
         junos:must "(!(\".. multicast-router-interface\"))";
         junos:must-message "interface cannot be both host-only and multicast-router";
         type empty;
       }
       leaf group-limit {
         description "Maximum number of (source,group) per interface";
         type union {
           type string {
             pattern "<.*>|$.*";
           }
           type uint16 {
             range "1 .. 65535";
           }
         }
       }
       container static {
         description "Static group or source membership";
         uses apply-advanced;
         list group {
           key name;
           ordered-by user;
           description "IP multicast group address";
           leaf name {
             description "IP multicast group address";
             type jt:ipv4addr;
           }
           uses apply-advanced;
           list source {
             key name;
             ordered-by user;
             description "IP multicast source address";
             leaf name {
               description "Source address of IP multicast data";
               type jt:ipv4addr;
             }
             uses apply-advanced;
           }
         }
       }
     }
     list pseudowire-remote-address {
       key name;
       ordered-by user;
       description "Pseudowire interface options for IGMP";
       junos:must "((\" .. .. .. igmp-snooping-options snoop-pseudowires\" || \" .. .. .. .. igmp-snooping-options snoop-pseudowires\"))";
       junos:must-message "Configure pseudowire-remote-address only with snoop-pseudowires instance config";
       leaf name {
         description "Pseudowire endpoint address";
         junos:must "(!(\".. .. .. .. vlan-id all\"))";
         junos:must-message "When 'vlan-id all' is configured, pseudowire-remote-address should be configured only under vlan";
         type jt:ipv4addr;
       }
       uses apply-advanced;
       leaf multicast-router-interface {
         description "Enabling multicast-router-interface on the interface";
         type empty;
       }
       leaf immediate-leave {
         description "Enable immediate group leave on interfaces";
         type empty;
       }
     }
     list qualified-vlan {
       key name;
       ordered-by user;
       description "VLAN options for qualified-learning";
       leaf name {
         description "VLAN ID of the learning-domain";
         junos:must "(\".. .. .. .. .. vlans ${vlan} vlan-id all\")";
         junos:must-message "vlan specific configuration is allowed with qualified-learning only";
         type union {
           type string {
             pattern "<.*>|$.*";
           }
           type uint32 {
             range "0 .. 1023";
           }
         }
       }
       uses apply-advanced;
       leaf query-interval {
         description "When to send host query messages";
         units "seconds";
         type union {
           type string {
             pattern "<.*>|$.*";
           }
           type uint32 {
             range "1 .. 1024";
           }
         }
       }
       leaf query-response-interval {
         description "How long to wait for a host query response";
         units "seconds";
         type string {
           junos:posix-pattern "^[0-9]{1,4}(.[0-9])?$";
           junos:pattern-message "Up to 1 digit to right of decimal point";
         }
       }
       leaf query-last-member-interval {
         description "When to send group query messages";
         units "seconds";
         type string {
           junos:posix-pattern "^[0-9]{1,4}(.[0-9])?$";
           junos:pattern-message "Up to 1 digit to right of decimal point";
         }
       }
       leaf robust-count {
         description "Expected packet loss on a subnet";
         type union {
           type string {
             pattern "<.*>|$.*";
           }
           type uint32 {
             range "2 .. 10";
           }
         }
       }
       leaf immediate-leave {
         description "Enable immediate group leave on interfaces";
         type empty;
       }
       container proxy {
         presence "enable proxy";
         description "Enable proxy mode";
         uses apply-advanced;
         leaf source-address {
           description "Source IP address to use for proxy";
           type jt:ipv4addr;
         }
       }
       leaf evpn-ssm-reports-only {
         description "Accept and process only <s,g> reports of SSM groups";
         type empty;
       }
       list interface {
         key name;
         ordered-by user;
         description "Interface options for IGMP";
         leaf name {
           description "Interface name";
           junos:must "(\".. .. .. .. .. .. vlans ${vlan} interface $$\")";
           junos:must-message "interface options can be specified for the interfaces in the routing-instance";
           type union {
             type jt:interface-name;
             type string {
               pattern "<.*>|$.*";
             }
           }
         }
         uses apply-advanced;
         leaf multicast-router-interface {
           description "Enabling multicast-router-interface on the interface";
           type empty;
         }
         leaf immediate-leave {
           description "Enable immediate group leave on interfaces";
           type empty;
         }
         leaf host-only-interface {
           description "Enable interfaces to be treated as host-side interfaces";
           junos:must "(!(\".. multicast-router-interface\"))";
           junos:must-message "interface cannot be both host-only and multicast-router";
           type empty;
         }
         leaf group-limit {
           description "Maximum number of (source,group) per interface";
           type union {
             type string {
               pattern "<.*>|$.*";
             }
             type uint16 {
               range "1 .. 65535";
             }
           }
         }
         container static {
           description "Static group or source membership";
           uses apply-advanced;
           list group {
             key name;
             ordered-by user;
             description "IP multicast group address";
             leaf name {
               description "IP multicast group address";
               type jt:ipv4addr;
             }
             uses apply-advanced;
             list source {
               key name;
               ordered-by user;
               description "IP multicast source address";
               leaf name {
                 description "Source address of IP multicast data";
                 type jt:ipv4addr;
               }
               uses apply-advanced;
             }
           }
         }
       }
       list pseudowire-remote-address {
         key name;
         ordered-by user;
         description "Pseudowire interface options for IGMP";
         junos:must "((\" .. .. .. igmp-snooping-options snoop-pseudowires\" || \" .. .. .. .. igmp-snooping-options snoop-pseudowires\"))";
         junos:must-message "Configure pseudowire-remote-address only with snoop-pseudowires instance config";
         leaf name {
           description "Pseudowire endpoint address";
           type jt:ipv4addr;
         }
         uses apply-advanced;
         leaf multicast-router-interface {
           description "Enabling multicast-router-interface on the interface";
           type empty;
         }
         leaf immediate-leave {
           description "Enable immediate group leave on interfaces";
           type empty;
         }
       }
     }
     list vlan {
       key name;
       ordered-by user;
       description "Vlan options";
       leaf name {
         description "VLAN name";
         junos:must "(!(\".. .. .. .. vlans ${vlan} private-vlan\"))";
         junos:must-message "Snooping cannot be enabled on secondary vlan";
         type string {
           length "1 .. 64";
         }
       }
       uses apply-advanced;
       leaf query-interval {
         description "When to send host query messages";
         units "seconds";
         type union {
           type string {
             pattern "<.*>|$.*";
           }
           type uint32 {
             range "1 .. 1024";
           }
         }
       }
       leaf query-response-interval {
         description "How long to wait for a host query response";
         units "seconds";
         type string {
           junos:posix-pattern "^[0-9]{1,4}(.[0-9])?$";
           junos:pattern-message "Up to 1 digit to right of decimal point";
         }
       }
       leaf query-last-member-interval {
         description "When to send group query messages";
         units "seconds";
         type string {
           junos:posix-pattern "^[0-9]{1,4}(.[0-9])?$";
           junos:pattern-message "Up to 1 digit to right of decimal point";
         }
       }
       leaf robust-count {
         description "Expected packet loss on a subnet";
         type union {
           type string {
             pattern "<.*>|$.*";
           }
           type uint32 {
             range "2 .. 10";
           }
         }
       }
       leaf immediate-leave {
         description "Enable immediate group leave on interfaces";
         type empty;
       }
       container proxy {
         presence "enable proxy";
         description "Enable proxy mode";
         uses apply-advanced;
         leaf source-address {
           description "Source IP address to use for proxy";
           junos:must "((!(\".. .. .. .. .. vlans ${vlan} vlan-id all\") && !(\".. .. .. .. .. vlans ${vlan} vlan-id inner-all\")))";
           junos:must-message "With qualified-learning source-address should be configured under Vlan options";
           type jt:ipv4addr;
         }
       }
       leaf evpn-ssm-reports-only {
         description "Accept and process only <s,g> reports of SSM groups";
         type empty;
       }
       list interface {
         key name;
         ordered-by user;
         description "Interface options for IGMP";
         leaf name {
           description "Interface name";
           junos:must "(!(\"interfaces $$-IFL vlan-tags inner-range\"))";
           junos:must-message "interface with vlan-tags inner-range should be specified in a learning-domain only";
           junos:must "(!(\"interfaces $$-IFL vlan-id-range\"))";
           junos:must-message "interface with vlan-id-range should be specified in a learning-domain only";
           junos:must "((!(\".. .. .. .. .. vlans ${vlan} vlan-id all\") && !(\".. .. .. .. .. vlans ${vlan} vlan-id inner-all\")))";
           junos:must-message "When 'vlan-id all' or 'vlan-id inner-all' is configured, interface should be configured only under vlan";
           type union {
             type jt:interface-name;
             type string {
               pattern "<.*>|$.*";
             }
           }
         }
         uses apply-advanced;
         leaf multicast-router-interface {
           description "Enabling multicast-router-interface on the interface";
           type empty;
         }
         leaf immediate-leave {
           description "Enable immediate group leave on interfaces";
           type empty;
         }
         leaf host-only-interface {
           description "Enable interfaces to be treated as host-side interfaces";
           junos:must "(!(\".. multicast-router-interface\"))";
           junos:must-message "interface cannot be both host-only and multicast-router";
           type empty;
         }
         leaf group-limit {
           description "Maximum number of (source,group) per interface";
           type union {
             type string {
               pattern "<.*>|$.*";
             }
             type uint16 {
               range "1 .. 65535";
             }
           }
         }
         container static {
           description "Static group or source membership";
           uses apply-advanced;
           list group {
             key name;
             ordered-by user;
             description "IP multicast group address";
             leaf name {
               description "IP multicast group address";
               type jt:ipv4addr;
             }
             uses apply-advanced;
             list source {
               key name;
               ordered-by user;
               description "IP multicast source address";
               leaf name {
                 description "Source address of IP multicast data";
                 type jt:ipv4addr;
               }
               uses apply-advanced;
             }
           }
         }
       }
       list pseudowire-remote-address {
         key name;
         ordered-by user;
         description "Pseudowire interface options for IGMP";
         junos:must "((\" .. .. .. igmp-snooping-options snoop-pseudowires\" || \" .. .. .. .. igmp-snooping-options snoop-pseudowires\"))";
         junos:must-message "Configure pseudowire-remote-address only with snoop-pseudowires instance config";
         leaf name {
           description "Pseudowire endpoint address";
           type jt:ipv4addr;
         }
         uses apply-advanced;
         leaf multicast-router-interface {
           description "Enabling multicast-router-interface on the interface";
           type empty;
         }
         leaf immediate-leave {
           description "Enable immediate group leave on interfaces";
           type empty;
         }
       }
       list qualified-vlan {
         key name;
         ordered-by user;
         description "VLAN options for qualified-learning";
         leaf name {
           description "VLAN ID of the learning-domain";
           junos:must "(\".. .. .. .. .. vlans ${vlan} vlan-id all\")";
           junos:must-message "vlan specific configuration is allowed with qualified-learning only";
           type union {
             type string {
               pattern "<.*>|$.*";
             }
             type uint32 {
               range "0 .. 1023";
             }
           }
         }
         uses apply-advanced;
         leaf query-interval {
           description "When to send host query messages";
           units "seconds";
           type union {
             type string {
               pattern "<.*>|$.*";
             }
             type uint32 {
               range "1 .. 1024";
             }
           }
         }
         leaf query-response-interval {
           description "How long to wait for a host query response";
           units "seconds";
           type string {
             junos:posix-pattern "^[0-9]{1,4}(.[0-9])?$";
             junos:pattern-message "Up to 1 digit to right of decimal point";
           }
         }
         leaf query-last-member-interval {
           description "When to send group query messages";
           units "seconds";
           type string {
             junos:posix-pattern "^[0-9]{1,4}(.[0-9])?$";
             junos:pattern-message "Up to 1 digit to right of decimal point";
           }
         }
         leaf robust-count {
           description "Expected packet loss on a subnet";
           type union {
             type string {
               pattern "<.*>|$.*";
             }
             type uint32 {
               range "2 .. 10";
             }
           }
         }
         leaf immediate-leave {
           description "Enable immediate group leave on interfaces";
           type empty;
         }
         container proxy {
           presence "enable proxy";
           description "Enable proxy mode";
           uses apply-advanced;
           leaf source-address {
             description "Source IP address to use for proxy";
             type jt:ipv4addr;
           }
         }
         leaf evpn-ssm-reports-only {
           description "Accept and process only <s,g> reports of SSM groups";
           type empty;
         }
         list interface {
           key name;
           ordered-by user;
           description "Interface options for IGMP";
           leaf name {
             description "Interface name";
             junos:must "(\".. .. .. .. .. .. vlans ${vlan} interface $$\")";
             junos:must-message "interface options can be specified for the interfaces in the routing-instance";
             type union {
               type jt:interface-name;
               type string {
                 pattern "<.*>|$.*";
               }
             }
           }
           uses apply-advanced;
           leaf multicast-router-interface {
             description "Enabling multicast-router-interface on the interface";
             type empty;
           }
           leaf immediate-leave {
             description "Enable immediate group leave on interfaces";
             type empty;
           }
           leaf host-only-interface {
             description "Enable interfaces to be treated as host-side interfaces";
             junos:must "(!(\".. multicast-router-interface\"))";
             junos:must-message "interface cannot be both host-only and multicast-router";
             type empty;
           }
           leaf group-limit {
             description "Maximum number of (source,group) per interface";
             type union {
               type string {
                 pattern "<.*>|$.*";
               }
               type uint16 {
                 range "1 .. 65535";
               }
             }
           }
           container static {
             description "Static group or source membership";
             uses apply-advanced;
             list group {
               key name;
               ordered-by user;
               description "IP multicast group address";
               leaf name {
                 description "IP multicast group address";
                 type jt:ipv4addr;
               }
               uses apply-advanced;
               list source {
                 key name;
                 ordered-by user;
                 description "IP multicast source address";
                 leaf name {
                   description "Source address of IP multicast data";
                   type jt:ipv4addr;
                 }
                 uses apply-advanced;
               }
             }
           }
         }
         list pseudowire-remote-address {
           key name;
           ordered-by user;
           description "Pseudowire interface options for IGMP";
           junos:must "((\" .. .. .. igmp-snooping-options snoop-pseudowires\" || \" .. .. .. .. igmp-snooping-options snoop-pseudowires\"))";
           junos:must-message "Configure pseudowire-remote-address only with snoop-pseudowires instance config";
           leaf name {
             description "Pseudowire endpoint address";
             type jt:ipv4addr;
           }
           uses apply-advanced;
           leaf multicast-router-interface {
             description "Enabling multicast-router-interface on the interface";
             type empty;
           }
           leaf immediate-leave {
             description "Enable immediate group leave on interfaces";
             type empty;
           }
         }
       }
     }
   }
   grouping juniper-ri-protocols-mld-snooping {
     description "MLD snooping options";
     uses apply-advanced;
     container traceoptions {
       description "Trace options for MLD Snooping";
       uses apply-advanced;
       container file {
         description "Trace file options";
         leaf filename {
           description "Name of file in which to write trace information";
           type string {
             length "1 .. 1024";
             junos:posix-pattern "![/ %]";
             junos:pattern-message "Must not contain '/', % or a space";
           }
         }
         leaf replace {
           description "Replace trace file rather than appending to it";
           status deprecated;
           type empty;
         }
         leaf size {
           description "Maximum trace file size";
           type string;
         }
         leaf files {
           description "Maximum number of trace files";
           default "10";
           type union {
             type string {
               pattern "<.*>|$.*";
             }
             type uint32 {
               range "2 .. 1000";
             }
           }
         }
         leaf no-stamp {
           description "Do not timestamp trace file";
           status deprecated;
           type empty;
         }
         choice world-readable-choice {
           leaf world-readable {
             description "Allow any user to read the log file";
             type empty;
           }
           leaf no-world-readable {
             description "Don't allow any user to read the log file";
             type empty;
           }
         }
       }
       list flag {
         key name;
         ordered-by user;
         description "Tracing parameters";
         leaf name {
           type enumeration {
             enum "packets" {
               description "Trace all MLD packets";
             }
             enum "query" {
               description "Trace MLD membership query messages";
             }
             enum "report" {
               description "Trace membership report messages";
             }
             enum "leave" {
               description "Trace leave group messages (MLDv2 only)";
             }
             enum "group" {
               description "Trace group operations";
             }
             enum "client-notification" {
               description "Trace notifications";
             }
             enum "host-notification" {
               description "Trace host notifications";
             }
             enum "route" {
               description "Trace routing information";
             }
             enum "normal" {
               description "Trace normal events";
             }
             enum "general" {
               description "Trace general events";
             }
             enum "state" {
               description "Trace state transitions";
             }
             enum "policy" {
               description "Trace policy processing";
             }
             enum "task" {
               description "Trace routing protocol task processing";
             }
             enum "timer" {
               description "Trace routing protocol timer processing";
             }
             enum "all" {
               description "Trace everything";
             }
           }
         }
         leaf send {
           description "Trace transmitted packets";
           type empty;
         }
         leaf receive {
           description "Trace received packets";
           type empty;
         }
         leaf detail {
           description "Trace detailed information";
           type empty;
         }
         leaf disable {
           description "Disable this trace flag";
           type empty;
         }
       }
     }
     leaf query-interval {
       description "When to send host query messages";
       default "125";
       units "seconds";
       type union {
         type string {
           pattern "<.*>|$.*";
         }
         type uint32 {
           range "1 .. 1024";
         }
       }
     }
     container l2-querier {
       description "Enable L2 querier mode";
       uses apply-advanced;
       leaf source-address {
         description "Source IP address to use for L2 querier";
         type jt:ipv6addr;
       }
     }
     leaf query-response-interval {
       description "How long to wait for a host query response";
       default "10";
       units "seconds";
       type string {
         junos:posix-pattern "^[0-9]{1,4}(.[0-9])?$";
         junos:pattern-message "Up to 1 digit to right of decimal point";
       }
     }
     leaf query-last-member-interval {
       description "When to send group query messages";
       default "1";
       units "seconds";
       type string {
         junos:posix-pattern "^[0-9]{1,4}(.[0-9])?$";
         junos:pattern-message "Up to 1 digit to right of decimal point";
       }
     }
     leaf robust-count {
       description "Expected packet loss on a subnet";
       default "2";
       type union {
         type string {
           pattern "<.*>|$.*";
         }
         type uint32 {
           range "2 .. 10";
         }
       }
     }
     leaf immediate-leave {
       description "Enable immediate group leave on interfaces";
       type empty;
     }
     leaf evpn-ssm-reports-only {
       description "Accept and process only <s,g> reports of SSM groups";
       type empty;
     }
     container proxy {
       presence "enable proxy";
       description "Enable proxy mode";
       uses apply-advanced;
       leaf source-address {
         description "Source IP address to use for proxy";
         junos:must "(!(\".. .. .. .. vlan-id all\"))";
         junos:must-message "With qualified-learning source-address should be configured under Vlan options";
         type jt:ipv6addr;
       }
       leaf irb {
         description "Proxy IGMP reports to IRB";
         type empty;
       }
     }
     list interface {
       key name;
       ordered-by user;
       description "Interface options for MLD";
       leaf name {
         description "Interface name";
         junos:must "(!(\"interfaces $$-IFL vlan-tags inner-range\"))";
         junos:must-message "interface with vlan-tags inner-range should be specified in a learning-domain only";
         junos:must "(!(\"interfaces $$-IFL vlan-id-range\"))";
         junos:must-message "interface with vlan-id-range should be specified in a learning-domain only";
         junos:must "(\".. .. .. .. interface $$\")";
         junos:must-message "interface options can be specified for the interfaces in the routing-instance";
         junos:must "(!(\".. .. .. .. vlan-id all\"))";
         junos:must-message "When 'vlan-id all' is configured, interface should be configured only under vlan";
         type union {
           type jt:interface-name;
           type string {
             pattern "<.*>|$.*";
           }
         }
       }
       uses apply-advanced;
       leaf multicast-router-interface {
         description "Enabling multicast-router-interface on the interface";
         type empty;
       }
       leaf immediate-leave {
         description "Enable immediate group leave on interfaces";
         type empty;
       }
       leaf host-only-interface {
         description "Enable interfaces to be treated as host-side interfaces";
         junos:must "(!(\".. multicast-router-interface\"))";
         junos:must-message "interface cannot be both host-only and multicast-router";
         type empty;
       }
       leaf group-limit {
         description "Maximum number of (source,group) per interface";
         type union {
           type string {
             pattern "<.*>|$.*";
           }
           type uint16 {
             range "1 .. 65535";
           }
         }
       }
       container static {
         description "Static group or source membership";
         uses apply-advanced;
         list group {
           key name;
           ordered-by user;
           description "IP multicast group address";
           leaf name {
             description "IP multicast group address";
             type jt:ipv6addr;
           }
           uses apply-advanced;
           list source {
             key name;
             ordered-by user;
             description "IP multicast source address";
             leaf name {
               description "Source address of IP multicast data";
               type jt:ipv6addr;
             }
             uses apply-advanced;
           }
         }
       }
     }
     list pseudowire-remote-address {
       key name;
       ordered-by user;
       description "Pseudowire interface options for MLD";
       junos:must "((\" .. .. .. mld-snooping-options snoop-pseudowires\" || \" .. .. .. .. mld-snooping-options snoop-pseudowires\"))";
       junos:must-message "Configure pseudowire-remote-address only with snoop-pseudowires instance config";
       leaf name {
         description "Pseudowire endpoint address";
         junos:must "(!(\".. .. .. .. vlan-id all\"))";
         junos:must-message "When 'vlan-id all' is configured, pseudowire-remote-address should be configured only under vlan";
         type jt:ipv4addr;
       }
       uses apply-advanced;
       leaf multicast-router-interface {
         description "Enabling multicast-router-interface on the interface";
         type empty;
       }
       leaf immediate-leave {
         description "Enable immediate group leave on interfaces";
         type empty;
       }
     }
     list qualified-vlan {
       key name;
       ordered-by user;
       description "VLAN options for qualified-learning";
       leaf name {
         description "VLAN ID of the learning-domain";
         junos:must "(\".. .. .. .. .. vlans ${vlan} vlan-id all\")";
         junos:must-message "vlan specific configuration is allowed with qualified-learning only";
         type union {
           type string {
             pattern "<.*>|$.*";
           }
           type uint32 {
             range "0 .. 1023";
           }
         }
       }
       uses apply-advanced;
       leaf query-interval {
         description "When to send host query messages";
         units "seconds";
         type union {
           type string {
             pattern "<.*>|$.*";
           }
           type uint32 {
             range "1 .. 1024";
           }
         }
       }
       leaf query-response-interval {
         description "How long to wait for a host query response";
         units "seconds";
         type string {
           junos:posix-pattern "^[0-9]{1,4}(.[0-9])?$";
           junos:pattern-message "Up to 1 digit to right of decimal point";
         }
       }
       leaf query-last-member-interval {
         description "When to send group query messages";
         units "seconds";
         type string {
           junos:posix-pattern "^[0-9]{1,4}(.[0-9])?$";
           junos:pattern-message "Up to 1 digit to right of decimal point";
         }
       }
       leaf robust-count {
         description "Expected packet loss on a subnet";
         type union {
           type string {
             pattern "<.*>|$.*";
           }
           type uint32 {
             range "2 .. 10";
           }
         }
       }
       leaf immediate-leave {
         description "Enable immediate group leave on interfaces";
         type empty;
       }
       container proxy {
         presence "enable proxy";
         description "Enable proxy mode";
         uses apply-advanced;
         leaf source-address {
           description "Source IP address to use for proxy";
           type jt:ipv6addr;
         }
       }
       leaf evpn-ssm-reports-only {
         description "Accept and process only <s,g> reports of SSM groups";
         type empty;
       }
       list interface {
         key name;
         ordered-by user;
         description "Interface options for MLD";
         leaf name {
           description "Interface name";
           junos:must "(\".. .. .. .. .. .. vlans ${vlan} interface $$\")";
           junos:must-message "interface options can be specified for the interfaces in the routing-instance";
           type union {
             type jt:interface-name;
             type string {
               pattern "<.*>|$.*";
             }
           }
         }
         uses apply-advanced;
         leaf multicast-router-interface {
           description "Enabling multicast-router-interface on the interface";
           type empty;
         }
         leaf immediate-leave {
           description "Enable immediate group leave on interfaces";
           type empty;
         }
         leaf host-only-interface {
           description "Enable interfaces to be treated as host-side interfaces";
           junos:must "(!(\".. multicast-router-interface\"))";
           junos:must-message "interface cannot be both host-only and multicast-router";
           type empty;
         }
         leaf group-limit {
           description "Maximum number of (source,group) per interface";
           type union {
             type string {
               pattern "<.*>|$.*";
             }
             type uint16 {
               range "1 .. 65535";
             }
           }
         }
         container static {
           description "Static group or source membership";
           uses apply-advanced;
           list group {
             key name;
             ordered-by user;
             description "IP multicast group address";
             leaf name {
               description "IP multicast group address";
               type jt:ipv6addr;
             }
             uses apply-advanced;
             list source {
               key name;
               ordered-by user;
               description "IP multicast source address";
               leaf name {
                 description "Source address of IP multicast data";
                 type jt:ipv6addr;
               }
               uses apply-advanced;
             }
           }
         }
       }
       list pseudowire-remote-address {
         key name;
         ordered-by user;
         description "Pseudowire interface options for MLD";
         junos:must "((\" .. .. .. mld-snooping-options snoop-pseudowires\" || \" .. .. .. .. mld-snooping-options snoop-pseudowires\"))";
         junos:must-message "Configure pseudowire-remote-address only with snoop-pseudowires instance config";
         leaf name {
           description "Pseudowire endpoint address";
           type jt:ipv4addr;
         }
         uses apply-advanced;
         leaf multicast-router-interface {
           description "Enabling multicast-router-interface on the interface";
           type empty;
         }
         leaf immediate-leave {
           description "Enable immediate group leave on interfaces";
           type empty;
         }
       }
     }
     list vlan {
       key name;
       ordered-by user;
       description "Vlan options";
       leaf name {
         description "Vlan of the bridge-domain";
         junos:must "(!(\".. .. .. .. vlans ${vlan} private-vlan\"))";
         junos:must-message "Snooping cannot be enabled on secondary vlan";
         type string {
           length "1 .. 64";
         }
       }
       uses apply-advanced;
       leaf query-interval {
         description "When to send host query messages";
         units "seconds";
         type union {
           type string {
             pattern "<.*>|$.*";
           }
           type uint32 {
             range "1 .. 1024";
           }
         }
       }
       leaf query-response-interval {
         description "How long to wait for a host query response";
         units "seconds";
         type string {
           junos:posix-pattern "^[0-9]{1,4}(.[0-9])?$";
           junos:pattern-message "Up to 1 digit to right of decimal point";
         }
       }
       leaf query-last-member-interval {
         description "When to send group query messages";
         units "seconds";
         type string {
           junos:posix-pattern "^[0-9]{1,4}(.[0-9])?$";
           junos:pattern-message "Up to 1 digit to right of decimal point";
         }
       }
       leaf robust-count {
         description "Expected packet loss on a subnet";
         type union {
           type string {
             pattern "<.*>|$.*";
           }
           type uint32 {
             range "2 .. 10";
           }
         }
       }
       leaf immediate-leave {
         description "Enable immediate group leave on interfaces";
         type empty;
       }
       container proxy {
         presence "enable proxy";
         description "Enable proxy mode";
         uses apply-advanced;
         leaf source-address {
           description "Source IP address to use for proxy";
           junos:must "((!(\".. .. .. .. .. vlans ${vlan} vlan-id all\") && !(\".. .. .. .. .. vlans ${vlan} vlan-id inner-all\")))";
           junos:must-message "With qualified-learning source-address should be configured under Vlan options";
           type jt:ipv6addr;
         }
       }
       leaf evpn-ssm-reports-only {
         description "Accept and process only <s,g> reports of SSM groups";
         type empty;
       }
       list interface {
         key name;
         ordered-by user;
         description "Interface options for MLD";
         leaf name {
           description "Interface name";
           junos:must "(!(\"interfaces $$-IFL vlan-tags inner-range\"))";
           junos:must-message "interface with vlan-tags inner-range should be specified in a learning-domain only";
           junos:must "(!(\"interfaces $$-IFL vlan-id-range\"))";
           junos:must-message "interface with vlan-id-range should be specified in a learning-domain only";
           junos:must "((!(\".. .. .. .. .. vlans ${vlan} vlan-id all\") && !(\".. .. .. .. .. vlans ${vlan} vlan-id inner-all\")))";
           junos:must-message "When 'vlan-id all' or 'vlan-id inner-all' is configured, interface should be configured only under vlan";
           type union {
             type jt:interface-name;
             type string {
               pattern "<.*>|$.*";
             }
           }
         }
         uses apply-advanced;
         leaf multicast-router-interface {
           description "Enabling multicast-router-interface on the interface";
           type empty;
         }
         leaf immediate-leave {
           description "Enable immediate group leave on interfaces";
           type empty;
         }
         leaf host-only-interface {
           description "Enable interfaces to be treated as host-side interfaces";
           junos:must "(!(\".. multicast-router-interface\"))";
           junos:must-message "interface cannot be both host-only and multicast-router";
           type empty;
         }
         leaf group-limit {
           description "Maximum number of (source,group) per interface";
           type union {
             type string {
               pattern "<.*>|$.*";
             }
             type uint16 {
               range "1 .. 65535";
             }
           }
         }
         container static {
           description "Static group or source membership";
           uses apply-advanced;
           list group {
             key name;
             ordered-by user;
             description "IP multicast group address";
             leaf name {
               description "IP multicast group address";
               type jt:ipv6addr;
             }
             uses apply-advanced;
             list source {
               key name;
               ordered-by user;
               description "IP multicast source address";
               leaf name {
                 description "Source address of IP multicast data";
                 type jt:ipv6addr;
               }
               uses apply-advanced;
             }
           }
         }
       }
       list pseudowire-remote-address {
         key name;
         ordered-by user;
         description "Pseudowire interface options for MLD";
         junos:must "((\" .. .. .. mld-snooping-options snoop-pseudowires\" || \" .. .. .. .. mld-snooping-options snoop-pseudowires\"))";
         junos:must-message "Configure pseudowire-remote-address only with snoop-pseudowires instance config";
         leaf name {
           description "Pseudowire endpoint address";
           type jt:ipv4addr;
         }
         uses apply-advanced;
         leaf multicast-router-interface {
           description "Enabling multicast-router-interface on the interface";
           type empty;
         }
         leaf immediate-leave {
           description "Enable immediate group leave on interfaces";
           type empty;
         }
       }
       list qualified-vlan {
         key name;
         ordered-by user;
         description "VLAN options for qualified-learning";
         leaf name {
           description "VLAN ID of the learning-domain";
           junos:must "(\".. .. .. .. .. vlans ${vlan} vlan-id all\")";
           junos:must-message "vlan specific configuration is allowed with qualified-learning only";
           type union {
             type string {
               pattern "<.*>|$.*";
             }
             type uint32 {
               range "0 .. 1023";
             }
           }
         }
         uses apply-advanced;
         leaf query-interval {
           description "When to send host query messages";
           units "seconds";
           type union {
             type string {
               pattern "<.*>|$.*";
             }
             type uint32 {
               range "1 .. 1024";
             }
           }
         }
         leaf query-response-interval {
           description "How long to wait for a host query response";
           units "seconds";
           type string {
             junos:posix-pattern "^[0-9]{1,4}(.[0-9])?$";
             junos:pattern-message "Up to 1 digit to right of decimal point";
           }
         }
         leaf query-last-member-interval {
           description "When to send group query messages";
           units "seconds";
           type string {
             junos:posix-pattern "^[0-9]{1,4}(.[0-9])?$";
             junos:pattern-message "Up to 1 digit to right of decimal point";
           }
         }
         leaf robust-count {
           description "Expected packet loss on a subnet";
           type union {
             type string {
               pattern "<.*>|$.*";
             }
             type uint32 {
               range "2 .. 10";
             }
           }
         }
         leaf immediate-leave {
           description "Enable immediate group leave on interfaces";
           type empty;
         }
         container proxy {
           presence "enable proxy";
           description "Enable proxy mode";
           uses apply-advanced;
           leaf source-address {
             description "Source IP address to use for proxy";
             type jt:ipv6addr;
           }
         }
         leaf evpn-ssm-reports-only {
           description "Accept and process only <s,g> reports of SSM groups";
           type empty;
         }
         list interface {
           key name;
           ordered-by user;
           description "Interface options for MLD";
           leaf name {
             description "Interface name";
             junos:must "(\".. .. .. .. .. .. vlans ${vlan} interface $$\")";
             junos:must-message "interface options can be specified for the interfaces in the routing-instance";
             type union {
               type jt:interface-name;
               type string {
                 pattern "<.*>|$.*";
               }
             }
           }
           uses apply-advanced;
           leaf multicast-router-interface {
             description "Enabling multicast-router-interface on the interface";
             type empty;
           }
           leaf immediate-leave {
             description "Enable immediate group leave on interfaces";
             type empty;
           }
           leaf host-only-interface {
             description "Enable interfaces to be treated as host-side interfaces";
             junos:must "(!(\".. multicast-router-interface\"))";
             junos:must-message "interface cannot be both host-only and multicast-router";
             type empty;
           }
           leaf group-limit {
             description "Maximum number of (source,group) per interface";
             type union {
               type string {
                 pattern "<.*>|$.*";
               }
               type uint16 {
                 range "1 .. 65535";
               }
             }
           }
           container static {
             description "Static group or source membership";
             uses apply-advanced;
             list group {
               key name;
               ordered-by user;
               description "IP multicast group address";
               leaf name {
                 description "IP multicast group address";
                 type jt:ipv6addr;
               }
               uses apply-advanced;
               list source {
                 key name;
                 ordered-by user;
                 description "IP multicast source address";
                 leaf name {
                   description "Source address of IP multicast data";
                   type jt:ipv6addr;
                 }
                 uses apply-advanced;
               }
             }
           }
         }
         list pseudowire-remote-address {
           key name;
           ordered-by user;
           description "Pseudowire interface options for MLD";
           junos:must "((\" .. .. .. mld-snooping-options snoop-pseudowires\" || \" .. .. .. .. mld-snooping-options snoop-pseudowires\"))";
           junos:must-message "Configure pseudowire-remote-address only with snoop-pseudowires instance config";
           leaf name {
             description "Pseudowire endpoint address";
             type jt:ipv4addr;
           }
           uses apply-advanced;
           leaf multicast-router-interface {
             description "Enabling multicast-router-interface on the interface";
             type empty;
           }
           leaf immediate-leave {
             description "Enable immediate group leave on interfaces";
             type empty;
           }
         }
       }
     }
   }
   grouping juniper-routing-instance-pbb-options {
     description "PBB options for the routing instance";
     uses apply-advanced;
     leaf peer-instance {
       description "Set the peer-pbbn routing instance";
       junos:must "((!(\"routing-instances $$ protocols evpn pbb-evpn-core\") || !(any \".. .. service-groups <*> pbb-service-options mac-address\")))";
       junos:must-message "mac-address should not be configured under service-groups pbb-service-options for PBB EVPN";
       junos:must "(!(any \".. vlan-id <*> isid-list <*>\"))";
       junos:must-message "vlan-id isid-list mapping & peer-instance can not exist in same routing-instance";
       junos:must "(\"routing-instances $$\")";
       junos:must-message "pbbn-peer routing instance must be configured";
       type string;
     }
     list vlan-id {
       key name;
       ordered-by user;
       description "Set B-VLAN to ISID mapping";
       junos:must "(!(any \".. peer-instance <*>\"))";
       junos:must-message "vlan-id isid-list mapping & peer-instance can not exist in same routing-instance";
       junos:must "(!(any \".. .. service-groups <*>\"))";
       junos:must-message "vlan-id isid-list mapping & service-groups can not exist in same routing-instance";
       leaf name {
         description "Configure B-Vlan";
         type union {
           type string {
             pattern "<.*>|$.*";
           }
           type uint32 {
             range "1 .. 4094";
           }
         }
       }
       leaf-list isid-list {
         ordered-by user;
         description "Configure ISID(Valid Range:256..16777214) for the B-VLAN";
         type string;
       }
     }
     leaf default-bvlan {
       description "Default B-VLAN for all un-mapped ISIDs";
       junos:must "(!(any \".. peer-instance <*>\"))";
       junos:must-message "default-bvlan & peer-instance can not exist in same routing-instance";
       junos:must "(!(any \".. .. service-groups <*>\"))";
       junos:must-message "default-bvlan mapping & service-groups can not exist in same routing-instance";
       type union {
         type string {
           pattern "<.*>|$.*";
         }
         type uint32 {
           range "1 .. 4094";
         }
       }
     }
   }
   grouping juniper-routing-instance-service-groups {
     description "Service-groups configuration";
     leaf name {
       description "Service-group name";
       junos:must "(any \".. .. pbb-options peer-instance <*>\")";
       junos:must-message "peer pbbn instance must be there for service-groups configuration";
       type string;
     }
     uses apply-advanced;
     leaf service-type {
       description "Service type as ethernet LAN or point-to-point";
       type enumeration {
         enum "eline" {
           description "Ethernet point-to-point";
           junos:must "(!(any \".. .. service-groups <*> service-type elan\"))";
           junos:must-message "Elan and eline services can not exist in same routing instance";
         }
         enum "elan" {
           description "Ethernet LAN service";
           junos:must "(!(any \".. .. service-groups <*> service-type eline\"))";
           junos:must-message "Elan and eline services can not exist in same routing instance";
         }
       }
     }
     container pbb-service-options {
       presence "enable pbb-service-options";
       description "Provider backbone instance service options";
       uses apply-advanced;
       list isid {
         key name;
         ordered-by user;
         description "ISID to S-VLAN configuration";
         junos:must "(!(any \".. .. .. pbb-options vlan-id <*> isid-list <*>\"))";
         junos:must-message "vlan-id to isid-list mapping is not allowed in PBN routing-instance";
         leaf name {
           description "Configure ISID";
           type union {
             type string {
               pattern "<.*>|$.*";
             }
             type uint32 {
               range "256 .. 16777214";
             }
           }
         }
         choice service-data {
           case case_1 {
             leaf-list vlan-id-list {
               description "List of S-VLANs";
               junos:must "(!(\".. .. .. service-type eline\"))";
               junos:must-message "Vlan-id-list cannot be specified for eline service";
               junos:must "(any \".. .. .. service-type <*>\")";
               junos:must-message "service-type must be specified";
               type jt:vlan-range;
             }
           }
           case case_2 {
             leaf interface {
               description "Point to point interface name";
               junos:must "(!(\".. .. .. service-type elan\"))";
               junos:must-message "Interface cannot be specified for elan service";
               junos:must "(!(any \".. .. .. .. bridge-domains <*> interface $$\"))";
               junos:must-message "Sub interface is not allowed for PBB configuration";
               junos:must "(any \".. .. .. service-type <*>\")";
               junos:must-message "service-type must be specified";
               type union {
                 type jt:interface-name;
                 type string {
                   pattern "<.*>|$.*";
                 }
               }
             }
           }
         }
       }
       leaf default-isid {
         description "Default ISID for all un-mapped S-VLANs";
         junos:must "(!(any \".. isid <*> vlan-id-list <*>\"))";
         junos:must-message "Default isid & explicit isid services not allowed in the same service-group";
         junos:must "(!(\".. .. service-type eline\"))";
         junos:must-message "Default-isid not valid for service-type eline";
         junos:must "(any \".. .. service-type <*>\")";
         junos:must-message "service-type must be specified";
         junos:must "(!(any \".. .. .. pbb-options vlan-id <*> isid-list <*>\"))";
         junos:must-message "vlan-id to isid-list mapping is not allowed in PBN routing-instance";
         type union {
           type string {
             pattern "<.*>|$.*";
           }
           type uint32 {
             range "256 .. 16777214";
           }
         }
       }
       leaf mac-address {
         description "Unicast or multicast mac address";
         type jt:mac-addr;
       }
       leaf source-bmac {
         description "Unicast Source B Mac address";
         type jt:mac-addr;
       }
     }
   }
   grouping juniper-routing-instance-switch-options {
     description "Bridge options for the routing instance";
     uses apply-advanced;
     container mac-table-size {
       junos:must "(!(((\".. .. .. protocols vpls\" || \".. .. .. protocols evpn\") && \".. .. ..  instance-type virtual-switch\")))";
       junos:must-message "mac-table-size needs to be specified under switch-options for a virtual-switch instance";
       description "Size of MAC address forwarding table";
       uses apply-advanced;
       leaf limit {
         description "Maximum number of MAC addresses";
         type union {
           type string {
             pattern "<.*>|$.*";
           }
           type uint32;
         }
       }
       leaf packet-action {
         description "Action when MAC limit is reached";
         type enumeration {
           enum "none" {
             description "Forward the packet";
           }
           enum "drop" {
             description "Drop packets and do not learn. Default is forward";
           }
         }
       }
     }
     container mac-ip-table-size {
       junos:must "(!(((\".. .. .. protocols vpls\" || \".. .. .. protocols evpn\") && \".. .. ..  instance-type virtual-switch\")))";
       junos:must-message "mac-ip-table-size needs to be specified under switch-options for a virtual-switch instance";
       description "Size of MAC+IP bindings table";
       uses apply-advanced;
       leaf limit {
         description "Maximum number of MAC+IP bindings";
         type union {
           type string {
             pattern "<.*>|$.*";
           }
           type uint32;
         }
       }
     }
     container interface-mac-limit {
       junos:must "(!(((\".. .. .. protocols vpls\" || \".. .. .. protocols evpn\") && \".. .. ..  instance-type virtual-switch\")))";
       junos:must-message "interface-mac-limit needs to be specified under switch-options for a virtual-switch instance";
       description "Maximum MAC address learned per interface";
       uses apply-advanced;
       leaf limit {
         description "Maximum number of MAC addresses per interface";
         type union {
           type string {
             pattern "<.*>|$.*";
           }
           type uint32;
         }
       }
       leaf packet-action {
         description "Action when MAC limit is reached";
         type enumeration {
           enum "none" {
             description "Forward the packet";
           }
           enum "drop" {
             description "Drop packets and do not learn. Default is forward";
           }
           enum "log" {
             description "Do not drop the packet but generate an alarm, an SNMP trap or a system log entry";
           }
           enum "shutdown" {
             description "Disable the interface and generate an alarm, an SNMP trap or a system log entry";
           }
           enum "drop-and-log" {
             description "Drop the packet and generate an alarm, an SNMP trap or a system log entry";
           }
         }
       }
     }
     container interface-mac-ip-limit {
       junos:must "(!(((\".. .. .. protocols vpls\" || \".. .. .. protocols evpn\") && \".. .. ..  instance-type virtual-switch\")))";
       junos:must-message "interface-mac-ip-limit needs to be specified under switch-options for a virtual-switch instance";
       description "Maximum MAC+IP bindings learned per interface";
       uses apply-advanced;
       leaf limit {
         description "Maximum number of MAC+IP bindings per interface";
         type union {
           type string {
             pattern "<.*>|$.*";
           }
           type uint32;
         }
       }
     }
     container mac-notification {
       presence "enable mac-notification";
       description "MAC notification options";
       uses apply-advanced;
       leaf notification-interval {
         description "Interval for sending MAC notifications";
         default "30";
         units "seconds";
         type union {
           type string {
             pattern "<.*>|$.*";
           }
           type uint32 {
             range "1 .. 60";
           }
         }
       }
     }
     leaf mac-table-aging-time {
       description "Delay for discarding MAC address if no updates are received";
       units "seconds";
       type union {
         type string {
           pattern "<.*>|$.*";
         }
         type uint32;
       }
     }
     leaf no-mac-learning {
       description "Disable dynamic MAC address learning";
       junos:must "(!(((\".. .. .. protocols vpls\" || \".. .. .. protocols evpn\") && \".. .. ..  instance-type virtual-switch\")))";
       junos:must-message "no-mac-learning needs to be specified under switch-options for a virtual-switch instance";
       type empty;
     }
     leaf no-normalization {
       description "Disable vlan id normalization for interfaces";
       type empty;
     }
     leaf mac-statistics {
       description "Enable MAC address statistics";
       junos:must "(!(((\".. .. .. protocols vpls\" || \".. .. .. protocols evpn\") && \".. .. ..  instance-type virtual-switch\")))";
       junos:must-message "mac-statistics needs to be specified under switch-options for a virtual-switch instance";
       type empty;
     }
     container mib {
       presence "enable mib";
       description "Snmp mib options";
       uses apply-advanced;
       container dot1q-mib {
         presence "enable dot1q-mib";
         description "Dot1q MIB configuration options";
         uses apply-advanced;
         leaf port-list {
           description "Port list for staticegressports and staticuntaggedports MIB";
           type enumeration {
             enum "bit-map" {
               description "Port list is represented in bit-map format";
             }
             enum "string" {
               description "Port list is represented in string format";
             }
           }
         }
       }
     }
     container static-rvtep-mac {
       description "Configure Static MAC and remote VxLAN tunnel endpoint entries";
       uses apply-advanced;
       list mac {
         key "mac_addr remote-vtep";
         description "Unicast MAC address";
         leaf mac_addr {
           type jt:mac-unicast;
         }
         leaf remote-vtep {
           description "Configure static remote VXLAN tunnel endpoints";
           type jt:ipaddr;
         }
       }
     }
     leaf service-id {
       description "Service ID required if multi-chassis AE is part of a bridge-domain";
       type union {
         type string {
           pattern "<.*>|$.*";
         }
         type uint32 {
           range "1 .. 65535";
         }
       }
     }
     leaf ovsdb-managed {
       description "All vxlan bridge domains in routing instance are remote managed";
       junos:must "(!(\"routing-instances ${instance} protocols evpn encapsulation vxlan\"))";
       junos:must-message "Not valid with protocols evpn encapsulation vxlan";
       type empty;
     }
     container network-isolation-profile {
       description "Network isolation configuration";
       uses apply-advanced;
       list group {
         key name;
         description "Network isolation group";
         leaf name {
           description "Group name";
           type string;
         }
         uses apply-advanced;
       }
     }
     list interface {
       key name;
       ordered-by user;
       description "Interface that connect this site to the VPN";
       junos:must "(!((\".. .. .. protocols vpls\" && \".. .. ..  instance-type virtual-switch\")))";
       junos:must-message "interface needs to be specified under switch-options for a virtual-switch instance";
       leaf name {
         description "Interface name";
         junos:must "((\".. .. .. interface $$\" || \"FALSE\"))";
         junos:must-message "Interface must be part of this routing instance";
         junos:must "((\".. .. .. interface $$\" || (\".. .. .. .. .. interface $$\" || (\".. .. .. .. interface $$\" || \"interfaces $$-IFL family ethernet-switching\"))))";
         junos:must-message "Interface must be part of this routing instance";
         type union {
           type jt:interface-name;
           type string {
             pattern "<.*>|$.*";
           }
         }
       }
       uses apply-advanced;
       container interface-mac-limit {
         junos:must "(!(\".. .. .. .. .. vlans ${vlan} private-vlan\"))";
         junos:must-message "Switch-options configuration is not allowed on interfaces which are part of secondary VLANs";
         description "Maximum number of MAC addresses learned on the interface";
         uses apply-advanced;
         leaf limit {
           description "Maximum number of MAC addresses per interface";
           type union {
             type string {
               pattern "<.*>|$.*";
             }
             type uint32;
           }
         }
         leaf disable {
           description "Disable interface for interface-mac-limit";
           type empty;
         }
         leaf packet-action {
           description "Action when MAC limit is reached";
           type enumeration {
             enum "none" {
               description "Forward the packet";
             }
             enum "drop" {
               description "Drop packets and do not learn. Default is forward";
             }
             enum "log" {
               description "Do not drop the packet but generate an alarm, an SNMP trap or a system log entry";
             }
             enum "shutdown" {
               description "Disable the interface and generate an alarm, an SNMP trap or a system log entry";
             }
             enum "drop-and-log" {
               description "Drop the packet and generate an alarm, an SNMP trap or a system log entry";
             }
           }
         }
       }
       leaf action-priority {
         description "Blocking priority of this interface on mac move detection";
         junos:must "(!(\".. .. .. .. .. vlans ${vlan} private-vlan\"))";
         junos:must-message "Switch-options configuration is not allowed on interfaces which are part of secondary VLANs";
         type union {
           type string {
             pattern "<.*>|$.*";
           }
           type uint32 {
             range "0 .. 8";
           }
         }
       }
       list static-mac {
         key name;
         ordered-by user;
         description "Static MAC addresses assigned to this interface";
         junos:must "(!(\".. .. .. .. .. vlans ${vlan} private-vlan\"))";
         junos:must-message "Switch-options configuration is not allowed on interfaces which are part of secondary VLANs";
         leaf name {
           description "MAC address";
           junos:must "((!(\"FALSE\") || all \".. vlan-id <*>\"))";
           junos:must-message " Specify vlan-id for qualified learning ";
           type jt:mac-addr;
         }
         uses apply-advanced;
         list vlan-id {
           key name;
           ordered-by user;
           description "VLAN ID of learning VLAN";
           junos:must "(\"FALSE\")";
           junos:must-message "'vlan-id all' has to be configured for the bridging domain";
           leaf name {
             description "Learning VLAN";
             type union {
               type string {
                 pattern "<.*>|$.*";
               }
               type uint32 {
                 range "0 .. 4094";
               }
             }
           }
           uses apply-advanced;
         }
       }
       container interface-mac-ip-limit {
         description "Maximum number of MAC+IP bindings learned on the interface";
         uses apply-advanced;
         leaf limit {
           description "Maximum number of MAC+IP bindings per interface";
           type union {
             type string {
               pattern "<.*>|$.*";
             }
             type uint32;
           }
         }
       }
       leaf no-mac-learning {
         description "Disable dynamic MAC address learning";
         junos:must "(!(\".. .. .. .. .. vlans ${vlan} private-vlan\"))";
         junos:must-message "Switch-options configuration is not allowed on interfaces which are part of secondary VLANs";
         type empty;
       }
       leaf mac-pinning {
         description "Enable MAC pinning";
         type empty;
       }
       leaf persistent-learning {
         description "Enable persistent MAC learning on this interface";
         junos:must "(!(\"switch-options mac-table-aging-time \"))";
         junos:must-message "Persistent learning can not co-exist with mac-table-aging-time";
         type empty;
       }
     }
     container traceoptions {
       description "Layer 2 trace options for this routing instance";
       uses apply-advanced;
       leaf no-remote-trace {
         description "Disable remote tracing";
         junos:must "(\"system tracing\")";
         junos:must-message "'no-remote-trace' is valid only when [system tracing] is configured";
         type empty;
       }
       container file {
         description "Trace file information";
         leaf filename {
           description "Name of file in which to write trace information";
           type string {
             length "1 .. 1024";
             junos:posix-pattern "![/ %]";
             junos:pattern-message "Must not contain '/', % or a space";
           }
         }
         leaf size {
           description "Maximum trace file size";
           type string;
         }
         leaf files {
           description "Maximum number of trace files";
           default "3";
           type union {
             type string {
               pattern "<.*>|$.*";
             }
             type uint32 {
               range "2 .. 1000";
             }
           }
         }
         choice world-readable-choice {
           leaf world-readable {
             description "Allow any user to read the log file";
             type empty;
           }
           leaf no-world-readable {
             description "Don't allow any user to read the log file";
             type empty;
           }
         }
         leaf match {
           description "Regular expression for lines to be logged";
           type jt:regular-expression;
         }
       }
       leaf level {
         description "Level of debugging output";
         default "error";
         type enumeration {
           enum "error" {
             description "Match error conditions";
           }
           enum "warning" {
             description "Match warning messages";
           }
           enum "notice" {
             description "Match conditions that should be handled specially";
           }
           enum "info" {
             description "Match informational messages";
           }
           enum "verbose" {
             description "Match verbose messages";
           }
           enum "all" {
             description "Match all levels";
           }
         }
       }
       list flag {
         key name;
         ordered-by user;
         description "Type of operation or event to include in trace";
         leaf name {
           type enumeration {
             enum "configuration" {
               description "Configuration operations";
             }
             enum "routing-socket" {
               description "Routing socket operations";
             }
             enum "interface-device" {
               description "Interface device operations";
             }
             enum "interface-logical" {
               description "Logical interface operations";
             }
             enum "interface-family" {
               description "Interface family operations";
             }
             enum "bridging-domain" {
               description "Bridging domain operations";
             }
             enum "bridge-interface" {
               description "Interface bridge operations";
             }
             enum "learning-domain" {
               description "Learning domain operations";
             }
             enum "ipc" {
               description "Inter-process communications operations";
             }
             enum "mac-learning" {
               description "MAC address learning operations";
             }
             enum "initialization" {
               description "Initialization operations";
             }
             enum "flood-next-hop" {
               description "Flood next hop operations";
             }
             enum "irb" {
               description "Integrated routing and bridging operations";
             }
             enum "vpls-ping" {
               description "VPLS ping operations";
             }
             enum "vpls-loop-prev" {
               description "VPLS loop prevention";
             }
             enum "storm-control" {
               description "Storm-control";
             }
             enum "unknown-unicast-forwarding" {
               description "Trace unknown unicast forwarding events";
             }
             enum "vxlan" {
               description "VXLAN";
             }
             enum "all" {
               description "All operations";
             }
           }
         }
       }
     }
     container voip {
       description "Voice-over-IP configuration";
       uses apply-advanced;
       list interface {
         key name;
         ordered-by user;
         description "Enable voice over IP on this port";
         leaf name {
           type string;
         }
         uses apply-advanced;
         leaf vlan {
           description "VLAN for voice over IP";
           junos:must "(!(\"vlans $$ vlan-range \"))";
           junos:must-message "Ranged vlan cannot be used by Voice-over-IP";
           type string {
           }
         }
         leaf forwarding-class {
           description "Forwarding class";
           type string {
             junos:posix-pattern "^.{1,64}$";
             junos:pattern-message "Must be string of 64 characters or less";
           }
         }
       }
     }
     container unknown-unicast-forwarding {
       description "Set interface for forwarding of unknown unicast packets";
       uses apply-advanced;
       list vlan {
         key name;
         description "VLAN for the unknown unicast packets";
         leaf name {
           description "VLAN name or VLAN Tag (1..4095)";
           type string {
           }
         }
         uses apply-advanced;
         leaf interface {
           description "Interface to send unknown unicast packets for the VLAN";
           type union {
             type jt:interface-name;
             type string {
               pattern "<.*>|$.*";
             }
           }
         }
       }
     }
     list authentication-whitelist {
       key name;
       ordered-by user;
       description "MAC authentication-whitelist configuration needed to bypass Authentication";
       leaf name {
         description "MAC addresses to bypass authentication";
         junos:must "(any \"services captive-portal interface <*> supplicant multiple\")";
         junos:must-message "At least one interface must be configured with captive portal multiple supplicant mode";
         type jt:mac-addr-prefix;
       }
       uses apply-advanced;
       leaf vlan-assignment {
         description "VLAN name or 802.1q tag for the MAC address";
         junos:must "(!(\"vlans $$ vlan-range\"))";
         junos:must-message "vlan with vlan-range not supported under static MAC vlan-assignment";
         junos:must "((\"vlans $$\" || any \"vlans <*> vlan-id $$\"))";
         junos:must-message "vlan assigned is not configured";
         type string {
         }
       }
       leaf bridge-domain-assignment {
         description "Bridge-domain name or 802.1q tag for the MAC address";
         junos:must "(!(\".. .. .. bridge-domains $$ vlan-id-list\"))";
         junos:must-message "Bridge-domain with vlan-id-list not supported under static MAC bridge-domain-assignment";
         junos:must "((\".. .. .. bridge-domains $$\" || any \".. .. .. bridge-domains <*> vlan-id $$\"))";
         junos:must-message "Bridge-domain assigned is not configured";
         type string {
           junos:posix-pattern "^([[:alpha:]][[:alnum:]_.-]+)|^([1-9][0-9]{0,2}|[1-3][0-9]{3}|40[0-8][0-9]|409[0-4])$";
           junos:pattern-message "Must be a valid Bridge-domain or VLAN tag";
         }
       }
       leaf interface {
         description "Interface on which authentication is bypassed";
         junos:must "((!(\".. .. .. switch-options no-mac-learning\") || !(any \".. .. .. bridge-domain <*> bridge-options interface $$ no-mac-learning\")))";
         junos:must-message "Cannot configure authentication-whitelist on this interface since no-mac-learning is enabled on the same interface";
         junos:must "(!(\"interfaces $$-IFL family bridge interface-mode trunk\"))";
         junos:must-message "Cannot configure whitelist on this interface since the interface-mode is defined as trunk";
         junos:must "(!(\"interfaces $$-IFL family ethernet-switching port-mode trunk\"))";
         junos:must-message "Cannot configure whitelist on this interface since the port-mode is defined as trunk";
         junos:must "((\"services captive-portal interface $$ supplicant multiple\" || \"services captive-portal interface all supplicant multiple\"))";
         junos:must-message "authentication-whitelist MAC can be configured only on interface configured with captive portal multiple supplicant mode";
         junos:must "((\"interfaces $$-IFL family ethernet-switching\" || \"interfaces $$-IFL family bridge\"))";
         junos:must-message "Interface must be defined in the interfaces hierarchy with family ethernet-switching or family bridge";
         type union {
           type jt:interface-name;
           type string {
             pattern "<.*>|$.*";
           }
         }
       }
     }
     choice vstp-flooding-option {
     }
     choice arp-trap-option {
     }
     choice mstp-flooding-option {
     }
     choice stp-flooding-option {
     }
   }
   grouping juniper-routing-options {
     uses apply-advanced;
     container rpm-tracking {
       description "RPM static route tracking options";
       uses apply-advanced;
       list route {
         key name;
         ordered-by user;
         description "Static Route";
         leaf name {
           description "IP address of destination";
           type jt:ipprefix;
         }
         uses apply-advanced;
         list next-hop {
           key name;
           ordered-by user;
           description "Next hop to destination";
           uses rpm-next-hop;
         }
         leaf metric {
           description "Metric value";
           type union {
             type string {
               pattern "<.*>|$.*";
             }
             type uint32 {
               range "1 .. 16";
             }
           }
         }
         leaf preference {
           description "Preference value";
           type union {
             type uint32;
             type string {
               pattern "<.*>|$.*";
             }
           }
         }
         leaf tag {
           description "Tag value";
           type union {
             type uint32;
             type string {
               pattern "<.*>|$.*";
             }
           }
         }
         list rpm-probe {
           key name;
           ordered-by user;
           leaf name {
             description "RPM probe to track";
             junos:must "(\"services rpm probe $$\")";
             junos:must-message "Referenced RPM probe must be defined under 'services rpm probe'";
             type string;
           }
           leaf rpm-test {
             description "RPM test to track";
             junos:must "(\"services rpm probe ${rpm-probe} test $$\")";
             junos:must-message "Referenced RPM test must be defined under 'services rpm probe <probe> test '";
             type string;
           }
         }
       }
     }
     container logical-system-mux {
       description "Logical system control daemon information";
       uses apply-advanced;
       container traceoptions {
         description "Trace options";
         uses apply-advanced;
         container file {
           description "Trace file options";
           leaf filename {
             description "Name of file in which to write trace information";
             type string {
               length "1 .. 1024";
               junos:posix-pattern "![/ %]";
               junos:pattern-message "Must not contain '/', % or a space";
             }
           }
           leaf replace {
             description "Replace trace file rather than appending to it";
             status deprecated;
             type empty;
           }
           leaf size {
             description "Maximum trace file size";
             type string;
           }
           leaf files {
             description "Maximum number of trace files";
             default "10";
             type union {
               type string {
                 pattern "<.*>|$.*";
               }
               type uint32 {
                 range "2 .. 1000";
               }
             }
           }
           leaf no-stamp {
             description "Do not timestamp trace file";
             status deprecated;
             type empty;
           }
           choice world-readable-choice {
             leaf world-readable {
               description "Allow any user to read the log file";
               type empty;
             }
             leaf no-world-readable {
               description "Don't allow any user to read the log file";
               type empty;
             }
           }
         }
         list flag {
           key name;
           ordered-by user;
           description "Tracing parameters";
           leaf name {
             type enumeration {
               enum "debug" {
                 description "Trace debug-level lrmuxd activities";
               }
               enum "parse" {
                 description "Trace configuration parsing";
               }
               enum "route" {
                 description "Trace routing information";
               }
               enum "normal" {
                 description "Trace normal events";
               }
               enum "general" {
                 description "Trace general events";
               }
               enum "state" {
                 description "Trace state transitions";
               }
               enum "policy" {
                 description "Trace policy processing";
               }
               enum "task" {
                 description "Trace routing protocol task processing";
               }
               enum "timer" {
                 description "Trace routing protocol timer processing";
               }
               enum "all" {
                 description "Trace everything";
               }
             }
           }
           leaf send {
             description "Trace transmitted packets";
             type empty;
           }
           leaf receive {
             description "Trace received packets";
             type empty;
           }
           leaf detail {
             description "Trace detailed information";
             type empty;
           }
           leaf disable {
             description "Disable this trace flag";
             type empty;
           }
         }
       }
     }
     container auto-bandwidth {
       presence "enable auto-bandwidth";
       description "Auto bandwidth";
       uses apply-advanced;
       list template {
         key name;
         ordered-by user;
         description "Auto bandwidth template";
         leaf name {
           description "Auto bandwidth template name (Maximum length 64)";
           type string {
             length "1 .. 64";
           }
         }
         uses apply-advanced;
         leaf adjust-interval {
           description "Adjust interval";
           type union {
             type string {
               pattern "<.*>|$.*";
             }
             type uint32 {
               range "30 .. 3600";
             }
           }
         }
         leaf adjust-threshold {
           description "Percentage threshhold";
           type union {
             type string {
               pattern "<.*>|$.*";
             }
             type uint32 {
               range "0 .. 100";
             }
           }
         }
         leaf statistic-collection-interval {
           description "Collection interval";
           type union {
             type string {
               pattern "<.*>|$.*";
             }
             type uint32 {
               range "10 .. 300";
             }
           }
         }
         leaf auto-bandwidth-subscription {
           description "Percentage threshhold for subscription";
           type union {
             type string {
               pattern "<.*>|$.*";
             }
             type uint32 {
               range "0 .. 200";
             }
           }
         }
       }
       container traceoptions {
         description "Trace options for sr stats";
         uses apply-advanced;
         container file {
           description "Trace file options";
           leaf filename {
             description "Name of file in which to write trace information";
             type string {
               length "1 .. 1024";
               junos:posix-pattern "![/ %]";
               junos:pattern-message "Must not contain '/', % or a space";
             }
           }
           leaf replace {
             description "Replace trace file rather than appending to it";
             status deprecated;
             type empty;
           }
           leaf size {
             description "Maximum trace file size";
             type string;
           }
           leaf files {
             description "Maximum number of trace files";
             default "10";
             type union {
               type string {
                 pattern "<.*>|$.*";
               }
               type uint32 {
                 range "2 .. 1000";
               }
             }
           }
           leaf no-stamp {
             description "Do not timestamp trace file";
             status deprecated;
             type empty;
           }
           choice world-readable-choice {
             leaf world-readable {
               description "Allow any user to read the log file";
               type empty;
             }
             leaf no-world-readable {
               description "Don't allow any user to read the log file";
               type empty;
             }
           }
         }
         list flag {
           key name;
           ordered-by user;
           description "Tracing parameters";
           leaf name {
             type enumeration {
               enum "all" {
                 description "Trace All";
               }
               enum "timer" {
                 description "Trace traffic recv by periodic timer";
               }
               enum "state" {
                 description "Trace state of sensor";
               }
             }
           }
           leaf send {
             description "Trace transmitted packets";
             type empty;
           }
           leaf receive {
             description "Trace received packets";
             type empty;
           }
           leaf detail {
             description "Trace detailed information";
             type empty;
           }
           leaf disable {
             description "Disable this trace flag";
             type empty;
           }
         }
       }
     }
     container backup-selection {
       presence "enable backup-selection";
       description "Backup selection options";
       uses apply-advanced;
       list destination {
         key name;
         description "IP/IPv6 prefix for which backup selection policy is configured";
         leaf name {
           description "IP/IPv6 address (and optional prefix length)";
           type jt:ipprefix-mandatory;
         }
         uses apply-advanced;
         list interface {
           key name;
           description "Primary nexthop interface for which backup selection policy is configured";
           leaf name {
             description "Interface name";
             type union {
               type jt:interface-name;
               type string {
                 pattern "<.*>|$.*";
               }
             }
           }
           uses apply-advanced;
           container admin-group {
             description "Administrative group policies for backup-selection";
             uses apply-advanced;
             leaf-list exclude {
               description "Do not use interface if any admin group available";
               type string;
             }
             leaf-list include-all {
               description "Use interface if admin groups available entirely";
               type string;
             }
             leaf-list include-any {
               description "Use interface if any admin group is available";
               type string;
             }
             leaf-list preference {
               ordered-by user;
               description "Administrative groups in descending preference order";
               type string;
             }
           }
           leaf srlg {
             description "Evaluate Shared Risk Link Group(SRLG) characteristics for backup selection";
             default "loose";
             type enumeration {
               enum "loose" {
                 description "Loose SRLG";
               }
               enum "strict" {
                 description "Strict SRLG";
               }
             }
           }
           leaf protection-type {
             description "Type of protection to be considered";
             type enumeration {
               enum "link" {
                 description "Protect the primary interface from link faults only";
               }
               enum "node" {
                 description "Protect the primary interface from node faults only";
               }
               enum "node-link" {
                 description "Protect the primary interface from either link or node faults; prefer node protection";
               }
             }
           }
           leaf downstream-paths-only {
             description "Choose only the downstream nodes for backup";
             type empty;
           }
           leaf bandwidth-greater-equal-primary {
             description "Use backup nexthop only if bandwidth is >= bandwidth of primary nexthop";
             type empty;
           }
           container backup-neighbor {
             description "Backup Neighbor ID based policies for backup selection";
             uses apply-advanced;
             leaf-list exclude {
               description "List of backup neighbors to be excluded";
               type jt:ipv4addr;
             }
             leaf-list preference {
               ordered-by user;
               description "List of backup neighbors in descending order preference";
               type jt:ipv4addr;
             }
           }
           container node {
             description "Node ID based policies for backup selection";
             uses apply-advanced;
             leaf-list exclude {
               description "List of nodes to be excluded";
               type jt:ipv4addr;
             }
             leaf-list preference {
               ordered-by user;
               description "List of nodes in the descending order of preference";
               type jt:ipv4addr;
             }
           }
           container node-tag {
             description "Node  tag policies";
             uses apply-advanced;
             leaf-list exclude {
               description "The set of node tags to be excluded";
               type union {
                 type uint32;
                 type string {
                   pattern "<.*>|$.*";
                 }
               }
             }
             leaf-list preference {
               ordered-by user;
               description "The set of node tags in the descending order of preference";
               type union {
                 type uint32;
                 type string {
                   pattern "<.*>|$.*";
                 }
               }
             }
           }
           leaf root-metric {
             description "Root metric";
             type enumeration {
               enum "lowest" {
                 description "Choose lowest root metric";
               }
               enum "highest" {
                 description "Choose highest root metric";
               }
             }
           }
           leaf dest-metric {
             description "Destination metric";
             type enumeration {
               enum "lowest" {
                 description "Choose lowest destination metric";
               }
               enum "highest" {
                 description "Choose highest destination metric";
               }
             }
           }
           leaf-list metric-order {
             ordered-by user;
             description "Metric evaluation order";
             type enumeration {
               enum "root" {
               }
               enum "dest" {
               }
             }
             max-elements 2;
           }
           leaf-list evaluation-order {
             ordered-by user;
             description "Interface policy criteria evaluation order";
             type enumeration {
               enum "admin-group" {
                 description "Administrative Group/Link Color";
               }
               enum "srlg" {
                 description "SRLG";
               }
               enum "bandwidth" {
                 description "Bandwidth";
               }
               enum "protection-type" {
                 description "Type of protection";
               }
               enum "backup-neighbor" {
                 description "Backup Neighbor";
               }
               enum "node" {
                 description "Node";
               }
               enum "node-tag" {
                 description "Node tag";
               }
               enum "metric" {
                 description "Metric related parameters";
               }
             }
           }
         }
       }
     }
     list flex-algorithm {
       key name;
       description "Configure flex-algorithms supported by this node.";
       leaf name {
         description "Algorithm id";
         type union {
           type string {
             pattern "<.*>|$.*";
           }
           type uint32 {
             range "128 .. 255";
           }
         }
       }
       uses apply-advanced;
       container definition {
         description "Configure flex-algorithm definition.";
         uses apply-advanced;
         leaf metric-type {
           type enumeration {
             enum "igp-metric" {
               description "Metric configured to be used for IGP";
             }
             enum "te-metric" {
               description "Traffic-engineering metric";
             }
             enum "delay-metric" {
               description "Min unidirectional link delay metric";
             }
           }
         }
         choice calculation-type {
           case case_1 {
             leaf spf {
               description "Normal SPF of type 0";
               type empty;
             }
           }
           case case_2 {
             leaf strict-spf {
               description "Strict SPF";
               type empty;
             }
           }
         }
         leaf use-flex-algorithm-prefix-metric {
           description "Set M flag in the flex-algorithm definition flags";
           type empty;
         }
         leaf priority {
           description "Priority of the flex-algorithm advertisement.";
           junos:must "(!(\".. no-advertise\"))";
           junos:must-message "Priority is relevant only if fad is advertised.";
           type union {
             type string {
               pattern "<.*>|$.*";
             }
             type uint32 {
               range "0 .. 255";
             }
           }
         }
         container admin-group {
           description "Administrative group policy";
           uses admin_group_include_exclude;
         }
       }
       leaf color {
         description "Color to be associated with this flex-algorithm";
         type union {
           type uint32;
           type string {
             pattern "<.*>|$.*";
           }
         }
       }
       leaf use-transport-class {
         description "Install ingress routes via transport class RIBs";
         type empty;
       }
     }
     container source-packet-routing {
       description "Source packet routing (SPRING)";
       uses apply-advanced;
       list mapping-server-entry {
         key name;
         ordered-by user;
         description "Mapping server entry";
         leaf name {
           description "Mapping server entry name";
           type string {
             length "1 .. 64";
           }
         }
         uses apply-advanced;
         list prefix-segment {
           key name;
           ordered-by user;
           description "Prefix segment";
           max-elements 64;
           leaf name {
             description "Prefix segment prefix";
             type jt:ipprefix;
           }
           uses apply-advanced;
           leaf index {
             description "Prefix segment index";
             type union {
               type string {
                 pattern "<.*>|$.*";
               }
               type uint32 {
                 range "0 .. 199999";
               }
             }
           }
           leaf attached {
             description "Set attached flag in IS-IS mapping server advertisement";
             type empty;
           }
           leaf domain-wide-flooding {
             description "Set S-flag in IS-IS mapping server advertisement";
             type empty;
           }
           leaf no-node-segment {
             description "Clear node segment flag in mapping server prefix segment";
             type empty;
           }
         }
         list prefix-segment-range {
           key name;
           ordered-by user;
           description "Prefix segment range";
           max-elements 64;
           leaf name {
             description "Prefix segment range name";
             type string {
               length "1 .. 64";
             }
           }
           uses apply-advanced;
           leaf start-prefix {
             description "Start prefix";
             type jt:ipprefix;
           }
           leaf start-index {
             description "Start index";
             type union {
               type string {
                 pattern "<.*>|$.*";
               }
               type uint32 {
                 range "0 .. 199999";
               }
             }
           }
           leaf size {
             description "Size of prefix segment range";
             type union {
               type string {
                 pattern "<.*>|$.*";
               }
               type uint32 {
                 range "1 .. 1024";
               }
             }
           }
           leaf attached {
             description "Set attached flag in IS-IS mapping server advertisement";
             type empty;
           }
           leaf domain-wide-flooding {
             description "Set S-flag in IS-IS mapping server advertisement";
             type empty;
           }
           leaf no-node-segment {
             description "Clear node segment flag in mapping server prefix segment";
             type empty;
           }
         }
       }
       container srv6 {
         description "SRv6 source-packet-routing";
         uses apply-advanced;
         list locator {
           key name;
           ordered-by user;
           leaf name {
             description "Locator entry name";
             type string {
               length "1 .. 64";
             }
           }
           uses apply-advanced;
           leaf algorithm {
             description "Algorithm associated with this locator";
             type union {
               type string {
                 pattern "<.*>|$.*";
               }
               type uint32 {
                 range "0 .. 255";
               }
             }
           }
           leaf address {
             description "Configure Locator Service for SRv6";
             type jt:ipv6prefix;
           }
         }
         leaf no-reduced-srh {
           description "SRv6 Encapsulation mode non reduced SRH";
           type empty;
         }
         leaf transit-srh-insert {
           description "SRv6 SRH insert mode on transit";
           type empty;
         }
       }
     }
     leaf route-distinguisher-id {
       description "Identifier used in route distinguishers for routing instances";
       type jt:ipv4addr;
     }
     list rib {
       key name;
       ordered-by user;
       description "Routing table options";
       leaf name {
         description "Routing table name";
         type string;
       }
       uses apply-advanced;
       container static {
         description "Static routes";
         uses apply-advanced;
         leaf rib-group {
           description "Routing table group";
           type string;
         }
         container defaults {
           description "Global route options";
           uses apply-advanced;
           choice retain-choice {
             leaf retain {
               description "Always keep route in forwarding table";
               junos:must "(!(\".. resolve\"))";
               junos:must-message "Must not specify resolve with retain";
               type empty;
             }
             leaf no-retain {
               description "Don't always keep route in forwarding table";
               junos:must "(!(\".. resolve\"))";
               junos:must-message "Must not specify resolve with retain";
               type empty;
             }
           }
           choice install-choice {
             leaf install {
               description "Install route into forwarding table";
               type empty;
             }
             leaf no-install {
               description "Don't install route into forwarding table";
               type empty;
             }
           }
           choice readvertise-choice {
             leaf readvertise {
               description "Mark route as eligible to be readvertised";
               type empty;
             }
             leaf no-readvertise {
               description "Don't mark route as eligible to be readvertised";
               type empty;
             }
           }
           choice resolve-choice {
             leaf resolve {
               description "Allow resolution of indirectly connected next hops";
               type empty;
             }
             leaf no-resolve {
               description "Don't allow resolution of indirectly connected next hops";
               type empty;
             }
           }
           choice longest-match-choice {
             leaf longest-match {
               description "Always use longest prefix match to resolve next hops";
               junos:must "(\".. resolve\")";
               junos:must-message "Requires resolve to be configured";
               type empty;
             }
             leaf no-longest-match {
               description "Don't always use longest prefix match to resolve next hops";
               junos:must "(\".. resolve\")";
               junos:must-message "Requires resolve to be configured";
               type empty;
             }
           }
           choice passive_flag {
             case case_1 {
               leaf active {
                 description "Remove inactive route from forwarding table";
                 type empty;
               }
             }
             case case_2 {
               leaf passive {
                 description "Retain inactive route in forwarding table";
                 type empty;
               }
             }
           }
           container metric {
             description "Metric value";
             presence "enable metric";
             uses rib_static_metric_type;
           }
           container metric2 {
             description "Metric value 2";
             presence "enable metric2";
             uses rib_static_metric_type;
           }
           container metric3 {
             description "Metric value 3";
             presence "enable metric3";
             uses rib_static_metric_type;
           }
           container metric4 {
             description "Metric value 4";
             presence "enable metric4";
             uses rib_static_metric_type;
           }
           container tag {
             description "Tag string";
             presence "enable tag";
             uses rib_static_metric_type;
           }
           container tag2 {
             description "Tag string 2";
             presence "enable tag2";
             uses rib_static_metric_type;
           }
           container preference {
             description "Preference value";
             presence "enable preference";
             uses rib_static_metric_type;
           }
           container preference2 {
             description "Preference value 2";
             presence "enable preference2";
             uses rib_static_metric_type;
           }
           container color {
             description "Color (preference) value";
             presence "enable color";
             uses rib_static_metric_type;
           }
           container color2 {
             description "Color (preference) value 2";
             presence "enable color2";
             uses rib_static_metric_type;
           }
           leaf-list community {
             ordered-by user;
             description "BGP community identifier";
             type jt:community;
           }
           container as-path {
             description "Autonomous system path";
             uses apply-advanced;
             leaf path {
               description "Autonomous system path";
               type string;
             }
             leaf origin {
               type enumeration {
                 enum "igp" {
                   description "Path originated in the local IGP";
                 }
                 enum "egp" {
                   description "Path originated in another AS";
                 }
                 enum "incomplete" {
                   description "Path was learned by some other means";
                 }
               }
             }
             leaf atomic-aggregate {
               description "Add ATOMIC_AGGREGATE path attribute to route";
               type empty;
             }
             container aggregator {
               presence "enable aggregator";
               description "Add AGGREGATOR path attribute to route";
             }
             leaf as-number {
               description " Autonomous system number in plain number or 'higher 16bits'.'Lower 16 bits' (asdot notation) format";
               type string {
                 junos:posix-pattern "^[0-9]+(.[0-9]+)?$";
                 junos:pattern-message "Use format 'x' or 'x.y' to specify number 'x' (Range 1 .. 4294967295) or number with higher 2 bytes 'x' (Range 0 .. 65535) and lower 2 bytes 'y' (Range 0 .. 65535) respectively";
               }
             }
             leaf address {
               description "Address of BGP system that formed the route";
               type jt:ipv4addr;
             }
           }
         }
         list route {
           key name;
           ordered-by user;
           description "Static route";
           leaf name {
             type jt:ipprefix;
           }
           uses apply-advanced;
           choice next_hop {
             case case_1 {
               leaf-list next-hop {
                 ordered-by user;
                 description "Next hop to destination";
                 type union {
                   type jt:ipaddr-or-interface;
                   type string {
                     pattern "<.*>|$.*";
                   }
                 }
               }
             }
             case case_2 {
               leaf reject {
                 description "Drop packets to destination; send ICMP unreachables";
                 type empty;
               }
             }
             case case_3 {
               leaf discard {
                 description "Drop packets to destination; send no ICMP unreachables";
                 type empty;
               }
             }
             case case_4 {
               leaf receive {
                 description "Install a receive route for the destination";
                 type empty;
               }
             }
             case case_5 {
               leaf next-table {
                 description "Next hop to another table";
                 type string {
                   junos:posix-pattern "^(((.{0,128})[:](.{1,128})[.]|((.{1,128})[.]))?([a-z]|[0-9]|[-_])+[.]((1?[0-9]{1,2})|(2[0-4][0-9])|(25[0-5])))$";
                   junos:pattern-message "Must match the format [<instance-name>[:<topology-name>].]<family-name>.<rib-id>";
                 }
               }
             }
           }
           list qualified-next-hop {
             key name;
             ordered-by user;
             description "Next hop with qualifiers";
             uses qualified_nh_obj;
           }
           leaf backup-pe-group {
             description "Multicast source redundancy group";
             junos:must "(\".. p2mp-lsp-next-hop\")";
             junos:must-message "Backup groups only allowed for static routes with p2mp lsp next-hop";
             type string;
           }
           container bfd-liveness-detection {
             description "Bidirectional Forwarding Detection (BFD) options";
             uses apply-advanced;
             leaf version {
               description "BFD protocol version number";
               default "automatic";
               type enumeration {
                 enum "0" {
                   description "BFD version 0 (deprecated)";
                 }
                 enum "1" {
                   description "BFD version 1";
                 }
                 enum "automatic" {
                   description "Choose BFD version automatically";
                 }
               }
             }
             leaf minimum-interval {
               description "Minimum transmit and receive interval";
               units "milliseconds";
               type union {
                 type string {
                   pattern "<.*>|$.*";
                 }
                 type uint32 {
                   range "1 .. 255000";
                 }
               }
             }
             leaf minimum-transmit-interval {
               description "Minimum transmit interval";
               status deprecated;
               units "milliseconds";
               type union {
                 type string {
                   pattern "<.*>|$.*";
                 }
                 type uint32 {
                   range "1 .. 255000";
                 }
               }
             }
             leaf minimum-receive-interval {
               description "Minimum receive interval";
               units "milliseconds";
               type union {
                 type string {
                   pattern "<.*>|$.*";
                 }
                 type uint32 {
                   range "1 .. 255000";
                 }
               }
             }
             leaf multiplier {
               description "Detection time multiplier";
               default "3";
               type union {
                 type string {
                   pattern "<.*>|$.*";
                 }
                 type uint32 {
                   range "1 .. 255";
                 }
               }
             }
             choice adaptation-choice {
               case case_1 {
                 leaf no-adaptation {
                   description "Disable adaptation";
                   type empty;
                 }
               }
             }
             container transmit-interval {
               description "Transmit-interval options";
               uses apply-advanced;
               leaf minimum-interval {
                 description "Minimum transmit interval";
                 units "milliseconds";
                 type union {
                   type string {
                     pattern "<.*>|$.*";
                   }
                   type uint32 {
                     range "1 .. 255000";
                   }
                 }
               }
               leaf threshold {
                 description "High transmit interval triggering a trap";
                 units "milliseconds";
                 type union {
                   type uint32;
                   type string {
                     pattern "<.*>|$.*";
                   }
                 }
               }
             }
             container detection-time {
               description "Detection-time options";
               uses apply-advanced;
               leaf threshold {
                 description "High detection-time triggering a trap";
                 units "milliseconds";
                 type union {
                   type uint32;
                   type string {
                     pattern "<.*>|$.*";
                   }
                 }
               }
             }
             container authentication {
               description "Authentication options";
               uses apply-advanced;
               leaf key-chain {
                 description "Key chain name";
                 junos:must "(\".. algorithm\")";
                 junos:must-message "May not be configured without algorithm";
                 junos:must "(\"security authentication-key-chains key-chain $$\")";
                 junos:must-message "Referenced key-chain must be defined";
                 type string;
               }
               leaf algorithm {
                 description "Algorithm name";
                 junos:must "(\".. key-chain\")";
                 junos:must-message "May not be configured without key-chain";
                 type enumeration {
                   enum "simple-password" {
                     description "Simple password";
                   }
                   enum "keyed-md5" {
                     description "Keyed message Digest 5";
                   }
                   enum "meticulous-keyed-md5" {
                     description "Meticulous keyed message Digest 5";
                   }
                   enum "keyed-sha-1" {
                     description "Keyed secure hash algorithm (SHA1) ";
                   }
                   enum "meticulous-keyed-sha-1" {
                     description "Meticulous keyed secure hash algorithm (SHA1) ";
                   }
                 }
               }
               leaf loose-check {
                 description "Verify authentication only if authentication is negotiated";
                 type empty;
               }
             }
             leaf neighbor {
               description "BFD neighbor address";
               type jt:ipaddr;
             }
             leaf local-address {
               description "BFD local address (for multihop only)";
               type jt:ipaddr;
             }
             leaf holddown-interval {
               description "Time to hold the session-UP notification to the client";
               units "milliseconds";
               type union {
                 type string {
                   pattern "<.*>|$.*";
                 }
                 type uint32 {
                   range "0 .. 255000";
                 }
               }
             }
             leaf minimum-receive-ttl {
               description "Minimum receive TTL below which to drop";
               type union {
                 type string {
                   pattern "<.*>|$.*";
                 }
                 type uint8 {
                   range "1 .. 255";
                 }
               }
             }
           }
           choice retain-choice {
             leaf retain {
               description "Always keep route in forwarding table";
               junos:must "(!(\".. resolve\"))";
               junos:must-message "Must not specify resolve with retain";
               type empty;
             }
             leaf no-retain {
               description "Don't always keep route in forwarding table";
               junos:must "(!(\".. resolve\"))";
               junos:must-message "Must not specify resolve with retain";
               type empty;
             }
           }
           choice install-choice {
             leaf install {
               description "Install route into forwarding table";
               type empty;
             }
             leaf no-install {
               description "Don't install route into forwarding table";
               type empty;
             }
           }
           choice readvertise-choice {
             leaf readvertise {
               description "Mark route as eligible to be readvertised";
               type empty;
             }
             leaf no-readvertise {
               description "Don't mark route as eligible to be readvertised";
               type empty;
             }
           }
           choice resolve-choice {
             leaf resolve {
               description "Allow resolution of indirectly connected next hops";
               type empty;
             }
             leaf no-resolve {
               description "Don't allow resolution of indirectly connected next hops";
               type empty;
             }
           }
           choice longest-match-choice {
             leaf longest-match {
               description "Always use longest prefix match to resolve next hops";
               junos:must "(\".. resolve\")";
               junos:must-message "Requires resolve to be configured";
               type empty;
             }
             leaf no-longest-match {
               description "Don't always use longest prefix match to resolve next hops";
               junos:must "(\".. resolve\")";
               junos:must-message "Requires resolve to be configured";
               type empty;
             }
           }
           choice passive_flag {
             case case_1 {
               leaf active {
                 description "Remove inactive route from forwarding table";
                 type empty;
               }
             }
             case case_2 {
               leaf passive {
                 description "Retain inactive route in forwarding table";
                 type empty;
               }
             }
           }
           container metric {
             description "Metric value";
             presence "enable metric";
             uses rib_static_metric_type;
           }
           container metric2 {
             description "Metric value 2";
             presence "enable metric2";
             uses rib_static_metric_type;
           }
           container metric3 {
             description "Metric value 3";
             presence "enable metric3";
             uses rib_static_metric_type;
           }
           container metric4 {
             description "Metric value 4";
             presence "enable metric4";
             uses rib_static_metric_type;
           }
           container tag {
             description "Tag string";
             presence "enable tag";
             uses rib_static_metric_type;
           }
           container tag2 {
             description "Tag string 2";
             presence "enable tag2";
             uses rib_static_metric_type;
           }
           container preference {
             description "Preference value";
             presence "enable preference";
             uses rib_static_metric_type;
           }
           container preference2 {
             description "Preference value 2";
             presence "enable preference2";
             uses rib_static_metric_type;
           }
           container color {
             description "Color (preference) value";
             presence "enable color";
             uses rib_static_metric_type;
           }
           container color2 {
             description "Color (preference) value 2";
             presence "enable color2";
             uses rib_static_metric_type;
           }
           leaf-list community {
             ordered-by user;
             description "BGP community identifier";
             type jt:community;
           }
           container as-path {
             description "Autonomous system path";
             uses apply-advanced;
             leaf path {
               description "Autonomous system path";
               type string;
             }
             leaf origin {
               type enumeration {
                 enum "igp" {
                   description "Path originated in the local IGP";
                 }
                 enum "egp" {
                   description "Path originated in another AS";
                 }
                 enum "incomplete" {
                   description "Path was learned by some other means";
                 }
               }
             }
             leaf atomic-aggregate {
               description "Add ATOMIC_AGGREGATE path attribute to route";
               type empty;
             }
             container aggregator {
               presence "enable aggregator";
               description "Add AGGREGATOR path attribute to route";
             }
             leaf as-number {
               description " Autonomous system number in plain number or 'higher 16bits'.'Lower 16 bits' (asdot notation) format";
               type string {
                 junos:posix-pattern "^[0-9]+(.[0-9]+)?$";
                 junos:pattern-message "Use format 'x' or 'x.y' to specify number 'x' (Range 1 .. 4294967295) or number with higher 2 bytes 'x' (Range 0 .. 65535) and lower 2 bytes 'y' (Range 0 .. 65535) respectively";
               }
             }
             leaf address {
               description "Address of BGP system that formed the route";
               type jt:ipv4addr;
             }
           }
           list lsp-next-hop {
             key name;
             ordered-by user;
             description "LSP next hop";
             uses lsp_nh_obj;
           }
           list p2mp-lsp-next-hop {
             key name;
             ordered-by user;
             description "Point-to-multipoint LSP next hop";
             max-elements 1;
             uses lsp_nh_obj;
           }
           container spring-te-lsp-next-hop {
             description "SPRING-TE LSP next hop";
             junos:must "(\"protocols source-packet-routing tunnel-tracking\")";
             junos:must-message "Please enable the tunnel-tracking  under 'protocols source-packet-routing' hierarchy";
             uses springte_lsp_nh_obj;
           }
           container p2mp-ldp-next-hop {
             description "Point-to-multipoint LDP LSP next hop";
             uses p2mp_ldp_lsp_nh_obj;
           }
           list static-lsp-next-hop {
             key name;
             ordered-by user;
             description "Static LSP next hop";
             uses lsp_nh_obj;
           }
         }
         container static-route {
           description "Static route Status";
           leaf bfd-admin-down {
             description "Static route State on BFD ADMIN DOWN";
             type enumeration {
               enum "active" {
                 description "Static route will be inactive on bfd-admin-down";
               }
               enum "passive" {
                 description "Static route will remain active on bfd-admin-down";
               }
             }
           }
         }
         list iso-route {
           key name;
           ordered-by user;
           description "ISO family static route";
           leaf name {
             type jt:isoprefix;
           }
           uses apply-advanced;
           choice next_hop {
             case case_1 {
               leaf-list next-hop {
                 ordered-by user;
                 description "Next hop to destination";
                 type union {
                   type jt:ipaddr-or-interface;
                   type string {
                     pattern "<.*>|$.*";
                   }
                 }
               }
             }
             case case_2 {
               leaf reject {
                 description "Drop packets to destination; send ICMP unreachables";
                 type empty;
               }
             }
             case case_3 {
               leaf discard {
                 description "Drop packets to destination; send no ICMP unreachables";
                 type empty;
               }
             }
             case case_4 {
               leaf receive {
                 description "Install a receive route for the destination";
                 type empty;
               }
             }
             case case_5 {
               leaf next-table {
                 description "Next hop to another table";
                 type string {
                   junos:posix-pattern "^(((.{0,128})[:](.{1,128})[.]|((.{1,128})[.]))?([a-z]|[0-9]|[-_])+[.]((1?[0-9]{1,2})|(2[0-4][0-9])|(25[0-5])))$";
                   junos:pattern-message "Must match the format [<instance-name>[:<topology-name>].]<family-name>.<rib-id>";
                 }
               }
             }
           }
           list qualified-next-hop {
             key name;
             ordered-by user;
             description "Next hop with qualifiers";
             uses qualified_nh_obj;
           }
           leaf backup-pe-group {
             description "Multicast source redundancy group";
             junos:must "(\".. p2mp-lsp-next-hop\")";
             junos:must-message "Backup groups only allowed for static routes with p2mp lsp next-hop";
             type string;
           }
           container bfd-liveness-detection {
             description "Bidirectional Forwarding Detection (BFD) options";
             uses apply-advanced;
             leaf version {
               description "BFD protocol version number";
               default "automatic";
               type enumeration {
                 enum "0" {
                   description "BFD version 0 (deprecated)";
                 }
                 enum "1" {
                   description "BFD version 1";
                 }
                 enum "automatic" {
                   description "Choose BFD version automatically";
                 }
               }
             }
             leaf minimum-interval {
               description "Minimum transmit and receive interval";
               units "milliseconds";
               type union {
                 type string {
                   pattern "<.*>|$.*";
                 }
                 type uint32 {
                   range "1 .. 255000";
                 }
               }
             }
             leaf minimum-transmit-interval {
               description "Minimum transmit interval";
               status deprecated;
               units "milliseconds";
               type union {
                 type string {
                   pattern "<.*>|$.*";
                 }
                 type uint32 {
                   range "1 .. 255000";
                 }
               }
             }
             leaf minimum-receive-interval {
               description "Minimum receive interval";
               units "milliseconds";
               type union {
                 type string {
                   pattern "<.*>|$.*";
                 }
                 type uint32 {
                   range "1 .. 255000";
                 }
               }
             }
             leaf multiplier {
               description "Detection time multiplier";
               default "3";
               type union {
                 type string {
                   pattern "<.*>|$.*";
                 }
                 type uint32 {
                   range "1 .. 255";
                 }
               }
             }
             choice adaptation-choice {
               case case_1 {
                 leaf no-adaptation {
                   description "Disable adaptation";
                   type empty;
                 }
               }
             }
             container transmit-interval {
               description "Transmit-interval options";
               uses apply-advanced;
               leaf minimum-interval {
                 description "Minimum transmit interval";
                 units "milliseconds";
                 type union {
                   type string {
                     pattern "<.*>|$.*";
                   }
                   type uint32 {
                     range "1 .. 255000";
                   }
                 }
               }
               leaf threshold {
                 description "High transmit interval triggering a trap";
                 units "milliseconds";
                 type union {
                   type uint32;
                   type string {
                     pattern "<.*>|$.*";
                   }
                 }
               }
             }
             container detection-time {
               description "Detection-time options";
               uses apply-advanced;
               leaf threshold {
                 description "High detection-time triggering a trap";
                 units "milliseconds";
                 type union {
                   type uint32;
                   type string {
                     pattern "<.*>|$.*";
                   }
                 }
               }
             }
             container authentication {
               description "Authentication options";
               uses apply-advanced;
               leaf key-chain {
                 description "Key chain name";
                 junos:must "(\".. algorithm\")";
                 junos:must-message "May not be configured without algorithm";
                 junos:must "(\"security authentication-key-chains key-chain $$\")";
                 junos:must-message "Referenced key-chain must be defined";
                 type string;
               }
               leaf algorithm {
                 description "Algorithm name";
                 junos:must "(\".. key-chain\")";
                 junos:must-message "May not be configured without key-chain";
                 type enumeration {
                   enum "simple-password" {
                     description "Simple password";
                   }
                   enum "keyed-md5" {
                     description "Keyed message Digest 5";
                   }
                   enum "meticulous-keyed-md5" {
                     description "Meticulous keyed message Digest 5";
                   }
                   enum "keyed-sha-1" {
                     description "Keyed secure hash algorithm (SHA1) ";
                   }
                   enum "meticulous-keyed-sha-1" {
                     description "Meticulous keyed secure hash algorithm (SHA1) ";
                   }
                 }
               }
               leaf loose-check {
                 description "Verify authentication only if authentication is negotiated";
                 type empty;
               }
             }
             leaf neighbor {
               description "BFD neighbor address";
               type jt:ipaddr;
             }
             leaf local-address {
               description "BFD local address (for multihop only)";
               type jt:ipaddr;
             }
             leaf holddown-interval {
               description "Time to hold the session-UP notification to the client";
               units "milliseconds";
               type union {
                 type string {
                   pattern "<.*>|$.*";
                 }
                 type uint32 {
                   range "0 .. 255000";
                 }
               }
             }
             leaf minimum-receive-ttl {
               description "Minimum receive TTL below which to drop";
               type union {
                 type string {
                   pattern "<.*>|$.*";
                 }
                 type uint8 {
                   range "1 .. 255";
                 }
               }
             }
           }
           choice retain-choice {
             leaf retain {
               description "Always keep route in forwarding table";
               junos:must "(!(\".. resolve\"))";
               junos:must-message "Must not specify resolve with retain";
               type empty;
             }
             leaf no-retain {
               description "Don't always keep route in forwarding table";
               junos:must "(!(\".. resolve\"))";
               junos:must-message "Must not specify resolve with retain";
               type empty;
             }
           }
           choice install-choice {
             leaf install {
               description "Install route into forwarding table";
               type empty;
             }
             leaf no-install {
               description "Don't install route into forwarding table";
               type empty;
             }
           }
           choice readvertise-choice {
             leaf readvertise {
               description "Mark route as eligible to be readvertised";
               type empty;
             }
             leaf no-readvertise {
               description "Don't mark route as eligible to be readvertised";
               type empty;
             }
           }
           choice resolve-choice {
             leaf resolve {
               description "Allow resolution of indirectly connected next hops";
               type empty;
             }
             leaf no-resolve {
               description "Don't allow resolution of indirectly connected next hops";
               type empty;
             }
           }
           choice longest-match-choice {
             leaf longest-match {
               description "Always use longest prefix match to resolve next hops";
               junos:must "(\".. resolve\")";
               junos:must-message "Requires resolve to be configured";
               type empty;
             }
             leaf no-longest-match {
               description "Don't always use longest prefix match to resolve next hops";
               junos:must "(\".. resolve\")";
               junos:must-message "Requires resolve to be configured";
               type empty;
             }
           }
           choice passive_flag {
             case case_1 {
               leaf active {
                 description "Remove inactive route from forwarding table";
                 type empty;
               }
             }
             case case_2 {
               leaf passive {
                 description "Retain inactive route in forwarding table";
                 type empty;
               }
             }
           }
           container metric {
             description "Metric value";
             presence "enable metric";
             uses rib_static_metric_type;
           }
           container metric2 {
             description "Metric value 2";
             presence "enable metric2";
             uses rib_static_metric_type;
           }
           container metric3 {
             description "Metric value 3";
             presence "enable metric3";
             uses rib_static_metric_type;
           }
           container metric4 {
             description "Metric value 4";
             presence "enable metric4";
             uses rib_static_metric_type;
           }
           container tag {
             description "Tag string";
             presence "enable tag";
             uses rib_static_metric_type;
           }
           container tag2 {
             description "Tag string 2";
             presence "enable tag2";
             uses rib_static_metric_type;
           }
           container preference {
             description "Preference value";
             presence "enable preference";
             uses rib_static_metric_type;
           }
           container preference2 {
             description "Preference value 2";
             presence "enable preference2";
             uses rib_static_metric_type;
           }
           container color {
             description "Color (preference) value";
             presence "enable color";
             uses rib_static_metric_type;
           }
           container color2 {
             description "Color (preference) value 2";
             presence "enable color2";
             uses rib_static_metric_type;
           }
           leaf-list community {
             ordered-by user;
             description "BGP community identifier";
             type jt:community;
           }
           container as-path {
             description "Autonomous system path";
             uses apply-advanced;
             leaf path {
               description "Autonomous system path";
               type string;
             }
             leaf origin {
               type enumeration {
                 enum "igp" {
                   description "Path originated in the local IGP";
                 }
                 enum "egp" {
                   description "Path originated in another AS";
                 }
                 enum "incomplete" {
                   description "Path was learned by some other means";
                 }
               }
             }
             leaf atomic-aggregate {
               description "Add ATOMIC_AGGREGATE path attribute to route";
               type empty;
             }
             container aggregator {
               presence "enable aggregator";
               description "Add AGGREGATOR path attribute to route";
             }
             leaf as-number {
               description " Autonomous system number in plain number or 'higher 16bits'.'Lower 16 bits' (asdot notation) format";
               type string {
                 junos:posix-pattern "^[0-9]+(.[0-9]+)?$";
                 junos:pattern-message "Use format 'x' or 'x.y' to specify number 'x' (Range 1 .. 4294967295) or number with higher 2 bytes 'x' (Range 0 .. 65535) and lower 2 bytes 'y' (Range 0 .. 65535) respectively";
               }
             }
             leaf address {
               description "Address of BGP system that formed the route";
               type jt:ipv4addr;
             }
           }
           list lsp-next-hop {
             key name;
             ordered-by user;
             description "LSP next hop";
             uses lsp_nh_obj;
           }
           list p2mp-lsp-next-hop {
             key name;
             ordered-by user;
             description "Point-to-multipoint LSP next hop";
             max-elements 1;
             uses lsp_nh_obj;
           }
           container spring-te-lsp-next-hop {
             description "SPRING-TE LSP next hop";
             junos:must "(\"protocols source-packet-routing tunnel-tracking\")";
             junos:must-message "Please enable the tunnel-tracking  under 'protocols source-packet-routing' hierarchy";
             uses springte_lsp_nh_obj;
           }
           container p2mp-ldp-next-hop {
             description "Point-to-multipoint LDP LSP next hop";
             uses p2mp_ldp_lsp_nh_obj;
           }
         }
         list route-target-filter {
           key name;
           ordered-by user;
           description "Route-target-filter route";
           leaf name {
             type string {
               length "1 .. 47";
               junos:posix-pattern "^[0-9.]{1,15}L?:[0-9]{1,10}/([0-9]|[2-5][0-9]|6[0-4])$";
               junos:pattern-message "Use format 'x:y/len' where 'x' is an AS number followed by an optional 'L' (To indicate 4 byte AS), or an IP address and 'y' is a number. e.g. 123456L:100 and len is a prefix length from 0 to 64";
             }
           }
           uses apply-advanced;
           leaf-list neighbor {
             ordered-by user;
             description "BGP peers for filter";
             type jt:ipaddr-scoped;
           }
           leaf-list group {
             ordered-by user;
             description "BGP groups for filter";
             type string;
           }
           leaf local {
             description "Locally originated filter";
             type empty;
           }
         }
       }
       list martians {
         key "address choice-ident choice-value";
         ordered-by user;
         description "Invalid routes";
         uses martian_type;
       }
       container aggregate {
         description "Coalesced routes";
         uses rib_aggregate_type;
       }
       container generate {
         description "Route of last resort";
         uses rib_aggregate_type;
       }
       choice maximum-paths-type {
         case case_1 {
           container maximum-routes {
             description "Maximum number of routes";
             status deprecated;
             leaf limit {
               description "Maximum number of routes";
               type union {
                 type string {
                   pattern "<.*>|$.*";
                 }
                 type uint32 {
                   range "1 .. 4294967295";
                 }
               }
             }
             choice log_type {
               case case_1 {
                 leaf threshold {
                   description "Percentage of limit at which to start generating warnings";
                   type union {
                     type string {
                       pattern "<.*>|$.*";
                     }
                     type uint32 {
                       range "1 .. 100";
                     }
                   }
                 }
               }
               case case_2 {
                 leaf log-only {
                   description "Generate warning messages only";
                   type empty;
                 }
               }
             }
             leaf log-interval {
               description "Minimum interval between log messages";
               units "seconds";
               type union {
                 type string {
                   pattern "<.*>|$.*";
                 }
                 type uint32 {
                   range "5 .. 86400";
                 }
               }
             }
           }
         }
         case case_2 {
           container maximum-paths {
             description "Maximum number of paths";
             leaf limit {
               description "Maximum number of paths";
               type union {
                 type string {
                   pattern "<.*>|$.*";
                 }
                 type uint32 {
                   range "1 .. 4294967295";
                 }
               }
             }
             choice log_type {
               case case_1 {
                 leaf threshold {
                   description "Percentage of limit at which to start generating warnings";
                   type union {
                     type string {
                       pattern "<.*>|$.*";
                     }
                     type uint32 {
                       range "1 .. 100";
                     }
                   }
                 }
               }
               case case_2 {
                 leaf log-only {
                   description "Generate warning messages only";
                   type empty;
                 }
               }
             }
             leaf log-interval {
               description "Minimum interval between log messages";
               units "seconds";
               type union {
                 type string {
                   pattern "<.*>|$.*";
                 }
                 type uint32 {
                   range "5 .. 86400";
                 }
               }
             }
           }
         }
       }
       container maximum-prefixes {
         description "Maximum number of prefixes";
         leaf limit {
           description "Maximum number of prefixes";
           type union {
             type string {
               pattern "<.*>|$.*";
             }
             type uint32 {
               range "1 .. 4294967295";
             }
           }
         }
         choice log_type {
           case case_1 {
             leaf threshold {
               description "Percentage of limit at which to start generating warnings";
               type union {
                 type string {
                   pattern "<.*>|$.*";
                 }
                 type uint32 {
                   range "1 .. 100";
                 }
               }
             }
           }
           case case_2 {
             leaf log-only {
               description "Generate warning messages only";
               type empty;
             }
           }
         }
         leaf log-interval {
           description "Minimum interval between log messages";
           units "seconds";
           type union {
             type string {
               pattern "<.*>|$.*";
             }
             type uint32 {
               range "5 .. 86400";
             }
           }
         }
       }
       container multipath {
         presence "enable multipath";
         description "Protocol-independent load balancing";
         uses apply-advanced;
         container vpn-unequal-cost {
           presence "enable vpn-unequal-cost";
           description "Include VPN routes with unequal IGP metrics";
           leaf equal-external-internal {
             description "Include external and internal VPN routes";
             type empty;
           }
         }
         leaf as-path-compare {
           description "Compare AS path sequences in addition to AS path length";
           type empty;
         }
         leaf preserve-nexthop-hierarchy {
           description "Force multipath to create List nexthop";
           type empty;
         }
       }
       container policy-multipath {
         description "Policy based multipath";
         uses apply-advanced;
         leaf-list policy {
           ordered-by user;
           description "Import policy to create policy based multipath";
           type jt:policy-algebra;
         }
         container traceoptions {
           description "Trace options";
           uses apply-advanced;
           container file {
             description "Trace file options";
             leaf filename {
               description "Name of file in which to write trace information";
               type string {
                 length "1 .. 1024";
                 junos:posix-pattern "![/ %]";
                 junos:pattern-message "Must not contain '/', % or a space";
               }
             }
             leaf replace {
               description "Replace trace file rather than appending to it";
               status deprecated;
               type empty;
             }
             leaf size {
               description "Maximum trace file size";
               type string;
             }
             leaf files {
               description "Maximum number of trace files";
               default "10";
               type union {
                 type string {
                   pattern "<.*>|$.*";
                 }
                 type uint32 {
                   range "2 .. 1000";
                 }
               }
             }
             leaf no-stamp {
               description "Do not timestamp trace file";
               status deprecated;
               type empty;
             }
             choice world-readable-choice {
               leaf world-readable {
                 description "Allow any user to read the log file";
                 type empty;
               }
               leaf no-world-readable {
                 description "Don't allow any user to read the log file";
                 type empty;
               }
             }
           }
           list flag {
             key name;
             ordered-by user;
             description "Tracing parameters";
             leaf name {
               type enumeration {
                 enum "route" {
                   description "Policy-multipath route tracing.";
                 }
               }
             }
             leaf send {
               description "Trace transmitted packets";
               type empty;
             }
             leaf receive {
               description "Trace received packets";
               type empty;
             }
             leaf detail {
               description "Trace detailed information";
               type empty;
             }
             leaf disable {
               description "Disable this trace flag";
               type empty;
             }
           }
         }
       }
       container protect {
         description "Protocol-independent protection";
         leaf core {
           description "Protect against unreachability to service-edge router";
           type empty;
         }
       }
       container access {
         description "Access routes";
         uses apply-advanced;
         list route {
           key name;
           ordered-by user;
           description "Access route";
           leaf name {
             description "IP address of destination";
             type jt:ipprefix;
           }
           uses apply-advanced;
           leaf-list next-hop {
             ordered-by user;
             description "Next hop to destination";
             type union {
               type jt:ipaddr-or-interface;
               type string {
                 pattern "<.*>|$.*";
               }
             }
           }
           list qualified-next-hop {
             key name;
             ordered-by user;
             description "Next hop with qualifiers";
             uses qualified_nh_obj;
           }
           leaf metric {
             description "Metric value";
             type union {
               type string {
                 pattern "<.*>|$.*";
               }
               type uint32 {
                 range "1 .. 255";
               }
             }
           }
           leaf preference {
             description "Preference value";
             type union {
               type uint32;
               type string {
                 pattern "<.*>|$.*";
               }
             }
           }
           leaf tag {
             description "Tag string";
             type union {
               type uint32;
               type string {
                 pattern "<.*>|$.*";
               }
             }
           }
           leaf tag2 {
             description "Tag2 string";
             type union {
               type uint32;
               type string {
                 pattern "<.*>|$.*";
               }
             }
           }
         }
       }
       container access-internal {
         description "Access-internal routes";
         uses apply-advanced;
         list route {
           key name;
           ordered-by user;
           description "Access-internal route";
           leaf name {
             description "IP address and optional prefix length of destination";
             type jt:ipprefix;
           }
           uses apply-advanced;
           leaf-list next-hop {
             ordered-by user;
             description "Next hop to destination";
             type union {
               type jt:ipaddr-or-interface;
               type string {
                 pattern "<.*>|$.*";
               }
             }
           }
           list qualified-next-hop {
             key name;
             ordered-by user;
             description "Next hop with qualifiers";
             uses qualified_nh_obj;
           }
         }
       }
       container bgp-static {
         description "Routes for BGP static advertisements";
         uses apply-advanced;
         list route {
           key name;
           ordered-by user;
           description "BGP-static route";
           leaf name {
             description "IP address and optional prefix length of destination";
             type jt:ipprefix;
           }
           uses apply-advanced;
           container metric {
             description "Metric value";
             presence "enable metric";
             uses rib_static_metric_type;
           }
           container metric2 {
             description "Metric value 2";
             presence "enable metric2";
             uses rib_static_metric_type;
           }
           container metric3 {
             description "Metric value 3";
             presence "enable metric3";
             uses rib_static_metric_type;
           }
           container metric4 {
             description "Metric value 4";
             presence "enable metric4";
             uses rib_static_metric_type;
           }
           container tag {
             description "Tag string";
             presence "enable tag";
             uses rib_static_metric_type;
           }
           container tag2 {
             description "Tag string 2";
             presence "enable tag2";
             uses rib_static_metric_type;
           }
           container preference {
             description "Preference value";
             presence "enable preference";
             uses rib_static_metric_type;
           }
           container preference2 {
             description "Preference value 2";
             presence "enable preference2";
             uses rib_static_metric_type;
           }
           container color {
             description "Color (preference) value";
             presence "enable color";
             uses rib_static_metric_type;
           }
           container color2 {
             description "Color (preference) value 2";
             presence "enable color2";
             uses rib_static_metric_type;
           }
           leaf-list community {
             ordered-by user;
             description "BGP community identifier";
             type jt:community;
           }
           container as-path {
             description "Autonomous system path";
             uses apply-advanced;
             leaf path {
               description "Autonomous system path";
               type string;
             }
             leaf origin {
               type enumeration {
                 enum "igp" {
                   description "Path originated in the local IGP";
                 }
                 enum "egp" {
                   description "Path originated in another AS";
                 }
                 enum "incomplete" {
                   description "Path was learned by some other means";
                 }
               }
             }
             leaf atomic-aggregate {
               description "Add ATOMIC_AGGREGATE path attribute to route";
               type empty;
             }
             container aggregator {
               presence "enable aggregator";
               description "Add AGGREGATOR path attribute to route";
             }
             leaf as-number {
               description " Autonomous system number in plain number or 'higher 16bits'.'Lower 16 bits' (asdot notation) format";
               type string {
                 junos:posix-pattern "^[0-9]+(.[0-9]+)?$";
                 junos:pattern-message "Use format 'x' or 'x.y' to specify number 'x' (Range 1 .. 4294967295) or number with higher 2 bytes 'x' (Range 0 .. 65535) and lower 2 bytes 'y' (Range 0 .. 65535) respectively";
               }
             }
             leaf address {
               description "Address of BGP system that formed the route";
               type jt:ipv4addr;
             }
           }
         }
       }
       container flow {
         description "Locally defined flow routing information";
         uses apply-advanced;
         container validation {
           description "Flow route validation options";
           presence "enable validation";
           uses flow-validation;
         }
         list route {
           key name;
           ordered-by user;
           description "Flow route";
           uses flow-route-inet6;
         }
         list security-group {
           key name;
           ordered-by user;
           description "Security groups";
           leaf name {
             description "Name of the security group";
             type string {
               length "1 .. 16";
             }
           }
           uses apply-advanced;
           list rule {
             key name;
             ordered-by user;
             description "Flow route";
             uses flow-rule-inet6;
           }
         }
         container interface-group {
           description "Interface-group for applying flow-spec filter";
           uses flow-interface-group;
         }
         leaf discard-action-for-unresolved-redir-addr {
           description "For action redirect IP if redirect address is unresolved install discard action filter";
           type empty;
         }
         choice per-route-accounting-choice {
           leaf per-route-accounting {
             description "Enable traffic accounting per flowspec route";
             type empty;
           }
           leaf no-per-route-accounting {
             description "Don't enable traffic accounting per flowspec route";
             type empty;
           }
         }
       }
       container label {
         presence "enable label";
         description "Label processing";
         uses apply-advanced;
         leaf-list allocation {
           ordered-by user;
           description "Label allocation policy";
           junos:must "(\".. .. .. instance-type vrf\")";
           junos:must-message "'allocation' policy is valid only for 'instance-type vrf'";
           type jt:policy-algebra;
         }
         leaf-list substitution {
           ordered-by user;
           description "Label substitution policy";
           junos:must "(\".. .. .. instance-type vrf\")";
           junos:must-message "'substitution' policy is valid only for 'instance-type vrf'";
           type jt:policy-algebra;
         }
       }
     }
     container label {
       presence "enable label";
       description "Label processing";
       uses apply-advanced;
       leaf-list allocation {
         ordered-by user;
         description "Label allocation policy";
         junos:must "(\".. .. .. instance-type vrf\")";
         junos:must-message "'allocation' policy is valid only for 'instance-type vrf'";
         type jt:policy-algebra;
       }
       leaf-list substitution {
         ordered-by user;
         description "Label substitution policy";
         junos:must "(\".. .. .. instance-type vrf\")";
         junos:must-message "'substitution' policy is valid only for 'instance-type vrf'";
         type jt:policy-algebra;
       }
     }
     container options {
       description "Miscellaneous options";
       uses apply-advanced;
       leaf no-send {
         description "Listen only; do not send protocol packets";
         status deprecated;
         type empty;
       }
       leaf no-resolve {
         description "Do not use DNS name resolution";
         status deprecated;
         type empty;
       }
       container syslog {
         description "Set system logging level";
         uses apply-advanced;
         container level {
           description "Logging level";
           leaf emergency {
             description "Emergency level";
             type empty;
           }
           leaf alert {
             description "Alert level";
             type empty;
           }
           leaf critical {
             description "Critical level";
             type empty;
           }
           leaf error {
             description "Error level";
             type empty;
           }
           leaf warning {
             description "Warning level";
             type empty;
           }
           leaf notice {
             description "Notice level";
             type empty;
           }
           leaf info {
             description "Informational level";
             type empty;
           }
           leaf debug {
             description "Debugging level";
             type empty;
           }
         }
         leaf upto {
           description "Log up to a particular logging level";
           type enumeration {
             enum "emergency" {
               description "Emergency level";
             }
             enum "alert" {
               description "Alert level";
             }
             enum "critical" {
               description "Critical level";
             }
             enum "error" {
               description "Error level";
             }
             enum "warning" {
               description "Warning level";
             }
             enum "notice" {
               description "Notice level";
             }
             enum "info" {
               description "Informational level";
             }
             enum "debug" {
               description "Debugging level";
             }
           }
         }
       }
       leaf mark {
         description "Periodically mark the trace file";
         units "seconds";
         type union {
           type int32;
           type string {
             pattern "<.*>|$.*";
           }
         }
       }
     }
     container resolution {
       presence "enable resolution";
       description "Route next-hop resolution options";
       uses apply-advanced;
       leaf-list tracefilter {
         ordered-by user;
         description "Filter policy";
         type jt:policy-algebra;
       }
       container traceoptions {
         description "Trace options";
         uses apply-advanced;
         container file {
           description "Trace file options";
           leaf filename {
             description "Name of file in which to write trace information";
             type string {
               length "1 .. 1024";
               junos:posix-pattern "![/ %]";
               junos:pattern-message "Must not contain '/', % or a space";
             }
           }
           leaf replace {
             description "Replace trace file rather than appending to it";
             status deprecated;
             type empty;
           }
           leaf size {
             description "Maximum trace file size";
             type string;
           }
           leaf files {
             description "Maximum number of trace files";
             default "10";
             type union {
               type string {
                 pattern "<.*>|$.*";
               }
               type uint32 {
                 range "2 .. 1000";
               }
             }
           }
           leaf no-stamp {
             description "Do not timestamp trace file";
             status deprecated;
             type empty;
           }
           choice world-readable-choice {
             leaf world-readable {
               description "Allow any user to read the log file";
               type empty;
             }
             leaf no-world-readable {
               description "Don't allow any user to read the log file";
               type empty;
             }
           }
         }
         list flag {
           key name;
           ordered-by user;
           description "Tracing parameters";
           leaf name {
             type enumeration {
               enum "event" {
                 description "Event processing";
               }
               enum "flash" {
                 description "Flash processing";
               }
               enum "kernel" {
                 description "Kernel communication";
               }
               enum "indirect" {
                 description "Indirect next-hop addition, change, or deletion";
               }
               enum "task" {
                 description "Task or job processing";
               }
               enum "igp-frr" {
                 description "IGP triggered FRR events";
               }
               enum "igp-frr-extensive" {
                 description "IGP triggered FRR Extensive events";
               }
               enum "tunnel" {
                 description "Resolver dynamic tunnel events";
               }
               enum "all" {
                 description "Trace everything";
               }
             }
           }
           leaf send {
             description "Trace transmitted packets";
             type empty;
           }
           leaf receive {
             description "Trace received packets";
             type empty;
           }
           leaf detail {
             description "Trace detailed information";
             type empty;
           }
           leaf disable {
             description "Disable this trace flag";
             type empty;
           }
         }
       }
       choice preserve-nexthop-hierarchy-choice {
         leaf preserve-nexthop-hierarchy {
           description "Preserve nexthop hierarchy when installing nexthop to forwarding plane";
           type empty;
         }
         leaf no-preserve-nexthop-hierarchy {
           description "Don't preserve nexthop hierarchy when installing nexthop to forwarding plane";
           type empty;
         }
       }
       list rib {
         key name;
         ordered-by user;
         description "Routing table resolution options";
         leaf name {
           description "Routing table name";
           type string;
         }
         uses apply-advanced;
         leaf-list resolution-family {
           ordered-by user;
           description "Family of resultion tree";
           type string;
         }
         leaf-list resolution-ribs {
           ordered-by user;
           description "Routing tables to use for default routing table family resolution";
           type string;
         }
         leaf-list inet-resolution-ribs {
           ordered-by user;
           description "Routing tables to use for ipv4 family protocol-next-hop resolution";
           type string;
         }
         leaf-list inet6-resolution-ribs {
           ordered-by user;
           description "Routing tables to use for ipv6 family protocol-next-hop resolution";
           type string;
         }
         leaf-list iso-resolution-ribs {
           ordered-by user;
           description "Routing tables to use for iso family protocol-next-hop resolution";
           type string;
         }
         leaf-list import {
           ordered-by user;
           description "Import policy";
           type jt:policy-algebra;
         }
         leaf-list inet-import {
           ordered-by user;
           description "Import policy for IPV4 family resolution tree";
           type jt:policy-algebra;
         }
         leaf-list inet6-import {
           ordered-by user;
           description "Import policy for IPV6 family resolution tree";
           type jt:policy-algebra;
         }
         leaf-list iso-import {
           ordered-by user;
           description "Import policy for ISO family resolution tree";
           type jt:policy-algebra;
         }
         leaf-list inetcolor-import {
           ordered-by user;
           description "Import policy for INETCOLOR family resolution tree";
           type jt:policy-algebra;
         }
         leaf-list inet6color-import {
           ordered-by user;
           description "Import policy for INET6COLOR family resolution tree";
           type jt:policy-algebra;
         }
       }
       choice prefer-recursive-primary-path-choice {
         leaf prefer-recursive-primary-path {
           description "Prefer primary path to resolve nexthop during recursive-resolution";
           type empty;
         }
         leaf no-prefer-recursive-primary-path {
           description "Don't prefer primary path to resolve nexthop during recursive-resolution";
           type empty;
         }
       }
       list scheme {
         key name;
         ordered-by user;
         description "Nexthop resolution fallback";
         leaf name {
           description "Name the resolution scheme";
           type string;
         }
         uses apply-advanced;
         leaf-list resolution-ribs {
           ordered-by user;
           description "Routing tables to use for nexthop resolution, in fallback order";
           junos:must "(!(\".. transport-classes\"))";
           junos:must-message "resolution-ribs and transport-classes are mutually exclusive options";
           type string;
         }
         leaf mapping-community {
           description "Community on service-route that maps to this transport";
           type jt:community;
         }
       }
     }
     container interface-routes {
       description "Define routing table groups for interface routes";
       uses apply-advanced;
       container rib-group {
         description "Routing table group";
         uses rib_group_type;
       }
       list family {
         key name;
         ordered-by user;
         description "Address family";
         leaf name {
           type enumeration {
             enum "inet" {
               description "IPv4 family";
             }
             enum "inet6" {
               description "IPv6 family";
             }
           }
         }
         uses apply-advanced;
         leaf-list import {
           ordered-by user;
           description "Import policy";
           type jt:policy-algebra;
         }
         container export {
           description "Control exportability of local routes";
           uses apply-advanced;
           leaf point-to-point {
             description "Make point-to-point routes exportable";
             type empty;
           }
           leaf lan {
             description "Make LAN routes exportable";
             type empty;
           }
         }
       }
     }
     leaf loopback-strict-disable {
       description "Completely disable lo0 host prefix when in admin-down state";
       type empty;
     }
     container traceoptions {
       description "Global routing protocol trace options";
       uses apply-advanced;
       container file {
         description "Trace file options";
         leaf filename {
           description "Name of file in which to write trace information";
           type string {
             length "1 .. 1024";
             junos:posix-pattern "![/ %]";
             junos:pattern-message "Must not contain '/', % or a space";
           }
         }
         leaf replace {
           description "Replace trace file rather than appending to it";
           status deprecated;
           type empty;
         }
         leaf size {
           description "Maximum trace file size";
           type string;
         }
         leaf files {
           description "Maximum number of trace files";
           default "10";
           type union {
             type string {
               pattern "<.*>|$.*";
             }
             type uint32 {
               range "2 .. 1000";
             }
           }
         }
         leaf no-stamp {
           description "Do not timestamp trace file";
           status deprecated;
           type empty;
         }
         choice world-readable-choice {
           leaf world-readable {
             description "Allow any user to read the log file";
             type empty;
           }
           leaf no-world-readable {
             description "Don't allow any user to read the log file";
             type empty;
           }
         }
       }
       list flag {
         key name;
         ordered-by user;
         description "Tracing parameters";
         leaf name {
           type enumeration {
             enum "parse" {
               description "Trace configuration parsing";
             }
             enum "regex-parse" {
               description "Trace regular-expression parsing";
             }
             enum "config-internal" {
               description "Trace configuration internals";
             }
             enum "nsr-synchronization" {
               description "Trace nonstop routing synchronization events";
             }
             enum "condition-manager" {
               description "Trace condition manager events";
             }
             enum "graceful-restart" {
               description "Trace Graceful Restart events";
             }
             enum "session" {
               description "Trace Session ID allocations/deallocations";
             }
             enum "hfrr-fsm" {
               description "Host FRR FSM events tracing";
             }
             enum "hfrr-route" {
               description "Host FRR route events tracing";
             }
             enum "statistics-id-group" {
               description "Trace Statistics ID Group operations";
             }
             enum "route-record" {
               description "Trace route-record server-side events";
             }
             enum "jvision-lsp" {
               description "Trace Jvision events and errors";
             }
             enum "dyn-nh-template" {
               description "Dynamic nexthops template events tracing";
             }
             enum "read-route" {
               description "Read route events tracing";
             }
             enum "events" {
               description "Trace-events events tracing";
             }
             enum "route" {
               description "Trace routing information";
             }
             enum "normal" {
               description "Trace normal events";
             }
             enum "general" {
               description "Trace general events";
             }
             enum "state" {
               description "Trace state transitions";
             }
             enum "policy" {
               description "Trace policy processing";
             }
             enum "task" {
               description "Trace routing protocol task processing";
             }
             enum "timer" {
               description "Trace routing protocol timer processing";
             }
             enum "all" {
               description "Trace everything";
             }
           }
         }
         leaf disable {
           description "Disable this trace flag";
           type empty;
         }
       }
     }
     container topologies {
       junos:must "(!(\"routing-options no-multi-topology-routing\"))";
       junos:must-message "Multi topology routing is disabled";
       description "Define routing topologies";
       uses apply-advanced;
       list family {
         key name;
         ordered-by user;
         description "Address family";
         leaf name {
           type enumeration {
             enum "inet" {
               description "IPv4 family";
             }
             enum "inet6" {
               description "IPv6 family";
             }
           }
         }
         uses apply-advanced;
         list topology {
           key name;
           ordered-by user;
           description "Topology information";
           leaf name {
             description "Topology name";
             type string {
               junos:posix-pattern "!^((.*:.*)|(.{129,}))$";
               junos:pattern-message "Must be a non-reserved string of 128 characters or less";
             }
           }
           uses apply-advanced;
           leaf table-id {
             description "Table-id";
             junos:must "(unique \".. .. topology <*> table-id $$\")";
             junos:must-message "Table-id has to be unique among all topology names";
             type union {
               type uint16;
               type string {
                 pattern "<.*>|$.*";
               }
             }
           }
         }
       }
     }
     leaf router-id {
       description "Router identifier";
       type jt:ipv4addr;
     }
     container autonomous-system {
       description "Autonomous system number";
       leaf as-number {
         description " Autonomous system number in plain number or 'higher 16bits'.'Lower 16 bits' (asdot notation) format";
         type string {
           junos:posix-pattern "^[0-9]+(.[0-9]+)?$";
           junos:pattern-message "Use format 'x' or 'x.y' to specify number 'x' (Range 1 .. 4294967295) or number with higher 2 bytes 'x' (Range 0 .. 65535) and lower 2 bytes 'y' (Range 0 .. 65535) respectively";
         }
       }
       leaf loops {
         description "Maximum number of times this AS can be in an AS path";
         type union {
           type string {
             pattern "<.*>|$.*";
           }
           type int32 {
             range "1 .. 10";
           }
         }
       }
       leaf asdot-notation {
         description "Use AS-Dot notation to display true 4 byte AS numbers";
         type empty;
       }
       container independent-domain {
         presence "enable independent-domain";
         description "Independent autonomous-system domain from master instance";
         container no-attrset {
           presence "enable no-attrset";
           description "Do not tunnel ce bgp attributes across provider network";
         }
       }
     }
     container confederation {
       description "Confederation autonomous system number";
       leaf confederation-as {
         description " Autonomous system number in plain number or 'higher 16bits'.'Lower 16 bits' (asdot notation) format";
         type string {
           junos:posix-pattern "^[0-9]+(.[0-9]+)?$";
           junos:pattern-message "Use format 'x' or 'x.y' to specify number 'x' (Range 1 .. 4294967295) or number with higher 2 bytes 'x' (Range 0 .. 65535) and lower 2 bytes 'y' (Range 0 .. 65535) respectively";
         }
       }
       leaf-list members {
         ordered-by user;
         description " Autonomous system number in plain number or 'higher 16bits'.'Lower 16 bits' (asdot notation) format";
         type string;
       }
     }
     leaf ipv6-router-id {
       description "IPv6 router identifier";
       type string;
     }
     container graceful-restart {
       presence "enable graceful-restart";
       junos:must "(!(\"routing-options nonstop-routing\"))";
       junos:must-message "Graceful restart and Nonstop routing may not be enabled simultaneously";
       description "Graceful or hitless routing restart options";
       uses apply-advanced;
       choice enable-disable {
         case case_1 {
           leaf disable {
             description "Disable graceful restart";
             type empty;
           }
         }
       }
       leaf restart-duration {
         description "Maximum time for which router is in graceful restart";
         type union {
           type string {
             pattern "<.*>|$.*";
           }
           type uint32 {
             range "120 .. 10000";
           }
         }
       }
     }
     container flow {
       description "Locally defined flow routing information";
       uses apply-advanced;
       leaf firewall-install-disable {
         description "Disable installing flowspec firewall filters in dfwd ";
         type empty;
       }
       choice per-route-accounting-choice {
         leaf per-route-accounting {
           description "Enable traffic accounting per flowspec route";
           type empty;
         }
         leaf no-per-route-accounting {
           description "Don't enable traffic accounting per flowspec route";
           type empty;
         }
       }
       container validation {
         description "Flow route validation options";
         presence "enable validation";
         uses flow-validation;
       }
       container interface-group {
         description "Interface-group for applying flow-spec filter";
         uses flow-interface-group;
       }
       list route {
         key name;
         ordered-by user;
         description "Flow route";
         uses flow-route-inet;
       }
       leaf term-order {
         description "Term evaluation order for flow routes";
         type enumeration {
           enum "legacy" {
             description "Legacy term order (default)";
           }
           enum "standard" {
             description "RFC compliant term order";
           }
         }
       }
       leaf discard-action-for-unresolved-redir-addr {
         description "For action redirect IP if redirect address is unresolved install discard action filter";
         type empty;
       }
       list security-group {
         key name;
         ordered-by user;
         description "Security groups";
         leaf name {
           description "Name of the security group";
           type string {
             length "1 .. 16";
           }
         }
         uses apply-advanced;
         list rule {
           key name;
           ordered-by user;
           description "Flow route";
           uses flow-rule-inet;
         }
       }
     }
     leaf no-soft-core {
       description "Disable soft assert to generate core and just log the event";
       type empty;
     }
     leaf med-igp-update-interval {
       description "Delay (in minutes) in updating MED IGP for bgp groups with 'delay-med-update' ";
       type union {
         type string {
           pattern "<.*>|$.*";
         }
         type uint32 {
           range "10 .. 600";
         }
       }
     }
     container bmp {
       presence "enable bmp";
       description "BGP Monitoring Protocol (BMP) configuration";
       uses apply-advanced;
       leaf authentication-key {
         description "MD5 authentication key";
         type string {
           length "1 .. 126";
         }
       }
       leaf authentication-algorithm {
         description "Authentication algorithm name";
         default "hmac-sha-1-96";
         junos:must "(!(\".. authentication-key\"))";
         junos:must-message "May not be configured with authentication-key";
         type enumeration {
           enum "md5" {
             description "Message Digest 5";
           }
           enum "hmac-sha-1-96" {
             description "Hash-based Message Authentication Code (SHA1) (96 bits)";
           }
           enum "aes-128-cmac-96" {
             description "Cipher-based Message Authentication Code (AES128) (96 bits)";
           }
           enum "ao" {
             description "TCP Authentication Option";
           }
         }
       }
       leaf tcpao-handling-with-digest-mismatch {
         description "Drop or continue without TCP-AO with digest mismatch with TCP-AO";
         junos:must "(!(\".. authentication-key\"))";
         junos:must-message "May not be configured with authentication-key";
         type enumeration {
           enum "drop-if-no-tcpao" {
             description "Drop the connection if Digest mismatched";
           }
           enum "allow-without-tcpao" {
             description "Allow the connection establishment without TCP-AO";
           }
         }
       }
       leaf authentication-key-chain {
         description "Key chain name";
         junos:must "(!(\".. authentication-key\"))";
         junos:must-message "May not be configured with authentication-key";
         junos:must "(\"security authentication-key-chains key-chain $$\")";
         junos:must-message "Referenced key-chain must be defined";
         type string {
           length "1 .. 128";
         }
       }
       container hold-down {
         presence "enable hold-down";
         leaf hold-down-time {
           description "Prevent re-establishment for this time";
           units "seconds";
           type union {
             type string {
               pattern "<.*>|$.*";
             }
             type uint32 {
               range "30 .. 65535";
             }
           }
         }
         leaf flaps {
           description "Number of flaps before damping";
           type union {
             type string {
               pattern "<.*>|$.*";
             }
             type uint32 {
               range "2 .. 10";
             }
           }
         }
         leaf period {
           description "Time period for flaps";
           units "seconds";
           type union {
             type string {
               pattern "<.*>|$.*";
             }
             type uint32 {
               range "30 .. 65535";
             }
           }
         }
       }
       leaf initiation-message {
         description "User string sent with the initiation message";
         type string {
           length "1 .. 255";
         }
       }
       leaf local-address {
         description "Address of local end of BMP session";
         type jt:ipaddr;
       }
       leaf local-port {
         description "Local port for listening";
         type union {
           type string {
             pattern "<.*>|$.*";
           }
           type uint32 {
             range "1024 .. 65535";
           }
         }
       }
       leaf connection-mode {
         description "Specify active or passive";
         type enumeration {
           enum "active" {
             description "Initiate the connection";
           }
           enum "passive" {
             description "Listen for the connection";
           }
         }
       }
       leaf priority {
         description "Relative dispatch priority";
         type enumeration {
           enum "low" {
             description "Lowest priority";
           }
           enum "medium" {
             description "Medium priority";
           }
           enum "high" {
             description "Highest priority";
           }
         }
       }
       leaf monitor {
         description "Enable/Disable monitoring";
         type enumeration {
           enum "enable" {
             description "Enable monitoring of BGP peer(s)";
           }
           enum "disable" {
             description "Disable monitoring of BGP peer(s)";
           }
         }
       }
       container route-monitoring {
         description "Control route monitoring settings";
         uses apply-advanced;
         leaf none {
           description "Do not send route monitoring messages";
           junos:must "((!(\".. pre-policy\") && (!(\".. post-policy\") && (!(\".. rib-out\") && !(\".. loc-rib\")))))";
           junos:must-message "May not be configured with pre-policy or post-policy or rib-out or loc-rib";
           type empty;
         }
         leaf loc-rib {
           description "Send local-rib route monitoring messages";
           junos:must "((!(\"system processes routing bgp update-threading\") || \"system processes routing bgp rib-sharding\"))";
           junos:must-message "Update threading can't be configured alone with bmp loc-rib monitoring";
           type empty;
         }
         container pre-policy {
           presence "enable pre-policy";
           description "Send pre policy route monitoring messages";
           leaf exclude-non-feasible {
             description "Exclude looped routes, etc";
             type empty;
           }
         }
         container post-policy {
           presence "enable post-policy";
           description "Send post policy route monitoring messages";
           leaf exclude-non-eligible {
             description "Exclude unresolved routes, etc.";
             type empty;
           }
         }
         container rib-out {
           presence "enable rib-out";
           junos:must "((!(\"system processes routing bgp update-threading\") || \"system processes routing bgp rib-sharding\"))";
           junos:must-message "Update threading can't be configured alone with bmp rib-out monitoring";
           description "Send adj-ribs-out route monitoring messages";
           leaf pre-policy {
             description "Send pre-policy adj-ribs-out route monitoring messages";
             type empty;
           }
           leaf post-policy {
             description "Send post-policy adj-ribs-out route monitoring messages";
             type empty;
           }
         }
       }
       leaf max-loc-rib-buffer-count {
         description "Max number of loc-rib outstanding buffers before blocking";
         type union {
           type string {
             pattern "<.*>|$.*";
           }
           type uint32 {
             range "1 .. 50";
           }
         }
       }
       leaf station-address {
         description "Address/name of monitoring station";
         type jt:ipaddr;
       }
       leaf routing-instance {
         description "Routing-instance through which BMP station is reachable";
         type string;
       }
       leaf station-port {
         description "Port of monitoring station";
         type union {
           type string {
             pattern "<.*>|$.*";
           }
           type uint32 {
             range "1 .. 65535";
           }
         }
       }
       leaf statistics-timeout {
         description "Statistics message timer, 15-65535, or 0 for no messages";
         units "seconds";
         type union {
           type string {
             pattern "<.*>|$.*";
           }
           type uint32 {
             range "0 .. 65535";
           }
         }
       }
       container traceoptions {
         description "Trace options";
         uses apply-advanced;
         container file {
           description "Trace file options";
           leaf filename {
             description "Name of file in which to write trace information";
             type string {
               length "1 .. 1024";
               junos:posix-pattern "![/ %]";
               junos:pattern-message "Must not contain '/', % or a space";
             }
           }
           leaf replace {
             description "Replace trace file rather than appending to it";
             status deprecated;
             type empty;
           }
           leaf size {
             description "Maximum trace file size";
             type string;
           }
           leaf files {
             description "Maximum number of trace files";
             default "10";
             type union {
               type string {
                 pattern "<.*>|$.*";
               }
               type uint32 {
                 range "2 .. 1000";
               }
             }
           }
           leaf no-stamp {
             description "Do not timestamp trace file";
             status deprecated;
             type empty;
           }
           choice world-readable-choice {
             leaf world-readable {
               description "Allow any user to read the log file";
               type empty;
             }
             leaf no-world-readable {
               description "Don't allow any user to read the log file";
               type empty;
             }
           }
         }
         list flag {
           key name;
           ordered-by user;
           description "Trace flag information";
           leaf name {
             type enumeration {
               enum "packets" {
                 description "Trace all messages";
               }
               enum "up" {
                 description "Trace up messages";
               }
               enum "down" {
                 description "Trace down messages";
               }
               enum "statistics" {
                 description "Trace statistics messages";
               }
               enum "route-monitoring" {
                 description "Trace route monitoring messages";
               }
               enum "event" {
                 description "Trace major events, station establishment, errors, events";
               }
               enum "error" {
                 description "Trace error conditions";
               }
               enum "write" {
                 description "Trace writing of messages";
               }
               enum "route" {
                 description "Trace routing information";
               }
               enum "normal" {
                 description "Trace normal events";
               }
               enum "general" {
                 description "Trace general events";
               }
               enum "state" {
                 description "Trace state transitions";
               }
               enum "policy" {
                 description "Trace policy processing";
               }
               enum "task" {
                 description "Trace routing protocol task processing";
               }
               enum "timer" {
                 description "Trace routing protocol timer processing";
               }
               enum "all" {
                 description "Trace everything";
               }
             }
           }
           leaf send {
             description "Trace transmitted packets";
             type empty;
           }
           leaf receive {
             description "Trace received packets";
             type empty;
           }
           leaf detail {
             description "Trace detailed information";
             type empty;
           }
           leaf disable {
             description "Disable this trace flag";
             type empty;
           }
         }
       }
       list station {
         key name;
         description "Define a BMP station";
         leaf name {
           description "Station name";
           type string;
         }
         uses apply-advanced;
         leaf authentication-key {
           description "MD5 authentication key";
           type string {
             length "1 .. 126";
           }
         }
         leaf authentication-algorithm {
           description "Authentication algorithm name";
           junos:must "(!(\".. authentication-key\"))";
           junos:must-message "May not be configured with authentication-key";
           type enumeration {
             enum "md5" {
               description "Message Digest 5";
             }
             enum "hmac-sha-1-96" {
               description "Hash-based Message Authentication Code (SHA1) (96 bits)";
             }
             enum "aes-128-cmac-96" {
               description "Cipher-based Message Authentication Code (AES128) (96 bits)";
             }
             enum "ao" {
               description "TCP Authentication Option";
             }
           }
         }
         leaf tcpao-handling-with-digest-mismatch {
           description "Drop or continue without TCP-AO with digest mismatch with TCP-AO";
           junos:must "(!(\".. authentication-key\"))";
           junos:must-message "May not be configured with authentication-key";
           type enumeration {
             enum "drop-if-no-tcpao" {
               description "Drop the connection if Digest mismatched";
             }
             enum "allow-without-tcpao" {
               description "Allow the connection establishment without TCP-AO";
             }
           }
         }
         leaf authentication-key-chain {
           description "Key chain name";
           junos:must "(!(\".. authentication-key\"))";
           junos:must-message "May not be configured with authentication-key";
           junos:must "(\"security authentication-key-chains key-chain $$\")";
           junos:must-message "Referenced key-chain must be defined";
           type string {
             length "1 .. 128";
           }
         }
         container hold-down {
           presence "enable hold-down";
           leaf hold-down-time {
             description "Prevent re-establishment for this time";
             units "seconds";
             type union {
               type string {
                 pattern "<.*>|$.*";
               }
               type uint32 {
                 range "30 .. 65535";
               }
             }
           }
           leaf flaps {
             description "Number of flaps before damping";
             type union {
               type string {
                 pattern "<.*>|$.*";
               }
               type uint32 {
                 range "2 .. 10";
               }
             }
           }
           leaf period {
             description "Time period for flaps";
             units "seconds";
             type union {
               type string {
                 pattern "<.*>|$.*";
               }
               type uint32 {
                 range "30 .. 65535";
               }
             }
           }
         }
         leaf initiation-message {
           description "User string sent with the initiation message";
           type string {
             length "1 .. 255";
           }
         }
         leaf local-address {
           description "Address of local end of BMP session";
           type jt:ipaddr;
         }
         leaf local-port {
           description "Local port for listening";
           type union {
             type string {
               pattern "<.*>|$.*";
             }
             type uint32 {
               range "1024 .. 65535";
             }
           }
         }
         leaf connection-mode {
           description "Specify active or passive";
           type enumeration {
             enum "active" {
               description "Initiate the connection";
             }
             enum "passive" {
               description "Listen for the connection";
             }
           }
         }
         leaf priority {
           description "Relative dispatch priority";
           type enumeration {
             enum "low" {
               description "Lowest priority";
             }
             enum "medium" {
               description "Medium priority";
             }
             enum "high" {
               description "Highest priority";
             }
           }
         }
         leaf monitor {
           description "Enable/Disable monitoring";
           type enumeration {
             enum "enable" {
               description "Enable monitoring of BGP peer(s)";
             }
             enum "disable" {
               description "Disable monitoring of BGP peer(s)";
             }
           }
         }
         container route-monitoring {
           description "Control route monitoring settings";
           uses apply-advanced;
           leaf none {
             description "Do not send route monitoring messages";
             junos:must "((!(\".. pre-policy\") && (!(\".. post-policy\") && (!(\".. rib-out\") && !(\".. loc-rib\")))))";
             junos:must-message "May not be configured with pre-policy or post-policy or rib-out or loc-rib";
             type empty;
           }
           leaf loc-rib {
             description "Send local-rib route monitoring messages";
             junos:must "((!(\"system processes routing bgp update-threading\") || \"system processes routing bgp rib-sharding\"))";
             junos:must-message "Update threading can't be configured alone with bmp loc-rib monitoring";
             type empty;
           }
           container pre-policy {
             presence "enable pre-policy";
             description "Send pre policy route monitoring messages";
             leaf exclude-non-feasible {
               description "Exclude looped routes, etc";
               type empty;
             }
           }
           container post-policy {
             presence "enable post-policy";
             description "Send post policy route monitoring messages";
             leaf exclude-non-eligible {
               description "Exclude unresolved routes, etc.";
               type empty;
             }
           }
           container rib-out {
             presence "enable rib-out";
             junos:must "((!(\"system processes routing bgp update-threading\") || \"system processes routing bgp rib-sharding\"))";
             junos:must-message "Update threading can't be configured alone with bmp rib-out monitoring";
             description "Send adj-ribs-out route monitoring messages";
             leaf pre-policy {
               description "Send pre-policy adj-ribs-out route monitoring messages";
               type empty;
             }
             leaf post-policy {
               description "Send post-policy adj-ribs-out route monitoring messages";
               type empty;
             }
           }
         }
         leaf max-loc-rib-buffer-count {
           description "Max number of loc-rib outstanding buffers before blocking";
           type union {
             type string {
               pattern "<.*>|$.*";
             }
             type uint32 {
               range "1 .. 50";
             }
           }
         }
         leaf station-address {
           description "Address/name of monitoring station";
           type jt:ipaddr;
         }
         leaf routing-instance {
           description "Routing-instance through which BMP station is reachable";
           type string;
         }
         leaf station-port {
           description "Port of monitoring station";
           type union {
             type string {
               pattern "<.*>|$.*";
             }
             type uint32 {
               range "1 .. 65535";
             }
           }
         }
         leaf statistics-timeout {
           description "Statistics message timer, 15-65535, or 0 for no messages";
           units "seconds";
           type union {
             type string {
               pattern "<.*>|$.*";
             }
             type uint32 {
               range "0 .. 65535";
             }
           }
         }
         container traceoptions {
           description "Trace options";
           uses apply-advanced;
           container file {
             description "Trace file options";
             leaf filename {
               description "Name of file in which to write trace information";
               type string {
                 length "1 .. 1024";
                 junos:posix-pattern "![/ %]";
                 junos:pattern-message "Must not contain '/', % or a space";
               }
             }
             leaf replace {
               description "Replace trace file rather than appending to it";
               status deprecated;
               type empty;
             }
             leaf size {
               description "Maximum trace file size";
               type string;
             }
             leaf files {
               description "Maximum number of trace files";
               default "10";
               type union {
                 type string {
                   pattern "<.*>|$.*";
                 }
                 type uint32 {
                   range "2 .. 1000";
                 }
               }
             }
             leaf no-stamp {
               description "Do not timestamp trace file";
               status deprecated;
               type empty;
             }
             choice world-readable-choice {
               leaf world-readable {
                 description "Allow any user to read the log file";
                 type empty;
               }
               leaf no-world-readable {
                 description "Don't allow any user to read the log file";
                 type empty;
               }
             }
           }
           list flag {
             key name;
             ordered-by user;
             description "Trace flag information";
             leaf name {
               type enumeration {
                 enum "packets" {
                   description "Trace all messages";
                 }
                 enum "up" {
                   description "Trace up messages";
                 }
                 enum "down" {
                   description "Trace down messages";
                 }
                 enum "statistics" {
                   description "Trace statistics messages";
                 }
                 enum "route-monitoring" {
                   description "Trace route monitoring messages";
                 }
                 enum "event" {
                   description "Trace major events, station establishment, errors, events";
                 }
                 enum "error" {
                   description "Trace error conditions";
                 }
                 enum "write" {
                   description "Trace writing of messages";
                 }
                 enum "route" {
                   description "Trace routing information";
                 }
                 enum "normal" {
                   description "Trace normal events";
                 }
                 enum "general" {
                   description "Trace general events";
                 }
                 enum "state" {
                   description "Trace state transitions";
                 }
                 enum "policy" {
                   description "Trace policy processing";
                 }
                 enum "task" {
                   description "Trace routing protocol task processing";
                 }
                 enum "timer" {
                   description "Trace routing protocol timer processing";
                 }
                 enum "all" {
                   description "Trace everything";
                 }
               }
             }
             leaf send {
               description "Trace transmitted packets";
               type empty;
             }
             leaf receive {
               description "Trace received packets";
               type empty;
             }
             leaf detail {
               description "Trace detailed information";
               type empty;
             }
             leaf disable {
               description "Disable this trace flag";
               type empty;
             }
           }
         }
       }
     }
     leaf bgp-orf-cisco-mode {
       description "Using BGP ORF capability code 130 and Prefix ORF type 128";
       type empty;
     }
     leaf highwatermark-log-interval {
       description "High watermark log interval (default 30 seconds)";
       units "seconds";
       type union {
         type string {
           pattern "<.*>|$.*";
         }
         type uint32 {
           range "5 .. 1200";
         }
       }
     }
     leaf time-averaged-watermark-interval {
       description "For calculating average watermark";
       units "days";
       type union {
         type string {
           pattern "<.*>|$.*";
         }
         type uint32 {
           range "1 .. 15";
         }
       }
     }
     container ppm {
       presence "enable ppm";
       description "Set periodic packet management properties";
       uses apply-advanced;
       leaf delegate-processing {
         description "Enable distribution of PPM sessions";
         status deprecated;
         type empty;
       }
       leaf no-delegate-processing {
         description "Disable PPM sessions distribution";
         type empty;
       }
       leaf inline-processing-enable {
         description "Enable PPM session inline distribution";
         type empty;
       }
       leaf inline-ae-processing-enable {
         description "Enable PPM session inline distribution on AE";
         status deprecated;
         type empty;
       }
       leaf redistribution-timer {
         description "Time to wait after switchover before starting timers";
         type union {
           type string {
             pattern "<.*>|$.*";
           }
           type uint32 {
             range "1 .. 120";
           }
         }
       }
     }
     leaf no-bfd-triggered-local-repair {
       description "Disable bfd triggered local repair";
       type empty;
     }
     leaf enable-sensors {
       description "Enable Sensor for MX/PTX/QFX/EX/ACX";
       type empty;
     }
     leaf maximum-ecmp {
       description "Maximum ECMP limit for nexthops";
       type enumeration {
         enum "16" {
           description "Maximum 16 ECMP routes";
         }
         enum "32" {
           description "Maximum 32 ECMP routes";
         }
         enum "64" {
           description "Maximum 64 ECMP routes";
         }
         enum "96" {
           description "Maximum 96 ECMP routes";
         }
         enum "128" {
           description "Maximum 128 ECMP routes";
         }
         enum "160" {
           description "Maximum 160 ECMP routes";
           junos:must "(!(\"system processes routing force-32-bit\"))";
           junos:must-message "32-bit rpd doesn't support ecmp greater than 128";
         }
         enum "192" {
           description "Maximum 192 ECMP routes";
           junos:must "(!(\"system processes routing force-32-bit\"))";
           junos:must-message "32-bit rpd doesn't support ecmp greater than 128";
         }
         enum "224" {
           description "Maximum 224 ECMP routes";
           junos:must "(!(\"system processes routing force-32-bit\"))";
           junos:must-message "32-bit rpd doesn't support ecmp greater than 128";
         }
         enum "256" {
           description "Maximum 256 ECMP routes";
           junos:must "(!(\"system processes routing force-32-bit\"))";
           junos:must-message "32-bit rpd doesn't support ecmp greater than 128";
         }
         enum "288" {
           description "Maximum 288 ECMP routes";
           junos:must "(!(\"system processes routing force-32-bit\"))";
           junos:must-message "32-bit rpd doesn't support ecmp greater than 128";
         }
         enum "320" {
           description "Maximum 320 ECMP routes";
           junos:must "(!(\"system processes routing force-32-bit\"))";
           junos:must-message "32-bit rpd doesn't support ecmp greater than 128";
         }
         enum "352" {
           description "Maximum 352 ECMP routes";
           junos:must "(!(\"system processes routing force-32-bit\"))";
           junos:must-message "32-bit rpd doesn't support ecmp greater than 128";
         }
         enum "384" {
           description "Maximum 384 ECMP routes";
           junos:must "(!(\"system processes routing force-32-bit\"))";
           junos:must-message "32-bit rpd doesn't support ecmp greater than 128";
         }
         enum "416" {
           description "Maximum 416 ECMP routes";
           junos:must "(!(\"system processes routing force-32-bit\"))";
           junos:must-message "32-bit rpd doesn't support ecmp greater than 128";
         }
         enum "448" {
           description "Maximum 448 ECMP routes";
           junos:must "(!(\"system processes routing force-32-bit\"))";
           junos:must-message "32-bit rpd doesn't support ecmp greater than 128";
         }
         enum "480" {
           description "Maximum 480 ECMP routes";
           junos:must "(!(\"system processes routing force-32-bit\"))";
           junos:must-message "32-bit rpd doesn't support ecmp greater than 128";
         }
         enum "512" {
           description "Maximum 512 ECMP routes";
           junos:must "(!(\"system processes routing force-32-bit\"))";
           junos:must-message "32-bit rpd doesn't support ecmp greater than 128";
         }
       }
     }
     container static {
       description "Static routes";
       uses apply-advanced;
       leaf rib-group {
         description "Routing table group";
         type string;
       }
       container defaults {
         description "Global route options";
         uses apply-advanced;
         choice retain-choice {
           leaf retain {
             description "Always keep route in forwarding table";
             junos:must "(!(\".. resolve\"))";
             junos:must-message "Must not specify resolve with retain";
             type empty;
           }
           leaf no-retain {
             description "Don't always keep route in forwarding table";
             junos:must "(!(\".. resolve\"))";
             junos:must-message "Must not specify resolve with retain";
             type empty;
           }
         }
         choice install-choice {
           leaf install {
             description "Install route into forwarding table";
             type empty;
           }
           leaf no-install {
             description "Don't install route into forwarding table";
             type empty;
           }
         }
         choice readvertise-choice {
           leaf readvertise {
             description "Mark route as eligible to be readvertised";
             type empty;
           }
           leaf no-readvertise {
             description "Don't mark route as eligible to be readvertised";
             type empty;
           }
         }
         choice resolve-choice {
           leaf resolve {
             description "Allow resolution of indirectly connected next hops";
             type empty;
           }
           leaf no-resolve {
             description "Don't allow resolution of indirectly connected next hops";
             type empty;
           }
         }
         choice longest-match-choice {
           leaf longest-match {
             description "Always use longest prefix match to resolve next hops";
             junos:must "(\".. resolve\")";
             junos:must-message "Requires resolve to be configured";
             type empty;
           }
           leaf no-longest-match {
             description "Don't always use longest prefix match to resolve next hops";
             junos:must "(\".. resolve\")";
             junos:must-message "Requires resolve to be configured";
             type empty;
           }
         }
         choice passive_flag {
           case case_1 {
             leaf active {
               description "Remove inactive route from forwarding table";
               type empty;
             }
           }
           case case_2 {
             leaf passive {
               description "Retain inactive route in forwarding table";
               type empty;
             }
           }
         }
         container metric {
           description "Metric value";
           presence "enable metric";
           uses rib_static_metric_type;
         }
         container metric2 {
           description "Metric value 2";
           presence "enable metric2";
           uses rib_static_metric_type;
         }
         container metric3 {
           description "Metric value 3";
           presence "enable metric3";
           uses rib_static_metric_type;
         }
         container metric4 {
           description "Metric value 4";
           presence "enable metric4";
           uses rib_static_metric_type;
         }
         container tag {
           description "Tag string";
           presence "enable tag";
           uses rib_static_metric_type;
         }
         container tag2 {
           description "Tag string 2";
           presence "enable tag2";
           uses rib_static_metric_type;
         }
         container preference {
           description "Preference value";
           presence "enable preference";
           uses rib_static_metric_type;
         }
         container preference2 {
           description "Preference value 2";
           presence "enable preference2";
           uses rib_static_metric_type;
         }
         container color {
           description "Color (preference) value";
           presence "enable color";
           uses rib_static_metric_type;
         }
         container color2 {
           description "Color (preference) value 2";
           presence "enable color2";
           uses rib_static_metric_type;
         }
         leaf-list community {
           ordered-by user;
           description "BGP community identifier";
           type jt:community;
         }
         container as-path {
           description "Autonomous system path";
           uses apply-advanced;
           leaf path {
             description "Autonomous system path";
             type string;
           }
           leaf origin {
             type enumeration {
               enum "igp" {
                 description "Path originated in the local IGP";
               }
               enum "egp" {
                 description "Path originated in another AS";
               }
               enum "incomplete" {
                 description "Path was learned by some other means";
               }
             }
           }
           leaf atomic-aggregate {
             description "Add ATOMIC_AGGREGATE path attribute to route";
             type empty;
           }
           container aggregator {
             presence "enable aggregator";
             description "Add AGGREGATOR path attribute to route";
           }
           leaf as-number {
             description " Autonomous system number in plain number or 'higher 16bits'.'Lower 16 bits' (asdot notation) format";
             type string {
               junos:posix-pattern "^[0-9]+(.[0-9]+)?$";
               junos:pattern-message "Use format 'x' or 'x.y' to specify number 'x' (Range 1 .. 4294967295) or number with higher 2 bytes 'x' (Range 0 .. 65535) and lower 2 bytes 'y' (Range 0 .. 65535) respectively";
             }
           }
           leaf address {
             description "Address of BGP system that formed the route";
             type jt:ipv4addr;
           }
         }
       }
       list route {
         key name;
         ordered-by user;
         description "Static route";
         leaf name {
           type jt:ipprefix;
         }
         uses apply-advanced;
         choice next_hop {
           case case_1 {
             leaf-list next-hop {
               ordered-by user;
               description "Next hop to destination";
               type union {
                 type jt:ipaddr-or-interface;
                 type string {
                   pattern "<.*>|$.*";
                 }
               }
             }
           }
           case case_2 {
             leaf reject {
               description "Drop packets to destination; send ICMP unreachables";
               type empty;
             }
           }
           case case_3 {
             leaf discard {
               description "Drop packets to destination; send no ICMP unreachables";
               type empty;
             }
           }
           case case_4 {
             leaf receive {
               description "Install a receive route for the destination";
               type empty;
             }
           }
           case case_5 {
             leaf next-table {
               description "Next hop to another table";
               type string {
                 junos:posix-pattern "^(((.{0,128})[:](.{1,128})[.]|((.{1,128})[.]))?([a-z]|[0-9]|[-_])+[.]((1?[0-9]{1,2})|(2[0-4][0-9])|(25[0-5])))$";
                 junos:pattern-message "Must match the format [<instance-name>[:<topology-name>].]<family-name>.<rib-id>";
               }
             }
           }
         }
         list qualified-next-hop {
           key name;
           ordered-by user;
           description "Next hop with qualifiers";
           uses qualified_nh_obj;
         }
         leaf backup-pe-group {
           description "Multicast source redundancy group";
           junos:must "(\".. p2mp-lsp-next-hop\")";
           junos:must-message "Backup groups only allowed for static routes with p2mp lsp next-hop";
           type string;
         }
         container bfd-liveness-detection {
           description "Bidirectional Forwarding Detection (BFD) options";
           uses apply-advanced;
           leaf version {
             description "BFD protocol version number";
             default "automatic";
             type enumeration {
               enum "0" {
                 description "BFD version 0 (deprecated)";
               }
               enum "1" {
                 description "BFD version 1";
               }
               enum "automatic" {
                 description "Choose BFD version automatically";
               }
             }
           }
           leaf minimum-interval {
             description "Minimum transmit and receive interval";
             units "milliseconds";
             type union {
               type string {
                 pattern "<.*>|$.*";
               }
               type uint32 {
                 range "1 .. 255000";
               }
             }
           }
           leaf minimum-transmit-interval {
             description "Minimum transmit interval";
             status deprecated;
             units "milliseconds";
             type union {
               type string {
                 pattern "<.*>|$.*";
               }
               type uint32 {
                 range "1 .. 255000";
               }
             }
           }
           leaf minimum-receive-interval {
             description "Minimum receive interval";
             units "milliseconds";
             type union {
               type string {
                 pattern "<.*>|$.*";
               }
               type uint32 {
                 range "1 .. 255000";
               }
             }
           }
           leaf multiplier {
             description "Detection time multiplier";
             default "3";
             type union {
               type string {
                 pattern "<.*>|$.*";
               }
               type uint32 {
                 range "1 .. 255";
               }
             }
           }
           choice adaptation-choice {
             case case_1 {
               leaf no-adaptation {
                 description "Disable adaptation";
                 type empty;
               }
             }
           }
           container transmit-interval {
             description "Transmit-interval options";
             uses apply-advanced;
             leaf minimum-interval {
               description "Minimum transmit interval";
               units "milliseconds";
               type union {
                 type string {
                   pattern "<.*>|$.*";
                 }
                 type uint32 {
                   range "1 .. 255000";
                 }
               }
             }
             leaf threshold {
               description "High transmit interval triggering a trap";
               units "milliseconds";
               type union {
                 type uint32;
                 type string {
                   pattern "<.*>|$.*";
                 }
               }
             }
           }
           container detection-time {
             description "Detection-time options";
             uses apply-advanced;
             leaf threshold {
               description "High detection-time triggering a trap";
               units "milliseconds";
               type union {
                 type uint32;
                 type string {
                   pattern "<.*>|$.*";
                 }
               }
             }
           }
           container authentication {
             description "Authentication options";
             uses apply-advanced;
             leaf key-chain {
               description "Key chain name";
               junos:must "(\".. algorithm\")";
               junos:must-message "May not be configured without algorithm";
               junos:must "(\"security authentication-key-chains key-chain $$\")";
               junos:must-message "Referenced key-chain must be defined";
               type string;
             }
             leaf algorithm {
               description "Algorithm name";
               junos:must "(\".. key-chain\")";
               junos:must-message "May not be configured without key-chain";
               type enumeration {
                 enum "simple-password" {
                   description "Simple password";
                 }
                 enum "keyed-md5" {
                   description "Keyed message Digest 5";
                 }
                 enum "meticulous-keyed-md5" {
                   description "Meticulous keyed message Digest 5";
                 }
                 enum "keyed-sha-1" {
                   description "Keyed secure hash algorithm (SHA1) ";
                 }
                 enum "meticulous-keyed-sha-1" {
                   description "Meticulous keyed secure hash algorithm (SHA1) ";
                 }
               }
             }
             leaf loose-check {
               description "Verify authentication only if authentication is negotiated";
               type empty;
             }
           }
           leaf neighbor {
             description "BFD neighbor address";
             type jt:ipaddr;
           }
           leaf local-address {
             description "BFD local address (for multihop only)";
             type jt:ipaddr;
           }
           leaf holddown-interval {
             description "Time to hold the session-UP notification to the client";
             units "milliseconds";
             type union {
               type string {
                 pattern "<.*>|$.*";
               }
               type uint32 {
                 range "0 .. 255000";
               }
             }
           }
           leaf minimum-receive-ttl {
             description "Minimum receive TTL below which to drop";
             type union {
               type string {
                 pattern "<.*>|$.*";
               }
               type uint8 {
                 range "1 .. 255";
               }
             }
           }
         }
         choice retain-choice {
           leaf retain {
             description "Always keep route in forwarding table";
             junos:must "(!(\".. resolve\"))";
             junos:must-message "Must not specify resolve with retain";
             type empty;
           }
           leaf no-retain {
             description "Don't always keep route in forwarding table";
             junos:must "(!(\".. resolve\"))";
             junos:must-message "Must not specify resolve with retain";
             type empty;
           }
         }
         choice install-choice {
           leaf install {
             description "Install route into forwarding table";
             type empty;
           }
           leaf no-install {
             description "Don't install route into forwarding table";
             type empty;
           }
         }
         choice readvertise-choice {
           leaf readvertise {
             description "Mark route as eligible to be readvertised";
             type empty;
           }
           leaf no-readvertise {
             description "Don't mark route as eligible to be readvertised";
             type empty;
           }
         }
         choice resolve-choice {
           leaf resolve {
             description "Allow resolution of indirectly connected next hops";
             type empty;
           }
           leaf no-resolve {
             description "Don't allow resolution of indirectly connected next hops";
             type empty;
           }
         }
         choice longest-match-choice {
           leaf longest-match {
             description "Always use longest prefix match to resolve next hops";
             junos:must "(\".. resolve\")";
             junos:must-message "Requires resolve to be configured";
             type empty;
           }
           leaf no-longest-match {
             description "Don't always use longest prefix match to resolve next hops";
             junos:must "(\".. resolve\")";
             junos:must-message "Requires resolve to be configured";
             type empty;
           }
         }
         choice passive_flag {
           case case_1 {
             leaf active {
               description "Remove inactive route from forwarding table";
               type empty;
             }
           }
           case case_2 {
             leaf passive {
               description "Retain inactive route in forwarding table";
               type empty;
             }
           }
         }
         container metric {
           description "Metric value";
           presence "enable metric";
           uses rib_static_metric_type;
         }
         container metric2 {
           description "Metric value 2";
           presence "enable metric2";
           uses rib_static_metric_type;
         }
         container metric3 {
           description "Metric value 3";
           presence "enable metric3";
           uses rib_static_metric_type;
         }
         container metric4 {
           description "Metric value 4";
           presence "enable metric4";
           uses rib_static_metric_type;
         }
         container tag {
           description "Tag string";
           presence "enable tag";
           uses rib_static_metric_type;
         }
         container tag2 {
           description "Tag string 2";
           presence "enable tag2";
           uses rib_static_metric_type;
         }
         container preference {
           description "Preference value";
           presence "enable preference";
           uses rib_static_metric_type;
         }
         container preference2 {
           description "Preference value 2";
           presence "enable preference2";
           uses rib_static_metric_type;
         }
         container color {
           description "Color (preference) value";
           presence "enable color";
           uses rib_static_metric_type;
         }
         container color2 {
           description "Color (preference) value 2";
           presence "enable color2";
           uses rib_static_metric_type;
         }
         leaf-list community {
           ordered-by user;
           description "BGP community identifier";
           type jt:community;
         }
         container as-path {
           description "Autonomous system path";
           uses apply-advanced;
           leaf path {
             description "Autonomous system path";
             type string;
           }
           leaf origin {
             type enumeration {
               enum "igp" {
                 description "Path originated in the local IGP";
               }
               enum "egp" {
                 description "Path originated in another AS";
               }
               enum "incomplete" {
                 description "Path was learned by some other means";
               }
             }
           }
           leaf atomic-aggregate {
             description "Add ATOMIC_AGGREGATE path attribute to route";
             type empty;
           }
           container aggregator {
             presence "enable aggregator";
             description "Add AGGREGATOR path attribute to route";
           }
           leaf as-number {
             description " Autonomous system number in plain number or 'higher 16bits'.'Lower 16 bits' (asdot notation) format";
             type string {
               junos:posix-pattern "^[0-9]+(.[0-9]+)?$";
               junos:pattern-message "Use format 'x' or 'x.y' to specify number 'x' (Range 1 .. 4294967295) or number with higher 2 bytes 'x' (Range 0 .. 65535) and lower 2 bytes 'y' (Range 0 .. 65535) respectively";
             }
           }
           leaf address {
             description "Address of BGP system that formed the route";
             type jt:ipv4addr;
           }
         }
         list lsp-next-hop {
           key name;
           ordered-by user;
           description "LSP next hop";
           uses lsp_nh_obj;
         }
         list p2mp-lsp-next-hop {
           key name;
           ordered-by user;
           description "Point-to-multipoint LSP next hop";
           max-elements 1;
           uses lsp_nh_obj;
         }
         container spring-te-lsp-next-hop {
           description "SPRING-TE LSP next hop";
           junos:must "(\"protocols source-packet-routing tunnel-tracking\")";
           junos:must-message "Please enable the tunnel-tracking  under 'protocols source-packet-routing' hierarchy";
           uses springte_lsp_nh_obj;
         }
         container p2mp-ldp-next-hop {
           description "Point-to-multipoint LDP LSP next hop";
           uses p2mp_ldp_lsp_nh_obj;
         }
         list static-lsp-next-hop {
           key name;
           ordered-by user;
           description "Static LSP next hop";
           uses lsp_nh_obj;
         }
       }
       container static-route {
         description "Static route Status";
         leaf bfd-admin-down {
           description "Static route State on BFD ADMIN DOWN";
           type enumeration {
             enum "active" {
               description "Static route will be inactive on bfd-admin-down";
             }
             enum "passive" {
               description "Static route will remain active on bfd-admin-down";
             }
           }
         }
       }
       list iso-route {
         key name;
         ordered-by user;
         description "ISO family static route";
         leaf name {
           type jt:isoprefix;
         }
         uses apply-advanced;
         choice next_hop {
           case case_1 {
             leaf-list next-hop {
               ordered-by user;
               description "Next hop to destination";
               type union {
                 type jt:ipaddr-or-interface;
                 type string {
                   pattern "<.*>|$.*";
                 }
               }
             }
           }
           case case_2 {
             leaf reject {
               description "Drop packets to destination; send ICMP unreachables";
               type empty;
             }
           }
           case case_3 {
             leaf discard {
               description "Drop packets to destination; send no ICMP unreachables";
               type empty;
             }
           }
           case case_4 {
             leaf receive {
               description "Install a receive route for the destination";
               type empty;
             }
           }
           case case_5 {
             leaf next-table {
               description "Next hop to another table";
               type string {
                 junos:posix-pattern "^(((.{0,128})[:](.{1,128})[.]|((.{1,128})[.]))?([a-z]|[0-9]|[-_])+[.]((1?[0-9]{1,2})|(2[0-4][0-9])|(25[0-5])))$";
                 junos:pattern-message "Must match the format [<instance-name>[:<topology-name>].]<family-name>.<rib-id>";
               }
             }
           }
         }
         list qualified-next-hop {
           key name;
           ordered-by user;
           description "Next hop with qualifiers";
           uses qualified_nh_obj;
         }
         leaf backup-pe-group {
           description "Multicast source redundancy group";
           junos:must "(\".. p2mp-lsp-next-hop\")";
           junos:must-message "Backup groups only allowed for static routes with p2mp lsp next-hop";
           type string;
         }
         container bfd-liveness-detection {
           description "Bidirectional Forwarding Detection (BFD) options";
           uses apply-advanced;
           leaf version {
             description "BFD protocol version number";
             default "automatic";
             type enumeration {
               enum "0" {
                 description "BFD version 0 (deprecated)";
               }
               enum "1" {
                 description "BFD version 1";
               }
               enum "automatic" {
                 description "Choose BFD version automatically";
               }
             }
           }
           leaf minimum-interval {
             description "Minimum transmit and receive interval";
             units "milliseconds";
             type union {
               type string {
                 pattern "<.*>|$.*";
               }
               type uint32 {
                 range "1 .. 255000";
               }
             }
           }
           leaf minimum-transmit-interval {
             description "Minimum transmit interval";
             status deprecated;
             units "milliseconds";
             type union {
               type string {
                 pattern "<.*>|$.*";
               }
               type uint32 {
                 range "1 .. 255000";
               }
             }
           }
           leaf minimum-receive-interval {
             description "Minimum receive interval";
             units "milliseconds";
             type union {
               type string {
                 pattern "<.*>|$.*";
               }
               type uint32 {
                 range "1 .. 255000";
               }
             }
           }
           leaf multiplier {
             description "Detection time multiplier";
             default "3";
             type union {
               type string {
                 pattern "<.*>|$.*";
               }
               type uint32 {
                 range "1 .. 255";
               }
             }
           }
           choice adaptation-choice {
             case case_1 {
               leaf no-adaptation {
                 description "Disable adaptation";
                 type empty;
               }
             }
           }
           container transmit-interval {
             description "Transmit-interval options";
             uses apply-advanced;
             leaf minimum-interval {
               description "Minimum transmit interval";
               units "milliseconds";
               type union {
                 type string {
                   pattern "<.*>|$.*";
                 }
                 type uint32 {
                   range "1 .. 255000";
                 }
               }
             }
             leaf threshold {
               description "High transmit interval triggering a trap";
               units "milliseconds";
               type union {
                 type uint32;
                 type string {
                   pattern "<.*>|$.*";
                 }
               }
             }
           }
           container detection-time {
             description "Detection-time options";
             uses apply-advanced;
             leaf threshold {
               description "High detection-time triggering a trap";
               units "milliseconds";
               type union {
                 type uint32;
                 type string {
                   pattern "<.*>|$.*";
                 }
               }
             }
           }
           container authentication {
             description "Authentication options";
             uses apply-advanced;
             leaf key-chain {
               description "Key chain name";
               junos:must "(\".. algorithm\")";
               junos:must-message "May not be configured without algorithm";
               junos:must "(\"security authentication-key-chains key-chain $$\")";
               junos:must-message "Referenced key-chain must be defined";
               type string;
             }
             leaf algorithm {
               description "Algorithm name";
               junos:must "(\".. key-chain\")";
               junos:must-message "May not be configured without key-chain";
               type enumeration {
                 enum "simple-password" {
                   description "Simple password";
                 }
                 enum "keyed-md5" {
                   description "Keyed message Digest 5";
                 }
                 enum "meticulous-keyed-md5" {
                   description "Meticulous keyed message Digest 5";
                 }
                 enum "keyed-sha-1" {
                   description "Keyed secure hash algorithm (SHA1) ";
                 }
                 enum "meticulous-keyed-sha-1" {
                   description "Meticulous keyed secure hash algorithm (SHA1) ";
                 }
               }
             }
             leaf loose-check {
               description "Verify authentication only if authentication is negotiated";
               type empty;
             }
           }
           leaf neighbor {
             description "BFD neighbor address";
             type jt:ipaddr;
           }
           leaf local-address {
             description "BFD local address (for multihop only)";
             type jt:ipaddr;
           }
           leaf holddown-interval {
             description "Time to hold the session-UP notification to the client";
             units "milliseconds";
             type union {
               type string {
                 pattern "<.*>|$.*";
               }
               type uint32 {
                 range "0 .. 255000";
               }
             }
           }
           leaf minimum-receive-ttl {
             description "Minimum receive TTL below which to drop";
             type union {
               type string {
                 pattern "<.*>|$.*";
               }
               type uint8 {
                 range "1 .. 255";
               }
             }
           }
         }
         choice retain-choice {
           leaf retain {
             description "Always keep route in forwarding table";
             junos:must "(!(\".. resolve\"))";
             junos:must-message "Must not specify resolve with retain";
             type empty;
           }
           leaf no-retain {
             description "Don't always keep route in forwarding table";
             junos:must "(!(\".. resolve\"))";
             junos:must-message "Must not specify resolve with retain";
             type empty;
           }
         }
         choice install-choice {
           leaf install {
             description "Install route into forwarding table";
             type empty;
           }
           leaf no-install {
             description "Don't install route into forwarding table";
             type empty;
           }
         }
         choice readvertise-choice {
           leaf readvertise {
             description "Mark route as eligible to be readvertised";
             type empty;
           }
           leaf no-readvertise {
             description "Don't mark route as eligible to be readvertised";
             type empty;
           }
         }
         choice resolve-choice {
           leaf resolve {
             description "Allow resolution of indirectly connected next hops";
             type empty;
           }
           leaf no-resolve {
             description "Don't allow resolution of indirectly connected next hops";
             type empty;
           }
         }
         choice longest-match-choice {
           leaf longest-match {
             description "Always use longest prefix match to resolve next hops";
             junos:must "(\".. resolve\")";
             junos:must-message "Requires resolve to be configured";
             type empty;
           }
           leaf no-longest-match {
             description "Don't always use longest prefix match to resolve next hops";
             junos:must "(\".. resolve\")";
             junos:must-message "Requires resolve to be configured";
             type empty;
           }
         }
         choice passive_flag {
           case case_1 {
             leaf active {
               description "Remove inactive route from forwarding table";
               type empty;
             }
           }
           case case_2 {
             leaf passive {
               description "Retain inactive route in forwarding table";
               type empty;
             }
           }
         }
         container metric {
           description "Metric value";
           presence "enable metric";
           uses rib_static_metric_type;
         }
         container metric2 {
           description "Metric value 2";
           presence "enable metric2";
           uses rib_static_metric_type;
         }
         container metric3 {
           description "Metric value 3";
           presence "enable metric3";
           uses rib_static_metric_type;
         }
         container metric4 {
           description "Metric value 4";
           presence "enable metric4";
           uses rib_static_metric_type;
         }
         container tag {
           description "Tag string";
           presence "enable tag";
           uses rib_static_metric_type;
         }
         container tag2 {
           description "Tag string 2";
           presence "enable tag2";
           uses rib_static_metric_type;
         }
         container preference {
           description "Preference value";
           presence "enable preference";
           uses rib_static_metric_type;
         }
         container preference2 {
           description "Preference value 2";
           presence "enable preference2";
           uses rib_static_metric_type;
         }
         container color {
           description "Color (preference) value";
           presence "enable color";
           uses rib_static_metric_type;
         }
         container color2 {
           description "Color (preference) value 2";
           presence "enable color2";
           uses rib_static_metric_type;
         }
         leaf-list community {
           ordered-by user;
           description "BGP community identifier";
           type jt:community;
         }
         container as-path {
           description "Autonomous system path";
           uses apply-advanced;
           leaf path {
             description "Autonomous system path";
             type string;
           }
           leaf origin {
             type enumeration {
               enum "igp" {
                 description "Path originated in the local IGP";
               }
               enum "egp" {
                 description "Path originated in another AS";
               }
               enum "incomplete" {
                 description "Path was learned by some other means";
               }
             }
           }
           leaf atomic-aggregate {
             description "Add ATOMIC_AGGREGATE path attribute to route";
             type empty;
           }
           container aggregator {
             presence "enable aggregator";
             description "Add AGGREGATOR path attribute to route";
           }
           leaf as-number {
             description " Autonomous system number in plain number or 'higher 16bits'.'Lower 16 bits' (asdot notation) format";
             type string {
               junos:posix-pattern "^[0-9]+(.[0-9]+)?$";
               junos:pattern-message "Use format 'x' or 'x.y' to specify number 'x' (Range 1 .. 4294967295) or number with higher 2 bytes 'x' (Range 0 .. 65535) and lower 2 bytes 'y' (Range 0 .. 65535) respectively";
             }
           }
           leaf address {
             description "Address of BGP system that formed the route";
             type jt:ipv4addr;
           }
         }
         list lsp-next-hop {
           key name;
           ordered-by user;
           description "LSP next hop";
           uses lsp_nh_obj;
         }
         list p2mp-lsp-next-hop {
           key name;
           ordered-by user;
           description "Point-to-multipoint LSP next hop";
           max-elements 1;
           uses lsp_nh_obj;
         }
         container spring-te-lsp-next-hop {
           description "SPRING-TE LSP next hop";
           junos:must "(\"protocols source-packet-routing tunnel-tracking\")";
           junos:must-message "Please enable the tunnel-tracking  under 'protocols source-packet-routing' hierarchy";
           uses springte_lsp_nh_obj;
         }
         container p2mp-ldp-next-hop {
           description "Point-to-multipoint LDP LSP next hop";
           uses p2mp_ldp_lsp_nh_obj;
         }
       }
       list route-target-filter {
         key name;
         ordered-by user;
         description "Route-target-filter route";
         leaf name {
           type string {
             length "1 .. 47";
             junos:posix-pattern "^[0-9.]{1,15}L?:[0-9]{1,10}/([0-9]|[2-5][0-9]|6[0-4])$";
             junos:pattern-message "Use format 'x:y/len' where 'x' is an AS number followed by an optional 'L' (To indicate 4 byte AS), or an IP address and 'y' is a number. e.g. 123456L:100 and len is a prefix length from 0 to 64";
           }
         }
         uses apply-advanced;
         leaf-list neighbor {
           ordered-by user;
           description "BGP peers for filter";
           type jt:ipaddr-scoped;
         }
         leaf-list group {
           ordered-by user;
           description "BGP groups for filter";
           type string;
         }
         leaf local {
           description "Locally originated filter";
           type empty;
         }
       }
     }
     list martians {
       key "address choice-ident choice-value";
       ordered-by user;
       description "Invalid routes";
       uses martian_type;
     }
     container aggregate {
       description "Coalesced routes";
       uses rib_aggregate_type;
     }
     container generate {
       description "Route of last resort";
       uses rib_aggregate_type;
     }
     choice maximum-paths-type {
       case case_1 {
         container maximum-routes {
           description "Maximum number of routes";
           status deprecated;
           leaf limit {
             description "Maximum number of routes";
             type union {
               type string {
                 pattern "<.*>|$.*";
               }
               type uint32 {
                 range "1 .. 4294967295";
               }
             }
           }
           choice log_type {
             case case_1 {
               leaf threshold {
                 description "Percentage of limit at which to start generating warnings";
                 type union {
                   type string {
                     pattern "<.*>|$.*";
                   }
                   type uint32 {
                     range "1 .. 100";
                   }
                 }
               }
             }
             case case_2 {
               leaf log-only {
                 description "Generate warning messages only";
                 type empty;
               }
             }
           }
           leaf log-interval {
             description "Minimum interval between log messages";
             units "seconds";
             type union {
               type string {
                 pattern "<.*>|$.*";
               }
               type uint32 {
                 range "5 .. 86400";
               }
             }
           }
         }
       }
       case case_2 {
         container maximum-paths {
           description "Maximum number of paths";
           leaf limit {
             description "Maximum number of paths";
             type union {
               type string {
                 pattern "<.*>|$.*";
               }
               type uint32 {
                 range "1 .. 4294967295";
               }
             }
           }
           choice log_type {
             case case_1 {
               leaf threshold {
                 description "Percentage of limit at which to start generating warnings";
                 type union {
                   type string {
                     pattern "<.*>|$.*";
                   }
                   type uint32 {
                     range "1 .. 100";
                   }
                 }
               }
             }
             case case_2 {
               leaf log-only {
                 description "Generate warning messages only";
                 type empty;
               }
             }
           }
           leaf log-interval {
             description "Minimum interval between log messages";
             units "seconds";
             type union {
               type string {
                 pattern "<.*>|$.*";
               }
               type uint32 {
                 range "5 .. 86400";
               }
             }
           }
         }
       }
     }
     container maximum-prefixes {
       description "Maximum number of prefixes";
       leaf limit {
         description "Maximum number of prefixes";
         type union {
           type string {
             pattern "<.*>|$.*";
           }
           type uint32 {
             range "1 .. 4294967295";
           }
         }
       }
       choice log_type {
         case case_1 {
           leaf threshold {
             description "Percentage of limit at which to start generating warnings";
             type union {
               type string {
                 pattern "<.*>|$.*";
               }
               type uint32 {
                 range "1 .. 100";
               }
             }
           }
         }
         case case_2 {
           leaf log-only {
             description "Generate warning messages only";
             type empty;
           }
         }
       }
       leaf log-interval {
         description "Minimum interval between log messages";
         units "seconds";
         type union {
           type string {
             pattern "<.*>|$.*";
           }
           type uint32 {
             range "5 .. 86400";
           }
         }
       }
     }
     container multipath {
       presence "enable multipath";
       description "Protocol-independent load balancing";
       uses apply-advanced;
       container vpn-unequal-cost {
         presence "enable vpn-unequal-cost";
         description "Include VPN routes with unequal IGP metrics";
         leaf equal-external-internal {
           description "Include external and internal VPN routes";
           type empty;
         }
       }
       leaf as-path-compare {
         description "Compare AS path sequences in addition to AS path length";
         type empty;
       }
       leaf preserve-nexthop-hierarchy {
         description "Force multipath to create List nexthop";
         type empty;
       }
     }
     container policy-multipath {
       description "Policy based multipath";
       uses apply-advanced;
       leaf-list policy {
         ordered-by user;
         description "Import policy to create policy based multipath";
         type jt:policy-algebra;
       }
       container traceoptions {
         description "Trace options";
         uses apply-advanced;
         container file {
           description "Trace file options";
           leaf filename {
             description "Name of file in which to write trace information";
             type string {
               length "1 .. 1024";
               junos:posix-pattern "![/ %]";
               junos:pattern-message "Must not contain '/', % or a space";
             }
           }
           leaf replace {
             description "Replace trace file rather than appending to it";
             status deprecated;
             type empty;
           }
           leaf size {
             description "Maximum trace file size";
             type string;
           }
           leaf files {
             description "Maximum number of trace files";
             default "10";
             type union {
               type string {
                 pattern "<.*>|$.*";
               }
               type uint32 {
                 range "2 .. 1000";
               }
             }
           }
           leaf no-stamp {
             description "Do not timestamp trace file";
             status deprecated;
             type empty;
           }
           choice world-readable-choice {
             leaf world-readable {
               description "Allow any user to read the log file";
               type empty;
             }
             leaf no-world-readable {
               description "Don't allow any user to read the log file";
               type empty;
             }
           }
         }
         list flag {
           key name;
           ordered-by user;
           description "Tracing parameters";
           leaf name {
             type enumeration {
               enum "route" {
                 description "Policy-multipath route tracing.";
               }
             }
           }
           leaf send {
             description "Trace transmitted packets";
             type empty;
           }
           leaf receive {
             description "Trace received packets";
             type empty;
           }
           leaf detail {
             description "Trace detailed information";
             type empty;
           }
           leaf disable {
             description "Disable this trace flag";
             type empty;
           }
         }
       }
     }
     container protect {
       description "Protocol-independent protection";
       leaf core {
         description "Protect against unreachability to service-edge router";
         type empty;
       }
     }
     container access {
       description "Access routes";
       uses apply-advanced;
       list route {
         key name;
         ordered-by user;
         description "Access route";
         leaf name {
           description "IP address of destination";
           type jt:ipprefix;
         }
         uses apply-advanced;
         leaf-list next-hop {
           ordered-by user;
           description "Next hop to destination";
           type union {
             type jt:ipaddr-or-interface;
             type string {
               pattern "<.*>|$.*";
             }
           }
         }
         list qualified-next-hop {
           key name;
           ordered-by user;
           description "Next hop with qualifiers";
           uses qualified_nh_obj;
         }
         leaf metric {
           description "Metric value";
           type union {
             type string {
               pattern "<.*>|$.*";
             }
             type uint32 {
               range "1 .. 255";
             }
           }
         }
         leaf preference {
           description "Preference value";
           type union {
             type uint32;
             type string {
               pattern "<.*>|$.*";
             }
           }
         }
         leaf tag {
           description "Tag string";
           type union {
             type uint32;
             type string {
               pattern "<.*>|$.*";
             }
           }
         }
         leaf tag2 {
           description "Tag2 string";
           type union {
             type uint32;
             type string {
               pattern "<.*>|$.*";
             }
           }
         }
       }
     }
     container access-internal {
       description "Access-internal routes";
       uses apply-advanced;
       list route {
         key name;
         ordered-by user;
         description "Access-internal route";
         leaf name {
           description "IP address and optional prefix length of destination";
           type jt:ipprefix;
         }
         uses apply-advanced;
         leaf-list next-hop {
           ordered-by user;
           description "Next hop to destination";
           type union {
             type jt:ipaddr-or-interface;
             type string {
               pattern "<.*>|$.*";
             }
           }
         }
         list qualified-next-hop {
           key name;
           ordered-by user;
           description "Next hop with qualifiers";
           uses qualified_nh_obj;
         }
       }
     }
     container bgp-static {
       description "Routes for BGP static advertisements";
       uses apply-advanced;
       list route {
         key name;
         ordered-by user;
         description "BGP-static route";
         leaf name {
           description "IP address and optional prefix length of destination";
           type jt:ipprefix;
         }
         uses apply-advanced;
         container metric {
           description "Metric value";
           presence "enable metric";
           uses rib_static_metric_type;
         }
         container metric2 {
           description "Metric value 2";
           presence "enable metric2";
           uses rib_static_metric_type;
         }
         container metric3 {
           description "Metric value 3";
           presence "enable metric3";
           uses rib_static_metric_type;
         }
         container metric4 {
           description "Metric value 4";
           presence "enable metric4";
           uses rib_static_metric_type;
         }
         container tag {
           description "Tag string";
           presence "enable tag";
           uses rib_static_metric_type;
         }
         container tag2 {
           description "Tag string 2";
           presence "enable tag2";
           uses rib_static_metric_type;
         }
         container preference {
           description "Preference value";
           presence "enable preference";
           uses rib_static_metric_type;
         }
         container preference2 {
           description "Preference value 2";
           presence "enable preference2";
           uses rib_static_metric_type;
         }
         container color {
           description "Color (preference) value";
           presence "enable color";
           uses rib_static_metric_type;
         }
         container color2 {
           description "Color (preference) value 2";
           presence "enable color2";
           uses rib_static_metric_type;
         }
         leaf-list community {
           ordered-by user;
           description "BGP community identifier";
           type jt:community;
         }
         container as-path {
           description "Autonomous system path";
           uses apply-advanced;
           leaf path {
             description "Autonomous system path";
             type string;
           }
           leaf origin {
             type enumeration {
               enum "igp" {
                 description "Path originated in the local IGP";
               }
               enum "egp" {
                 description "Path originated in another AS";
               }
               enum "incomplete" {
                 description "Path was learned by some other means";
               }
             }
           }
           leaf atomic-aggregate {
             description "Add ATOMIC_AGGREGATE path attribute to route";
             type empty;
           }
           container aggregator {
             presence "enable aggregator";
             description "Add AGGREGATOR path attribute to route";
           }
           leaf as-number {
             description " Autonomous system number in plain number or 'higher 16bits'.'Lower 16 bits' (asdot notation) format";
             type string {
               junos:posix-pattern "^[0-9]+(.[0-9]+)?$";
               junos:pattern-message "Use format 'x' or 'x.y' to specify number 'x' (Range 1 .. 4294967295) or number with higher 2 bytes 'x' (Range 0 .. 65535) and lower 2 bytes 'y' (Range 0 .. 65535) respectively";
             }
           }
           leaf address {
             description "Address of BGP system that formed the route";
             type jt:ipv4addr;
           }
         }
       }
     }
     list rib-groups {
       key name;
       ordered-by user;
       description "Group of routing tables";
       uses rpd_rib_group_type;
     }
     leaf route-record {
       description "Enable route recording";
       type empty;
     }
     container localized-fib {
       presence "enable localized-fib";
       junos:must "(!(\".. .. .. .. .. logical-systems\"))";
       junos:must-message "localized-fib cannot be configured on logical systems";
       junos:must "(!(\"virtual-chassis\"))";
       junos:must-message "localized-fib cannot be configured on virtual-chassis";
       junos:must "(any \"chassis fpc <*> vpn-localization\")";
       junos:must-message "To configure localized-fib, at least one core facing FPC must be configured at 'chassis fpc <*> vpn-localization'";
       junos:must "(\".. .. instance-type vrf\")";
       junos:must-message "localized-fib is valid only for instance-type vrf";
       description "Localize vrf routing-instance routes to specific FPC hardware";
       uses apply-advanced;
       leaf-list fpc-slot {
         ordered-by user;
         description "Local FPC list";
         type union {
           type uint32;
           type string {
             pattern "<.*>|$.*";
           }
         }
       }
     }
     leaf-list instance-import {
       ordered-by user;
       description "Import policy for instance RIBs";
       type jt:policy-algebra;
     }
     leaf-list instance-export {
       ordered-by user;
       description "Export policy for instance RIBs";
       type jt:policy-algebra;
     }
     container auto-export {
       presence "enable auto-export";
       description "Export routes between routing instances";
       uses apply-advanced;
       choice enable-disable {
         case case_1 {
           leaf disable {
             description "Disable auto-export";
             type empty;
           }
         }
       }
       container traceoptions {
         description "Trace options";
         uses apply-advanced;
         container file {
           description "Trace file options";
           leaf filename {
             description "Name of file in which to write trace information";
             type string {
               length "1 .. 1024";
               junos:posix-pattern "![/ %]";
               junos:pattern-message "Must not contain '/', % or a space";
             }
           }
           leaf replace {
             description "Replace trace file rather than appending to it";
             status deprecated;
             type empty;
           }
           leaf size {
             description "Maximum trace file size";
             type string;
           }
           leaf files {
             description "Maximum number of trace files";
             default "10";
             type union {
               type string {
                 pattern "<.*>|$.*";
               }
               type uint32 {
                 range "2 .. 1000";
               }
             }
           }
           leaf no-stamp {
             description "Do not timestamp trace file";
             status deprecated;
             type empty;
           }
           choice world-readable-choice {
             leaf world-readable {
               description "Allow any user to read the log file";
               type empty;
             }
             leaf no-world-readable {
               description "Don't allow any user to read the log file";
               type empty;
             }
           }
         }
         list flag {
           key name;
           ordered-by user;
           description "Tracing parameters";
           leaf name {
             type enumeration {
               enum "export" {
                 description "Export processing";
               }
               enum "route" {
                 description "Trace routing information";
               }
               enum "normal" {
                 description "Trace normal events";
               }
               enum "general" {
                 description "Trace general events";
               }
               enum "state" {
                 description "Trace state transitions";
               }
               enum "policy" {
                 description "Trace policy processing";
               }
               enum "task" {
                 description "Trace routing protocol task processing";
               }
               enum "timer" {
                 description "Trace routing protocol timer processing";
               }
               enum "all" {
                 description "Trace everything";
               }
             }
           }
           leaf send {
             description "Trace transmitted packets";
             type empty;
           }
           leaf receive {
             description "Trace received packets";
             type empty;
           }
           leaf detail {
             description "Trace detailed information";
             type empty;
           }
           leaf disable {
             description "Disable this trace flag";
             type empty;
           }
         }
       }
       container family {
         container inet {
           description "IPv4 parameters";
           uses export-af-obj;
         }
         container inet6 {
           description "IPv6 parameters";
           uses export-af-obj;
         }
         container iso {
           description "ISO parameters";
           uses export-af-obj;
         }
       }
     }
     container transport-class {
       presence "enable transport-class";
       junos:must "(\"routing-options route-distinguisher-id\")";
       junos:must-message "transport classes use auto-rd. Please configure route-distinguisher-id";
       description "Transport layer options";
       uses apply-advanced;
       leaf auto-create {
         description "Auto create on color discovery";
         type empty;
       }
       container fallback {
         description "Service routes resolution fallback";
         uses apply-advanced;
         leaf none {
           description "Resolve associated service-routes using this transport-class tunnels only";
           type empty;
         }
       }
       list name {
         key name;
         ordered-by user;
         description "Transport layer collecting Tunnels with similar characteristics";
         leaf name {
           description "Transport class name";
           type string;
         }
         uses apply-advanced;
         leaf color {
           description "Color(0..4294967295). This auto derives the Mapping Community and Route Target";
           type union {
             type uint32;
             type string {
               pattern "<.*>|$.*";
             }
           }
         }
         container fallback {
           description "Service routes resolution fallback";
           uses apply-advanced;
           leaf none {
             description "Resolve associated service-routes using this transport-class tunnels only";
             type empty;
           }
         }
         container tunnel-egress {
           description "Tunnel-Egress endpoint origination";
           uses apply-advanced;
           list end-point {
             key name;
             ordered-by user;
             description "Configure Tunnel-Egress endpoints";
             leaf name {
               description "Address of Tunnel egress endpoint";
               type jt:ipaddr;
             }
             uses apply-advanced;
             leaf-list import {
               ordered-by user;
               description "Import policy to set attributes";
               type jt:policy-algebra;
             }
           }
         }
       }
     }
     container dynamic-tunnels {
       description "Dynamic tunnel definitions";
       uses apply-advanced;
       list tunnel-attributes {
         key name;
         ordered-by user;
         description "Dynamic tunnel attributes definition";
         leaf name {
           description "Dynamic Tunnel attribute name";
           type string {
             junos:posix-pattern "![^a-zA-Z0-9_-]|(^(all|.{64,})$)";
             junos:pattern-message "Tunnel attribute name is a string consisting of up to 63 letters, numbers, dashes, and underscores";
           }
         }
         uses apply-advanced;
         leaf dynamic-tunnel-source-prefix {
           description "Tunnel source address";
           junos:must "(\".. dynamic-tunnel-type V4oV6\")";
           junos:must-message "Tunnel source address, only valid for V4oV6 tunnel type";
           type jt:ipaddr;
         }
         leaf dynamic-tunnel-type {
           type enumeration {
             enum "GRE" {
               description "Tunnel type GRE";
             }
             enum "V4oV6" {
               description "Tunnel type is IPV4oIPV6";
             }
             enum "UDP" {
               description "Tunnel type UDP";
             }
             enum "BGP-SIGNAL" {
               description "Tunnel type BGP-SIGNAL";
             }
           }
         }
         leaf dynamic-tunnel-mtu {
           description "Dynamic Tunnel MTU value";
           junos:must "(\".. dynamic-tunnel-type V4oV6\")";
           junos:must-message "Only supported for tunnel type V4oV6";
           type union {
             type string {
               pattern "<.*>|$.*";
             }
             type uint32 {
               range "296 .. 9232";
             }
           }
         }
         leaf dynamic-tunnel-gre-key {
           description "RFC 2890 Dynamic Tunnel GRE Key";
           junos:must "(\".. dynamic-tunnel-type GRE\")";
           junos:must-message "Only supported for tunnel type GRE";
           type union {
             type string {
               pattern "<.*>|$.*";
             }
             type uint32 {
               range "1 .. 4294967295";
             }
           }
         }
         leaf dynamic-tunnel-anchor-pfe {
           description "Dynamic Tunnel anchor PFE name of format pfe-x/y/z";
           type string {
             junos:posix-pattern "^(pfe-)[1-9]?[0-9]/[1-9]?[0-9]/[1-9]?[0-9]$";
             junos:pattern-message "Must be a PFE interface of form pfe-x/y/z";
           }
         }
         leaf dynamic-tunnel-anti-spoof {
           junos:must "(\".. dynamic-tunnel-type V4oV6\")";
           junos:must-message "Only supported for tunnel type V4oV6";
           type enumeration {
             enum "on" {
               description "Enable antispoofing check. Default is enabled";
             }
             enum "off" {
               description "Disable antispoofing check";
             }
           }
         }
         leaf dynamic-tunnel-reassembly {
           junos:must "(\".. dynamic-tunnel-type V4oV6\")";
           junos:must-message "Only supported for tunnel type V4oV6";
           type enumeration {
             enum "on" {
               description "Enable reassembly check. Default is disabled";
             }
             enum "off" {
               description "Disable reassembly check";
             }
           }
         }
       }
       list forwarding-rib {
         key name;
         ordered-by user;
         description "Forwarding routing table for dynamic-tunnel";
         leaf name {
           description "Routing table name";
           type string;
         }
         uses apply-advanced;
         leaf-list inet-import {
           ordered-by user;
           description "Import policy for V4 dynamic-tunnel";
           type jt:policy-algebra;
         }
       }
       container statistics {
         description "Fetch traffic statistics for  dynamic tunnels";
         uses apply-advanced;
         leaf interval {
           description "Time after which statistics has to be fetched";
           units "seconds";
           type union {
             type string {
               pattern "<.*>|$.*";
             }
             type uint16 {
               range "1 .. 65535";
             }
           }
         }
       }
       container traceoptions {
         description "Trace options";
         uses apply-advanced;
         container file {
           description "Trace file options";
           leaf filename {
             description "Name of file in which to write trace information";
             type string {
               length "1 .. 1024";
               junos:posix-pattern "![/ %]";
               junos:pattern-message "Must not contain '/', % or a space";
             }
           }
           leaf replace {
             description "Replace trace file rather than appending to it";
             status deprecated;
             type empty;
           }
           leaf size {
             description "Maximum trace file size";
             type string;
           }
           leaf files {
             description "Maximum number of trace files";
             default "10";
             type union {
               type string {
                 pattern "<.*>|$.*";
               }
               type uint32 {
                 range "2 .. 1000";
               }
             }
           }
           leaf no-stamp {
             description "Do not timestamp trace file";
             status deprecated;
             type empty;
           }
           choice world-readable-choice {
             leaf world-readable {
               description "Allow any user to read the log file";
               type empty;
             }
             leaf no-world-readable {
               description "Don't allow any user to read the log file";
               type empty;
             }
           }
         }
         list flag {
           key name;
           ordered-by user;
           description "Tracing parameters";
           leaf name {
             type enumeration {
               enum "kernel" {
                 description "Trace kernel communication";
               }
               enum "tunnel" {
                 description "Trace tunnel addition, change, or deletion";
               }
               enum "task" {
                 description "Trace task or job processing";
               }
               enum "tunnel-event" {
                 description "Trace create, delete, up, down event for nh based tunnel";
               }
               enum "flash-event" {
                 description "Trace flash event for tunnel forwarding route";
               }
               enum "stats-job" {
                 description "Trace taffic statistics job related stuff";
               }
               enum "all" {
                 description "Trace everything";
               }
             }
           }
           leaf send {
             description "Trace transmitted packets";
             type empty;
           }
           leaf receive {
             description "Trace received packets";
             type empty;
           }
           leaf detail {
             description "Trace detailed information";
             type empty;
           }
           leaf disable {
             description "Disable this trace flag";
             type empty;
           }
         }
       }
       leaf v4ov6 {
         description "Enable dynamic tunnel V4oV6 mode";
         type enumeration {
           enum "ipv6-anycast-source-duplication" {
             description "Enable full resolved nh base source-tunnel";
           }
         }
       }
       leaf gre {
         description "Enable dynamic gre tunnel mode";
         type enumeration {
           enum "next-hop-based-tunnel" {
             description "Enable nh base dynamic-tunnel";
           }
         }
       }
       container signal-tunnel-preference {
         presence "enable signal-tunnel-preference";
         description "Set tunnel preference for signalled tunnels";
         uses apply-advanced;
         leaf gre {
           description "Preference of GRE signalled tunnels";
           type union {
             type string {
               pattern "<.*>|$.*";
             }
             type uint32 {
               range "1 .. 10";
             }
           }
         }
         leaf udp {
           description "Preference of UDP signalled tunnels";
           type union {
             type string {
               pattern "<.*>|$.*";
             }
             type uint32 {
               range "1 .. 10";
             }
           }
         }
         leaf ipip {
           description "Preference of IPIP signalled tunnels";
           type union {
             type string {
               pattern "<.*>|$.*";
             }
             type uint32 {
               range "1 .. 10";
             }
           }
         }
       }
       list dynamic-tunnel {
         key name;
         ordered-by user;
         uses dynamic_tunnel_type;
       }
     }
     list interface {
       key name;
       ordered-by user;
       description "Direct/Host route FRR protection";
       leaf name {
         description "Interface name";
         type union {
           type jt:interface-name;
           type string {
             pattern "<.*>|$.*";
           }
         }
       }
       uses apply-advanced;
       leaf arp-prefix-limit {
         description "Max ARP/Host FRR routes allowed";
         type union {
           type string {
             pattern "<.*>|$.*";
           }
           type uint32 {
             range "1 .. 10000";
           }
         }
       }
       leaf supplementary-blackout-timer {
         description "ARP plimit blackout timer = kernel ARP timeout + supplementary-blackout-timer minutes.";
         type union {
           type string {
             pattern "<.*>|$.*";
           }
           type uint32 {
             range "1 .. 15";
           }
         }
       }
       choice protection-type {
         case case_1 {
           leaf link-protection {
             description "Protect interface from link faults only";
             type empty;
           }
         }
       }
     }
     container host-fast-reroute {
       presence "enable host-fast-reroute";
       description "Host Fast Re-route global values. Applies to all host FRR profiles.";
       uses apply-advanced;
       leaf global-arp-prefix-limit {
         description "Max ARP/Host FRR routes allowed per protected IFL";
         type union {
           type string {
             pattern "<.*>|$.*";
           }
           type uint32 {
             range "1 .. 10000";
           }
         }
       }
       leaf global-supplementary-blackout-timer {
         description "ARP plimit global blackout timer = kernel ARP timeout + global-supplementary-blackout-timer minutes.";
         type union {
           type string {
             pattern "<.*>|$.*";
           }
           type uint32 {
             range "1 .. 15";
           }
         }
       }
     }
     leaf warm-standby {
       description "Enable warm-standby";
       junos:must "(!(\"routing-options nonstop-routing\"))";
       junos:must-message "Warm standby and Nonstop routing cannot be enabled simultaneously";
       junos:must "(\"system commit synchronize\")";
       junos:must-message "Synchronized commits must be configured with warm-standby";
       junos:must "(\"chassis redundancy graceful-switchover\")";
       junos:must-message "Graceful switchover needs to be configured";
       type empty;
     }
     leaf nonstop-routing {
       description "Enable nonstop routing";
       junos:must "(\"system commit synchronize\")";
       junos:must-message "Synchronized commits must be configured with nonstop-routing";
       junos:must "(\"chassis redundancy graceful-switchover\")";
       junos:must-message "Graceful switchover needs to be configured";
       type empty;
     }
     container nonstop-routing-options {
       presence "enable nonstop-routing-options";
       description "Nonstop routing options";
       uses apply-advanced;
       leaf precision-timers-max-period {
         description "Set Max period for precision timer support from kernel after switchover";
         type union {
           type string {
             pattern "<.*>|$.*";
           }
           type uint32 {
             range "60 .. 1800";
           }
         }
       }
     }
     leaf nsr-phantom-holdtime {
       description "Set NSR phantom route hold time";
       junos:must "(\"routing-options nonstop-routing\")";
       junos:must-message "Nonstop routing must be enabled";
       type union {
         type string {
           pattern "<.*>|$.*";
         }
         type uint32 {
           range "0 .. 10000";
         }
       }
     }
     list srlg {
       key name;
       ordered-by user;
       description "SRLG configuration";
       leaf name {
         description "Group name";
         type string {
           length "1 .. 64";
         }
       }
       uses apply-advanced;
       leaf srlg-value {
         description "Group id";
         type union {
           type string {
             pattern "<.*>|$.*";
           }
           type uint32 {
             range "1 .. 4294967295";
           }
         }
       }
       leaf srlg-cost {
         description "Cost value";
         type union {
           type string {
             pattern "<.*>|$.*";
           }
           type uint32 {
             range "1 .. 65535";
           }
         }
       }
     }
     container admin-groups-extended-range {
       description "Extended administrative groups range";
       uses apply-advanced;
       leaf minimum {
         description "Minimum value of the range for extended administrative groups";
         type union {
           type string {
             pattern "<.*>|$.*";
           }
           type uint32 {
             range "32 .. 4294967295";
           }
         }
       }
       leaf maximum {
         description "Maximum value of the range for extended administrative groups";
         type union {
           type string {
             pattern "<.*>|$.*";
           }
           type uint32 {
             range "32 .. 4294967295";
           }
         }
       }
     }
     list admin-groups-extended {
       key name;
       ordered-by user;
       description "Extended administrative groups";
       junos:must "(\".. admin-groups-extended-range\")";
       junos:must-message "admin-groups-extended-range must be configured with admin-groups-extended";
       leaf name {
         description "Group name (Maximum length 64)";
         type string {
           length "1 .. 64";
         }
       }
       uses apply-advanced;
       leaf group-value {
         description "Group id";
         type union {
           type string {
             pattern "<.*>|$.*";
           }
           type uint32 {
             range "32 .. 4294967295";
           }
         }
       }
     }
     leaf lsp-telemetry {
       description "Turn on Jvision LSP telemetry";
       type empty;
     }
     container l3vpn-composite-nexthop {
       presence "enable l3vpn-composite-nexthop";
       junos:must "(!(\".. forwarding-table chained-composite-next-hop ingress l3vpn\"))";
       junos:must-message "Deprecated/duplicate option configured; use [forwarding-table chained-composite-next-hop ingress l3vpn] only";
       description "Enable composite nexthop for l3vpn";
       status deprecated;
       uses apply-advanced;
     }
     container source-routing {
       description "Source-routing options";
       uses apply-advanced;
       leaf ip {
         description "Enable IP Source Routing";
         type empty;
       }
       leaf ipv6 {
         description "Enable Type 0 RouteHeader processing";
         type empty;
       }
     }
     container forwarding-table {
       uses forwarding-table-type;
     }
     container fate-sharing {
       description "Fate-sharing links or nodes database";
       uses apply-advanced;
       list group {
         key name;
         ordered-by user;
         description "Group of objects sharing common characteristics";
         leaf name {
           description "Name of object groups sharing the same fate";
           type string {
             junos:posix-pattern "^.{1,32}$";
             junos:pattern-message "Must be a string of <= 32 characters";
           }
         }
         uses apply-advanced;
         leaf cost {
           description "Cost value";
           type union {
             type string {
               pattern "<.*>|$.*";
             }
             type uint32 {
               range "1 .. 65535";
             }
           }
         }
         leaf use-for-post-convergence-lfa {
           description "Use this fate-sharing group as a constraint for post-convergence-lfa";
           type empty;
         }
         list from {
           key name;
           uses fate_sharing_links;
         }
       }
     }
     container multicast {
       description "Global multicast options";
       uses apply-advanced;
       container traceoptions {
         description "Global multicast trace options";
         uses apply-advanced;
         container file {
           description "Trace file options";
           leaf filename {
             description "Name of file in which to write trace information";
             type string {
               length "1 .. 1024";
               junos:posix-pattern "![/ %]";
               junos:pattern-message "Must not contain '/', % or a space";
             }
           }
           leaf replace {
             description "Replace trace file rather than appending to it";
             status deprecated;
             type empty;
           }
           leaf size {
             description "Maximum trace file size";
             type string;
           }
           leaf files {
             description "Maximum number of trace files";
             default "10";
             type union {
               type string {
                 pattern "<.*>|$.*";
               }
               type uint32 {
                 range "2 .. 1000";
               }
             }
           }
           leaf no-stamp {
             description "Do not timestamp trace file";
             status deprecated;
             type empty;
           }
           choice world-readable-choice {
             leaf world-readable {
               description "Allow any user to read the log file";
               type empty;
             }
             leaf no-world-readable {
               description "Don't allow any user to read the log file";
               type empty;
             }
           }
         }
         list flag {
           key name;
           ordered-by user;
           description "Tracing parameters";
           leaf name {
             type enumeration {
               enum "parse" {
                 description "Trace configuration parsing";
               }
               enum "config-internal" {
                 description "Trace configuration internals";
               }
               enum "route" {
                 description "Trace routing information";
               }
               enum "normal" {
                 description "Trace normal events";
               }
               enum "general" {
                 description "Trace general events";
               }
               enum "state" {
                 description "Trace state transitions";
               }
               enum "policy" {
                 description "Trace policy processing";
               }
               enum "task" {
                 description "Trace routing protocol task processing";
               }
               enum "timer" {
                 description "Trace routing protocol timer processing";
               }
               enum "all" {
                 description "Trace everything";
               }
             }
           }
           leaf disable {
             description "Disable this trace flag";
             type empty;
           }
         }
       }
       leaf rpf {
         status deprecated;
         type string;
       }
       list scope {
         key name;
         ordered-by user;
         description "Multicast address scope";
         leaf name {
           description "Name to identify multicast address scope";
           type string;
         }
         uses apply-advanced;
         leaf prefix {
           description "Administratively scoped address";
           type jt:ipprefix;
         }
         leaf-list interface {
           ordered-by user;
           description "Interface on which to configure scoping";
           type union {
             type jt:interface-name;
             type string {
               pattern "<.*>|$.*";
             }
           }
         }
       }
       leaf-list scope-policy {
         ordered-by user;
         description "Scoping policy";
         type jt:policy-algebra;
       }
       list flow-map {
         key name;
         ordered-by user;
         description "Multicast flow map configuration";
         leaf name {
           description "Name of the flow map";
           type string;
         }
         uses apply-advanced;
         leaf-list policy {
           ordered-by user;
           description "Policy for matched flows";
           type jt:policy-algebra;
         }
         container bandwidth {
           presence "enable bandwidth";
           description "Bandwidth properties for matched flows";
           leaf bandwidth-value {
             description "Static or default bandwidth for the matched flows";
             units "bps";
             type string;
           }
           leaf adaptive {
             description "Auto-sense bandwidth for matched flows";
             type empty;
           }
         }
         leaf-list redundant-sources {
           ordered-by user;
           description "Redundant source addresses";
           junos:must "(\".. bandwidth adaptive\")";
           junos:must-message "redundant-sources can only be configured together with 'bandwidth adaptive'";
           type jt:ipaddr;
         }
         container forwarding-cache {
           description "Forwarding cache properties for matched flows";
           uses apply-advanced;
           container timeout {
             description "Timeout properties for matched flows";
             choice timeout_choice {
               case case_1 {
                 leaf timeout-value {
                   description "Timeout for forwarding cache entry";
                   units "minutes";
                   type union {
                     type string {
                       pattern "<.*>|$.*";
                     }
                     type uint32 {
                       range "1 .. 720";
                     }
                   }
                 }
               }
               case case_2 {
                 container never {
                   presence "enable never";
                   description "Forwarding cache entries never time out";
                   uses apply-advanced;
                   leaf non-discard-entry-only {
                     description "Apply only to non-discard entries";
                     type empty;
                   }
                 }
               }
             }
           }
         }
       }
       leaf-list resolve-filter {
         ordered-by user;
         description "Multicast resolve policy filter";
         status deprecated;
         type jt:policy-algebra;
       }
       leaf-list ssm-groups {
         ordered-by user;
         description "Source-specific multicast group ranges";
         type jt:ipprefix;
       }
       leaf cont-stats-collection-interval {
         description "IGMP/MLD continuous statistics collection interval";
         default "300";
         type union {
           type string {
             pattern "<.*>|$.*";
           }
           type uint16 {
             range "60 .. 3600";
           }
         }
       }
       leaf asm-override-ssm {
         description "Allow ASM state for SSM group ranges";
         type empty;
       }
       leaf-list rpf-check-policy {
         ordered-by user;
         description "Disable RPF check for a source group pair";
         type jt:policy-algebra;
       }
       container pim-to-igmp-proxy {
         description "PIM-to-IGMP proxy";
         uses apply-advanced;
         leaf-list upstream-interface {
           ordered-by user;
           description "Upstream interface list";
           type union {
             type jt:interface-name;
             type string {
               pattern "<.*>|$.*";
             }
           }
           max-elements 2;
         }
       }
       container pim-to-mld-proxy {
         description "PIM-to-MLD proxy";
         uses apply-advanced;
         leaf-list upstream-interface {
           ordered-by user;
           description "Upstream interface list";
           type union {
             type jt:interface-name;
             type string {
               pattern "<.*>|$.*";
             }
           }
           max-elements 2;
         }
       }
       container forwarding-cache {
         description "Multicast forwarding cache";
         uses apply-advanced;
         leaf allow-maximum {
           description "Allow maximum of global and family level threshold values for suppress and reuse";
           type empty;
         }
         list family {
           key name;
           ordered-by user;
           description "Protocol family";
           junos:must "((!(\".. threshold\") || \".. allow-maximum\"))";
           junos:must-message "Family threshold cannot be configured if global threshold is already configured";
           leaf name {
             description "Protocol family";
             type enumeration {
               enum "inet" {
                 description "IPv4 family";
               }
               enum "inet6" {
                 description "IPv6 family";
               }
             }
           }
           uses apply-advanced;
           container threshold {
             presence "enable threshold";
             description "Multicast forwarding cache suppress threshold";
             uses apply-advanced;
             leaf suppress {
               description "Suppress threshold";
               type union {
                 type string {
                   pattern "<.*>|$.*";
                 }
                 type uint32 {
                   range "1 .. 200000";
                 }
               }
             }
             leaf reuse {
               description "Reuse threshold";
               junos:must "(\".. suppress\")";
               junos:must-message "To configure reuse, suppress must be configured";
               type union {
                 type string {
                   pattern "<.*>|$.*";
                 }
                 type uint32 {
                   range "1 .. 200000";
                 }
               }
             }
             leaf mvpn-rpt-suppress {
               description "MVPN RP tree entry suppress threshold";
               junos:must "(\".. suppress\")";
               junos:must-message "To configure mvpn-rpt-suppress, suppress must be configured";
               type union {
                 type string {
                   pattern "<.*>|$.*";
                 }
                 type uint32 {
                   range "1 .. 200000";
                 }
               }
             }
             leaf mvpn-rpt-reuse {
               description "MVPN RP tree entry reuse threshold";
               junos:must "(\".. mvpn-rpt-suppress\")";
               junos:must-message "To configure mvpn-rpt-reuse, mvpn-rpt-suppress must be configured";
               type union {
                 type string {
                   pattern "<.*>|$.*";
                 }
                 type uint32 {
                   range "1 .. 200000";
                 }
               }
             }
             leaf log-warning {
               description "Percentage at which to start generating warnings";
               junos:must "(\".. suppress\")";
               junos:must-message "To configure log-warning, suppress must be configured";
               type union {
                 type string {
                   pattern "<.*>|$.*";
                 }
                 type uint32 {
                   range "1 .. 100";
                 }
               }
             }
           }
         }
         container threshold {
           junos:must "((!(\".. family\") || \".. allow-maximum\"))";
           junos:must-message "Global threshold cannot be configured if family threshold is configured";
           description "Threshold";
           uses apply-advanced;
           leaf suppress {
             description "Suppress threshold";
             type union {
               type string {
                 pattern "<.*>|$.*";
               }
               type uint32 {
                 range "1 .. 200000";
               }
             }
           }
           leaf reuse {
             description "Reuse threshold";
             junos:must "(\".. suppress\")";
             junos:must-message "To configure reuse, suppress must be configured";
             type union {
               type string {
                 pattern "<.*>|$.*";
               }
               type uint32 {
                 range "1 .. 200000";
               }
             }
           }
           leaf mvpn-rpt-suppress {
             description "MVPN RP tree entry suppress threshold";
             junos:must "(\".. suppress\")";
             junos:must-message "To configure mvpn-rpt-suppress, suppress must be configured";
             type union {
               type string {
                 pattern "<.*>|$.*";
               }
               type uint32 {
                 range "1 .. 200000";
               }
             }
           }
           leaf mvpn-rpt-reuse {
             description "MVPN RP tree entry reuse threshold";
             junos:must "(\".. mvpn-rpt-suppress\")";
             junos:must-message "To configure mvpn-rpt-reuse, mvpn-rpt-suppress must be configured";
             type union {
               type string {
                 pattern "<.*>|$.*";
               }
               type uint32 {
                 range "1 .. 200000";
               }
             }
           }
           leaf log-warning {
             description "Percentage at which to start generating warnings";
             junos:must "(\".. suppress\")";
             junos:must-message "To configure log-warning, suppress must be configured";
             type union {
               type string {
                 pattern "<.*>|$.*";
               }
               type uint32 {
                 range "1 .. 100";
               }
             }
           }
         }
         leaf timeout {
           description "Forwarding cache entry timeout in minutes";
           type union {
             type string {
               pattern "<.*>|$.*";
             }
             type uint32 {
               range "1 .. 720";
             }
           }
         }
       }
       list interface {
         key name;
         ordered-by user;
         description "Multicast interface options";
         uses multicast_interface_options_type;
       }
       list ssm-map {
         key name;
         ordered-by user;
         description "SSM map definitions";
         leaf name {
           description "SSM map name";
           type string;
         }
         uses apply-advanced;
         leaf-list policy {
           ordered-by user;
           description "Policy for matching group";
           type jt:policy-algebra;
         }
         leaf-list source {
           ordered-by user;
           description "One or more source addresses";
           type jt:ipaddr;
         }
       }
       container stream-protection {
         presence "enable stream-protection";
         description "Multicast only Fast Re-Route";
         uses apply-advanced;
         leaf mofrr-primary-path-selection-by-routing {
           description "Multicast only Fast Re-Route primary path by Routing";
           type empty;
         }
         leaf mofrr-disjoint-upstream-only {
           description "Multicast only Fast Re-Route disjoint upstream only";
           type empty;
         }
         leaf mofrr-no-backup-join {
           description "Multicast only Fast Re-Route no backup join";
           type empty;
         }
         leaf mofrr-asm-starg {
           description "Multicast only Fast Re-Route asm (*,G)";
           type empty;
         }
         leaf-list policy {
           ordered-by user;
           description "MoFRR Policy";
           type jt:policy-algebra;
         }
       }
       list backup-pe-group {
         key name;
         ordered-by user;
         description "Backup PE group definitions";
         leaf name {
           description "PE group name";
           type string;
         }
         uses apply-advanced;
         leaf-list backups {
           ordered-by user;
           description "One or more IP addresses";
           type jt:ipaddr;
           max-elements 8;
         }
         leaf local-address {
           description "Address to be used as local-address for this group";
           type jt:ipaddr;
         }
       }
       leaf omit-wildcard-address {
         description "Omit wildcard source/group fields in SPMSI AD NLRI";
         type empty;
       }
       leaf local-address {
         description "Local address for PIM and MVPN sessions";
         type jt:ipv4addr;
       }
     }
     container programmable-rpd {
       description "RPD Server module management options";
       uses programmable-rpd-type;
     }
     container validation {
       description "Define Route validation";
       uses apply-advanced;
       container traceoptions {
         description "Trace options for route validation";
         uses apply-advanced;
         container file {
           description "Trace file options";
           leaf filename {
             description "Name of file in which to write trace information";
             type string {
               length "1 .. 1024";
               junos:posix-pattern "![/ %]";
               junos:pattern-message "Must not contain '/', % or a space";
             }
           }
           leaf replace {
             description "Replace trace file rather than appending to it";
             status deprecated;
             type empty;
           }
           leaf size {
             description "Maximum trace file size";
             type string;
           }
           leaf files {
             description "Maximum number of trace files";
             default "10";
             type union {
               type string {
                 pattern "<.*>|$.*";
               }
               type uint32 {
                 range "2 .. 1000";
               }
             }
           }
           leaf no-stamp {
             description "Do not timestamp trace file";
             status deprecated;
             type empty;
           }
           choice world-readable-choice {
             leaf world-readable {
               description "Allow any user to read the log file";
               type empty;
             }
             leaf no-world-readable {
               description "Don't allow any user to read the log file";
               type empty;
             }
           }
         }
         list flag {
           key name;
           ordered-by user;
           description "Tracing parameters";
           leaf name {
             type enumeration {
               enum "error" {
                 description "Trace errored packets";
               }
               enum "packets" {
                 description "Trace all I/O packets";
               }
               enum "keepalive" {
                 description "Trace keepalive packets";
               }
               enum "update" {
                 description "Trace update packets";
               }
               enum "nsr-synchronization" {
                 description "Trace NSR synchronization events";
               }
               enum "state" {
                 description "Trace state transitions";
               }
               enum "policy" {
                 description "Trace policy processing";
               }
               enum "task" {
                 description "Trace routing protocol task processing";
               }
               enum "timer" {
                 description "Trace routing protocol timer processing";
               }
               enum "client" {
                 description "Trace route validation client events";
               }
               enum "all" {
                 description "Trace everything";
               }
             }
           }
           leaf send {
             description "Trace transmitted packets";
             type empty;
           }
           leaf receive {
             description "Trace received packets";
             type empty;
           }
           leaf detail {
             description "Trace detailed information";
             type empty;
           }
           leaf disable {
             description "Disable this trace flag";
             type empty;
           }
         }
       }
       leaf-list notification-rib {
         ordered-by user;
         description "Define routing tables that get notified upon validation state change";
         type string;
       }
       list group {
         key name;
         description "Define a group of sessions";
         leaf name {
           description "Group name";
           type string;
         }
         uses apply-advanced;
         leaf authentication-key {
           description "MD5 authentication key";
           type string {
             length "1 .. 126";
           }
         }
         leaf authentication-algorithm {
           description "Authentication algorithm name";
           default "hmac-sha-1-96";
           junos:must "(\".. authentication-key-chain\")";
           junos:must-message "May not be configured without authentication-key-chain";
           junos:must "(!(\".. authentication-key\"))";
           junos:must-message "May not be configured with authentication-key";
           type enumeration {
             enum "md5" {
               description "Message Digest 5";
             }
             enum "hmac-sha-1-96" {
               description "Hash-based Message Authentication Code (SHA1) (96 bits)";
             }
             enum "aes-128-cmac-96" {
               description "Cipher-based Message Authentication Code (AES128) (96 bits)";
             }
             enum "ao" {
               description "TCP Authentication Option";
             }
           }
         }
         leaf tcpao-handling-with-digest-mismatch {
           description "Drop or continue without TCP-AO with digest mismatch with TCP-AO";
           junos:must "(!(\".. authentication-key\"))";
           junos:must-message "May not be configured with authentication-key";
           type enumeration {
             enum "drop-if-no-tcpao" {
               description "Drop the connection if Digest mismatched";
             }
             enum "allow-without-tcpao" {
               description "Allow the connection establishment without TCP-AO";
             }
           }
         }
         leaf authentication-key-chain {
           description "Key chain name";
           junos:must "(!(\".. authentication-key\"))";
           junos:must-message "May not be configured with authentication-key";
           junos:must "(\"security authentication-key-chains key-chain $$\")";
           junos:must-message "Referenced key-chain must be defined";
           type string {
             length "1 .. 128";
           }
         }
         leaf max-sessions {
           description "Maximum connected session in this group";
           type union {
             type string {
               pattern "<.*>|$.*";
             }
             type uint32 {
               range "1 .. 63";
             }
           }
         }
         list session {
           key name;
           description "Configure a session";
           leaf name {
             type jt:ipaddr;
           }
           uses apply-advanced;
           container traceoptions {
             description "Trace options for route validation";
             uses apply-advanced;
             container file {
               description "Trace file options";
               leaf filename {
                 description "Name of file in which to write trace information";
                 type string {
                   length "1 .. 1024";
                   junos:posix-pattern "![/ %]";
                   junos:pattern-message "Must not contain '/', % or a space";
                 }
               }
               leaf replace {
                 description "Replace trace file rather than appending to it";
                 status deprecated;
                 type empty;
               }
               leaf size {
                 description "Maximum trace file size";
                 type string;
               }
               leaf files {
                 description "Maximum number of trace files";
                 default "10";
                 type union {
                   type string {
                     pattern "<.*>|$.*";
                   }
                   type uint32 {
                     range "2 .. 1000";
                   }
                 }
               }
               leaf no-stamp {
                 description "Do not timestamp trace file";
                 status deprecated;
                 type empty;
               }
               choice world-readable-choice {
                 leaf world-readable {
                   description "Allow any user to read the log file";
                   type empty;
                 }
                 leaf no-world-readable {
                   description "Don't allow any user to read the log file";
                   type empty;
                 }
               }
             }
             list flag {
               key name;
               ordered-by user;
               description "Tracing parameters";
               leaf name {
                 type enumeration {
                   enum "error" {
                     description "Trace errored packets";
                   }
                   enum "packets" {
                     description "Trace all I/O packets";
                   }
                   enum "keepalive" {
                     description "Trace keepalive packets";
                   }
                   enum "update" {
                     description "Trace update packets";
                   }
                   enum "state" {
                     description "Trace state transitions";
                   }
                   enum "task" {
                     description "Trace routing protocol task processing";
                   }
                   enum "timer" {
                     description "Trace routing protocol timer processing";
                   }
                   enum "all" {
                     description "Trace everything";
                   }
                 }
               }
               leaf send {
                 description "Trace transmitted packets";
                 type empty;
               }
               leaf receive {
                 description "Trace received packets";
                 type empty;
               }
               leaf detail {
                 description "Trace detailed information";
                 type empty;
               }
               leaf disable {
                 description "Disable this trace flag";
                 type empty;
               }
             }
           }
           leaf authentication-key {
             description "MD5 authentication key";
             type string {
               length "1 .. 126";
             }
           }
           leaf authentication-algorithm {
             description "Authentication algorithm name";
             default "hmac-sha-1-96";
             junos:must "(\".. authentication-key-chain\")";
             junos:must-message "May not be configured without authentication-key-chain";
             junos:must "(!(\".. authentication-key\"))";
             junos:must-message "May not be configured with authentication-key";
             type enumeration {
               enum "md5" {
                 description "Message Digest 5";
               }
               enum "hmac-sha-1-96" {
                 description "Hash-based Message Authentication Code (SHA1) (96 bits)";
               }
               enum "aes-128-cmac-96" {
                 description "Cipher-based Message Authentication Code (AES128) (96 bits)";
               }
               enum "ao" {
                 description "TCP Authentication Option";
               }
             }
           }
           leaf tcpao-handling-with-digest-mismatch {
             description "Drop or continue without TCP-AO with digest mismatch with TCP-AO";
             junos:must "(!(\".. authentication-key\"))";
             junos:must-message "May not be configured with authentication-key";
             type enumeration {
               enum "drop-if-no-tcpao" {
                 description "Drop the connection if Digest mismatched";
               }
               enum "allow-without-tcpao" {
                 description "Allow the connection establishment without TCP-AO";
               }
             }
           }
           leaf authentication-key-chain {
             description "Key chain name";
             junos:must "(!(\".. authentication-key\"))";
             junos:must-message "May not be configured with authentication-key";
             junos:must "(\"security authentication-key-chains key-chain $$\")";
             junos:must-message "Referenced key-chain must be defined";
             type string {
               length "1 .. 128";
             }
           }
           leaf refresh-time {
             description "Interval between keepalive packet transmissions";
             units "seconds";
             type union {
               type string {
                 pattern "<.*>|$.*";
               }
               type uint32 {
                 range "1 .. 1800";
               }
             }
           }
           leaf hold-time {
             description "Time after which the session is declared down.";
             units "seconds";
             type union {
               type string {
                 pattern "<.*>|$.*";
               }
               type uint32 {
                 range "10 .. 3600";
               }
             }
           }
           leaf record-lifetime {
             description "Lifetime of route validation records";
             units "seconds";
             type union {
               type string {
                 pattern "<.*>|$.*";
               }
               type uint32 {
                 range "60 .. 604800";
               }
             }
           }
           leaf preference {
             description "Preference for session establishment";
             type union {
               type string {
                 pattern "<.*>|$.*";
               }
               type uint32 {
                 range "1 .. 255";
               }
             }
           }
           leaf port {
             description "Portnumber to connect";
             type union {
               type string {
                 pattern "<.*>|$.*";
               }
               type uint16 {
                 range "1 .. 65535";
               }
             }
           }
           leaf local-address {
             type jt:ipaddr;
           }
         }
       }
       container static {
         description "Define static route validation record";
         uses apply-advanced;
         list record {
           key name;
           description "Static route validation record";
           leaf name {
             type jt:ipprefix;
           }
           uses apply-advanced;
           list maximum-length {
             key name;
             ordered-by user;
             leaf name {
               description "Maximum prefix-length for route validation record";
               type union {
                 type string {
                   pattern "<.*>|$.*";
                 }
                 type uint32 {
                   range "1 .. 128";
                 }
               }
             }
             uses apply-advanced;
             list origin-autonomous-system {
               key name;
               ordered-by user;
               leaf name {
                 description "Legitimate Origin Autonomous System";
                 type union {
                   type uint32;
                   type string {
                     pattern "<.*>|$.*";
                   }
                 }
               }
               uses apply-advanced;
               leaf validation-state {
                 description "Validation state for route validation record";
                 type enumeration {
                   enum "invalid" {
                     description "Invalid route validation state";
                   }
                   enum "valid" {
                     description "Valid route validation state";
                   }
                 }
               }
             }
           }
         }
       }
     }
   }
   grouping dynamic_tunnel_type {
     description "Dynamic tunnel definition";
     leaf name {
       description "Tunnel name";
       type string {
         junos:posix-pattern "![^a-zA-Z0-9_-]|(^(all|.{64,})$)";
         junos:pattern-message "Tunnel name is a string consisting of up to 63 letters, numbers, dashes, and underscores";
       }
     }
     uses apply-advanced;
     leaf source-address {
       description "Tunnel source address";
       junos:must "((\".. gre\" || (\".. udp\" || (\".. bgp-signal\" || \".. ipip\"))))";
       junos:must-message "Tunnel type GRE, UDP or BGP-SIGNAL must be configured";
       type jt:ipaddr;
     }
     choice tunnel-type {
       case case_1 {
         list rsvp-te {
           key name;
           ordered-by user;
           description "RSVP-TE point-to-point LSP";
           leaf name {
             description "Configure multiple entries for RSVP tunnel";
             type string;
           }
           uses apply-advanced;
           container label-switched-path-template {
             description "Template for dynamic point-to-point LSP parameters";
             uses apply-advanced;
             choice dynamic-template {
               case case_1 {
                 leaf template-name {
                   description "Name of point-to-point LSP template";
                   junos:must "((\"protocols mpls label-switched-path $$\" && \"protocols mpls label-switched-path $$ template\"))";
                   junos:must-message "Referenced point-to-point LSP template does not exist";
                   type string {
                     junos:posix-pattern "^.{1,32}$";
                     junos:pattern-message "Must be a string of 32 characters or less";
                   }
                 }
               }
               case case_2 {
                 leaf default-template {
                   description "Use default parameters";
                   type empty;
                 }
               }
             }
           }
           list destination-networks {
             key name;
             ordered-by user;
             description "Create tunnels for routes in these destination networks";
             uses app_network_type;
           }
         }
       }
       case case_2 {
         container spring-te {
           description "SPRING-TE LSP's";
           uses apply-advanced;
           list source-routing-path-template {
             key name;
             ordered-by user;
             description "Template color mapping for SPRING-TE dynamic LSP parameters";
             uses spring-te-template-map;
           }
           list destination-networks {
             key name;
             ordered-by user;
             description "Create tunnels for routes in these destination networks";
             uses app_network_type;
           }
         }
       }
       case case_3 {
         leaf gre {
           description "Generic routing encapsulation type for IPv4";
           junos:must "((\".. source-address\" && \".. destination-networks\"))";
           junos:must-message "Source address and Destination Networks must be configured for tunnel type GRE";
           type empty;
         }
       }
       case case_4 {
         leaf udp {
           description "UDP encapsulation type for IPv4";
           junos:must "((\".. source-address\" && \".. destination-networks\"))";
           junos:must-message "Source address and Destination Networks must be configured for tunnel type UDP";
           type empty;
         }
       }
       case case_5 {
         leaf bgp-signal {
           description "BGP signals the encapsulation type for IPv4";
           junos:must "((\".. source-address\" && \".. destination-networks\"))";
           junos:must-message "Source address and Destination Networks must be configured for tunnel type BGP-Signal";
           type empty;
         }
       }
       case case_6 {
         leaf ipip {
           description "IPIP encapsulation type for IPv4";
           junos:must "((\".. source-address\" && \".. destination-networks\"))";
           junos:must-message "Source address and Destination Networks must be configured for tunnel type IPIP";
           type empty;
         }
       }
     }
     list destination-networks {
       key name;
       ordered-by user;
       description "Create tunnels for routes in these destination networks";
       junos:must "(((\".. gre\" || (\".. udp\" || (\".. bgp-signal\" || \".. ipip\"))) && (!(\".. rsvp-te\") && !(\".. spring-te\"))))";
       junos:must-message "Tunnel type GRE or UDP must be configured";
       uses network_type;
     }
   }
   grouping app_network_type {
     leaf name {
       description "Network prefix";
       type jt:ipprefix;
     }
     uses apply-advanced;
   }
   grouping export-af-obj {
     uses apply-advanced;
     choice enable-disable {
       case case_1 {
         leaf disable {
           description "Disable auto-export for address family";
           type empty;
         }
       }
     }
     container unicast {
       description "Unicast routing information";
       presence "enable unicast";
       uses export-subaf-obj;
     }
     container multicast {
       description "Multicast routing information";
       presence "enable multicast";
       uses export-subaf-obj;
     }
     container flow {
       description "Flow routing information";
       presence "enable flow";
       uses export-subaf-obj;
     }
   }
   grouping export-subaf-obj {
     uses apply-advanced;
     choice enable-disable {
       case case_1 {
         leaf disable {
           description "Disable instance export";
           type empty;
         }
       }
     }
     leaf rib-group {
       description "Auxiliary rib-group of additional RIBs to consider";
       type string;
     }
   }
   grouping fate_sharing_links {
     leaf name {
       description "Router ID or LAN interface address";
       type jt:ipv4addr;
     }
     leaf to {
       description "Point-to-point links";
       type jt:ipv4addr;
     }
   }
   grouping flow-interface-group {
     leaf group {
       description "Interface group ID to match traffic";
       type union {
         type string {
           pattern "<.*>|$.*";
         }
         type uint32 {
           range "1 .. 255";
         }
       }
     }
     leaf exclude {
       description "Don't apply flow-spec filter to traffic on this group";
       type empty;
     }
   }
   grouping flow-route-inet {
     leaf name {
       type string;
     }
     uses apply-advanced;
     leaf no-install {
       description "Don't install firewall filter in forwarding";
       type empty;
     }
     container match {
       description "Flow definition";
       uses flow-route-qualifier-inet;
     }
     container then {
       description "Actions to take for this flow";
       uses flow-route-op;
     }
   }
   grouping flow-route-inet6 {
     leaf name {
       type string;
     }
     uses apply-advanced;
     leaf no-install {
       description "Don't install firewall filter in forwarding";
       type empty;
     }
     container match {
       description "Flow definition";
       uses flow-route-qualifier-inet6;
     }
     container then {
       description "Actions to take for this flow";
       uses flow-route-op;
     }
   }
   grouping flow-route-op {
     uses apply-advanced;
     leaf community {
       description "Name of BGP community";
       type string;
     }
     choice flow_op_action {
       case case_1 {
         leaf accept {
           description "Allow traffic through";
           type empty;
         }
       }
       case case_2 {
         leaf discard {
           description "Discard all traffic for this flow";
           type empty;
         }
       }
       case case_3 {
         leaf rate-limit {
           description "Rate in bits/sec to limit the flow traffic";
           type string;
         }
       }
     }
     leaf routing-instance {
       description "Redirect to instance identified via Route Target community";
       type string {
         junos:posix-pattern "^[a-z]+:[0-9.]+L?:[0-9]+$";
         junos:pattern-message "Use format 'target:x:y' where 'x' is an AS number followed by an optional 'L' (To indicate 4 byte AS), or an IP address and 'y' is a number. e.g. target:123456L:100";
       }
     }
     leaf sample {
       description "Sample traffic that matches this flow";
       type empty;
     }
     leaf mark {
       description "Set DSCP value for traffic that matches this flow";
       type union {
         type string {
           pattern "<.*>|$.*";
         }
         type uint32 {
           range "0 .. 63";
         }
       }
     }
     leaf next-term {
       description "Continue the filter evaluation after matching this flow";
       type empty;
     }
     choice redirect_op_action {
       case case_1 {
         leaf-list redirect {
           ordered-by user;
           description "Redirect(Tunnel) this flow's traffic to given next-hop address";
           type jt:ipaddr;
         }
       }
     }
   }
   grouping flow-route-qualifier-inet {
     uses apply-advanced;
     leaf-list protocol {
       ordered-by user;
       description "IP protocol value";
       type string;
     }
     leaf-list port {
       ordered-by user;
       type string;
     }
     leaf-list destination-port {
       ordered-by user;
       type string;
     }
     leaf-list source-port {
       ordered-by user;
       type string;
     }
     leaf-list tcp-flags {
       ordered-by user;
       description "TCP flags";
       type string;
     }
     leaf-list packet-length {
       ordered-by user;
       description "Packet length (0-65535)";
       type jt:policy-algebra;
     }
     leaf-list dscp {
       ordered-by user;
       description "Differentiated Services (DiffServ) code point (DSCP) (0-63)";
       type jt:policy-algebra;
     }
     leaf-list fragment {
       ordered-by user;
       type enumeration {
         enum "dont-fragment" {
           description "Don't Fragment flag is set";
         }
         enum "not-a-fragment" {
           description "Not a fragment";
         }
         enum "is-fragment" {
           description "Fragmented packet";
         }
         enum "first-fragment" {
           description "First fragment";
         }
         enum "last-fragment" {
           description "Last fragment";
         }
       }
     }
     leaf destination {
       description "Destination prefix for this traffic flow";
       type jt:ipv4prefix;
     }
     leaf source {
       description "Source prefix for this traffic flow";
       type jt:ipv4prefix;
     }
     leaf-list icmp-code {
       ordered-by user;
       description "ICMP message code";
       type string;
     }
     leaf-list icmp-type {
       ordered-by user;
       description "ICMP message type";
       type string;
     }
   }
   grouping flow-route-qualifier-inet6 {
     uses apply-advanced;
     leaf-list protocol {
       ordered-by user;
       description "IP protocol value";
       type string;
     }
     leaf-list port {
       ordered-by user;
       type string;
     }
     leaf-list destination-port {
       ordered-by user;
       type string;
     }
     leaf-list source-port {
       ordered-by user;
       type string;
     }
     leaf-list tcp-flags {
       ordered-by user;
       description "TCP flags";
       type string;
     }
     leaf-list packet-length {
       ordered-by user;
       description "Packet length (0-65535)";
       type jt:policy-algebra;
     }
     leaf-list dscp {
       ordered-by user;
       description "Differentiated Services (DiffServ) code point (DSCP) (0-63)";
       type jt:policy-algebra;
     }
     leaf-list fragment {
       ordered-by user;
       type enumeration {
         enum "dont-fragment" {
           description "Don't Fragment flag is set";
         }
         enum "not-a-fragment" {
           description "Not a fragment";
         }
         enum "is-fragment" {
           description "Fragmented packet";
         }
         enum "first-fragment" {
           description "First fragment";
         }
         enum "last-fragment" {
           description "Last fragment";
         }
       }
     }
     container destination {
       description "Destination prefix for this traffic flow";
       presence "enable destination";
       uses flow-prefix-with-offset;
     }
     container source {
       description "Source prefix for this traffic flow";
       presence "enable source";
       uses flow-prefix-with-offset;
     }
     leaf-list icmp6-type {
       ordered-by user;
       description "ICMP message type";
       type string;
     }
     leaf-list icmp6-code {
       ordered-by user;
       description "ICMP message code";
       type string;
     }
     leaf-list flow-label {
       ordered-by user;
       description "Flow-label (0-1048575)";
       type jt:policy-algebra;
     }
   }
   grouping flow-prefix-with-offset {
     leaf prefix {
       type jt:ipv6prefix;
     }
     leaf prefix-offset {
       description "Offset from where prefix match will start";
       type union {
         type uint32;
         type string {
           pattern "<.*>|$.*";
         }
       }
     }
   }
   grouping flow-rule-inet {
     leaf name {
       type string;
     }
     uses apply-advanced;
     leaf no-install {
       description "Don't install firewall filter in forwarding";
       type empty;
     }
     container match {
       description "Flow definition";
       uses flow-rule-qualifier-inet;
     }
     container then {
       description "Actions to take for this flow";
       uses flow-rule-op;
     }
   }
   grouping flow-rule-inet6 {
     leaf name {
       type string;
     }
     uses apply-advanced;
     leaf no-install {
       description "Don't install firewall filter in forwarding";
       type empty;
     }
     container match {
       description "Flow definition";
       uses flow-rule-qualifier-inet6;
     }
     container then {
       description "Actions to take for this flow";
       uses flow-rule-op;
     }
   }
   grouping flow-rule-op {
     uses apply-advanced;
     choice flow_op_action {
       case case_1 {
         leaf accept {
           description "Allow traffic through";
           type empty;
         }
       }
       case case_2 {
         leaf discard {
           description "Discard all traffic for this flow";
           type empty;
         }
       }
       case case_3 {
         leaf rate-limit {
           description "Rate in bits/sec to limit the flow traffic";
           type string;
         }
       }
     }
   }
   grouping flow-rule-qualifier-inet {
     uses apply-advanced;
     leaf-list protocol {
       ordered-by user;
       description "IP protocol value";
       type string;
     }
     leaf-list port {
       ordered-by user;
       type string;
     }
     leaf-list destination-port {
       ordered-by user;
       type string;
     }
     leaf-list source-port {
       ordered-by user;
       type string;
     }
     leaf destination {
       description "Destination prefix for this traffic flow";
       type jt:ipv4prefix;
     }
     leaf source {
       description "Source prefix for this traffic flow";
       type jt:ipv4prefix;
     }
   }
   grouping flow-rule-qualifier-inet6 {
     uses apply-advanced;
     leaf-list protocol {
       ordered-by user;
       description "IP protocol value";
       type string;
     }
     leaf-list port {
       ordered-by user;
       type string;
     }
     leaf-list destination-port {
       ordered-by user;
       type string;
     }
     leaf-list source-port {
       ordered-by user;
       type string;
     }
     container destination {
       description "Destination prefix for this traffic flow";
       presence "enable destination";
       uses flow-prefix-with-offset;
     }
     container source {
       description "Source prefix for this traffic flow";
       presence "enable source";
       uses flow-prefix-with-offset;
     }
   }
   grouping flow-validation {
     uses apply-advanced;
     container traceoptions {
       description "Trace options";
       uses flow-dep-traceoptions;
     }
   }
   grouping flow-dep-traceoptions {
     uses apply-advanced;
     container file {
       description "Trace file options";
       leaf filename {
         description "Name of file in which to write trace information";
         type string {
           length "1 .. 1024";
           junos:posix-pattern "![/ %]";
           junos:pattern-message "Must not contain '/', % or a space";
         }
       }
       leaf replace {
         description "Replace trace file rather than appending to it";
         status deprecated;
         type empty;
       }
       leaf size {
         description "Maximum trace file size";
         type string;
       }
       leaf files {
         description "Maximum number of trace files";
         default "10";
         type union {
           type string {
             pattern "<.*>|$.*";
           }
           type uint32 {
             range "2 .. 1000";
           }
         }
       }
       leaf no-stamp {
         description "Do not timestamp trace file";
         status deprecated;
         type empty;
       }
       choice world-readable-choice {
         leaf world-readable {
           description "Allow any user to read the log file";
           type empty;
         }
         leaf no-world-readable {
           description "Don't allow any user to read the log file";
           type empty;
         }
       }
     }
     list flag {
       key name;
       ordered-by user;
       description "Tracing parameters";
       leaf name {
         type enumeration {
           enum "resolution" {
             description "Trace flow to unicast route resolution";
           }
           enum "flash" {
             description "Trace flash processing";
           }
           enum "route" {
             description "Trace routing information";
           }
           enum "normal" {
             description "Trace normal events";
           }
           enum "general" {
             description "Trace general events";
           }
           enum "state" {
             description "Trace state transitions";
           }
           enum "policy" {
             description "Trace policy processing";
           }
           enum "task" {
             description "Trace routing protocol task processing";
           }
           enum "timer" {
             description "Trace routing protocol timer processing";
           }
           enum "all" {
             description "Trace everything";
           }
         }
       }
       leaf send {
         description "Trace transmitted packets";
         type empty;
       }
       leaf receive {
         description "Trace received packets";
         type empty;
       }
       leaf detail {
         description "Trace detailed information";
         type empty;
       }
       leaf disable {
         description "Disable this trace flag";
         type empty;
       }
       container filter {
         presence "enable filter";
         description "Filter to apply to tracing";
         leaf match-on {
           description "Argument on which to match";
           type enumeration {
             enum "prefix" {
               description "Filter based on prefix";
             }
             enum "route-attribute" {
               description "Filter based on route attributes";
             }
           }
         }
         leaf-list policy {
           ordered-by user;
           description "Filter policy";
           type jt:policy-algebra;
         }
       }
     }
   }
   grouping forwarding-table-type {
     description "Forwarding table management options";
     uses apply-advanced;
     leaf remnant-holdtime {
       description "Time to hold inherited routes from FIB";
       type union {
         type string {
           pattern "<.*>|$.*";
         }
         type uint32 {
           range "0 .. 10000";
         }
       }
     }
     leaf send-gr-issu-message {
       description "Simulate gr-issu message reception from rpd-agent";
       type union {
         type string {
           pattern "<.*>|$.*";
         }
         type uint32 {
           range "1 .. 65535";
         }
       }
     }
     leaf chain-composite-max-label-count {
       description "Maximum labels inside chain composite for the platform.";
       type union {
         type string {
           pattern "<.*>|$.*";
         }
         type uint32 {
           range "1 .. 16";
         }
       }
     }
     leaf krt-nexthop-ack-timeout {
       description "Kernel nexthop ack timeout interval";
       type union {
         type string {
           pattern "<.*>|$.*";
         }
         type uint32 {
           range "1 .. 400";
         }
       }
     }
     leaf srv6-chain-merge {
       description "Enable merging of srv6 chain nexthops";
       type empty;
     }
     choice session-id-change-limiter-indirect-choice {
       leaf session-id-change-limiter-indirect {
         description "Enable indirect nexthop to limit session-id change propagation";
         type empty;
       }
       leaf no-session-id-change-limiter-indirect {
         description "Don't enable indirect nexthop to limit session-id change propagation";
         type empty;
       }
     }
     container consistency-checking {
       description "RIB/FIB consistency checking";
       status deprecated;
       uses apply-advanced;
       choice enable-disable {
         case case_1 {
           leaf enable {
             description "Enable consistency checking";
             type empty;
           }
         }
         case case_2 {
           leaf disable {
             description "Disable consistency checking";
             type empty;
           }
         }
       }
       leaf period {
         description "Periodicity of scan in seconds";
         type union {
           type string {
             pattern "<.*>|$.*";
           }
           type uint32 {
             range "30 .. 4294967295";
           }
         }
       }
       leaf threshold {
         description "Mismatch threshold until complaint";
         type union {
           type uint32;
           type string {
             pattern "<.*>|$.*";
           }
         }
       }
     }
     leaf-list export {
       ordered-by user;
       description "Export policy";
       type jt:policy-algebra;
     }
     leaf dynamic-list-next-hop {
       description "Dynamic next-hop mode for EVPN";
       junos:must "(!(\".. evpn-aliasing-optimize\"))";
       junos:must-message "please disable evpn-aliasing-optimize";
       type empty;
     }
     container evpn-egress-link-protection {
       presence "enable evpn-egress-link-protection";
       description "EVPN PE-CE egress link failure protection";
       uses apply-advanced;
     }
     container egress-chaining {
       description "Enable egress-chaining";
       uses apply-advanced;
       leaf spring-te {
         description "Enable egress-chaining for SPRING-TE routes";
         type empty;
       }
     }
     leaf evpn-aliasing-optimize {
       description "EVPN Aliasing convergence improvement";
       junos:must "(!(\".. evpn-egress-link-protection\"))";
       junos:must-message "please disable evpn-egress-link-protection";
       junos:must "(!(\".. dynamic-list-next-hop\"))";
       junos:must-message "please disable dynamic-list-next-hop";
       type empty;
     }
     choice ecmp-fast-reroute-choice {
       leaf ecmp-fast-reroute {
         description "Enable fast reroute for ECMP next hops";
         type empty;
       }
       leaf no-ecmp-fast-reroute {
         description "Don't enable fast reroute for ECMP next hops";
         type empty;
       }
     }
     choice indirect-next-hop-choice {
       leaf indirect-next-hop {
         description "Install indirect next hops in Packet Forwarding Engine";
         type empty;
       }
       leaf no-indirect-next-hop {
         description "Don't install indirect next hops in Packet Forwarding Engine";
         type empty;
       }
     }
     choice route-ack-converge-choice {
       leaf route-ack-converge {
         description "Enable the route ack convergence feature";
         type empty;
       }
       leaf no-route-ack-converge {
         description "Don't enable the route ack convergence feature";
         type empty;
       }
     }
     leaf long-live-ack-timer-val {
       description "Set default long live acknowledgement timer value";
       type union {
         type string {
           pattern "<.*>|$.*";
         }
         type uint32 {
           range "1 .. 65535";
         }
       }
     }
     choice indirect-next-hop-change-acknowledgements-choice {
       leaf indirect-next-hop-change-acknowledgements {
         description "Request acknowledgements for Indirect next hop changes";
         type empty;
       }
       leaf no-indirect-next-hop-change-acknowledgements {
         description "Don't request acknowledgements for Indirect next hop changes";
         type empty;
       }
     }
     list rib {
       key name;
       ordered-by user;
       status deprecated;
       leaf name {
         type string;
       }
     }
     leaf unicast-reverse-path {
       description "Unicast reverse path (RP) verification";
       type enumeration {
         enum "active-paths" {
           description "Consider active paths when performing RP verification";
         }
         enum "feasible-paths" {
           description "Consider all feasible paths for RP verification";
         }
       }
     }
     container ip-tunnel-rpf-check {
       presence "enable ip-tunnel-rpf-check";
       description "IP tunnel Reverse Path Forwarding Check";
       uses apply-advanced;
       leaf mode {
         default "strict";
         type enumeration {
           enum "strict" {
             description "Strict mode for rpf-check(Default)";
           }
           enum "loose" {
             description "Loose mode for rpf-check";
           }
         }
       }
       leaf fail-filter {
         description "Fail filter name for RPF check(family inet|inet6|any)";
         junos:must "((\"firewall family any filter $$\" || ((!(\"firewall\") && \".. .. .. .. .. firewall family any filter $$\") || (\"firewall family inet filter $$\" || ((!(\"firewall\") && \".. .. .. .. .. firewall family inet filter $$\") || (\"firewall family inet6 filter $$\" || (!(\"firewall\") && \".. .. .. .. .. firewall family inet6 filter $$\")))))))";
         junos:must-message "referenced filter must be defined under firewall family any|inet|inet6";
         type string {
           junos:posix-pattern "!^((__.*)|(.{65,}))$";
           junos:pattern-message "Must be a non-reserved string of 64 characters or less";
         }
       }
     }
     list source-class {
       key name;
       ordered-by user;
       description "Source class filters";
       uses source-class-filters;
     }
     list destination-class {
       key name;
       ordered-by user;
       description "Destination class filters";
       uses destination-class-filters;
     }
     leaf transit-lsp-statistics-from-route {
       description "Enable LSP statistics collection from the route";
       type empty;
     }
     container chained-composite-next-hop {
       description "Next-hop chaining mode";
       uses apply-advanced;
       container ingress {
         description "Ingress LSP nexthop settings";
         uses apply-advanced;
         choice l2vpn-choice {
           leaf l2vpn {
             description "Create composite-chained nexthops for ingress l2vpn LSPs";
             type empty;
           }
           leaf no-l2vpn {
             description "Don't create composite-chained nexthops for ingress l2vpn LSPs";
             type empty;
           }
         }
         choice l2ckt-choice {
           leaf l2ckt {
             description "Create composite-chained nexthops for ingress l2ckt LSPs";
             type empty;
           }
           leaf no-l2ckt {
             description "Don't create composite-chained nexthops for ingress l2ckt LSPs";
             type empty;
           }
         }
         choice fec129-vpws-choice {
           leaf fec129-vpws {
             description "Create composite-chained nexthops for ingress fec129-vpws LSPs";
             type empty;
           }
           leaf no-fec129-vpws {
             description "Don't create composite-chained nexthops for ingress fec129-vpws LSPs";
             type empty;
           }
         }
         choice evpn-choice {
           leaf evpn {
             description "Create composite-chained nexthops for ingress EVPN LSPs";
             type empty;
           }
           leaf no-evpn {
             description "Don't create composite-chained nexthops for ingress EVPN LSPs";
             type empty;
           }
         }
         container labeled-bgp {
           description "Create composite-chained nexthops for ingress labeled-bgp LSPs";
           uses apply-advanced;
           choice inet-choice {
             leaf inet {
               description "Enable inet labeled-bgp composite nexthop creation";
               type empty;
             }
             leaf no-inet {
               description "Don't enable inet labeled-bgp composite nexthop creation";
               type empty;
             }
           }
           choice inet6-choice {
             leaf inet6 {
               description "Enable inet6 labeled-bgp composite nexthop creation";
               type empty;
             }
             leaf no-inet6 {
               description "Don't enable inet6 labeled-bgp composite nexthop creation";
               type empty;
             }
           }
         }
         container l3vpn {
           presence "enable l3vpn";
           junos:must "(!(\".. .. .. .. l3vpn-composite-nexthop\"))";
           junos:must-message "Equivalent options; only one may be configured; this way is preferred";
           description "Create composite-chained nexthops for ingress l3vpn LSPs";
           leaf extended-space {
             description "Allocate in extended-space for scalability";
             junos:must "(\"chassis network-services enhanced-ip\")";
             junos:must-message "Network services mode must be Enhanced IP for extended space l3vpn";
             type empty;
           }
         }
         choice ldp-choice {
           leaf ldp {
             description "Create chained-composite nexthops to support segmentation LDP tunnels";
             type empty;
           }
           leaf no-ldp {
             description "Don't create chained-composite nexthops to support segmentation LDP tunnels";
             type empty;
           }
         }
       }
       container transit {
         description "Transit LSP nexthops settings";
         uses apply-advanced;
         choice l2vpn-choice {
           leaf l2vpn {
             description "Create composite-chained nexthops for transit l2vpn LSPs";
             type empty;
           }
           leaf no-l2vpn {
             description "Don't create composite-chained nexthops for transit l2vpn LSPs";
             type empty;
           }
         }
         choice l3vpn-choice {
           leaf l3vpn {
             description "Create composite-chained nexthops for transit l3vpn LSPs";
             type empty;
           }
           leaf no-l3vpn {
             description "Don't create composite-chained nexthops for transit l3vpn LSPs";
             type empty;
           }
         }
         choice labeled-bgp-choice {
           leaf labeled-bgp {
             description "Create composite-chained nexthops for transit labeled BGP routes";
             type empty;
           }
           leaf no-labeled-bgp {
             description "Don't create composite-chained nexthops for transit labeled BGP routes";
             type empty;
           }
         }
         choice static-choice {
           leaf static {
             description "Create composite-chained nexthops for static LSPs";
             type empty;
           }
           leaf no-static {
             description "Don't create composite-chained nexthops for static LSPs";
             type empty;
           }
         }
         choice rsvp-choice {
           leaf rsvp {
             description "Create composite-chained nexthops for RSVP LSPs";
             type empty;
           }
           leaf no-rsvp {
             description "Don't create composite-chained nexthops for RSVP LSPs";
             type empty;
           }
         }
         choice rsvp-p2mp-choice {
           leaf rsvp-p2mp {
             description "Create composite-chained nexthops for RSVP p2mp LSPs";
             junos:must "(!(\"chassis network-services enhanced-ip\"))";
             junos:must-message "Transit rsvp-p2mp is not supported with enhanced-ip mode on MX platform";
             type empty;
           }
           leaf no-rsvp-p2mp {
             description "Don't create composite-chained nexthops for RSVP p2mp LSPs";
             junos:must "(!(\"chassis network-services enhanced-ip\"))";
             junos:must-message "Transit rsvp-p2mp is not supported with enhanced-ip mode on MX platform";
             type empty;
           }
         }
         choice express-segments-choice {
           leaf express-segments {
             description "Create composite-chained nexthops for Express Segments";
             type empty;
           }
           leaf no-express-segments {
             description "Don't create composite-chained nexthops for Express Segments";
             type empty;
           }
         }
         choice ldp-choice {
           leaf ldp {
             description "Create composite-chained nexthops for LDP LSPs";
             type empty;
           }
           leaf no-ldp {
             description "Don't create composite-chained nexthops for LDP LSPs";
             type empty;
           }
         }
         choice ldp-p2mp-choice {
           leaf ldp-p2mp {
             description "Create composite-chained nexthops for LDP P2MP LSPs";
             junos:must "(!(\"chassis network-services enhanced-ip\"))";
             junos:must-message "Transit ldp-p2mp is not supported with enhanced-ip mode on MX platform";
             type empty;
           }
           leaf no-ldp-p2mp {
             description "Don't create composite-chained nexthops for LDP P2MP LSPs";
             junos:must "(!(\"chassis network-services enhanced-ip\"))";
             junos:must-message "Transit ldp-p2mp is not supported with enhanced-ip mode on MX platform";
             type empty;
           }
         }
         choice labeled-isis-choice {
           leaf labeled-isis {
             description "Create composite-chained nexthops for labeled ISIS routes";
             type empty;
           }
           leaf no-labeled-isis {
             description "Don't create composite-chained nexthops for labeled ISIS routes";
             type empty;
           }
         }
       }
     }
     container fib-next-hop-split {
       description "Split nexthop to chain nexthop when installing fom rib to fib";
       uses apply-advanced;
       leaf labeled-isis {
         description "Create composite-chained nexthops for labeled ISIS routes";
         type empty;
       }
     }
     container fib-agent {
       presence "enable fib-agent";
       junos:must "(!(\"routing-options forwarding-table channel\"))";
       junos:must-message "Can not be configured together with 'routing-options forwarding-table channel'";
       description "Configure fib-agent parameters";
       uses apply-advanced;
       leaf address {
         description "IP address of the FIB agent";
         default "127.0.0.1";
         type jt:ipaddr;
       }
       leaf port {
         description "TCP port of the FIB agent";
         default "2620";
         type union {
           type string {
             pattern "<.*>|$.*";
           }
           type uint32 {
             range "1 .. 65535";
           }
         }
       }
       leaf protocol-id {
         description "Protocol ID to be used for programming routes";
         default "22";
         type union {
           type string {
             pattern "<.*>|$.*";
           }
           type uint32 {
             range "0 .. 255";
           }
         }
       }
     }
     list channel {
       key name;
       ordered-by user;
       description "Configure fib-channel parameters";
       junos:must "(!(\"routing-options forwarding-table fib-agent\"))";
       junos:must-message "Can not be configured together with 'routing-options forwarding-table fib-agent'";
       leaf name {
         description "FIB Channel Name";
         type string;
       }
       uses apply-advanced;
       container protocol {
         presence "enable protocol";
         description "Configure fib-channel protocol";
         uses apply-advanced;
         leaf protocol-type {
           junos:must "((unique \"routing-options forwarding-table channel <*> protocol protocol-type netlink-fpm\" || unique \"routing-options forwarding-table channel <*> protocol protocol-type gRPC\"))";
           junos:must-message "protocol-type is already configured for a different channel";
           type enumeration {
             enum "netlink-fpm" {
               description "Configure SONiC FIB Channel";
             }
             enum "gRPC" {
               description "Configure vRouter FIB channel.";
             }
           }
         }
         leaf destination {
           description "Destination of the FIB";
           type string;
         }
         leaf source-id {
           description "Source ID to be used for programming routes";
           default "22";
           type union {
             type string {
               pattern "<.*>|$.*";
             }
             type uint32 {
               range "0 .. 255";
             }
           }
         }
       }
       leaf-list export {
         ordered-by user;
         description "Export policy";
         type jt:policy-algebra;
       }
     }
   }
   grouping destination-class-filters {
     leaf name {
       description "Destination class name";
       junos:must "((any \"policy-options policy-statement <*> then destination-class $$\" || (any \"policy-options policy-statement <*> term <*> then destination-class $$\" || (any \"policy-options policy-statement <*> from route-filter <*> <*> destination-class $$\" || (any \"policy-options policy-statement <*> term <*> from route-filter <*> <*> destination-class $$\" || (any \"policy-options policy-statement <*> then forwarding-class $$\" || (any \"policy-options policy-statement <*> term <*> then forwarding-class $$\" || (any \"policy-options policy-statement <*> from route-filter <*> <*> forwarding-class $$\" || (any \"logical-systems <*> policy-options policy-statement <*> then destination-class $$\" || (any \"logical-systems <*> policy-options policy-statement <*> term <*> then destination-class $$\" || (any \"logical-systems <*> policy-options policy-statement <*> from route-filter <*> <*> destination-class $$\" || (any \"logical-systems <*> policy-options policy-statement <*> term <*> from route-filter <*> <*> destination-class $$\" || (any \"logical-systems <*> policy-options policy-statement <*> then forwarding-class $$\" || (any \"logical-systems <*> policy-options policy-statement <*> term <*> then forwarding-class $$\" || any \"logical-systems <*> policy-options policy-statement <*> from route-filter <*> <*> forwarding-class $$\"))))))))))))))";
       junos:must-message "referenced destination-class must be defined";
       type string;
     }
     uses apply-advanced;
     container family {
       description "Protocol family";
       container inet {
         description "Protocol family IPv4 for firewall filter";
         uses apply-advanced;
         container filter {
           description "Packet filtering";
           uses apply-advanced;
           leaf filter-name {
             description "Inet Filter name";
             type string;
           }
         }
       }
       container inet6 {
         description "Protocol family IPv6 for firewall filter";
         uses apply-advanced;
         container filter {
           description "Packet filtering";
           uses apply-advanced;
           leaf filter-name {
             description "Inet6 Filter name";
             type string;
           }
         }
       }
     }
   }
   grouping juniper-sampling-options {
     uses apply-advanced;
     choice enable-disable {
       case case_1 {
         leaf disable {
           description "Disable global sampling instance";
           type empty;
         }
       }
     }
     container traceoptions {
       description "Traffic sampling trace options";
       uses sampling_traceoptions_type;
     }
     leaf sample-once {
       description "Sample the packet for active-monitoring only once";
       type empty;
     }
     leaf pre-rewrite-tos {
       description "Sample the packet retaining tos value before normalization";
       type empty;
     }
     container input {
       description "Traffic Sampling data acquisition";
       uses sampling_input_type;
     }
     container output {
       description "Traffic sampling data disposition";
       status deprecated;
       junos:must "(!(\".. family\"))";
       junos:must-message " 'sampling family <*> ' and 'sampling output' are mutually exclusive";
       junos:must "(\"forwarding-options sampling input\")";
       junos:must-message "Sampling input configuration is not specified";
       uses sampling_output_type;
     }
     container family {
       description "Address family of packets to sample";
       container inet {
         description "Sample IPv4 packets";
         uses apply-advanced;
         choice enable-disable {
           case case_1 {
             leaf disable {
               description "Disable sampling family inet";
               type empty;
             }
           }
         }
         container input {
           description "Settings for sampling of input packets";
           junos:must "(!(\".. .. .. input\"))";
           junos:must-message "instance <*> 'family <*> input' and 'instance <*> input' are mutually exclusive";
           uses sampling_family_input_type;
         }
         container output {
           description "Traffic sampling data disposition";
           junos:must "((!(\"forwarding-options sampling input family inet\") && (!(\"forwarding-options sampling input family inet6\") && !(\"forwarding-options sampling input family mpls\"))))";
           junos:must-message "output configuration mismatch with old deprecated input configuration";
           junos:must "((\".. .. .. input rate\" || \" .. input rate\"))";
           junos:must-message "sampling input rate is not specified";
           junos:must "((\".. .. .. input\" || \".. input\"))";
           junos:must-message "Sampling input configuration is not specified";
           uses sampling_instance_inet_global_output_type;
         }
       }
       container inet6 {
         description "Sample IPv6 packets";
         uses apply-advanced;
         choice enable-disable {
           case case_1 {
             leaf disable {
               description "Disable sampling family inet6";
               type empty;
             }
           }
         }
         container input {
           description "Settings for sampling of input packets";
           junos:must "(!(\".. .. .. input\"))";
           junos:must-message "instance <*> 'family <*> input' and 'instance <*> input' are mutually exclusive";
           uses sampling_family_input_type;
         }
         container output {
           description "Traffic sampling data disposition";
           junos:must "((!(\"forwarding-options sampling input family inet\") && (!(\"forwarding-options sampling input family inet6\") && !(\"forwarding-options sampling input family mpls\"))))";
           junos:must-message "output configuration mismatch with old deprecated input configuration";
           junos:must "((\".. .. .. input\" || \".. input\"))";
           junos:must-message "Sampling input configuration is not specified";
           uses sampling_family_inet6_output_type;
         }
       }
       container mpls {
         description "Sample mpls packets";
         uses apply-advanced;
         choice enable-disable {
           case case_1 {
             leaf disable {
               description "Disable sampling family mpls";
               type empty;
             }
           }
         }
         container input {
           description "Settings for sampling of input packets";
           junos:must "(!(\".. .. .. input\"))";
           junos:must-message "instance <*> 'family <*> input' and 'instance <*> input' are mutually exclusive";
           uses sampling_family_input_type;
         }
         container output {
           description "Traffic sampling data disposition";
           junos:must "((!(\"forwarding-options sampling input family inet\") && (!(\"forwarding-options sampling input family inet6\") && !(\"forwarding-options sampling input family mpls\"))))";
           junos:must-message "output configuration mismatch with old deprecated input configuration";
           junos:must "((\".. .. .. input\" || \".. input\"))";
           junos:must-message "Sampling input configuration is not specified";
           uses sampling_global_mpls_output_type;
         }
       }
     }
     list instance {
       key name;
       ordered-by user;
       description "Instance of sampling parameters";
       leaf name {
         description "Name for sampling instance";
         junos:must "(!(\"forwarding-options port-mirroring instance $$\"))";
         junos:must-message "Instance $$ is also defined under port-mirroring hierarchy";
         type string;
       }
       uses apply-advanced;
       choice enable-disable {
         case case_1 {
           leaf disable {
             description "Disable sampling instance";
             type empty;
           }
         }
       }
       container input {
         description "Traffic Sampling data acquisition";
         uses sampling_instance_input_type;
       }
       container family {
         description "Address family of packets to sample";
         container inet {
           description "Sample IPv4 packets";
           uses apply-advanced;
           choice enable-disable {
             case case_1 {
               leaf disable {
                 description "Disable instance family inet";
                 status deprecated;
                 type empty;
               }
             }
           }
           container input {
             description "Settings for sampling of input packets";
             junos:must "(!(\".. .. .. input\"))";
             junos:must-message "instance <*> 'family <*> input' and 'instance <*> input' are mutually exclusive";
             uses sampling_family_input_type;
           }
           container output {
             description "Traffic sampling data disposition";
             junos:must "((!(\"forwarding-options sampling input family inet\") && (!(\"forwarding-options sampling input family inet6\") && !(\"forwarding-options sampling input family mpls\"))))";
             junos:must-message "output configuration mismatch with old deprecated input configuration";
             junos:must "((\".. .. .. input\" || \".. input\"))";
             junos:must-message "Sampling input configuration is not specified";
             uses sampling_instance_inet_output_type;
           }
         }
         container inet6 {
           description "Sample IPv6 packets";
           uses apply-advanced;
           choice enable-disable {
             case case_1 {
               leaf disable {
                 description "Disable instance family inet6";
                 status deprecated;
                 type empty;
               }
             }
           }
           container input {
             description "Settings for sampling of input packets";
             junos:must "(!(\".. .. .. input\"))";
             junos:must-message "instance <*> 'family <*> input' and 'instance <*> input' are mutually exclusive";
             uses sampling_family_input_type;
           }
           container output {
             description "Traffic sampling data disposition";
             junos:must "((!(\"forwarding-options sampling input family inet\") && (!(\"forwarding-options sampling input family inet6\") && !(\"forwarding-options sampling input family mpls\"))))";
             junos:must-message "output configuration mismatch with old deprecated input configuration";
             junos:must "((\".. .. .. input\" || \".. input\"))";
             junos:must-message "Sampling input configuration is not specified";
             uses sampling_instance_inet6_output_type;
           }
         }
         container mpls {
           description "Sample mpls packets";
           uses apply-advanced;
           choice enable-disable {
             case case_1 {
               leaf disable {
                 description "Disable instance family mpls";
                 status deprecated;
                 type empty;
               }
             }
           }
           container input {
             description "Settings for sampling of input packets";
             junos:must "(!(\".. .. .. input\"))";
             junos:must-message "instance <*> 'family <*> input' and 'instance <*> input' are mutually exclusive";
             uses sampling_family_input_type;
           }
           container output {
             description "Traffic sampling data disposition";
             junos:must "((!(\"forwarding-options sampling input family inet\") && (!(\"forwarding-options sampling input family inet6\") && !(\"forwarding-options sampling input family mpls\"))))";
             junos:must-message "output configuration mismatch with old deprecated input configuration";
             junos:must "((\".. .. .. input\" || \".. input\"))";
             junos:must-message "Sampling input configuration is not specified";
             uses sampling_instance_mpls_output_type;
           }
         }
         container vpls {
           description "Sample vpls packets";
           status deprecated;
           uses apply-advanced;
           choice enable-disable {
             case case_1 {
               leaf disable {
                 description "Disable instance family vpls";
                 type empty;
               }
             }
           }
           container input {
             description "Settings for sampling of input packets";
             junos:must "(!(\".. .. .. input\"))";
             junos:must-message "instance <*> 'family <*> input' and 'instance <*> input' are mutually exclusive";
             uses sampling_family_input_type;
           }
           container output {
             description "Traffic sampling data disposition";
             junos:must "((\".. .. .. input\" || \".. input\"))";
             junos:must-message "Sampling input configuration is not specified";
             uses sampling_instance_vpls_output_type;
           }
         }
         container bridge {
           junos:must "(!(\".. .. family vpls\"))";
           junos:must-message "bridge and vpls families are mutually exclusive";
           description "Sample bridge packets";
           uses apply-advanced;
           choice enable-disable {
             case case_1 {
               leaf disable {
                 description "Disable instance family bridge";
                 type empty;
               }
             }
           }
           container input {
             description "Settings for sampling of input packets";
             junos:must "(!(\".. .. .. input\"))";
             junos:must-message "instance <*> 'family <*> input' and 'instance <*> input' are mutually exclusive";
             uses sampling_family_input_type;
           }
           container output {
             description "Traffic sampling data disposition";
             junos:must "((\".. .. .. input\" || \".. input\"))";
             junos:must-message "Sampling input configuration is not specified";
             uses sampling_instance_bridge_output_type;
           }
         }
       }
     }
     container jflow-service {
       description "Jflow service configuration";
       uses apply-advanced;
       container traceoptions {
         description "Jflow service trace options";
         uses jflow_service_traceoptions;
       }
     }
     container route-record {
       description "Sampling route record configuration";
       uses apply-advanced;
       container traceoptions {
         description "Sampling route record trace options";
         uses route_record_traceoptions;
       }
     }
   }
   grouping jflow_service_traceoptions {
     description "Traceoptions for jflow-service";
     uses apply-advanced;
     leaf no-remote-trace {
       description "Disable remote tracing";
       junos:must "(\"system tracing\")";
       junos:must-message "'no-remote-trace' is valid only when [system tracing] is configured";
       type empty;
     }
     container file {
       description "Trace file information";
       leaf filename {
         description "Name of file in which to write trace information";
         type string {
           length "1 .. 1024";
           junos:posix-pattern "![/ %]";
           junos:pattern-message "Must not contain '/', % or a space";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     leaf level {
       description "Level of debugging output";
       default "error";
       type enumeration {
         enum "error" {
           description "Match error conditions";
         }
         enum "warning" {
           description "Match warning messages";
         }
         enum "notice" {
           description "Match conditions that should be handled specially";
         }
         enum "info" {
           description "Match informational messages";
         }
         enum "verbose" {
           description "Match verbose messages";
         }
         enum "all" {
           description "Match all levels";
         }
       }
     }
     list flag {
       key name;
       ordered-by user;
       description "Area of jflow-service to enable debuging output";
       leaf name {
         type enumeration {
           enum "parse" {
             description "Trace parsing code";
           }
           enum "rtsock" {
             description "Trace rtsock code";
           }
           enum "sm" {
             description "Trace State machine code";
           }
           enum "all" {
             description "Trace all area of jflow-service code";
           }
         }
       }
     }
   }
   grouping junos_hash_key {
     description "Select data used in the hash key";
     uses apply-advanced;
     container hash-seed {
       presence "enable hash-seed";
       description "Hash seed";
       uses apply-advanced;
       leaf seed-value {
         description "Hash seed value";
         type union {
           type string {
             pattern "<.*>|$.*";
           }
           type uint32 {
             range "0 .. 4294967295";
           }
         }
       }
     }
     container family {
       description "Protocol family";
       container fcoe {
         description "FCoE protocol family";
         uses apply-advanced;
         container ethernet-interfaces {
           description "FCoE hash-key configuration on ethernet interfaces";
           uses apply-advanced;
           leaf oxid {
             description "Originator Exchange ID";
             type enumeration {
               enum "enable" {
                 description "Include Originator Exchange ID in the hash key";
               }
               enum "disable" {
                 description "Do not include Originator Exchange ID in the hash key";
               }
             }
           }
         }
         container fabric-interfaces {
           description "FCoE hash-key configuration on fabric interfaces";
           uses apply-advanced;
           leaf oxid {
             description "Originator Exchange ID";
             type enumeration {
               enum "enable" {
                 description "Include Originator Exchange ID in the hash key";
               }
               enum "disable" {
                 description "Do not include Originator Exchange ID in the hash key";
               }
             }
           }
         }
         leaf oxid {
           description "Originator Exchange ID";
           type enumeration {
             enum "enable" {
               description "Include Originator Exchange ID in the hash key";
             }
             enum "disable" {
               description "Do not include Originator Exchange ID in the hash key";
             }
           }
         }
       }
       container inet {
         description "IPv4 protocol family";
         uses apply-advanced;
         container layer-3 {
           presence "enable layer-3";
           description "Include Layer 3 (IP) data in the hash key";
           uses apply-advanced;
           leaf destination-address {
             description "Include IP destination address in the hash key";
             type empty;
           }
         }
         container layer-4 {
           presence "enable layer-4";
           description "Include Layer 4 (TCP or UDP) data in the hash key";
           uses apply-advanced;
           leaf gtp-tunnel-endpoint-identifier {
             description "Include GTP TEID in the hash key";
             type empty;
           }
         }
         leaf session-id {
           description "Include session ID in the hash key";
           type empty;
         }
         container symmetric-hash {
           presence "enable symmetric-hash";
           junos:must "((\"forwarding-options hash-key family inet layer-3\" || \"forwarding-options hash-key family inet layer-4\"))";
           junos:must-message "layer-3 and/or layer-4 to be configured for symmetric/complement Hash";
           description "Create symmetric hash-key with source & destination ports";
           uses apply-advanced;
           leaf complement {
             description "Create complement of symmetric hash-key";
             type empty;
           }
         }
         leaf no-incoming-port {
           description "Exclude incoming port from the hash key";
           type empty;
         }
       }
       container inet6 {
         description "IPv6 protocol family";
         uses apply-advanced;
         container layer-3 {
           presence "enable layer-3";
           description "Include Layer 3 (IP) data in the hash key";
           uses apply-advanced;
           leaf destination-address {
             description "Include IP destination address in the hash key";
             type empty;
           }
           leaf incoming-interface-index {
             description "Include incoming interface index in the hash key";
             type empty;
           }
           leaf next-header {
             description "Include IP Next Header field in the hash key";
             type empty;
           }
           leaf source-address {
             description "Include IP source address in the hash key";
             type empty;
           }
           leaf traffic-class {
             description "Include Traffic Class field in the hash key";
             type empty;
           }
           leaf ipv6-flow-label {
             description "Include IPV6 flow label field in the hash key";
             type empty;
           }
         }
         container layer-4 {
           presence "enable layer-4";
           description "Include Layer 4 (TCP or UDP) data in the hash key";
           uses apply-advanced;
           leaf destination-port {
             description "Include IP destination port in the hash key";
             type empty;
           }
           leaf source-port {
             description "Include IP source port in the hash key";
             type empty;
           }
           leaf gtp-tunnel-endpoint-identifier {
             description "Include GTP TEID in the hash key";
             type empty;
           }
         }
         leaf session-id {
           description "Include session ID in the hash key";
           type empty;
         }
         leaf no-incoming-port {
           description "Exclude incoming port from the hash key";
           type empty;
         }
       }
       container mpls {
         description "MPLS protocol family";
         uses apply-advanced;
         choice label {
           case case_1 {
             leaf label-1 {
               description "Include the first MPLS label in the hash key";
               type empty;
             }
           }
           case case_2 {
             leaf all-labels {
               description "Include all MPLS labels in hash key";
               type empty;
             }
           }
           case case_3 {
             leaf no-labels {
               description "Exclude all MPLS labels from hash key";
               type empty;
             }
           }
           case case_4 {
             leaf bottom-label-1 {
               description "Include the first MPLS label from bottom-of-stack in the hash key";
               type empty;
             }
           }
         }
         leaf label-2 {
           description "Include the second MPLS label in the hash key";
           junos:must "(\".. label-1\")";
           junos:must-message "Must also specify label 1;";
           type empty;
         }
         leaf label-3 {
           description "Include the third MPLS label in the hash key";
           junos:must "(\".. label-2\")";
           junos:must-message "Must also specify label 2;";
           type empty;
         }
         leaf bottom-label-2 {
           description "Include the second MPLS label from bottom-of-stack in the hash key";
           junos:must "(\".. bottom-label-1\")";
           junos:must-message "Must also specify bottom-label-1. Cannot use top-of-stack labels.";
           type empty;
         }
         leaf bottom-label-3 {
           description "Include the third MPLS label from bottom-of-stack in the hash key";
           junos:must "(\".. bottom-label-2\")";
           junos:must-message "Must also specify bottom-label-2. Cannot use top-of-stack labels.";
           type empty;
         }
         leaf no-label-1-exp {
           description "Omit EXP bits of first MPLS label from the hash key";
           junos:must "((\".. label-1\" || \".. no-labels\"))";
           junos:must-message "Either label-1 or no-labels statement is mandatory";
           type empty;
         }
         container payload {
           junos:must "((\".. label-1\" || (\".. no-labels\" || (\".. all-labels\" || \".. bottom-label-1\"))))";
           junos:must-message "Either label-1, bottom-label-1, all-labels or no-labels statement is mandatory";
           description "Include payload data in the hash key";
           uses apply-advanced;
           container ether-pseudowire {
             presence "enable ether-pseudowire";
             description "Load-balance IP over ethernet PW";
             uses apply-advanced;
             leaf zero-control-word {
               description "MPLS ether-pseudowire payload with zero-control-word preceding ethernet packet";
               type empty;
             }
           }
           container ip {
             presence "enable ip";
             description "Include IPv4 or IPv6 payload data in the hash key";
             uses apply-advanced;
             choice layer-4-select {
               case case_1 {
                 choice ip-payload {
                   case case_1 {
                     leaf layer-3-only {
                       description "Include only layer-3 IP information";
                       type empty;
                     }
                   }
                   case case_2 {
                     leaf enable {
                       description "Include layer3/4 IP payload in the hash key";
                       type empty;
                     }
                   }
                   case case_3 {
                     leaf disable {
                       description "Exclude layer3/4 IP payload in the hash key";
                       type empty;
                     }
                   }
                 }
               }
               case case_2 {
                 container port-data {
                   presence "enable port-data";
                   uses apply-advanced;
                   leaf source-msb {
                     description "Include the most significant byte of the source port";
                     type empty;
                   }
                   leaf source-lsb {
                     description "Include the least significant byte of the source port";
                     type empty;
                   }
                   leaf destination-msb {
                     description "Include the most significant byte of the destination port";
                     type empty;
                   }
                   leaf destination-lsb {
                     description "Include the least significant byte of the destination port";
                     type empty;
                   }
                 }
               }
             }
           }
         }
       }
       container multiservice {
         description "Multiservice protocol family";
         uses apply-advanced;
         leaf source-mac {
           description "Include source MAC address in hash key";
           type empty;
         }
         leaf destination-mac {
           description "Include destination MAC address in hash key";
           type empty;
         }
         leaf label-1 {
           description "Include the first MPLS label in the hash key";
           type empty;
         }
         leaf label-2 {
           description "Include the second MPLS label in the hash key";
           junos:must "(\".. label-1\")";
           junos:must-message "Must also specify label 1;";
           type empty;
         }
         container payload {
           description "Include payload data in the hash key";
           uses apply-advanced;
           container ip {
             description "Include IPv4 payload data in the hash key";
             uses apply-advanced;
             container layer-3 {
               presence "enable layer-3";
               description "Include layer-3 ip info for VPLS/Bridge";
               uses apply-advanced;
               choice layer-3-options {
                 case case_1 {
                   leaf source-ip-only {
                     description "Include source IP only in hash-key";
                     type empty;
                   }
                 }
                 case case_2 {
                   leaf destination-ip-only {
                     description "Include desintation IP only in hash-key";
                     type empty;
                   }
                 }
               }
             }
             leaf layer-4 {
               description "Include layer-4 IP information for VPLS/Bridge";
               type empty;
             }
             leaf layer-3-only {
               description "Include only layer-3 IP information";
               type empty;
             }
           }
         }
         container symmetric-hash {
           presence "enable symmetric-hash";
           junos:must "((\"forwarding-options hash-key family multiservice payload\" || (\"forwarding-options hash-key family multiservice source-mac\" || \"forwarding-options hash-key family multiservice destination-mac\")))";
           junos:must-message "Payload and/or source-MAC and/or destination-MAC to be configured for symmetric/complement Hash";
           description "Create a/symmetric hash-key with any attributes";
           uses apply-advanced;
           leaf complement {
             description "Create complement of symmetric hash-key";
             type empty;
           }
         }
       }
     }
     container resilient-hash-seed {
       presence "enable resilient-hash-seed";
       description "Resilient hash seed";
       uses apply-advanced;
       leaf resilient-seed-value {
         description "Hash seed value for resilient ECMP and LAG";
         type union {
           type string {
             pattern "<.*>|$.*";
           }
           type uint32 {
             range "0 .. 4294967295";
           }
         }
       }
     }
   }
   grouping layer2_pm_family_output_type {
     uses apply-advanced;
     choice interface-or-next-hop-index {
       case case_1 {
         leaf interface {
           description "Interface through which to send sampled traffic";
           type union {
             type jt:interface-name;
             type string {
               pattern "<.*>|$.*";
             }
           }
         }
       }
       case case_2 {
         leaf next-hop-group {
           description "Next-hop-group through which to send port-mirror traffic";
           junos:must "(!(\".. no-filter-check\"))";
           junos:must-message "no-filter-check is not allowed with next-hop-group";
           junos:must "(\"forwarding-options next-hop-group $$ group-type layer-2\")";
           junos:must-message "Referenced next-hop-group must be defined as layer-2 group";
           type string;
         }
       }
       case case_3 {
         list routing-instance {
           key name;
           description "Routing instances";
           max-elements 1;
           uses layer2_pm_output-routing-instance-type;
         }
       }
       case case_4 {
         list vlan {
           key name;
           description "Outgoing VLAN for mirrored packets";
           max-elements 1;
           uses pm-rspan-vlan;
         }
       }
       case case_5 {
         list bridge-domain {
           key name;
           description "Outgoing bridge-domain for mirrored packets";
           max-elements 1;
           uses pm-rspan-bridge-domain;
         }
       }
     }
     leaf no-filter-check {
       description "Do not check for filters on port-mirroring interface";
       type empty;
     }
   }
   grouping layer2_pm_output-routing-instance-type {
     leaf name {
       description "Routing instance name";
       type string {
         junos:posix-pattern "!^((__.*__)|(all)|(.*[ ].*)|(\"\")|(.{129,}))$";
         junos:pattern-message "Must be a non-reserved string of 128 characters or less with no spaces.";
       }
     }
     uses apply-advanced;
     list vlan {
       key name;
       description "Outgoing VLAN for mirrored packets";
       max-elements 1;
       uses pm-rspan-vlan;
     }
     list bridge-domain {
       key name;
       description "Outgoing bridge-domain for mirrored packets";
       max-elements 1;
       uses pm-rspan-bridge-domain;
     }
   }
   grouping ldap-allowed-groups-object {
     leaf name {
       description "LDAP Group name";
       type string {
         length "1 .. 63";
       }
     }
     uses apply-advanced;
     container address-assignment {
       description "Address assignment pool";
       uses apply-advanced;
       leaf pool {
         description "Name of address-assignment pool";
         type string {
           length "1 .. 63";
         }
       }
       leaf inet6-pool {
         description "Name of address-assignment pool for family inet6";
         type string {
           length "1 .. 63";
         }
       }
     }
   }
   grouping ldap-server-object {
     leaf name {
       description "Hostname or IPv4 address of LDAP server";
       type string {
         junos:posix-pattern "^[[:alnum:]._-]+$";
         junos:pattern-message "Hostname can only contain alphanumeric characters, '.', '-', and '_'. The format of IPv4 address is 'n.n.n.n'";
       }
     }
     uses apply-advanced;
     leaf port {
       description "LDAP server port number";
       default "389";
       type union {
         type string {
           pattern "<.*>|$.*";
         }
         type uint16 {
           range "1 .. 65535";
         }
       }
     }
     leaf source-address {
       description "Use specified address as source address";
       type jt:ipv4addr;
     }
     leaf routing-instance {
       description "Use specified routing instance";
       junos:must "((\"routing-instances $$\" || any \"tenants <*> routing-instances $$\"))";
       junos:must-message "referenced routing-instance must be defined";
       type string;
     }
     leaf retry {
       description "Number of times to resend requests";
       default "3";
       type union {
         type string {
           pattern "<.*>|$.*";
         }
         type uint32 {
           range "1 .. 10";
         }
       }
     }
     leaf timeout {
       description "Delay before resending unacknowledged request";
       default "5";
       units "seconds";
       type union {
         type string {
           pattern "<.*>|$.*";
         }
         type uint32 {
           range "3 .. 90";
         }
       }
     }
     leaf tls-type {
       type enumeration {
         enum "start-tls" {
           description "Negotiate start-tls for connection";
         }
       }
     }
     leaf tls-timeout {
       description "Limit on tls handshake time";
       default "5";
       units "seconds";
       type union {
         type string {
           pattern "<.*>|$.*";
         }
         type uint32 {
           range "3 .. 90";
         }
       }
     }
     leaf tls-min-version {
       default "v1.2";
       type enumeration {
         enum "v1.1" {
           description "Require tls 1.1 and 1.2";
         }
         enum "v1.2" {
           description "Require tls 1.2";
         }
       }
     }
     leaf no-tls-certificate-check {
       description "Do not validate peer certificate";
       type empty;
     }
     leaf tls-peer-name {
       description "Expected peer fdqn";
       type string {
         length "1 .. 255";
       }
     }
   }
   grouping ldp-sync-obj {
     uses apply-advanced;
     choice enable-disable {
       case case_1 {
         leaf disable {
           description "Disable LDP synchronization";
           type empty;
         }
       }
     }
     leaf hold-time {
       description "Time during which maximum metric is advertised";
       type union {
         type string {
           pattern "<.*>|$.*";
         }
         type uint32 {
           range "1 .. 65535";
         }
       }
     }
   }
   grouping ldp_filter_obj {
     description "Filter to apply to tracing";
     leaf match-on {
       description "Argument on which to match";
       type enumeration {
         enum "fec" {
           description "Filter based on FEC associated to the traced object.";
         }
         enum "address" {
           description "Filter based on packet source and destination addresses.";
         }
       }
     }
     leaf-list policy {
       ordered-by user;
       description "Filter policy";
       type jt:policy-algebra;
     }
   }
   grouping localauth-subscriber-object {
     leaf name {
       description "Subscriber username";
       type string;
     }
     uses apply-advanced;
     leaf password {
       description "Password for the subscriber";
       type string {
         length "1 .. 64";
       }
     }
     leaf framed-ip-address {
       description "IP address to assign to the subscriber";
       type jt:ipv4addr;
     }
     leaf framed-pool {
       description "Pool name to assign an IP address to the subscriber";
       junos:must "(\"access address-assignment pool $$\")";
       junos:must-message "referenced address pool must be defined";
       type string {
         length "1 .. 63";
       }
     }
     leaf delegated-pool {
       description "Pool name to assign an IPv6 delegated prefix to the subscriber";
       junos:must "(\"access address-assignment pool $$\")";
       junos:must-message "referenced address pool must be defined";
       type string {
         length "1 .. 64";
       }
     }
     leaf framed-ipv6-pool {
       description "Pool name to assign an IPv6 address or NDRA prefix to the subscriber";
       junos:must "(\"access address-assignment pool $$\")";
       junos:must-message "referenced address pool must be defined";
       type string {
         length "1 .. 64";
       }
     }
     choice ri_or_ls {
       case case_1 {
         leaf target-routing-instance {
           description "Routing instance to be assigned to the subscriber";
           type string;
         }
       }
       case case_2 {
         container target-logical-system {
           presence "enable target-logical-system";
           description "Logical system to be assigned to the subscriber";
           uses apply-advanced;
           leaf logical-system-name {
             description "Logical system name";
             junos:must "(\"logical-systems $$\")";
             junos:must-message "Referenced logical system must be defined";
             type string;
           }
           leaf target-routing-instance {
             description "Routing instance ";
             type string;
           }
         }
       }
     }
   }
   grouping log-object {
     description "Configure security log";
     uses apply-advanced;
     list exclude {
       key name;
       ordered-by user;
       description "List of security log criteria to exclude from the audit log";
       status deprecated;
       leaf name {
         description "Exclude criteria name";
         type string;
       }
       uses apply-advanced;
       leaf destination-address {
         description "Destination address";
         type jt:ipaddr;
       }
       leaf destination-port {
         description "Destination port";
         type union {
           type uint32;
           type string {
             pattern "<.*>|$.*";
           }
         }
       }
       leaf event-id {
         description "Event ID filter";
         type string;
       }
       leaf failure {
         description "Event was a failure";
         type empty;
       }
       leaf interface-name {
         description "Name of interface";
         type string;
       }
       leaf policy-name {
         description "Policy name filter";
         type string;
       }
       leaf process {
         description "Process that generated the event";
         type string;
       }
       leaf protocol {
         description "Protocol filter";
         type string;
       }
       leaf source-address {
         description "Source address";
         type jt:ipaddr;
       }
       leaf source-port {
         description "Source port";
         type union {
           type uint32;
           type string {
             pattern "<.*>|$.*";
           }
         }
       }
       leaf success {
         description "Event was successful";
         type empty;
       }
       leaf username {
         description "Username filter";
         type string;
       }
     }
     leaf limit {
       description "Limit number of security log entries to keep in memory";
       status deprecated;
       default "10000";
       type union {
         type uint32;
         type string {
           pattern "<.*>|$.*";
         }
       }
     }
     container cache {
       presence "enable cache";
       description "Cache security log events in the audit log buffer";
       uses apply-advanced;
       list exclude {
         key name;
         ordered-by user;
         description "List of security log criteria to exclude from the audit log";
         junos:must "(!(\".. .. exclude\"))";
         junos:must-message "'security log cache exclude' and 'security log exclude' are mutually exclusive";
         leaf name {
           description "Exclude criteria name";
           type string;
         }
         uses apply-advanced;
         leaf destination-address {
           description "Destination address";
           type jt:ipaddr;
         }
         leaf destination-port {
           description "Destination port";
           type union {
             type uint32;
             type string {
               pattern "<.*>|$.*";
             }
           }
         }
         leaf event-id {
           description "Event ID filter";
           type string;
         }
         leaf failure {
           description "Event was a failure";
           type empty;
         }
         leaf interface-name {
           description "Name of interface";
           type string;
         }
         leaf policy-name {
           description "Policy name filter";
           type string;
         }
         leaf process {
           description "Process that generated the event";
           type string;
         }
         leaf protocol {
           description "Protocol filter";
           type string;
         }
         leaf source-address {
           description "Source address";
           type jt:ipaddr;
         }
         leaf source-port {
           description "Source port";
           type union {
             type uint32;
             type string {
               pattern "<.*>|$.*";
             }
           }
         }
         leaf success {
           description "Event was successful";
           type empty;
         }
         leaf username {
           description "Username filter";
           type string;
         }
       }
       leaf limit {
         description "Limit number of security log entries to keep in memory";
         default "10000";
         junos:must "(!(\".. .. limit\"))";
         junos:must-message "'security log cache limit' and 'security log limit' are mutually exclusive";
         type union {
           type uint32;
           type string {
             pattern "<.*>|$.*";
           }
         }
       }
     }
     list host {
       key name;
       ordered-by user;
       max-elements 10;
       leaf name {
         description "Name of host to notify";
         type string {
           junos:posix-pattern "^[[:alnum:]:._-]+$";
           junos:pattern-message "Must be a string of letters, numbers, dashes, colons or underscores";
         }
       }
       uses apply-advanced;
       list contents {
         key name;
         leaf name {
           description "Facility type";
           type enumeration {
             enum "services" {
               description "Adaptive Services PIC";
             }
           }
         }
         choice level {
           case case_1 {
             leaf any {
               description "All levels";
               type empty;
             }
           }
           case case_2 {
             leaf emergency {
               description "Panic conditions";
               type empty;
             }
           }
           case case_3 {
             leaf alert {
               description "Conditions that should be corrected immediately";
               type empty;
             }
           }
           case case_4 {
             leaf critical {
               description "Critical conditions";
               type empty;
             }
           }
           case case_5 {
             leaf error {
               description "Error conditions";
               type empty;
             }
           }
           case case_6 {
             leaf warning {
               description "Warning messages";
               type empty;
             }
           }
           case case_7 {
             leaf notice {
               description "Conditions that should be handled specially";
               type empty;
             }
           }
           case case_8 {
             leaf info {
               description "Informational messages";
               type empty;
             }
           }
           case case_9 {
             leaf none {
               description "No messages";
               type empty;
             }
           }
         }
       }
       leaf facility-override {
         description "Alternate facility for logging to remote host";
         type enumeration {
           enum "authorization" {
             description "Authorization system";
           }
           enum "daemon" {
             description "Various system processes";
           }
           enum "ftp" {
             description "FTP process";
           }
           enum "kernel" {
             description "Kernel";
           }
           enum "user" {
             description "User processes";
           }
           enum "local0" {
             description "Local logging option number 0";
           }
           enum "local1" {
             description "Local logging option number 1";
           }
           enum "local2" {
             description "Local logging option number 2";
           }
           enum "local3" {
             description "Local logging option number 3";
           }
           enum "local4" {
             description "Local logging option number 4";
           }
           enum "local5" {
             description "Local logging option number 5";
           }
           enum "local6" {
             description "Local logging option number 6";
           }
           enum "local7" {
             description "Local logging option number 7";
           }
         }
       }
       leaf log-prefix {
         description "Prefix for all logging to this host";
         type string {
           junos:posix-pattern "![ =:]{1,15}";
           junos:pattern-message "Must be a string of 15 characters or less";
         }
       }
       leaf port {
         description "UDP port for syslogd on the host";
         type union {
           type string {
             pattern "<.*>|$.*";
           }
           type uint16 {
             range "1 .. 65535";
           }
         }
       }
       container class {
         description "Syslog messages classes";
         uses apply-advanced;
         container session-logs {
           presence "enable session-logs";
           description "Allow syslog messages for session events";
           uses apply-advanced;
           container open {
             presence "enable open";
             description "Allow syslog messages for session open events";
           }
           container close {
             presence "enable close";
             description "Allow syslog messages for session close events";
           }
         }
         container packet-logs {
           presence "enable packet-logs";
           description "Allow syslog messages for packet related events";
         }
         container stateful-firewall-logs {
           presence "enable stateful-firewall-logs";
           description "Allow syslog messages for stateful firewall events";
         }
         container alg-logs {
           presence "enable alg-logs";
           description "Allow syslog messages for ALG events";
         }
         container nat-logs {
           presence "enable nat-logs";
           description "Allow syslog messages for NAT events";
           uses apply-advanced;
           container deterministic-nat-configuration-log {
             presence "enable deterministic-nat-configuration-log";
             description "Allow syslog messages for Determinisitic NAT config events";
           }
         }
         container ids-logs {
           presence "enable ids-logs";
           description "Allow syslog messages for IDS events";
         }
         container pcp-logs {
           presence "enable pcp-logs";
           description "PCP logs";
           container map {
             presence "enable map";
             description "Allow syslog messages for PCP";
           }
           container debug {
             presence "enable debug";
             description "Allow PCP debug syslogs";
           }
         }
         container ha-logs {
           description "Stateful high availability logs";
           uses apply-advanced;
           container open-synchronized {
             presence "enable open-synchronized";
             description "Allow syslog message for session open events";
           }
           container close-synchronized {
             presence "enable close-synchronized";
             description "Allow syslog message for session close events";
           }
         }
         container urlf-logs {
           presence "enable urlf-logs";
           description "Allow syslog messages for URLF events";
         }
       }
       leaf source-address {
         description "Use specified address as source address";
         type jt:ipv4addr;
       }
       container tcp-log {
         presence "enable tcp-log";
         description "Enable tcp log for this service-set";
         uses apply-advanced;
         leaf source-address {
           description "Source address for tcp logging";
           junos:must "(!(\".. .. source-address\"))";
           junos:must-message "source-address must not be configured under host when tcp-log is configured";
           type jt:ipaddr;
         }
         leaf vrf-name {
           description "Routing instance name for tcp logging";
           junos:must "(\"routing-instances $$\")";
           junos:must-message "referenced routing instance must be defined";
           type string;
         }
         leaf ssl-profile {
           description "SSL profile name for tcp logging";
           junos:must "(\"services ssl initiation profile $$\")";
           junos:must-message "referenced ssl profile must be defined";
           type string {
             length "1 .. 63";
           }
         }
       }
     }
     leaf message-rate-limit {
       description "Maximum syslog messages per second allowed from this interface. Applies per member if set at aggregate level";
       units "messages per second";
       type union {
         type string {
           pattern "<.*>|$.*";
         }
         type uint32 {
           range "0 .. 2147483647";
         }
       }
     }
     leaf disable {
       description "Disable security logging for the device";
       type empty;
     }
     leaf utc-timestamp {
       description "Use UTC time for security log timestamps";
       type empty;
     }
     leaf mode {
       description "Controls how security logs are processed and exported";
       type enumeration {
         enum "stream" {
           description "Process security logs directly in the forwarding plane";
         }
         enum "event" {
           description "Process security logs in the control plane";
         }
         enum "stream-event" {
           description "Process security logs in both forwarding plane and control plane";
         }
       }
     }
     leaf event-rate {
       description "Control plane event rate";
       units "logs per second";
       junos:must "((\"security log mode event\" || (\"services service-set ${service-set} syslog mode event\" || (\"security log mode stream-event\" || \"services service-set ${service-set} syslog mode stream-event\"))))";
       junos:must-message "To configure event-rate, security log must be in event or stream-event mode";
       type union {
         type string {
           pattern "<.*>|$.*";
         }
         type uint32 {
           range "0 .. 1500";
         }
       }
     }
     leaf format {
       description "Set security log format for the device";
       type enumeration {
         enum "syslog" {
           description "Traditional syslog";
         }
         enum "sd-syslog" {
           description "Structured syslog";
         }
         enum "binary" {
           description "Binary log";
         }
       }
     }
     leaf escape {
       description "Enable escape defined by RFC5424 for the sd and binary format logs";
       type empty;
     }
     container time-format {
       description "Configure year or millisecond for syslog";
       uses time-format-object;
     }
     leaf rate-cap {
       description "Data plane event rate";
       units "logs per second";
       type union {
         type string {
           pattern "<.*>|$.*";
         }
         type uint32 {
           range "0 .. 5000";
         }
       }
     }
     leaf max-database-record {
       description "Maximum records in database";
       default "0";
       type union {
         type string {
           pattern "<.*>|$.*";
         }
         type uint32;
       }
     }
     container report {
       presence "enable report";
       description "Set security log report settings";
       uses apply-advanced;
       container logs-per-table {
         presence "enable logs-per-table";
         description "Log number per table in database";
         uses apply-advanced;
         leaf session-all {
           description "Log number of session";
           type union {
             type string {
               pattern "<.*>|$.*";
             }
             type uint32;
           }
         }
         leaf screen {
           description "Log number of screen";
           type union {
             type string {
               pattern "<.*>|$.*";
             }
             type uint32;
           }
         }
         leaf idp {
           description "Log number of idp";
           type union {
             type string {
               pattern "<.*>|$.*";
             }
             type uint32;
           }
         }
         leaf utm {
           description "Log number of utm";
           type union {
             type string {
               pattern "<.*>|$.*";
             }
             type uint32;
           }
         }
         leaf ipsec-vpn {
           description "Log number of ipsec-vpn";
           type union {
             type string {
               pattern "<.*>|$.*";
             }
             type uint32;
           }
         }
         leaf sky {
           description "Log number of sky";
           type union {
             type string {
               pattern "<.*>|$.*";
             }
             type uint32;
           }
         }
       }
       leaf table-lifetime {
         description "Table lifetime day(s)";
         default "90";
         type union {
           type string {
             pattern "<.*>|$.*";
           }
           type uint32 {
             range "0 .. 365";
           }
         }
       }
       container table-mode {
         presence "enable table-mode";
         description "Report table mode";
         uses apply-advanced;
         leaf dense {
           description "Applicable when massive log and long duration";
           type empty;
         }
       }
       container database-filter {
         presence "enable database-filter";
         description "Check the logs whether should be inserted into database";
         uses apply-advanced;
         list event-category {
           key name;
           ordered-by user;
           description "Filter by event-category";
           leaf name {
             description "Name";
             type enumeration {
               enum "session" {
                 description "Session log";
               }
               enum "screen" {
                 description "Screen log";
               }
               enum "idp" {
                 description "IDP log";
               }
               enum "webfilter" {
                 description "Webfilter log";
               }
               enum "content-filter" {
                 description "Content-filter log";
               }
               enum "anti-virus" {
                 description "Antivirus log";
               }
               enum "anti-spam" {
                 description "Anti-spam log";
               }
               enum "ipsec" {
                 description "IPsec VPN log";
               }
               enum "sky" {
                 description "Sky ATP log";
               }
               enum "secintel" {
                 description "Secintel log";
               }
               enum "icap" {
                 description "ICAP log";
               }
               enum "ssl-proxy" {
                 description "SSL proxy log";
               }
               enum "dnsf" {
                 description "DNSF log";
               }
               enum "session-create" {
                 description "Session create log";
               }
               enum "session-close" {
                 description "Session close log";
               }
               enum "session-deny" {
                 description "Session deny log";
               }
             }
           }
           uses apply-advanced;
         }
         leaf exclude {
           description "Exclude the logs";
           type empty;
         }
       }
     }
     choice source {
       case case_1 {
         leaf source-address {
           description "Source ip address used when exporting security logs";
           junos:must "(!(\"services service-set ${service-set} syslog mode event\"))";
           junos:must-message "To configure source address, mode must be stream or stream-event";
           type jt:ipaddr;
         }
       }
       case case_2 {
         leaf source-interface {
           description "Source interface used when exporting security logs";
           junos:must "(!(\"services service-set ${service-set} syslog mode event\"))";
           junos:must-message "To configure source interface, mode must be stream or stream-event";
           type union {
             type jt:interface-name;
             type string {
               pattern "<.*>|$.*";
             }
           }
         }
       }
     }
     container transport {
       presence "enable transport";
       junos:must "(!(\"services service-set ${service-set} syslog mode event\"))";
       junos:must-message "To configure transport info, mode must be stream or stream-event";
       description "Set security log transport settings";
       uses apply-advanced;
       leaf tcp-connections {
         description "Set tcp connection number per-stream";
         type union {
           type string {
             pattern "<.*>|$.*";
           }
           type uint32 {
             range "1 .. 5";
           }
         }
       }
       leaf protocol {
         description "Set security log transport protocol for the device";
         type enumeration {
           enum "udp" {
             description "UDP transfer for log";
           }
           enum "tcp" {
             description "TCP transfer for log";
           }
           enum "tls" {
             description "TLS transfer for log";
           }
         }
       }
       leaf tls-profile {
         description "TLS profile";
         junos:must "(\"services ssl initiation profile $$\")";
         junos:must-message "SSl profile must be defined under [services ssl initiation profile]";
         type string;
       }
     }
     leaf facility-override {
       description "Alternate facility for logging to remote host";
       type enumeration {
         enum "authorization" {
           description "Authorization system";
         }
         enum "daemon" {
           description "Various system processes";
         }
         enum "ftp" {
           description "FTP process";
         }
         enum "kernel" {
           description "Kernel";
         }
         enum "user" {
           description "User processes";
         }
         enum "local0" {
           description "Local logging option number 0";
         }
         enum "local1" {
           description "Local logging option number 1";
         }
         enum "local2" {
           description "Local logging option number 2";
         }
         enum "local3" {
           description "Local logging option number 3";
         }
         enum "local4" {
           description "Local logging option number 4";
         }
         enum "local5" {
           description "Local logging option number 5";
         }
         enum "local6" {
           description "Local logging option number 6";
         }
         enum "local7" {
           description "Local logging option number 7";
         }
       }
     }
     leaf local-log-tag {
       description "Tag included in logs";
       junos:must "(!(\"services service-set ${service-set} syslog mode stream\"))";
       junos:must-message "To configure local-log-tag, mode must be event or stream-event";
       type string {
         junos:posix-pattern "![ =:]{1,15}";
         junos:pattern-message "Must be a string of 15 characters or less";
       }
     }
     list local-category {
       key name;
       ordered-by user;
       description "Selects the type of events that may be logged locally";
       junos:must "(!(\"services service-set ${service-set} syslog mode stream\"))";
       junos:must-message "To configure local-category, mode must be event or stream-event";
       leaf name {
         type enumeration {
           enum "all" {
             description "All events are logged";
           }
           enum "content-security" {
             description "Content security events are logged";
           }
           enum "fw-auth" {
             description "Fw-auth events are logged";
           }
           enum "screen" {
             description "Screen events are logged";
           }
           enum "alg" {
             description "Alg events are logged";
           }
           enum "nat" {
             description "Nat events are logged";
           }
           enum "flow" {
             description "Flow events are logged";
           }
           enum "sctp" {
             description "Sctp events are logged";
           }
           enum "gtp" {
             description "Gtp events are logged";
           }
           enum "ipsec" {
             description "Ipsec events are logged";
           }
           enum "idp" {
             description "Idp events are logged";
           }
           enum "rtlog" {
             description "Rtlog events are logged";
           }
           enum "pst-ds-lite" {
             description "Pst-ds-lite events are logged";
           }
           enum "appqos" {
             description "Appqos events are logged";
           }
           enum "secintel" {
             description "Secintel events are logged";
           }
           enum "aamw" {
             description "AAMW events are logged";
           }
           enum "sfw" {
             description "Stateful Firewall events are logged";
           }
           enum "session" {
             description "Session open and close events are logged";
           }
           enum "session-open" {
             description "Session open events are logged";
           }
           enum "session-close" {
             description "Session close events are logged";
           }
           enum "urlf" {
             description "URLF events are logged";
           }
           enum "ha" {
             description "Stateful High-Availability open and close events are logged";
           }
           enum "ha-open" {
             description "Stateful High-Availability open events are logged";
           }
           enum "ha-close" {
             description "Stateful High-Availability close events are logged";
           }
           enum "pcp" {
             description "PCP logs";
           }
           enum "dnsf" {
             description "DNSF";
           }
         }
       }
       uses apply-advanced;
     }
     leaf root-streaming {
       description "Logs will be streamed from the Root LSYS";
       type empty;
     }
     list stream {
       key name;
       ordered-by user;
       description "Set security log stream settings";
       junos:must "(!(\"services service-set ${service-set} syslog mode event\"))";
       junos:must-message "To configure stream, mode must be stream or stream-event";
       max-elements 8;
       leaf name {
         description "Name of security log stream";
         type string {
           length "1 .. 63";
           junos:posix-pattern "^[[:alnum:]._-]+$";
           junos:pattern-message "Must be a string consisting of letters, numbers, dashes and underscores";
         }
       }
       uses apply-advanced;
       leaf severity {
         description "Severity threshold for security logs";
         type enumeration {
           enum "emergency" {
             description "Conditions that cause security functions to stop";
           }
           enum "alert" {
             description "Conditions that require immediate attention";
           }
           enum "critical" {
             description "Critical conditions";
           }
           enum "error" {
             description "General error conditions";
           }
           enum "warning" {
             description "General warning conditions";
           }
           enum "notice" {
             description "Non-error conditions that are of interest";
           }
           enum "info" {
             description "Information about normal security operations";
           }
           enum "debug" {
             description "Information normally used in debugging";
           }
         }
       }
       leaf format {
         description "Specify the log stream format";
         type enumeration {
           enum "syslog" {
             description "Traditional syslog";
           }
           enum "sd-syslog" {
             description "Structured syslog";
           }
           enum "welf" {
             description "Web Trends Extended Log Format";
           }
           enum "binary" {
             description "Binary log";
           }
         }
       }
       list category {
         key name;
         ordered-by user;
         description "Selects the type of events that may be logged";
         junos:must "(!(\"security log stream ${stream} filter\"))";
         junos:must-message "Category is exclusive with filter";
         leaf name {
           type enumeration {
             enum "all" {
               description "All events are logged";
             }
             enum "content-security" {
               description "Content security events are logged";
             }
             enum "fw-auth" {
               description "Fw-auth events are logged";
             }
             enum "screen" {
               description "Screen events are logged";
             }
             enum "alg" {
               description "Alg events are logged";
             }
             enum "nat" {
               description "Nat events are logged";
             }
             enum "flow" {
               description "Flow events are logged";
             }
             enum "sctp" {
               description "Sctp events are logged";
             }
             enum "gtp" {
               description "Gtp events are logged";
             }
             enum "ipsec" {
               description "Ipsec events are logged";
             }
             enum "idp" {
               description "Idp events are logged";
             }
             enum "rtlog" {
               description "Rtlog events are logged";
             }
             enum "pst-ds-lite" {
               description "Pst-ds-lite events are logged";
             }
             enum "appqos" {
               description "Appqos events are logged";
             }
             enum "secintel" {
               description "Secintel events are logged";
             }
             enum "aamw" {
               description "AAMW events are logged";
             }
             enum "sfw" {
               description "Stateful Firewall events are logged";
             }
             enum "session" {
               description "Session open and close events are logged";
             }
             enum "session-open" {
               description "Session open events are logged";
             }
             enum "session-close" {
               description "Session close events are logged";
             }
             enum "urlf" {
               description "URLF events are logged";
             }
             enum "ha" {
               description "Stateful High-Availability open and close events are logged";
             }
             enum "ha-open" {
               description "Stateful High-Availability open events are logged";
             }
             enum "ha-close" {
               description "Stateful High-Availability close events are logged";
             }
             enum "pcp" {
               description "PCP logs";
             }
             enum "dnsf" {
               description "DNSF";
             }
           }
         }
         uses apply-advanced;
       }
       list filter {
         key name;
         ordered-by user;
         description "Selects the filter to filter the logs to be logged";
         junos:must "(!(\"security log stream ${stream} category\"))";
         junos:must-message "filter is exclusive with category";
         leaf name {
           type enumeration {
             enum "threat-attack" {
               description "Threat-attack security events are logged";
             }
           }
         }
         uses apply-advanced;
       }
       container host {
         description "Destination to send security logs to";
         junos:must "(!(\"security log stream ${stream} file\"))";
         junos:must-message "host is exclusive with file";
         junos:must "((\"security log source-address\" || (\"security log source-interface\" || (\"security log stream ${stream} source-address\" || (\"services service-set ${service-set} syslog source-interface\" || (\"services service-set ${service-set} syslog source-address\" || \"services service-set ${service-set} syslog stream ${stream} source-address\"))))))";
         junos:must-message "To configure host stream, security log source-address/source-interface must be configured";
         uses host-object;
       }
       container rate-limit {
         description "Rate-limit for security logs";
         uses apply-advanced;
         leaf rate {
           description "Log rate";
           units "logs per second";
           type union {
             type string {
               pattern "<.*>|$.*";
             }
             type uint32 {
               range "1 .. 65535";
             }
           }
         }
       }
       container file {
         junos:must "(!(\"security log stream ${stream} host\"))";
         junos:must-message "file is exclusive with host";
         description "Security log file options for logs in local file";
         uses apply-advanced;
         leaf localfilename {
           description "Name of local log file";
           type string {
             length "1 .. 256";
             junos:posix-pattern "![/ %]";
             junos:pattern-message "Must not contain '/', % or a space";
           }
         }
         leaf size {
           description "Maximum size of local log file in megabytes";
           type union {
             type string {
               pattern "<.*>|$.*";
             }
             type uint32;
           }
         }
         leaf rotation {
           description "Maximum number of rotate files";
           default "10";
           type union {
             type string {
               pattern "<.*>|$.*";
             }
             type uint32;
           }
         }
         leaf allow-duplicates {
           description "To disable log consolidation";
           type empty;
         }
       }
       container transport {
         presence "enable transport";
         description "Set security log transport settings";
         uses apply-advanced;
         leaf tcp-connections {
           description "Set tcp connection number per-stream";
           type union {
             type string {
               pattern "<.*>|$.*";
             }
             type uint32 {
               range "1 .. 5";
             }
           }
         }
         leaf protocol {
           description "Set security log transport protocol for the device";
           type enumeration {
             enum "udp" {
               description "UDP transfer for log";
             }
             enum "tcp" {
               description "TCP transfer for log";
             }
             enum "tls" {
               description "TLS transfer for log";
             }
           }
         }
         leaf tls-profile {
           description "TLS profile";
           junos:must "(\"services ssl initiation profile $$\")";
           junos:must-message "SSL profile must be defined under [services ssl initiation profile]";
           type string;
         }
       }
       container time-format {
         description "Configure year or millisecond for syslog";
         uses time-format-object;
       }
       leaf source-address {
         description "Source ip address used when exporting security logs";
         type jt:ipaddr;
       }
     }
     container file {
       description "Security log file options for logs in binary/protobuf format";
       uses apply-advanced;
       leaf filename {
         description "Name of log file";
         type string {
           length "1 .. 256";
         }
       }
       leaf size {
         description "Maximum size of log file in megabytes";
         type union {
           type string {
             pattern "<.*>|$.*";
           }
           type uint32 {
             range "1 .. 10";
           }
         }
       }
       leaf path {
         description "Path to log files";
         type string {
           length "1 .. 256";
         }
       }
       leaf files {
         description "Maximum number of log files";
         type union {
           type string {
             pattern "<.*>|$.*";
           }
           type uint32 {
             range "2 .. 10";
           }
         }
       }
     }
     container apply {
       description "Apply settings from other features";
       uses apply-advanced;
       leaf dscp-code-point {
         description "Apply setting class-of-service host-outbound-traffic dscp-code-point";
         junos:must "(\"class-of-service host-outbound-traffic dscp-code-point\")";
         junos:must-message "class-of-service host-outbound-traffic dscp-code-point must be defined";
         type empty;
       }
     }
     container traceoptions {
       description "Security log daemon trace options";
       uses apply-advanced;
       leaf no-remote-trace {
         description "Disable remote tracing";
         junos:must "(\"system tracing\")";
         junos:must-message "'no-remote-trace' is valid only when [system tracing] is configured";
         type empty;
       }
       container file {
         description "Trace file information";
         leaf filename {
           description "Name of file in which to write trace information";
           type string {
             length "1 .. 1024";
             junos:posix-pattern "![/ %]";
             junos:pattern-message "Must not contain '/', % or a space";
           }
         }
         leaf size {
           description "Maximum trace file size";
           type string;
         }
         leaf files {
           description "Maximum number of trace files";
           default "3";
           type union {
             type string {
               pattern "<.*>|$.*";
             }
             type uint32 {
               range "2 .. 1000";
             }
           }
         }
         choice world-readable-choice {
           leaf world-readable {
             description "Allow any user to read the log file";
             type empty;
           }
           leaf no-world-readable {
             description "Don't allow any user to read the log file";
             type empty;
           }
         }
         leaf match {
           description "Regular expression for lines to be logged";
           type jt:regular-expression;
         }
       }
       list flag {
         key name;
         ordered-by user;
         description "List of things to include in trace";
         leaf name {
           type enumeration {
             enum "source" {
               description "Communication with security log forwarder";
             }
             enum "configuration" {
               description "Reading of configuration";
             }
             enum "all" {
               description "Everything";
             }
             enum "report" {
               description "Trace report";
             }
             enum "hpl" {
               description "Trace HPL logging";
             }
           }
         }
       }
     }
     list profile {
       key name;
       ordered-by user;
       description "Security log profile setting";
       max-elements 10;
       leaf name {
         description "Name of security log profile";
         type string {
           length "1 .. 63";
           junos:posix-pattern "^[[:alnum:].-]+$";
           junos:pattern-message "Must be a string consisting of letters, numbers, dashes";
         }
       }
       uses apply-advanced;
       list stream-name {
         key name;
         ordered-by user;
         description "Use which stream ";
         junos:must "((\".. category\" || \".. template\"))";
         junos:must-message "To send logs must define cagetory or template";
         max-elements 4;
         leaf name {
           description "Name of the stream";
           junos:must "(\"security log stream $$\")";
           junos:must-message "stream must be defined under [security log stream]";
           type string;
         }
         uses apply-advanced;
       }
       container category {
         presence "enable category";
         junos:must "(!(\" .. template\"))";
         junos:must-message "Cannot configure category and template for the same profile";
         description "Selects the category of events for the profile";
         uses apply-advanced;
         container session {
           presence "enable session";
           description "Select session category";
           uses apply-advanced;
           list field-extra-name {
             key name;
             description "Select the extra Fields, only apply to sd-syslog and syslog formt";
             leaf name {
               description "The name of the extra field";
               type enumeration {
                 enum "sd-id" {
                   description "Add SD-ID field, only apply to sd-syslog and syslog formt";
                 }
                 enum "hostname" {
                   description "Add hostname field, only apply to sd-syslog and syslog formt";
                 }
                 enum "timestamp" {
                   description "Add timestamp field, only apply to sd-syslog and syslog formt";
                 }
               }
             }
             uses apply-advanced;
           }
           list field-name {
             key name;
             ordered-by user;
             description "Select the fields by order";
             leaf name {
               description "The name of the field";
               type string;
             }
             uses apply-advanced;
           }
         }
         container webfilter {
           presence "enable webfilter";
           description "Select webfilter category";
           uses apply-advanced;
           list field-extra-name {
             key name;
             description "Select the extra Fields, only apply to sd-syslog and syslog formt";
             leaf name {
               description "The name of the extra field";
               type enumeration {
                 enum "sd-id" {
                   description "Add SD-ID field, only apply to sd-syslog and syslog formt";
                 }
                 enum "hostname" {
                   description "Add hostname field, only apply to sd-syslog and syslog formt";
                 }
                 enum "timestamp" {
                   description "Add timestamp field, only apply to sd-syslog and syslog formt";
                 }
               }
             }
             uses apply-advanced;
           }
           list field-name {
             key name;
             ordered-by user;
             description "Select the fields by order";
             leaf name {
               description "The name of the field";
               type string;
             }
             uses apply-advanced;
           }
         }
         container antivirus {
           presence "enable antivirus";
           description "Select antivirus category";
           uses apply-advanced;
           list field-extra-name {
             key name;
             description "Select the extra Fields, only apply to sd-syslog and syslog formt";
             leaf name {
               description "The name of the extra field";
               type enumeration {
                 enum "sd-id" {
                   description "Add SD-ID field, only apply to sd-syslog and syslog formt";
                 }
                 enum "hostname" {
                   description "Add hostname field, only apply to sd-syslog and syslog formt";
                 }
                 enum "timestamp" {
                   description "Add timestamp field, only apply to sd-syslog and syslog formt";
                 }
               }
             }
             uses apply-advanced;
           }
           list field-name {
             key name;
             ordered-by user;
             description "Select the fields by order";
             leaf name {
               description "The name of the field";
               type string;
             }
             uses apply-advanced;
           }
         }
         container content-filter {
           presence "enable content-filter";
           description "Select content-filter category";
           uses apply-advanced;
           list field-extra-name {
             key name;
             description "Select the extra Fields, only apply to sd-syslog and syslog formt";
             leaf name {
               description "The name of the extra field";
               type enumeration {
                 enum "sd-id" {
                   description "Add SD-ID field, only apply to sd-syslog and syslog formt";
                 }
                 enum "hostname" {
                   description "Add hostname field, only apply to sd-syslog and syslog formt";
                 }
                 enum "timestamp" {
                   description "Add timestamp field, only apply to sd-syslog and syslog formt";
                 }
               }
             }
             uses apply-advanced;
           }
           list field-name {
             key name;
             ordered-by user;
             description "Select the fields by order";
             leaf name {
               description "The name of the field";
               type string;
             }
             uses apply-advanced;
           }
         }
         container antispam {
           presence "enable antispam";
           description "Select antispam category";
           uses apply-advanced;
           list field-extra-name {
             key name;
             description "Select the extra Fields, only apply to sd-syslog and syslog formt";
             leaf name {
               description "The name of the extra field";
               type enumeration {
                 enum "sd-id" {
                   description "Add SD-ID field, only apply to sd-syslog and syslog formt";
                 }
                 enum "hostname" {
                   description "Add hostname field, only apply to sd-syslog and syslog formt";
                 }
                 enum "timestamp" {
                   description "Add timestamp field, only apply to sd-syslog and syslog formt";
                 }
               }
             }
             uses apply-advanced;
           }
           list field-name {
             key name;
             ordered-by user;
             description "Select the fields by order";
             leaf name {
               description "The name of the field";
               type string;
             }
             uses apply-advanced;
           }
         }
         container idp {
           presence "enable idp";
           description "Select idp category";
           uses apply-advanced;
           list field-extra-name {
             key name;
             description "Select the extra Fields, only apply to sd-syslog and syslog formt";
             leaf name {
               description "The name of the extra field";
               type enumeration {
                 enum "sd-id" {
                   description "Add SD-ID field, only apply to sd-syslog and syslog formt";
                 }
                 enum "hostname" {
                   description "Add hostname field, only apply to sd-syslog and syslog formt";
                 }
                 enum "timestamp" {
                   description "Add timestamp field, only apply to sd-syslog and syslog formt";
                 }
               }
             }
             uses apply-advanced;
           }
           list field-name {
             key name;
             ordered-by user;
             description "Select the fields by order";
             leaf name {
               description "The name of the field";
               type string;
             }
             uses apply-advanced;
           }
         }
         container secintel {
           presence "enable secintel";
           description "Select secintel category";
           uses apply-advanced;
           list field-extra-name {
             key name;
             description "Select the extra Fields, only apply to sd-syslog and syslog formt";
             leaf name {
               description "The name of the extra field";
               type enumeration {
                 enum "sd-id" {
                   description "Add SD-ID field, only apply to sd-syslog and syslog formt";
                 }
                 enum "hostname" {
                   description "Add hostname field, only apply to sd-syslog and syslog formt";
                 }
                 enum "timestamp" {
                   description "Add timestamp field, only apply to sd-syslog and syslog formt";
                 }
               }
             }
             uses apply-advanced;
           }
           list field-name {
             key name;
             ordered-by user;
             description "Select the fields by order";
             leaf name {
               description "The name of the field";
               type string;
             }
             uses apply-advanced;
           }
         }
         container aamw {
           presence "enable aamw";
           description "Select aamw category";
           uses apply-advanced;
           list field-extra-name {
             key name;
             description "Select the extra Fields, only apply to sd-syslog and syslog formt";
             leaf name {
               description "The name of the extra field";
               type enumeration {
                 enum "sd-id" {
                   description "Add SD-ID field, only apply to sd-syslog and syslog formt";
                 }
                 enum "hostname" {
                   description "Add hostname field, only apply to sd-syslog and syslog formt";
                 }
                 enum "timestamp" {
                   description "Add timestamp field, only apply to sd-syslog and syslog formt";
                 }
               }
             }
             uses apply-advanced;
           }
           list field-name {
             key name;
             ordered-by user;
             description "Select the fields by order";
             leaf name {
               description "The name of the field";
               type string;
             }
             uses apply-advanced;
           }
         }
         container ssl-proxy {
           presence "enable ssl-proxy";
           description "Select ssl-proxy category";
           uses apply-advanced;
           list field-extra-name {
             key name;
             description "Select the extra Fields, only apply to sd-syslog and syslog formt";
             leaf name {
               description "The name of the extra field";
               type enumeration {
                 enum "sd-id" {
                   description "Add SD-ID field, only apply to sd-syslog and syslog formt";
                 }
                 enum "hostname" {
                   description "Add hostname field, only apply to sd-syslog and syslog formt";
                 }
                 enum "timestamp" {
                   description "Add timestamp field, only apply to sd-syslog and syslog formt";
                 }
               }
             }
             uses apply-advanced;
           }
           list field-name {
             key name;
             ordered-by user;
             description "Select the fields by order";
             leaf name {
               description "The name of the field";
               type string;
             }
             uses apply-advanced;
           }
         }
         container apptrack {
           presence "enable apptrack";
           description "Select apptrack category";
           uses apply-advanced;
           list field-extra-name {
             key name;
             description "Select the extra Fields, only apply to sd-syslog and syslog formt";
             leaf name {
               description "The name of the extra field";
               type enumeration {
                 enum "sd-id" {
                   description "Add SD-ID field, only apply to sd-syslog and syslog formt";
                 }
                 enum "hostname" {
                   description "Add hostname field, only apply to sd-syslog and syslog formt";
                 }
                 enum "timestamp" {
                   description "Add timestamp field, only apply to sd-syslog and syslog formt";
                 }
               }
             }
             uses apply-advanced;
           }
           list field-name {
             key name;
             ordered-by user;
             description "Select the fields by order";
             leaf name {
               description "The name of the field";
               type string;
             }
             uses apply-advanced;
           }
         }
       }
       container default-profile {
         presence "enable default-profile";
         uses apply-advanced;
         leaf activate {
           description "Set this profile as default profile";
           type empty;
         }
       }
       container template {
         presence "enable template";
         junos:must "(!(\" .. category\"))";
         junos:must-message "Cannot configure category and template for the same profile";
         description "Select the template for the profile";
         uses apply-advanced;
         choice template-id {
           case case_1 {
             leaf traditional-firewall {
               description "Traditional-firewall";
               type empty;
             }
           }
           case case_2 {
             leaf unified-ngfw {
               description "Unified-ngfw";
               type empty;
             }
           }
           case case_3 {
             leaf sd-wan {
               description "Sd-wan";
               type empty;
             }
           }
         }
       }
     }
   }
   grouping host-object {
     uses apply-advanced;
     leaf ipaddr {
       description "IP address/Host name";
       type string {
         length "1 .. 256";
       }
     }
     leaf port {
       description "Host port number";
       type union {
         type uint16;
         type string {
           pattern "<.*>|$.*";
         }
       }
     }
     leaf routing-instance {
       description "Routing-instance name";
       junos:must "(((\"security\" && \"routing-instances $$ instance-type virtual-router\") || \"services\"))";
       junos:must-message "Virtual router must be defined under [routing-instances]";
       junos:must "(\"routing-instances $$\")";
       junos:must-message "Routing-instance must be defined";
       type string;
     }
     leaf log-tag {
       description "Tag included in logs to this host";
       type string {
         junos:posix-pattern "![ =:]{1,15}";
         junos:pattern-message "Must be a string of 15 characters or less";
       }
     }
   }
   grouping logical-system-type {
     description "Logical system name";
     leaf name {
       description "Logical system name";
       junos:must "(\"logical-systems $$\")";
       junos:must-message "Logical systems must be defined under [logical-systems] ";
       type string;
     }
     uses apply-advanced;
     leaf max-sessions {
       description "Max number of IDP sessions";
       type union {
         type uint32;
         type string {
           pattern "<.*>|$.*";
         }
       }
     }
   }
   grouping lsp-set-match-type {
     uses apply-advanced;
     leaf lsp-name {
       description "LSP name that matches this string";
       junos:must "((!(\".. lsp-regex\") && (!(\".. p2mp-name\") && !(\".. p2mp-regex\"))))";
       junos:must-message "Can't configure lsp-name when lsp-regex or p2mp-name or p2mp-regex is configured";
       type string;
     }
     leaf lsp-regex {
       description "All LSPs that match this regular expression pattern";
       junos:must "((!(\".. lsp-name\") && (!(\".. p2mp-name\") && !(\".. p2mp-regex\"))))";
       junos:must-message "Can't configure lsp-regex when lsp-name or p2mp-name or p2mp-regex is configured";
       type string;
     }
     leaf p2mp-name {
       description "P2MP names that match this string";
       junos:must "((!(\".. lsp-name\") && (!(\".. lsp-regex\") && !(\".. p2mp-regex\"))))";
       junos:must-message "Can't configure p2mp-name when lsp-name or lsp-regex or p2mp-regex is configured";
       type string;
     }
     leaf p2mp-regex {
       description "P2MP names that match this regular expression pattern";
       junos:must "((!(\".. lsp-name\") && (!(\".. lsp-regex\") && !(\".. p2mp-name\"))))";
       junos:must-message "Can't configure p2mp-regex when lsp-name or lsp-regex or p2mp-name is configured";
       type string;
     }
     choice router-type {
       case case_1 {
         leaf egress {
           description "All LSPs for which this router is egress";
           type empty;
         }
       }
       case case_2 {
         leaf ingress {
           description "All LSPs for which this router is ingress";
           type empty;
         }
       }
       case case_3 {
         leaf transit {
           description "All LSPs for which this router is transit";
           type empty;
         }
       }
     }
   }
   grouping lsp_nh_obj {
     leaf name {
       description "LSP to use to reach destination";
       type string;
     }
     uses apply-advanced;
     leaf preference {
       description "Preference of LSP next hop";
       type union {
         type uint32;
         type string {
           pattern "<.*>|$.*";
         }
       }
     }
     leaf metric {
       description "Metric of LSP next hop";
       type union {
         type uint32;
         type string {
           pattern "<.*>|$.*";
         }
       }
     }
   }
   grouping macro-data-type {
     leaf name {
       description "Keyword part of the keyword-value pair";
       type string;
     }
     leaf value {
       description "Value part of the keyword-value pair";
       type string;
     }
   }
   grouping martian_type {
     description "Invalid routes";
     leaf address {
       description "IP address or hostname";
       type jt:ipprefix;
     }
     leaf choice-ident {
       type enumeration {
         enum "exact" {
         }
         enum "longer" {
         }
         enum "orlonger" {
         }
         enum "upto" {
         }
         enum "through" {
         }
         enum "prefix-length-range" {
         }
         enum "allow" {
         }
       }
     }
     leaf choice-value {
       type string;
     }
     leaf allow {
       type empty;
     }
   }
   grouping message-object {
     uses apply-advanced;
     container v0 {
       description "GTPv0 message type";
       uses apply-advanced;
       leaf msg-list-name {
         description "GTP message list name";
         junos:must "((\"security gprs gtp message-list $$\" || \"security gtp message-list $$\"))";
         junos:must-message "referenced message-list not found";
         type string {
           length "1 .. 23";
         }
       }
     }
     container v1 {
       description "GTPv1 message type";
       uses apply-advanced;
       leaf msg-list-name {
         description "GTP message list name";
         junos:must "((\"security gprs gtp message-list $$\" || \"security gtp message-list $$\"))";
         junos:must-message "referenced message-list not found";
         type string {
           length "1 .. 23";
         }
       }
     }
     container v2 {
       description "GTPv2 message type";
       uses apply-advanced;
       leaf msg-list-name {
         description "GTP message list name";
         junos:must "((\"security gprs gtp message-list $$\" || \"security gtp message-list $$\"))";
         junos:must-message "referenced message-list not found";
         type string {
           length "1 .. 23";
         }
       }
     }
   }
   grouping mime-list-type {
     description "Configure mime-list object";
     leaf name {
       description "Configure name of mime-list object";
       type string {
         length "1 .. 40";
         junos:posix-pattern "^[a-zA-Z_]+[a-zA-Z_0-9-]*$";
         junos:pattern-message "Must be a string beginning with a letter or underscore and consisting of letters, numbers, dashes and underscores.";
       }
     }
     uses apply-advanced;
     leaf-list value {
       ordered-by user;
       description "Configure MIME value";
       type string {
         length "1 .. 249";
       }
     }
   }
   grouping mirror-filter-type {
     description "Secuirty mirror filter settings";
     leaf name {
       description "Name of the filter";
       type string {
         length "1 .. 63";
         junos:posix-pattern "^[[:alnum:]._-]+$";
         junos:pattern-message "Must be a string of letters, numbers, dashes or underscores";
       }
     }
     uses apply-advanced;
     leaf protocol {
       description "Match IP protocol type";
       type string;
     }
     leaf source-prefix {
       description "Source IP address prefix";
       type jt:ipprefix;
     }
     leaf destination-prefix {
       description "Destination IP address prefix";
       type jt:ipprefix;
     }
     leaf source-port {
       description "Match TCP/UDP source port";
       type string;
     }
     leaf destination-port {
       description "Match TCP/UDP destination port";
       type string;
     }
     leaf interface-in {
       description "Incoming Logical interface";
       type union {
         type jt:interface-name;
         type string {
           pattern "<.*>|$.*";
         }
       }
     }
     leaf interface-out {
       description "Outgoing Logical interface";
       type union {
         type jt:interface-name;
         type string {
           pattern "<.*>|$.*";
         }
       }
     }
     container output {
       description "Configure output interface and MAC address";
       uses apply-advanced;
       leaf interface {
         description "Outgoing Logical interface";
         type union {
           type jt:interface-name;
           type string {
             pattern "<.*>|$.*";
           }
         }
       }
       leaf destination-mac {
         description "MAC address to match";
         type string;
       }
     }
   }
   grouping mirror-profile-attributes {
     description "Mirror profile attributes";
     leaf name {
       description "Mirror profile name";
       type string {
         length "1 .. 63";
         junos:posix-pattern "!^((__.*__)|(all)|(.*[ ].*)|(\"\")|(.{129,}))$";
         junos:pattern-message "Must be a non-reserved string of 128 characters or less with no spaces.";
       }
     }
     uses apply-advanced;
     leaf ptp-packet-timestamp {
       description "Enable precision-time-protocol packet timestamp";
       junos:must "(\".. collector\")";
       junos:must-message "configure collector details when packet-timestamp is enabled";
       type empty;
     }
     container collector {
       description "Send mirrored traffic to collector";
       uses apply-advanced;
       leaf ip-address {
         description "Collector destination ip-address";
         type jt:ipaddr;
       }
       leaf l4-port {
         description "Layer 4 UDP/TCP port number of the collector";
         type union {
           type uint16;
           type string {
             pattern "<.*>|$.*";
           }
         }
       }
       container routing-instance {
         presence "enable routing-instance";
         description "Routing instances";
         uses apply-advanced;
         leaf routing-instance-name {
           description "Routing instance name";
           type string {
             junos:posix-pattern "!^((__.*__)|(all)|(.*[ ].*)|(\"\")|(.{129,}))$";
             junos:pattern-message "Must be a non-reserved string of 128 characters or less with no spaces.";
           }
         }
         leaf ip-address {
           description "Collector destination ip-address";
           type jt:ipaddr;
         }
         leaf l4-port {
           description "Layer 4 UDP/TCP port number of the collector";
           type union {
             type uint16;
             type string {
               pattern "<.*>|$.*";
             }
           }
         }
       }
     }
     leaf observation-domain-id {
       description "Observation domain Id";
       type union {
         type uint16;
         type string {
           pattern "<.*>|$.*";
         }
       }
     }
   }
   grouping monitoring_input_type {
     uses apply-advanced;
     list interface {
       key name;
       ordered-by user;
       leaf name {
         description "Interface which will be monitored";
         type union {
           type jt:interface-name;
           type string {
             pattern "<.*>|$.*";
           }
         }
       }
       uses apply-advanced;
     }
   }
   grouping monitoring_output_type {
     uses apply-advanced;
     leaf export-format {
       description "Format for sending monitoring information";
       type enumeration {
         enum "cflowd-version-5" {
           description "Export in cflowd version 5 format";
         }
       }
     }
     leaf destination-address {
       description "Address to which monitored packets will be sent";
       status deprecated;
       type jt:ipv4addr;
     }
     leaf destination-port {
       description "Port to which monitored packets will be sent";
       status deprecated;
       type union {
         type uint16;
         type string {
           pattern "<.*>|$.*";
         }
       }
     }
     leaf source-address {
       description "Address to use for generating monitored packets";
       status deprecated;
       type jt:ipv4addr;
     }
     leaf flow-active-timeout {
       description "Interval after which an active flow is exported";
       default "1800";
       units "seconds";
       type union {
         type string {
           pattern "<.*>|$.*";
         }
         type uint32 {
           range "60 .. 1800";
         }
       }
     }
     leaf flow-inactive-timeout {
       description "Interval of inactivity that marks a flow inactive";
       default "60";
       units "seconds";
       type union {
         type string {
           pattern "<.*>|$.*";
         }
         type uint32 {
           range "15 .. 1800";
         }
       }
     }
     leaf flow-export-destination {
       description "Destination for flow export";
       type enumeration {
         enum "collector-pic" {
           description "Send flow information to collector PIC";
         }
         enum "cflowd-collector" {
           description "Send flow information to cflowd collector";
         }
       }
     }
     list cflowd {
       key name;
       description "Collector destination where flow records are sent";
       junos:must "(!(\".. flow-export-destination collector-pic\"))";
       junos:must-message "cflowd cannot be configured when flow collection mode is set";
       uses cflowd_monitoring_type;
     }
     list interface {
       key name;
       description "Interfaces used to send monitored information";
       uses monitor_export_intf_type;
     }
   }
   grouping cflowd_monitoring_type {
     leaf name {
       description "Name of host collecting cflowd packets";
       type jt:ipaddr;
     }
     uses apply-advanced;
     leaf port {
       description "UDP port number on host collecting cflowd packets";
       type union {
         type uint16;
         type string {
           pattern "<.*>|$.*";
         }
       }
     }
     leaf dscp {
       description "Numeric DSCP value in the range 0 to 63";
       default "0";
       junos:must "(\".. .. inline-jflow\")";
       junos:must-message "DSCP can be configured for inline-jflow";
       type union {
         type string {
           pattern "<.*>|$.*";
         }
         type uint8 {
           range "0 .. 63";
         }
       }
     }
     leaf forwarding-class {
       description "Forwarding-class for exported jflow packets, applicable only for inline-jflow";
       junos:must "(\".. .. inline-jflow\")";
       junos:must-message "forwarding-class can be configured for inline-jflow";
       type string {
         length "1 .. 64";
       }
     }
     leaf routing-instance {
       description "Name of routing instance on which flow collector is reachable";
       junos:must "(\".. .. inline-jflow\")";
       junos:must-message "Routing Instances can be configured for inline-jflow";
       junos:must "(\"routing-instances $$ instance-type vrf\")";
       junos:must-message "routing instance should be defined and should be of type Virtual routing forwarding instance(VRF)";
       type string;
     }
   }
   grouping monitor_export_intf_type {
     leaf name {
       description "Interface to be used for sending monitored information";
       type union {
         type jt:interface-name;
         type string {
           pattern "<.*>|$.*";
         }
       }
     }
     uses apply-advanced;
     leaf engine-id {
       description "Identity (number) of this monitoring interface";
       type union {
         type uint8;
         type string {
           pattern "<.*>|$.*";
         }
       }
     }
     leaf engine-type {
       description "Type (number) of this monitoring interface";
       type union {
         type uint8;
         type string {
           pattern "<.*>|$.*";
         }
       }
     }
     leaf input-interface-index {
       description "Input interface index for records from this interface";
       default "0";
       type union {
         type uint32;
         type string {
           pattern "<.*>|$.*";
         }
       }
     }
     leaf output-interface-index {
       description "Output interface index for records from this interface";
       default "0";
       type union {
         type uint32;
         type string {
           pattern "<.*>|$.*";
         }
       }
     }
     leaf source-address {
       description "Address to use for generating monitored packets";
       type jt:ipv4addr;
     }
   }
   grouping mpls_pm_family_output_type {
     uses apply-advanced;
     leaf server-profile {
       description "Server profile name";
       junos:must "((\"services hosted-services server-profile $$\" && (\"services hosted-services server-profile $$ server-address\" && \"services hosted-services server-profile $$ client-address\")))";
       junos:must-message "Only complete server profiles configured under [services hosted-services server-profile] can be configured here";
       type string {
         length "3 .. 32";
       }
     }
   }
   grouping mrp-trace-options {
     description "Trace options for MMRP Protocol";
     uses apply-advanced;
     container file {
       description "Trace file options";
       leaf filename {
         description "Name of file in which to write trace information";
         type string {
           length "1 .. 1024";
           junos:posix-pattern "![/ %]";
           junos:pattern-message "Must not contain '/', % or a space";
         }
       }
       leaf replace {
         description "Replace trace file rather than appending to it";
         status deprecated;
         type empty;
       }
       leaf size {
         description "Maximum trace file size";
         type string;
       }
       leaf files {
         description "Maximum number of trace files";
         default "10";
         type union {
           type string {
             pattern "<.*>|$.*";
           }
           type uint32 {
             range "2 .. 1000";
           }
         }
       }
       leaf no-stamp {
         description "Do not timestamp trace file";
         status deprecated;
         type empty;
       }
       choice world-readable-choice {
         leaf world-readable {
           description "Allow any user to read the log file";
           type empty;
         }
         leaf no-world-readable {
           description "Don't allow any user to read the log file";
           type empty;
         }
       }
     }
     list flag {
       key name;
       ordered-by user;
       description "Tracing parameters";
       junos:must "(\".. file\")";
       junos:must-message "Trace file name required to enable tracing";
       leaf name {
         type enumeration {
           enum "events" {
             description "Trace events to the protocol state machine";
           }
           enum "pdu" {
             description "Trace RAPS PDU reception and transmission";
           }
           enum "timers" {
             description "Trace protocol timers";
           }
           enum "state-machine" {
             description "Trace information of the state machine";
           }
           enum "socket" {
             description "Trace soccket activity";
           }
           enum "error" {
             description "Trace all failure conditions";
           }
           enum "all" {
             description "Trace all";
           }
         }
       }
       leaf disable {
         description "Disable this trace flag";
         type empty;
       }
     }
   }
   grouping mstp-interface {
     leaf name {
       type string;
     }
     uses apply-advanced;
     leaf priority {
       description "Interface priority (in increments of 16 - 0,16,..240)";
       type union {
         type string {
           pattern "<.*>|$.*";
         }
         type uint16 {
           range "0 .. 255";
         }
       }
     }
     leaf cost {
       description "Cost of the interface";
       type union {
         type string {
           pattern "<.*>|$.*";
         }
         type uint32 {
           range "1 .. 200000000";
         }
       }
     }
     leaf mode {
       description "Interface mode (P2P or shared)";
       type enumeration {
         enum "point-to-point" {
           description "Interface mode is point-to-point";
         }
         enum "shared" {
           description "Interface mode is shared";
         }
       }
     }
     leaf edge {
       description "Port is an edge port";
       type empty;
     }
     leaf access-trunk {
       description "Send/Receive untagged RSTP BPDUs on this interface";
       type empty;
     }
     container bpdu-timeout-action {
       presence "enable bpdu-timeout-action";
       description "Define action on BPDU expiry (Loop Protect)";
       uses apply-advanced;
       leaf block {
         description "Block the interface";
         type empty;
       }
       leaf alarm {
         description "Generate an alarm";
         type empty;
       }
     }
     leaf no-root-port {
       description "Do not allow the interface to become root (Root Protect)";
       type empty;
     }
     leaf disable {
       description "Disable Spanning Tree on port";
       type empty;
     }
   }
   grouping multicast_interface_options_type {
     description "Multicast interface options";
     leaf name {
       description "Interface name";
       type union {
         type jt:interface-unit;
         type string {
           pattern "<.*>|$.*";
         }
       }
     }
     uses apply-advanced;
     container maximum-bandwidth {
       presence "enable maximum-bandwidth";
       description "Maximum multicast bandwidth for the interface";
       leaf bandwidth-limit {
         description "Maximum multicast bandwidth on the interface";
         units "bps";
         type string;
       }
     }
     choice enable-disable {
       case case_1 {
         leaf enable {
           description "Enable Multicast";
           status deprecated;
           type empty;
         }
       }
       case case_2 {
         leaf disable {
           description "Disable Multicast";
           status deprecated;
           type empty;
         }
       }
     }
     container reverse-oif-mapping {
       presence "enable reverse-oif-mapping";
       description "Enable reverse OIF mapping on the multicast interface";
       uses apply-advanced;
       leaf no-qos-adjust {
         description "Disable reverse OIF mapping QoS adjustment";
         type empty;
       }
     }
     leaf subscriber-leave-timer {
       description "Timeout in seconds to credit back the bandwidth on the subscriber interface";
       units "seconds";
       junos:must "(\".. reverse-oif-mapping\")";
       junos:must-message "reverse-oif-mapping must be set";
       type union {
         type string {
           pattern "<.*>|$.*";
         }
         type uint32 {
           range "0 .. 30";
         }
       }
     }
     leaf no-qos-adjust {
       description "Disable QoS adjustment for this interface";
       type empty;
     }
   }
   grouping multilink-object {
     description "Configuration for Multilink";
     uses apply-advanced;
     leaf fragment-threshold {
       description "Fragmentation threshold";
       units "bytes";
       type union {
         type string {
           pattern "<.*>|$.*";
         }
         type uint16 {
           range "128 .. 9192";
         }
       }
     }
     leaf drop-timeout {
       description "Drop timeout";
       default "0";
       units "milliseconds";
       type union {
         type string {
           pattern "<.*>|$.*";
         }
         type uint16 {
           range "0 .. 2000";
         }
       }
     }
   }
   grouping named-address-book-type {
     description "Configure global address book";
     leaf name {
       description "Address book name";
       type string;
     }
     uses apply-advanced;
     leaf description {
       description "Text description of address book";
       type string {
         length "1 .. 900";
         junos:posix-pattern "^[^&<>\n]+$";
         junos:pattern-message "Must be a string excluding '&', '<', '>' and '\n'";
       }
     }
     list address {
       key name;
       ordered-by user;
       description "Define a security address";
       uses address_type;
     }
     list address-set {
       key name;
       ordered-by user;
       description "Define a security address set";
       uses address_set_type;
     }
     container attach {
       junos:must "(!(\"security address-book global attach\"))";
       junos:must-message "It is not allowed to attach the global address book to any particular interface, zone or routing-instance.";
       description "Attach this address book to interface, zone or routing-instance";
       uses apply-advanced;
       list zone {
         key name;
         ordered-by user;
         description "Define a zone to be attached";
         leaf name {
           description "Security zone name";
           junos:must "(unique \"security address-book <*> attach zone $$\")";
           junos:must-message "Security zone must be unique in address books";
           junos:must "(\"security zones security-zone $$\")";
           junos:must-message "Security zone must be defined";
           type string {
             length "1 .. 63";
           }
         }
         uses apply-advanced;
       }
     }
   }
   grouping address_set_type {
     leaf name {
       description "Security address-set name";
       junos:must "(!(\".. .. address $$\"))";
       junos:must-message "Security address and address-set cannot have same name";
       type string {
         length "1 .. 63";
         junos:posix-pattern "^[[:alnum:]][[:alnum:]:./_-]*$";
         junos:pattern-message "Must be a string beginning with a number or letter and consisting of letters, numbers, colons, periods, slashes, dashes and underscores";
       }
     }
     uses apply-advanced;
     leaf description {
       description "Text description of address set";
       type string {
         length "1 .. 900";
         junos:posix-pattern "^[^&<>\n]+$";
         junos:pattern-message "Must be a string excluding '&', '<', '>' and '\n'";
       }
     }
     list address {
       key name;
       ordered-by user;
       description "Address to be included in this set";
       max-elements 16384;
       leaf name {
         description "Security address name";
         junos:must "(\".. .. .. address $$\")";
         junos:must-message "referenced address must be defined under address-book";
         type string {
           length "1 .. 63";
           junos:posix-pattern "^[[:alnum:]][[:alnum:]:./_-]*$";
           junos:pattern-message "Must be a string beginning with a number or letter and consisting of letters, numbers, colons, periods, slashes, dashes and underscores";
         }
       }
       uses apply-advanced;
     }
     list address-set {
       key name;
       ordered-by user;
       description "Define an address-set name";
       max-elements 16384;
       leaf name {
         junos:must "(\".. .. .. address-set $$\")";
         junos:must-message "referenced address must be defined under address-book";
         type string {
           length "1 .. 63";
           junos:posix-pattern "^[[:alnum:]][[:alnum:]:./_-]*$";
           junos:pattern-message "Must be a string beginning with a number or letter and consisting of letters, numbers, colons, periods, slashes, dashes and underscores";
         }
       }
       uses apply-advanced;
     }
   }
   grouping address_type {
     leaf name {
       description "Security address name";
       type string {
         length "1 .. 63";
         junos:posix-pattern "^[[:alnum:]][[:alnum:]:./_-]*$";
         junos:pattern-message "Must be a string beginning with a number or letter and consisting of letters, numbers, colons, periods, slashes, dashes and underscores";
       }
     }
     uses apply-advanced;
     leaf description {
       description "Text description of address";
       type string {
         length "1 .. 900";
         junos:posix-pattern "^[^&<>\n]+$";
         junos:pattern-message "Must be a string excluding '&', '<', '>' and '\n'";
       }
     }
     choice address-content {
       case case_1 {
         leaf ip-prefix {
           description "Numeric IPv4 or IPv6 address with prefix";
           type jt:ipprefix;
         }
       }
       case case_2 {
         list dns-name {
           key name;
           ordered-by user;
           description "DNS address name";
           max-elements 1;
           uses dns-name-type;
         }
       }
       case case_3 {
         list wildcard-address {
           key name;
           ordered-by user;
           description "Numeric IPv4 wildcard address with in the form of a.d.d.r/netmask";
           max-elements 1;
           uses wildcard-address-type;
         }
       }
       case case_4 {
         list range-address {
           key name;
           ordered-by user;
           description "Address range";
           max-elements 1;
           uses range-address-type;
         }
       }
       case case_5 {
         list address-range {
           key name;
           ordered-by user;
           description "Address range";
           max-elements 1;
           uses usf-range-address-type;
         }
       }
     }
   }
   grouping dns-name-type {
     description "DNS address name";
     leaf name {
       description "Fully qualified hostname";
       type string {
         length "1 .. 253";
         junos:posix-pattern "^[[:alnum:]._-]+$|^\\\\*$";
         junos:pattern-message "Must be a valid DNS name";
       }
     }
     uses apply-advanced;
     leaf ipv4-only {
       description "IPv4 dns address";
       type empty;
     }
     leaf ipv6-only {
       description "IPv6 dns address";
       junos:must "(!(\".. ipv4-only\"))";
       junos:must-message "ipv4-only and ipv6-only cannot be configured together";
       type empty;
     }
   }
   grouping nat-object {
     description "Configure Network Address Translation";
     uses apply-advanced;
     container source {
       description "Configure Source NAT";
       uses ssg-source-nat-object;
     }
     container destination {
       description "Configure Destination NAT";
       uses ssg-destination-nat-object;
     }
     container static {
       description "Configure Static NAT";
       uses ssg-static-nat-object;
     }
     container proxy-arp {
       description "Configure Proxy ARP";
       uses ssg-proxy-arp-object;
     }
     container proxy-ndp {
       description "Configure Proxy NDP";
       uses ssg-proxy-ndp-object;
     }
     container natv6v4 {
       description "Configure NAT between IPv6 and IPv4 options";
       uses apply-advanced;
       leaf no-v6-frag-header {
         description "V6 packet does not always add fragment header when performing nat translation from v4 side to v6 side ";
         type empty;
       }
     }
     leaf allow-overlapping-pools {
       description "IP addresses of NAT pools can overlap with other pool";
       type empty;
     }
     container traceoptions {
       description "NAT trace options";
       uses apply-advanced;
       leaf no-remote-trace {
         description "Disable remote tracing";
         junos:must "(\"system tracing\")";
         junos:must-message "'no-remote-trace' is valid only when [system tracing] is configured";
         type empty;
       }
       container file {
         description "Trace file information";
         leaf filename {
           description "Name of file in which to write trace information";
           type string {
             length "1 .. 1024";
             junos:posix-pattern "![/ %]";
             junos:pattern-message "Must not contain '/', % or a space";
           }
         }
         leaf size {
           description "Maximum trace file size";
           type string;
         }
         leaf files {
           description "Maximum number of trace files";
           default "3";
           type union {
             type string {
               pattern "<.*>|$.*";
             }
             type uint32 {
               range "2 .. 1000";
             }
           }
         }
         choice world-readable-choice {
           leaf world-readable {
             description "Allow any user to read the log file";
             type empty;
           }
           leaf no-world-readable {
             description "Don't allow any user to read the log file";
             type empty;
           }
         }
         leaf match {
           description "Regular expression for lines to be logged";
           type jt:regular-expression;
         }
       }
       list flag {
         key name;
         ordered-by user;
         description "Tracing parameters";
         leaf name {
           type enumeration {
             enum "configuration" {
               description "Trace configuration events";
             }
             enum "flow" {
               description "Trace flow events";
             }
             enum "routing-socket" {
               description "Trace routing socket events";
             }
             enum "routing-protocol" {
               description "Trace routing protocol events";
             }
             enum "all" {
               description "Trace everything";
             }
             enum "source-nat-re" {
               description "Trace source nat events on RE side";
             }
             enum "source-nat-rt" {
               description "Trace source nat events on PFE-RT side";
             }
             enum "source-nat-pfe" {
               description "Trace source nat events on PFE-ukernel side";
             }
             enum "destination-nat-re" {
               description "Trace destination nat events on RE side";
             }
             enum "destination-nat-rt" {
               description "Trace destination nat events on PFE-RT side";
             }
             enum "destination-nat-pfe" {
               description "Trace destination nat events on PFE-ukernel side";
             }
             enum "static-nat-re" {
               description "Trace static nat events on RE side";
             }
             enum "static-nat-rt" {
               description "Trace static nat events on PFE-RT side";
             }
             enum "static-nat-pfe" {
               description "Trace static nat events on PFE-ukernel side";
             }
             enum "nat-svc-set-re" {
               description "Trace NAT and svc-set events on RE side";
             }
           }
         }
         leaf syslog {
           description "Write NAT flow traces to system log also";
           type empty;
         }
       }
     }
     list pool {
       key name;
       ordered-by user;
       description "Define a NAT pool";
       uses nat_pool_object;
     }
     list ipv6-multicast-interfaces {
       key name;
       ordered-by user;
       description "Enable IPv6 multicast filter for IPv6 NAT";
       leaf name {
         description "Interface name";
         type string;
       }
       uses apply-advanced;
       leaf disable {
         description "Disable IPv6 multicast filter for IPv6 NAT";
         type empty;
       }
     }
     leaf allow-overlapping-nat-pools {
       description "Allow usage of overlapping and same nat pools in multiple service sets";
       type empty;
     }
     list rule {
       key name;
       ordered-by user;
       description "Define a NAT rule";
       uses nat_rule_object;
     }
     list port-forwarding {
       key name;
       ordered-by user;
       description "Define a port-forwarding pool";
       uses pf_mapping;
     }
     list rule-set {
       key name;
       ordered-by user;
       description "Defines a set of NAT rules";
       max-elements 16960;
       leaf name {
         description "Name of the rule set";
         type string {
           length "1 .. 63";
           junos:posix-pattern "^[[:alnum:]][[:alnum:]/.:_-]*$";
           junos:pattern-message "Must be a string beginning with a number or letter and consisting of letters, numbers, dashes, underscores, forward slashes, colons and dots.";
         }
       }
       uses apply-advanced;
       list rule {
         key name;
         ordered-by user;
         description "Rule to be included in this rule set";
         max-elements 16960;
         leaf name {
           description "Rule name";
           junos:must "(\"services nat rule $$\")";
           junos:must-message "rule must be configured";
           type string {
             junos:posix-pattern "^[[:alnum:]][[:alnum:]/.:_-]{0,62}$";
             junos:pattern-message "Must be a string beginning with a number or letter and consisting of no more than 63 total letters, numbers, dashes, underscores, forward slashes, colons and dots.";
           }
         }
         uses apply-advanced;
       }
     }
   }
   grouping nat_pool_object {
     leaf name {
       description "Pool name";
       type string {
         length "1 .. 63";
         junos:posix-pattern "^[[:alnum:]][[:alnum:]_-]*$";
         junos:pattern-message "Must be a string beginning with a number or letter and consisting of letters, numbers, dashes and underscores.";
       }
     }
     uses apply-advanced;
     container pgcp {
       presence "enable pgcp";
       description "NAT pool should be used exclusive by the pgcp service";
       uses apply-advanced;
       leaf remotely-controlled {
         description "Remotely controlled NAT pool allocation";
         type empty;
       }
       leaf ports-per-session {
         description "Number of ports to allocate in each call setup";
         default "2";
         type union {
           type uint8;
           type string {
             pattern "<.*>|$.*";
           }
         }
       }
       list hint {
         key name;
         ordered-by user;
         description "NAT-hint list (Any string available up to 3 characters, not mandatory field)";
         max-elements 5;
         uses nat_pgcp_hint_list_object;
       }
       leaf-list transport {
         ordered-by user;
         description "NAT pool transport types list";
         type enumeration {
           enum "tcp" {
             description "TCP";
           }
           enum "udp" {
             description "UDP";
           }
           enum "rtp-avp" {
             description "RTP/AVP";
           }
         }
       }
     }
     list address {
       key name;
       ordered-by user;
       description "Address or address prefix for NAT";
       leaf name {
         type jt:ipprefix-only;
       }
       uses apply-advanced;
     }
     container interface {
       description "Interface for nat pool";
       leaf interface-name {
         junos:must "(\".. .. address-overload\")";
         junos:must-message "interface must be configured with address-overload in a pool";
         junos:must "(!(\".. .. address-range\"))";
         junos:must-message "interface cannot be configured along with address-range in a pool";
         junos:must "(!(\".. .. address\"))";
         junos:must-message "interface cannot be configured along with address in a pool";
         junos:must "((\"interfaces $$-IFL family inet address\" || \"interfaces $$-IFL family inet dhcp\"))";
         junos:must-message "Interface with ipv4 address or dhcp-client must be defined in the interfaces hierarchy";
         type union {
           type jt:interface-unit;
           type string {
             pattern "<.*>|$.*";
           }
         }
       }
     }
     leaf address-overload {
       description "Nat pool address overload with JunOS";
       junos:must "(\".. port\")";
       junos:must-message "port range must be configured with address-overload in a pool";
       type empty;
     }
     list address-range {
       key "low high";
       ordered-by user;
       description "Range of addresses for NAT";
       leaf low {
         description "Lower limit of address range";
         type jt:ipaddr;
       }
       leaf high {
         description "Upper limit of address range";
         type jt:ipaddr;
       }
     }
     container port {
       description "Specify ports for NAT";
       uses apply-advanced;
       choice port_choice {
         case case_1 {
           container automatic {
             presence "enable automatic";
             uses apply-advanced;
             choice automatic_choice {
               case case_1 {
                 leaf auto {
                   description "Automatically choose ports";
                   status deprecated;
                   type empty;
                 }
               }
               case case_2 {
                 leaf sequential {
                   description "Allocate ports in sequence";
                   type empty;
                 }
               }
               case case_3 {
                 leaf random-allocation {
                   description "Allocate ports randomly";
                   type empty;
                 }
               }
             }
           }
         }
         case case_2 {
           container range {
             description "Range of ports";
             leaf low {
               description "Lower limit of port range";
               type union {
                 type string {
                   pattern "<.*>|$.*";
                 }
                 type uint16 {
                   range "1 .. 65535";
                 }
               }
             }
             leaf high {
               description "Upper limit of port range";
               type union {
                 type string {
                   pattern "<.*>|$.*";
                 }
                 type uint16 {
                   range "1 .. 65535";
                 }
               }
             }
             leaf random-allocation {
               description "Allocate ports randomly";
               type empty;
             }
           }
         }
       }
       choice block-allocation-choice {
         case case_1 {
           container secured-port-block-allocation {
             presence "enable secured-port-block-allocation";
             description "Secured Port block allocation";
             leaf block-size {
               description "Number of port per block.";
               default "128";
               type union {
                 type string {
                   pattern "<.*>|$.*";
                 }
                 type uint16 {
                   range "1 .. 64512";
                 }
               }
             }
             leaf max-blocks-per-address {
               description "Max block per address";
               default "8";
               type union {
                 type string {
                   pattern "<.*>|$.*";
                 }
                 type uint16 {
                   range "1 .. 512";
                 }
               }
             }
             leaf active-block-timeout {
               description "Active block timeout";
               default "120";
               type union {
                 type string {
                   pattern "<.*>|$.*";
                 }
                 type uint32 {
                   range "0 .. 86400";
                 }
               }
             }
           }
         }
         case case_2 {
           container deterministic-port-block-allocation {
             presence "enable deterministic-port-block-allocation";
             junos:must "(!(\".. preserve-range\"))";
             junos:must-message "preserve-range is not supported with deterministic-port-block-allocation";
             junos:must "(!(\".. preserve-parity\"))";
             junos:must-message "preserve-parity is not supported with deterministic-port-block-allocation";
             description "Deterministic Port Block Allocation";
             leaf block-size {
               description "Number of ports per block";
               default "512";
               type union {
                 type string {
                   pattern "<.*>|$.*";
                 }
                 type uint16 {
                   range "0 .. 64512";
                 }
               }
             }
             leaf include-boundary-addresses {
               description "Include network and broadcast in 'from' src-addresses";
               type empty;
             }
           }
         }
       }
       leaf preserve-parity {
         description "Allocate port with same parity as original port";
         type empty;
       }
       leaf preserve-range {
         description "Preserve privileged port range after NAT";
         type empty;
       }
     }
     container address-allocation {
       presence "enable address-allocation";
       junos:must "((\".. port automatic random-allocation\" || (\".. port range random-allocation\" || \".. port secured-port-block-allocation\")))";
       junos:must-message "address-allocation applies only with port automatic random-allocation or port range random-allocation or secured-port-block-allocation";
       description "Address allocation method for NAPT";
       uses apply-advanced;
       leaf round-robin {
         description "Round robin method of allocation";
         type empty;
       }
     }
     leaf mapping-timeout {
       description "Address-pooling paired and endpoint-independent mapping timeout (120..86400)";
       default "300";
       units "second";
       type union {
         type int32;
         type string {
           pattern "<.*>|$.*";
         }
       }
     }
     leaf flow-timeout {
       description "Default flow timeout for NAT flows";
       default "300";
       units "second";
       type union {
         type string {
           pattern "<.*>|$.*";
         }
         type int32 {
           range "30 .. 86400";
         }
       }
     }
     leaf ei-mapping-timeout {
       description "Endpoint-independent mapping timeout (120..86400)";
       units "second";
       type union {
         type int32;
         type string {
           pattern "<.*>|$.*";
         }
       }
     }
     leaf app-mapping-timeout {
       description "Address-pooling paired mapping timeout (120..86400)";
       units "second";
       junos:must "(!(\".. mapping-timeout\"))";
       junos:must-message "Both app-mapping-timeout and mapping-timeout should not be configured, any one only is allowed";
       type union {
         type int32;
         type string {
           pattern "<.*>|$.*";
         }
       }
     }
     leaf limit-ports-per-address {
       description "Limit number of ports allocated per host (IP address)";
       units "connections";
       type union {
         type string {
           pattern "<.*>|$.*";
         }
         type int32 {
           range "2 .. 65435";
         }
       }
     }
     container snmp-trap-thresholds {
       presence "enable snmp-trap-thresholds";
       description "Define snmp traps for service sets";
       uses apply-advanced;
       container address-port {
         presence "enable address-port";
         description "Nat pool address and port usage trap threshold range";
         leaf low {
           description "Lower limit of pool trap threshold";
           units "percent";
           type union {
             type string {
               pattern "<.*>|$.*";
             }
             type uint16 {
               range "0 .. 100";
             }
           }
         }
         leaf high {
           description "Upper limit of pool trap threshold";
           units "percent";
           type union {
             type string {
               pattern "<.*>|$.*";
             }
             type uint16 {
               range "0 .. 100";
             }
           }
         }
       }
     }
   }
   grouping nat_pgcp_hint_list_object {
     description "NAT hints";
     leaf name {
       description "NAT-hint string list";
       type string {
         length "1 .. 4";
         junos:posix-pattern "^[[:alnum:]][[:alnum:]_-]{0,3}$";
         junos:pattern-message "NAT-hint is a string which should begin with a digit or a letter only. And consist of up to 3 numbers, dashes and underscores";
       }
     }
   }
   grouping nat_rule_object {
     leaf name {
       description "Rule name";
       type string {
         length "1 .. 63";
         junos:posix-pattern "^[[:alnum:]][[:alnum:]/.:_-]*$";
         junos:pattern-message "Must be a string beginning with a number or letter and consisting of letters, numbers, dashes, underscores, forward slashes, colons and dots.";
       }
     }
     uses apply-advanced;
     leaf match-direction {
       description "Direction for which the rule match is applied";
       type enumeration {
         enum "input" {
           description "Match on input to interface";
         }
         enum "output" {
           description "Match on output from interface";
         }
         enum "input-output" {
           description "Match an input to or output from on interface";
         }
       }
     }
     list term {
       key name;
       ordered-by user;
       description "Define a NAT term";
       leaf name {
         description "Term name";
         type string {
           length "1 .. 63";
           junos:posix-pattern "^[[:alnum:]][[:alnum:]/.:_-]*$";
           junos:pattern-message "Must be a string beginning with a number or letter and consisting of letters, numbers, dashes, underscores, forward slashes, colons and dots.";
         }
       }
       uses apply-advanced;
       leaf nat-type {
         description "NAT type (symmetric/full-cone)";
         type enumeration {
           enum "symmetric" {
             description "Symmetric NAT";
           }
           enum "full-cone" {
             description "Full Cone NAT";
           }
         }
       }
       container from {
         description "Define match criteria";
         uses sfw_match_object;
       }
       container then {
         description "Action to take if the 'from' condition is matched";
         uses apply-advanced;
         choice designation {
           case case_1 {
             leaf no-translation {
               description "Do not perform translation";
               junos:must "(!(\".. translated\"))";
               junos:must-message "translated should not be configured when no-translation is configured";
               type empty;
             }
           }
         }
         choice port-forwarding {
           case case_1 {
             leaf port-forwarding-mappings {
               description "Port forwarding mappings";
               type string {
                 length "1 .. 63";
                 junos:posix-pattern "^[[:alnum:]][[:alnum:]_-]*$";
                 junos:pattern-message "Must be a string beginning with a number or letter and consisting of letters, numbers, dashes and underscores.";
               }
             }
           }
         }
         container translated {
           description "Define translation parameters";
           uses apply-advanced;
           choice source-pool-choice {
             case case_1 {
               leaf source-pool {
                 description "NAT pool for source translation";
                 junos:must "((!(\"services nat pool $$ port deterministic-port-block-allocation\") || (\".. translation-type deterministic-napt44\" || \".. translation-type deterministic-napt64\")))";
                 junos:must-message "Deterministic source pool must be used with deterministic-napt44 or deterministic-napt64 rule only";
                 junos:must "((!(\".. address-pooling\") || \"services nat pool $$ port\"))";
                 junos:must-message "Port configuration is mandatory in the pool used with Address Pooling";
                 junos:must "((!(\".. mapping-type\") || \"services nat pool $$ port\"))";
                 junos:must-message "Port configuration is mandatory in the pool used with End Point Independent Mapping";
                 type string {
                   length "1 .. 63";
                   junos:posix-pattern "^[[:alnum:]][[:alnum:]_-]*$";
                   junos:pattern-message "Must be a string beginning with a number or letter and consisting of letters, numbers, dashes and underscores.";
                 }
               }
             }
             case case_2 {
               leaf source-prefix {
                 description "NAT prefix for source translation";
                 junos:must "(!(\".. translation-type stateful-nat64\"))";
                 junos:must-message "Source prefix is not supported with NAT64";
                 type jt:ipprefix-only;
               }
             }
           }
           leaf clat-prefix {
             description "Clat-prefix to be used for 464 translation type";
             junos:must "(\".. translation-type stateful-nat464\")";
             junos:must-message "Clat-prefix should only be used with stateful-nat464";
             type jt:ipprefix-only;
           }
           leaf clat-ipv6-prefix-length {
             description "The ipv6 prefix length for CLAT source address";
             default "64";
             junos:must "(\".. translation-type stateful-nat464\")";
             junos:must-message "Clat-ipv6-prefix-length should only be used with stateful-nat464";
             type enumeration {
               enum "32" {
                 description "The ipv6 prefix length of 32";
               }
               enum "40" {
                 description "The ipv6 prefix length of 40";
               }
               enum "48" {
                 description "The ipv6 prefix length of 48";
               }
               enum "56" {
                 description "The ipv6 prefix length of 56";
               }
               enum "64" {
                 description "The ipv6 prefix length of 64";
               }
               enum "96" {
                 description "The ipv6 prefix length of 96";
               }
             }
           }
           choice destination-pool-choice {
             case case_1 {
               leaf destination-pool {
                 description "NAT pool for destination translation";
                 type string {
                   length "1 .. 63";
                   junos:posix-pattern "^[[:alnum:]][[:alnum:]_-]*$";
                   junos:pattern-message "Must be a string beginning with a number or letter and consisting of letters, numbers, dashes and underscores.";
                 }
               }
             }
             case case_2 {
               leaf destination-prefix {
                 description "NAT prefix for destination translation";
                 type jt:ipprefix-only;
               }
             }
           }
           choice dns-alg-pool-choice {
             case case_1 {
               leaf dns-alg-pool {
                 description "NAT pool for dns alg mappings";
                 type string {
                   length "1 .. 63";
                   junos:posix-pattern "^[[:alnum:]][[:alnum:]_-]*$";
                   junos:pattern-message "Must be a string beginning with a number or letter and consisting of letters, numbers, dashes and underscores.";
                 }
               }
             }
             case case_2 {
               leaf dns-alg-prefix {
                 description "DNS ALG 96 bit prefix for mapping IPv4 addresses to IPv6 addresses";
                 type jt:ipprefix-only;
               }
             }
           }
           choice dns-map-address-for-destination-translation-choice {
             case case_1 {
               leaf use-dns-map-for-destination-translation {
                 description "Use dns alg address map for destination translation";
                 status deprecated;
                 type empty;
               }
             }
           }
           choice overload-pool-choice {
             case case_1 {
               leaf overload-pool {
                 description "NAT pool to be used when source pool is overloaded";
                 type string {
                   length "1 .. 63";
                   junos:posix-pattern "^[[:alnum:]][[:alnum:]_-]*$";
                   junos:pattern-message "Must be a string beginning with a number or letter and consisting of letters, numbers, dashes and underscores.";
                 }
               }
             }
             case case_2 {
               leaf overload-prefix {
                 description "NAT prefix to be used when source pool is overloaded";
                 type jt:ipprefix-only;
               }
             }
           }
           container translation-type {
             description "Type of translation to perform";
             uses apply-advanced;
             leaf source {
               description "Type of source translation";
               status deprecated;
               type enumeration {
                 enum "static" {
                   description "Static translation";
                   status deprecated;
                 }
                 enum "dynamic" {
                   description "Dynamic translation";
                   status deprecated;
                 }
               }
             }
             leaf destination {
               description "Type of destination translation";
               status deprecated;
               type enumeration {
                 enum "static" {
                   description "Static translation";
                   status deprecated;
                 }
               }
             }
             container basic-nat44 {
               presence "enable basic-nat44";
               description "Static source address (IPv4 to IPv4) translation";
             }
             container dynamic-nat44 {
               presence "enable dynamic-nat44";
               description "Dynamic source address only (IPv4 to IPv4) translation";
             }
             container napt-44 {
               presence "enable napt-44";
               description "Source address (IPv4 to IPv4) and port translation";
             }
             container dnat-44 {
               presence "enable dnat-44";
               description "Static Destination address (IPv4 to IPv4) translation";
             }
             container stateful-nat64 {
               presence "enable stateful-nat64";
               description "Dynamic source address (IPv6 to IPv4) and prefix removal for destination address (IPv6 to IPv4)translation";
             }
             container stateful-nat464 {
               presence "enable stateful-nat464";
               junos:must "(((\".. .. .. translated clat-prefix\" && (\".. .. .. translated destination-prefix\" && (\".. .. .. .. from destination-address\" && (\".. .. .. .. from source-address\" && (\".. .. .. translated source-pool\" && !(\".. .. .. translated clat-ipv6-prefix-length\")))))) || (\".. .. .. translated clat-ipv6-prefix-length\" && (\".. .. .. translated destination-prefix\" && (\".. .. .. .. from destination-address\" && (!(\".. .. .. translated clat-prefix\") && \".. .. .. translated source-pool\"))))))";
               junos:must-message "All clat-prefix/destination-prefix/source-address/destination-address/source-pool are required for NAT464 when clat-prefix is configured and clat-ipv6-prefix-length/destination-prefix/destination-address/source-pool are required for NAT464 when clat-ipv6-prefix-length is configured. Either clat-prefix or clat-ipv6-prefix-length should be configured with NAT464 ";
               description "Prefix removal for Src and Dest address (IPv6 to IPv4) translation";
             }
             container basic-nat-pt {
               presence "enable basic-nat-pt";
               description "NAT-PT (static source address (IPv6 to IPv4) and prefix removal for destination address (IPv6 to IPv4) translation)";
             }
             container napt-pt {
               presence "enable napt-pt";
               description "NAT-PT (source address (IPv6 to IPv4) and source port and prefix removal for destination address (IPv6 to IPv4) translation)";
             }
             container basic-nat66 {
               presence "enable basic-nat66";
               description "Static source address (IPv6 to IPv6) translation [same as basic-nat44 but for IPv6 address family]";
             }
             container nptv6 {
               presence "enable nptv6";
               description "Stateless source address (IPv6 to IPv6) translation";
             }
             container napt-66 {
               presence "enable napt-66";
               description "Source address (IPv6 to IPv6) and port translation [same as napt-44 but for IPv6 address family]";
             }
             container twice-napt-44 {
               presence "enable twice-napt-44";
               description "Source NAPT and destination static translation for IPv4 address family";
             }
             container twice-basic-nat-44 {
               presence "enable twice-basic-nat-44";
               description "Source static and destination static translation for IPv4 address family";
             }
             container twice-dynamic-nat-44 {
               presence "enable twice-dynamic-nat-44";
               description "Source dynamic and destination static translation for IPv4 address family";
             }
             container deterministic-napt44 {
               presence "enable deterministic-napt44";
               junos:must "((\".. .. .. .. from source-address\" || (\".. .. .. .. from source-address-range\" || \".. .. .. .. from source-prefix-list\")))";
               junos:must-message "Deterministic NAT translation requires source-address or source-prefix-list in the from clause";
               description "Deterministic source NAPT for IPv4 family";
               uses apply-advanced;
             }
             container deterministic-napt64 {
               presence "enable deterministic-napt64";
               junos:must "((\".. .. .. .. from source-address\" || (\".. .. .. .. from source-address-range\" || \".. .. .. .. from source-prefix-list\")))";
               junos:must-message "Deterministic NAT translation requires source-address or source-prefix-list in the from clause";
               description "Deterministic source NAPT for IPv6 family";
             }
           }
           leaf mapping-type {
             description "Source NAT mapping type";
             junos:must "((\".. translation-type source\" || (\".. translation-type napt-44\" || (\".. translation-type deterministic-napt44\" || (\".. translation-type deterministic-napt64\" || (\".. translation-type stateful-nat64\" || \".. translation-type stateful-nat464\"))))))";
             junos:must-message "mapping-type applies only to source NAPT";
             type enumeration {
               enum "endpoint-independent" {
                 description "Endpoint independent mapping";
               }
             }
           }
           leaf flow-type {
             description "Source NAT flow type";
             junos:must "((\".. translation-type napt-44\" || \".. translation-type dynamic-nat44\"))";
             junos:must-message "flow-type applies only to napt-44 or dynamic-nat44";
             type enumeration {
               enum "endpoint-independent" {
                 description "Endpoint independent flow";
               }
             }
           }
           leaf ignore-dst-nat-1to1-limitation {
             description "Ignore destination NAT 1:1 limitation";
             type empty;
           }
           container secure-nat-mapping {
             presence "enable secure-nat-mapping";
             description "Mapping options for enhanced security";
             uses apply-advanced;
             leaf eif-flow-limit {
               description "Number of inbound flows to be allowed for a EIF mapping";
               junos:must "(\".. .. filtering-type\")";
               junos:must-message "eif-flow-limit applies only to filtering-type";
               type union {
                 type string {
                   pattern "<.*>|$.*";
                 }
                 type uint16 {
                   range "0 .. 65534";
                 }
               }
             }
             leaf mapping-refresh {
               description "Enable timer refresh option";
               type enumeration {
                 enum "inbound" {
                   description "Enable timer refresh for inbound connections only";
                 }
                 enum "outbound" {
                   description "Enable timer refresh for outbound connections only";
                 }
                 enum "inbound-outbound" {
                   description "Enable timer refresh for inbound & outbound connections";
                 }
               }
             }
             leaf flow-refresh {
               description "Enable timer refresh option";
               type enumeration {
                 enum "inbound" {
                   description "Enable timer refresh for inbound connections only";
                 }
                 enum "outbound" {
                   description "Enable timer refresh for outbound connections only";
                 }
                 enum "inbound-outbound" {
                   description "Enable timer refresh for inbound & outbound connections";
                 }
               }
             }
           }
           container filtering-type {
             junos:must "(\".. mapping-type endpoint-independent\")";
             junos:must-message "endpoint independent filtering can be configured with endpoint-independent mapping only";
             junos:must "((\".. translation-type source\" || (\".. translation-type napt-44\" || (\".. translation-type deterministic-napt44\" || (\".. translation-type deterministic-napt64\" || (\".. translation-type stateful-nat64\" || \".. translation-type stateful-nat464\"))))))";
             junos:must-message "filtering-type applies only to source NAPT";
             description "Source NAT filtering type";
             uses apply-advanced;
             container endpoint-independent {
               presence "enable endpoint-independent";
               description "Endpoint independent filtering";
               uses apply-advanced;
               list prefix-list {
                 key name;
                 ordered-by user;
                 description "One or more named lists of source prefixes to match";
                 leaf name {
                   description "Name of prefix list to match against";
                   type string;
                 }
                 leaf except {
                   description "Name of prefix list not to match against";
                   type empty;
                 }
               }
             }
           }
           leaf address-pooling {
             description "Address pooling behavior for source NAT";
             junos:must "((\".. translation-type source\" || (\".. translation-type napt-44\" || (\".. translation-type stateful-nat64\" || (\".. translation-type stateful-nat464\" || (\".. translation-type deterministic-napt44\" || \".. translation-type deterministic-napt64\"))))))";
             junos:must-message "address-pooling applies only to source NAPT, stateful NAT64 and stateful NAT464";
             type enumeration {
               enum "paired" {
                 description "Address pooling behavior of paired";
               }
             }
           }
         }
         leaf syslog {
           description "System log information about the packet";
           type empty;
         }
       }
     }
   }
   grouping network_type {
     leaf name {
       description "Network prefix";
       type jt:ipprefix;
     }
     uses apply-advanced;
     leaf-list dyn-tunnel-attribute-policy {
       ordered-by user;
       description "Import policy for dynamic-tunnel under this destination network";
       type jt:policy-algebra;
     }
     leaf preference {
       description "Preference of tunnel route under this destination network";
       type union {
         type uint32;
         type string {
           pattern "<.*>|$.*";
         }
       }
     }
     leaf-list colors {
       ordered-by user;
       description "Set of color list that will be supported for tunnel creation";
       type union {
         type uint32;
         type string {
           pattern "<.*>|$.*";
         }
       }
     }
   }
   grouping next_hop_group_intf_type {
     leaf name {
       description "Interface through which to send sampled traffic";
       type union {
         type jt:interface-name;
         type string {
           pattern "<.*>|$.*";
         }
       }
     }
     uses apply-advanced;
     list next-hop {
       key name;
       ordered-by user;
       description "Address of next hop through which to send sampled traffic";
       junos:must "((\".. .. group-type inet\" || \".. .. group-type inet6\"))";
       junos:must-message "Next-hop can be specified only for group-type inet or inet6";
       uses next_hop_type;
     }
   }
   grouping next_hop_subgroup_intf_type {
     leaf name {
       description "Interface through which to send sampled traffic";
       type union {
         type jt:interface-name;
         type string {
           pattern "<.*>|$.*";
         }
       }
     }
     uses apply-advanced;
     list next-hop {
       key name;
       ordered-by user;
       description "Address of next hop through which to send sampled traffic";
       junos:must "((\".. .. .. group-type inet\" || \".. .. .. group-type inet6\"))";
       junos:must-message "Next-hop can be specified only for group-type inet or inet6";
       uses next_hop_type;
     }
   }
   grouping next_hop_type {
     description "Address of next hop through which to send sampled traffic";
     leaf name {
       type jt:ipaddr;
     }
     uses apply-advanced;
   }
   grouping override-local-server-type {
     description "DHCP override processing";
     uses apply-advanced;
     leaf interface-client-limit {
       description "Limit the number of clients allowed on an interface";
       type union {
         type string {
           pattern "<.*>|$.*";
         }
         type uint32 {
           range "1 .. 500000";
         }
       }
     }
     leaf no-arp {
       description "Disable DHCP ARP table population";
       status deprecated;
       junos:must "((!(\".. route-suppression destination\") && !(\".. route-suppression access-internal\")))";
       junos:must-message "Cannot specify route-suppression with overrides no-arp";
       type empty;
     }
     leaf bootp-support {
       description "Allow processing of bootp requests";
       type empty;
     }
     container client-discover-match {
       presence "enable client-discover-match";
       description "Use secondary match criteria for DISCOVER PDU";
       choice match-with {
         case case_1 {
           leaf option60-and-option82 {
             description "Use option 60 and option 82";
             type empty;
           }
         }
         case case_2 {
           leaf incoming-interface {
             description "Use incoming interface";
             type empty;
           }
         }
       }
     }
     container delay-offer {
       description "Filter options for dhcp-server";
       uses dhcpv4-filter-option;
     }
     container process-inform {
       presence "enable process-inform";
       description "Process INFORM PDUs";
       uses apply-advanced;
       leaf pool {
         description "Pool name for family inet";
         type string {
           length "1 .. 64";
         }
       }
     }
     container include-option-82 {
       description "Include option-82 in reply packets";
       uses apply-advanced;
       leaf nak {
         description "Include option-82 in NAK";
         type empty;
       }
       leaf forcerenew {
         description "Include option-82 in FORCERENEW";
         type empty;
       }
     }
     leaf delete-binding-on-renegotiation {
       description "Delete binding on renegotiation";
       type empty;
     }
     leaf allow-no-end-option {
       description "Allow packets without end-of-option";
       type empty;
     }
     leaf asymmetric-lease-time {
       description "Use a reduced lease time for the client. In seconds";
       units "seconds";
       type union {
         type string {
           pattern "<.*>|$.*";
         }
         type uint32 {
           range "600 .. 86400";
         }
       }
     }
     leaf protocol-attributes {
       description "DHCPv4 attributes to use as defined under access protocol-attributes";
       type string {
         length "1 .. 64";
       }
     }
     leaf dual-stack {
       description "Dual stack group to use";
       type string {
         length "1 .. 64";
       }
     }
   }
   grouping dhcpv4-filter-option {
     description "Generic DHCPv4 filter processing";
     uses apply-advanced;
     leaf delay-time {
       description "Time delay between discover and offer";
       default "3";
       units "seconds";
       type union {
         type string {
           pattern "<.*>|$.*";
         }
         type uint32 {
           range "1 .. 30";
         }
       }
     }
     container based-on {
       description "Option number";
       uses apply-advanced;
       container option-82 {
         presence "enable option-82";
         description "Option 82";
         uses apply-advanced;
         container equals {
           description "Generic option equals";
           uses server-v6-option-ascii-hex;
         }
         container not-equals {
           description "Generic option not equals";
           uses server-v6-option-ascii-hex;
         }
         container starts-with {
           description "Generic option starts-with";
           uses server-v6-option-ascii-hex;
         }
       }
       container option-60 {
         presence "enable option-60";
         description "Option 60";
         uses apply-advanced;
         container equals {
           description "Generic option equals";
           uses server-v6-option-ascii-hex;
         }
         container not-equals {
           description "Generic option not equals";
           uses server-v6-option-ascii-hex;
         }
         container starts-with {
           description "Generic option starts-with";
           uses server-v6-option-ascii-hex;
         }
       }
       container option-77 {
         presence "enable option-77";
         description "Option 77";
         uses apply-advanced;
         container equals {
           description "Generic option equals";
           uses server-v6-option-ascii-hex;
         }
         container not-equals {
           description "Generic option not equals";
           uses server-v6-option-ascii-hex;
         }
         container starts-with {
           description "Generic option starts-with";
           uses server-v6-option-ascii-hex;
         }
       }
     }
   }
   grouping override-type {
     description "DHCP override processing";
     uses apply-advanced;
     leaf no-unicast-replies {
       description "Overwrite unicast bit in incoming packet, when present";
       junos:must "(!(\".. layer2-unicast-replies\"))";
       junos:must-message "no-unicast-replies cannot be configured with layer2-unicast-replies";
       type empty;
     }
     choice allow-snooped-clients-choice {
       leaf allow-snooped-clients {
         description "Allow client creation from snooped PDUs";
         type empty;
       }
       leaf no-allow-snooped-clients {
         description "Don't allow client creation from snooped PDUs";
         type empty;
       }
     }
     leaf allow-no-end-option {
       description "Allow packets without end-of-option";
       type empty;
     }
     leaf always-write-giaddr {
       description "Overwrite existing 'giaddr' field, when present";
       type empty;
     }
     container always-write-option-82 {
       description "Overwrite existing value of option 82, when present";
       presence "enable always-write-option-82";
       uses write-option-82-type;
     }
     leaf user-defined-option-82 {
       description "Set user defined description for option-82";
       type string {
         length "1 .. 252";
       }
     }
     leaf layer2-unicast-replies {
       description "Do not broadcast client responses";
       junos:must "(!(\".. no-unicast-replies\"))";
       junos:must-message "layer2-unicast-replies cannot be configured with no-unicast-replies";
       type empty;
     }
     leaf trust-option-82 {
       description "Trust options-82 option";
       type empty;
     }
     leaf delay-authentication {
       description "Delay subscriber authentication in DHCP protocol processing until request packet";
       type empty;
     }
     leaf disable-relay {
       description "Disable DHCP relay processing";
       type empty;
     }
     leaf no-bind-on-request {
       description "Do not bind if stray DHCP request is received";
       type empty;
     }
     leaf interface-client-limit {
       description "Limit the number of client allowed on an interface";
       type union {
         type string {
           pattern "<.*>|$.*";
         }
         type uint32 {
           range "1 .. 500000";
         }
       }
     }
     leaf no-arp {
       description "Disable DHCP ARP table population";
       status deprecated;
       junos:must "((!(\".. route-suppression destination\") && !(\".. route-suppression access-internal\")))";
       junos:must-message "Cannot specify route-suppression with overrides no-arp";
       type empty;
     }
     leaf bootp-support {
       description "Allows relay of bootp req and reply";
       type empty;
     }
     leaf dual-stack {
       description "Dual stack group to use.";
       type string {
         length "1 .. 64";
       }
     }
     container client-discover-match {
       presence "enable client-discover-match";
       description "Use secondary match criteria for DISCOVER PDU";
       choice match-with {
         case case_1 {
           leaf option60-and-option82 {
             description "Use option 60 and option 82";
             type empty;
           }
         }
         case case_2 {
           leaf incoming-interface {
             description "Use incoming interface";
             type empty;
           }
         }
       }
     }
     container proxy-mode {
       presence "enable proxy-mode";
       description "Put the relay in proxy mode";
     }
     leaf asymmetric-lease-time {
       description "Use a reduced lease time for the client. In seconds";
       units "seconds";
       type union {
         type string {
           pattern "<.*>|$.*";
         }
         type uint32 {
           range "600 .. 86400";
         }
       }
     }
     container replace-ip-source-with {
       description "Replace IP source address in request and release packets";
       choice replacement-type {
         case case_1 {
           leaf giaddr {
             description "Replace IP source address with giaddr";
             type empty;
           }
         }
       }
     }
     leaf send-release-on-delete {
       description "Always send RELEASE to the server when a binding is deleted";
       type empty;
     }
     leaf apply-secondary-as-giaddr {
       description "Enable DHCP relay to use secondary gateway ip for relay interfaces";
       type empty;
     }
     leaf relay-source {
       description "Interface for relay source";
       type union {
         type jt:interface-name;
         type string {
           pattern "<.*>|$.*";
         }
       }
     }
     leaf delete-binding-on-renegotiation {
       description "Delete binding on rengotiation";
       type empty;
     }
   }
   grouping p2mp_ldp_lsp_nh_obj {
     uses apply-advanced;
     list root-address {
       key name;
       description "Configure the root address of P2MP LSP";
       leaf name {
         description "Root address of the P2MP LSP";
         type jt:ipaddr;
       }
       uses apply-advanced;
       leaf lsp-id {
         description "Configure the generic LSP identifier";
         type union {
           type string {
             pattern "<.*>|$.*";
           }
           type uint32 {
             range "1 .. 65535";
           }
         }
       }
       list group-address {
         key name;
         description "IPv4/Ipv6 group address for mLDP LSP";
         leaf name {
           description "IPv4/Ipv6 group address";
           type jt:ipaddr;
         }
         uses apply-advanced;
         list source-address {
           key name;
           description "IPv4/Ipv6 source address";
           leaf name {
             description "IPv4/Ipv6 source address for mLDP LSP";
             type jt:ipaddr;
           }
           uses apply-advanced;
         }
       }
     }
   }
   grouping packet-capture-egress-intf-type {
     uses apply-advanced;
     list interface {
       key name;
       description "Interface options";
       leaf name {
         description "Interface name";
         type union {
           type jt:interface-device;
           type string {
             pattern "<.*>|$.*";
           }
         }
       }
       uses apply-advanced;
     }
   }
   grouping packet_accounting_output_type {
     uses apply-advanced;
     leaf aggregate-export-interval {
       description "Interval of exporting aggregate accounting information";
       default "90";
       units "seconds";
       type union {
         type string {
           pattern "<.*>|$.*";
         }
         type uint32 {
           range "90 .. 1800";
         }
       }
     }
     leaf flow-inactive-timeout {
       description "Interval of inactivity that marks a flow inactive";
       default "60";
       units "seconds";
       type union {
         type string {
           pattern "<.*>|$.*";
         }
         type uint32 {
           range "15 .. 1800";
         }
       }
     }
     leaf flow-active-timeout {
       description "Interval after which an active flow is exported";
       default "1800";
       units "seconds";
       type union {
         type string {
           pattern "<.*>|$.*";
         }
         type uint32 {
           range "60 .. 1800";
         }
       }
     }
     list cflowd {
       key name;
       description "Cflowd collector where flow records are sent";
       junos:must "(all \".. interface <*> source-address\")";
       junos:must-message "'forwarding-options accounting output interface source-address' must be specified with 'flow-server' and 'interface'";
       junos:must "(any \".. interface <*>\")";
       junos:must-message "'forwarding-options accounting output interface' must be specified";
       uses cflowd_packet_accounting_type;
     }
     list interface {
       key name;
       description "Interfaces used to send monitored information";
       uses packet_export_intf_type;
     }
   }
   grouping cflowd_packet_accounting_type {
     leaf name {
       description "Name of host collecting cflowd packets";
       type jt:ipaddr;
     }
     uses apply-advanced;
     leaf port {
       description "UDP port number on host collecting cflowd packets";
       type union {
         type uint16;
         type string {
           pattern "<.*>|$.*";
         }
       }
     }
     leaf dscp {
       description "Numeric DSCP value in the range 0 to 63";
       default "0";
       junos:must "(\".. .. inline-jflow\")";
       junos:must-message "DSCP can be configured for inline-jflow";
       type union {
         type string {
           pattern "<.*>|$.*";
         }
         type uint8 {
           range "0 .. 63";
         }
       }
     }
     leaf forwarding-class {
       description "Forwarding-class for exported jflow packets, applicable only for inline-jflow";
       junos:must "(\".. .. inline-jflow\")";
       junos:must-message "forwarding-class can be configured for inline-jflow";
       type string {
         length "1 .. 64";
       }
     }
     leaf routing-instance {
       description "Name of routing instance on which flow collector is reachable";
       junos:must "(\".. .. inline-jflow\")";
       junos:must-message "Routing Instances can be configured for inline-jflow";
       junos:must "(\"routing-instances $$ instance-type vrf\")";
       junos:must-message "routing instance should be defined and should be of type Virtual routing forwarding instance(VRF)";
       type string;
     }
     leaf version {
       description "Format of exported cflowd aggregates";
       default "5";
       type enumeration {
         enum "5" {
           description "Export cflowd aggregates in version 5 format";
         }
         enum "8" {
           description "Export cflowd aggregates in version 8 format";
         }
       }
     }
     leaf autonomous-system-type {
       description "Type of autonomous system number to export";
       default "origin";
       type enumeration {
         enum "origin" {
           description "Export origin-AS numbers";
         }
         enum "peer" {
           description "Export peer-AS numbers";
         }
       }
     }
     container aggregation {
       description "Aggregations to perform for exported flows (version 8 only)";
       uses aggregation_type;
     }
   }
   grouping aggregation_type {
     uses apply-advanced;
     leaf autonomous-system {
       description "Aggregate by autonomous system number";
       type empty;
     }
     leaf protocol-port {
       description "Aggregate by protocol and port number";
       type empty;
     }
     leaf source-prefix {
       description "Aggregate by source prefix";
       type empty;
     }
     leaf destination-prefix {
       description "Aggregate by destination prefix";
       type empty;
     }
     container source-destination-prefix {
       presence "enable source-destination-prefix";
       description "Aggregate by source and destination prefix";
       uses apply-advanced;
       leaf caida-compliant {
         description "Compatible with Caida record format for prefix aggregation (v8)";
         type empty;
       }
     }
   }
   grouping packet_export_intf_type {
     leaf name {
       description "Interfaces used to send monitored information";
       type union {
         type jt:interface-unit;
         type string {
           pattern "<.*>|$.*";
         }
       }
     }
     uses apply-advanced;
     leaf engine-id {
       description "Identity (number) of this accounting interface";
       type union {
         type uint8;
         type string {
           pattern "<.*>|$.*";
         }
       }
     }
     leaf engine-type {
       description "Type (number) of this accounting interface";
       type union {
         type uint8;
         type string {
           pattern "<.*>|$.*";
         }
       }
     }
     leaf source-address {
       description "Address to use for generating monitored packets";
       type jt:ipaddr;
     }
     container export-port {
       description "Jflow export port configuration";
       presence "enable export-port";
       uses export_port_address_type;
     }
   }
   grouping export_port_address_type {
     uses apply-advanced;
     leaf address {
       description "Address to use for jflow export port";
       type jt:ipv4prefix;
     }
     leaf gateway {
       description "Gateway address to reach jflow server";
       type jt:ipv4addr;
     }
   }
   grouping periodic_oam {
     uses apply-advanced;
     container mpls-tp-mode {
       presence "enable mpls-tp-mode";
       description "MPLS-TP Mode, Do not use IP addressing for OAM";
       uses apply-advanced;
       container lsping-channel-type {
         description "Supported Control-channel types for MPLS-TP mode....";
         uses apply-advanced;
         choice action-choice {
           case case_1 {
             leaf ipv4 {
               description "Use channel-type IPv4(0x0021), With IP-UDP encapsulation";
               type empty;
             }
           }
           case case_2 {
             leaf on-demand-cv {
               description "Use channel-type On-Demand-CV(0x0025), Without IP-UDP encapsulation";
               type empty;
             }
           }
         }
       }
     }
     container bfd-port {
       description "Egress knob to select MHOP-BFD port for MPLS BFD";
       uses apply-advanced;
       leaf-list import {
         ordered-by user;
         description "Import policy";
         type jt:policy-algebra;
       }
     }
     container bfd-liveness-detection {
       description "Bidirectional Forwarding Detection options";
       uses apply-advanced;
       leaf version {
         description "BFD protocol version number";
         default "automatic";
         type enumeration {
           enum "0" {
             description "BFD version 0 (deprecated)";
           }
           enum "1" {
             description "BFD version 1";
           }
           enum "automatic" {
             description "Choose BFD version automatically";
           }
         }
       }
       leaf minimum-interval {
         description "Minimum transmit and receive interval";
         units "milliseconds";
         type union {
           type string {
             pattern "<.*>|$.*";
           }
           type uint32 {
             range "1 .. 255000";
           }
         }
       }
       leaf minimum-transmit-interval {
         description "Minimum transmit interval";
         status deprecated;
         units "milliseconds";
         type union {
           type string {
             pattern "<.*>|$.*";
           }
           type uint32 {
             range "1 .. 255000";
           }
         }
       }
       leaf minimum-receive-interval {
         description "Minimum receive interval";
         units "milliseconds";
         type union {
           type string {
             pattern "<.*>|$.*";
           }
           type uint32 {
             range "1 .. 255000";
           }
         }
       }
       leaf multiplier {
         description "Detection time multiplier";
         default "3";
         type union {
           type string {
             pattern "<.*>|$.*";
           }
           type uint32 {
             range "1 .. 255";
           }
         }
       }
       choice adaptation-choice {
         case case_1 {
           leaf no-adaptation {
             description "Disable adaptation";
             type empty;
           }
         }
       }
       container transmit-interval {
         description "Transmit-interval options";
         uses apply-advanced;
         leaf minimum-interval {
           description "Minimum transmit interval";
           units "milliseconds";
           type union {
             type string {
               pattern "<.*>|$.*";
             }
             type uint32 {
               range "1 .. 255000";
             }
           }
         }
         leaf threshold {
           description "High transmit interval triggering a trap";
           units "milliseconds";
           type union {
             type uint32;
             type string {
               pattern "<.*>|$.*";
             }
           }
         }
       }
       container detection-time {
         description "Detection-time options";
         uses apply-advanced;
         leaf threshold {
           description "High detection-time triggering a trap";
           units "milliseconds";
           type union {
             type uint32;
             type string {
               pattern "<.*>|$.*";
             }
           }
         }
       }
       container failure-action {
         description "Action to take when BFD session goes down";
         choice action-choice {
           case case_1 {
             leaf teardown {
               description "Teardown label switched path and resignal";
               type empty;
             }
           }
           case case_2 {
             container make-before-break {
               presence "enable make-before-break";
               description "Resignal the label switched path before teardown";
               uses apply-advanced;
               leaf teardown-timeout {
                 description "Time to wait before teardown";
                 units "seconds";
                 type union {
                   type string {
                     pattern "<.*>|$.*";
                   }
                   type uint32 {
                     range "0 .. 30";
                   }
                 }
               }
             }
           }
         }
       }
       leaf no-router-alert-option {
         description "Do not set Router-Alert options in IP header for MPLS-BFD";
         type empty;
       }
       leaf use-ip-ttl-1 {
         description "Set TTL value to 1 in IP header for MPLS-BFD";
         type empty;
       }
     }
     container performance-monitoring {
       description "Performance monitoring options";
       uses apply-advanced;
       container traceoptions {
         description "Trace options for PM";
         uses apply-advanced;
         container file {
           description "Trace file options";
           leaf filename {
             description "Name of file in which to write trace information";
             type string {
               length "1 .. 1024";
               junos:posix-pattern "![/ %]";
               junos:pattern-message "Must not contain '/', % or a space";
             }
           }
           leaf replace {
             description "Replace trace file rather than appending to it";
             status deprecated;
             type empty;
           }
           leaf size {
             description "Maximum trace file size";
             type string;
           }
           leaf files {
             description "Maximum number of trace files";
             default "10";
             type union {
               type string {
                 pattern "<.*>|$.*";
               }
               type uint32 {
                 range "2 .. 1000";
               }
             }
           }
           leaf no-stamp {
             description "Do not timestamp trace file";
             status deprecated;
             type empty;
           }
           choice world-readable-choice {
             leaf world-readable {
               description "Allow any user to read the log file";
               type empty;
             }
             leaf no-world-readable {
               description "Don't allow any user to read the log file";
               type empty;
             }
           }
         }
         list flag {
           key name;
           ordered-by user;
           description "Tracing parameters";
           leaf name {
             type enumeration {
               enum "init" {
                 description "Trace init commnad";
               }
               enum "error" {
                 description "Trace error conditions";
               }
               enum "event" {
                 description "Trace state machine events";
               }
               enum "general" {
                 description "Trace general events";
               }
               enum "packet" {
                 description "Trace various packets ";
               }
               enum "timer" {
                 description "Trace timer processing";
               }
               enum "all" {
                 description "Trace everything";
               }
             }
           }
         }
       }
       container querier {
         junos:must "(\".. .. .. ultimate-hop-popping\")";
         junos:must-message "Performance monitoring can be configured only on ultimate-hop-popping LSPs";
         junos:must "(\".. .. .. associate-lsp\")";
         junos:must-message "Performance monitoring can be configured only for associated LSPs";
         description "Querier options";
         uses apply-advanced;
         container loss {
           description "Loss measurement options";
           uses apply-advanced;
           list traffic-class {
             key name;
             description "Traffic class specific options";
             leaf name {
               description "Traffic class value";
               type enumeration {
                 enum "tc-0" {
                   description "Traffic class 0";
                   junos:must "(\"protocols mpls statistics traffic-class-statistics\")";
                   junos:must-message "Traffic class can be configured only for traffic-class-statistics";
                 }
                 enum "tc-1" {
                   description "Traffic class 1";
                   junos:must "(\"protocols mpls statistics traffic-class-statistics\")";
                   junos:must-message "Traffic class can be configured only for traffic-class-statistics";
                 }
                 enum "tc-2" {
                   description "Traffic class 2";
                   junos:must "(\"protocols mpls statistics traffic-class-statistics\")";
                   junos:must-message "Traffic class can be configured only for traffic-class-statistics";
                 }
                 enum "tc-3" {
                   description "Traffic class 3";
                   junos:must "(\"protocols mpls statistics traffic-class-statistics\")";
                   junos:must-message "Traffic class can be configured only for traffic-class-statistics";
                 }
                 enum "tc-4" {
                   description "Traffic class 4";
                   junos:must "(\"protocols mpls statistics traffic-class-statistics\")";
                   junos:must-message "Traffic class can be configured only for traffic-class-statistics";
                 }
                 enum "tc-5" {
                   description "Traffic class 5";
                   junos:must "(\"protocols mpls statistics traffic-class-statistics\")";
                   junos:must-message "Traffic class can be configured only for traffic-class-statistics";
                 }
                 enum "tc-6" {
                   description "Traffic class 6";
                   junos:must "(\"protocols mpls statistics traffic-class-statistics\")";
                   junos:must-message "Traffic class can be configured only for traffic-class-statistics";
                 }
                 enum "tc-7" {
                   description "Traffic class 7";
                   junos:must "(\"protocols mpls statistics traffic-class-statistics\")";
                   junos:must-message "Traffic class can be configured only for traffic-class-statistics";
                 }
                 enum "all" {
                   description "All Traffic class";
                   junos:must "(\"protocols mpls statistics traffic-class-statistics\")";
                   junos:must-message "Traffic class can be configured only for traffic-class-statistics";
                 }
                 enum "none" {
                   description "No Traffic class";
                 }
               }
             }
             uses apply-advanced;
             leaf query-interval {
               description "Minimum transmit interval";
               units "milliseconds";
               type union {
                 type string {
                   pattern "<.*>|$.*";
                 }
                 type uint32 {
                   range "1000 .. 4294967295";
                 }
               }
             }
             leaf measurement-quantity {
               description "Loss measurement quantity";
               default "packets";
               type enumeration {
                 enum "bytes" {
                   description "Byte loss measurement";
                 }
                 enum "packets" {
                   description "Packet loss measurement";
                 }
               }
             }
             leaf average-sample-size {
               description "Number of samples used in average calculation";
               type union {
                 type string {
                   pattern "<.*>|$.*";
                 }
                 type uint16 {
                   range "1 .. 30";
                 }
               }
             }
             leaf loss-threshold {
               description "Loss threshold value";
               type union {
                 type string {
                   pattern "<.*>|$.*";
                 }
                 type uint32 {
                   range "1 .. 4294967295";
                 }
               }
             }
             leaf loss-threshold-window {
               description "Number of samples for loss threshold calculation";
               type union {
                 type string {
                   pattern "<.*>|$.*";
                 }
                 type uint32 {
                   range "1 .. 30";
                 }
               }
             }
           }
         }
         container delay {
           description "Delay measurement options";
           uses apply-advanced;
           list traffic-class {
             key name;
             description "Traffic class specific options";
             leaf name {
               description "Traffic class value";
               type enumeration {
                 enum "tc-0" {
                   description "Traffic class 0";
                   junos:must "(\"protocols mpls statistics traffic-class-statistics\")";
                   junos:must-message "Traffic class can be configured only for traffic-class-statistics";
                 }
                 enum "tc-1" {
                   description "Traffic class 1";
                   junos:must "(\"protocols mpls statistics traffic-class-statistics\")";
                   junos:must-message "Traffic class can be configured only for traffic-class-statistics";
                 }
                 enum "tc-2" {
                   description "Traffic class 2";
                   junos:must "(\"protocols mpls statistics traffic-class-statistics\")";
                   junos:must-message "Traffic class can be configured only for traffic-class-statistics";
                 }
                 enum "tc-3" {
                   description "Traffic class 3";
                   junos:must "(\"protocols mpls statistics traffic-class-statistics\")";
                   junos:must-message "Traffic class can be configured only for traffic-class-statistics";
                 }
                 enum "tc-4" {
                   description "Traffic class 4";
                   junos:must "(\"protocols mpls statistics traffic-class-statistics\")";
                   junos:must-message "Traffic class can be configured only for traffic-class-statistics";
                 }
                 enum "tc-5" {
                   description "Traffic class 5";
                   junos:must "(\"protocols mpls statistics traffic-class-statistics\")";
                   junos:must-message "Traffic class can be configured only for traffic-class-statistics";
                 }
                 enum "tc-6" {
                   description "Traffic class 6";
                   junos:must "(\"protocols mpls statistics traffic-class-statistics\")";
                   junos:must-message "Traffic class can be configured only for traffic-class-statistics";
                 }
                 enum "tc-7" {
                   description "Traffic class 7";
                   junos:must "(\"protocols mpls statistics traffic-class-statistics\")";
                   junos:must-message "Traffic class can be configured only for traffic-class-statistics";
                 }
                 enum "all" {
                   description "All Traffic classes";
                   junos:must "(\"protocols mpls statistics traffic-class-statistics\")";
                   junos:must-message "Traffic class can be configured only for traffic-class-statistics";
                 }
               }
             }
             uses apply-advanced;
             leaf query-interval {
               description "Minimum transmit interval";
               units "milliseconds";
               type union {
                 type string {
                   pattern "<.*>|$.*";
                 }
                 type uint32 {
                   range "1000 .. 4294967295";
                 }
               }
             }
             leaf padding-size {
               description "Size of padding";
               type union {
                 type string {
                   pattern "<.*>|$.*";
                 }
                 type uint16 {
                   range "1 .. 1500";
                 }
               }
             }
             leaf average-sample-size {
               description "Number of samples used in average calculation";
               type union {
                 type string {
                   pattern "<.*>|$.*";
                 }
                 type uint16 {
                   range "1 .. 30";
                 }
               }
             }
             leaf twcd-delay-threshold {
               description "Two way channel delay threshold value";
               units "microseconds";
               type union {
                 type string {
                   pattern "<.*>|$.*";
                 }
                 type uint32 {
                   range "1 .. 4294967295";
                 }
               }
             }
             leaf rtt-delay-threshold {
               description "Round trip delay threshold value";
               units "microseconds";
               type union {
                 type string {
                   pattern "<.*>|$.*";
                 }
                 type uint32 {
                   range "1 .. 4294967295";
                 }
               }
             }
           }
         }
         container loss-delay {
           description "Combined loss-delay measurement options";
           uses apply-advanced;
           list traffic-class {
             key name;
             description "Traffic class specific options";
             leaf name {
               description "Traffic class value";
               type enumeration {
                 enum "tc-0" {
                   description "Traffic class 0";
                   junos:must "(\"protocols mpls statistics traffic-class-statistics\")";
                   junos:must-message "Traffic class can be configured only for traffic-class-statistics";
                 }
                 enum "tc-1" {
                   description "Traffic class 1";
                   junos:must "(\"protocols mpls statistics traffic-class-statistics\")";
                   junos:must-message "Traffic class can be configured only for traffic-class-statistics";
                 }
                 enum "tc-2" {
                   description "Traffic class 2";
                   junos:must "(\"protocols mpls statistics traffic-class-statistics\")";
                   junos:must-message "Traffic class can be configured only for traffic-class-statistics";
                 }
                 enum "tc-3" {
                   description "Traffic class 3";
                   junos:must "(\"protocols mpls statistics traffic-class-statistics\")";
                   junos:must-message "Traffic class can be configured only for traffic-class-statistics";
                 }
                 enum "tc-4" {
                   description "Traffic class 4";
                   junos:must "(\"protocols mpls statistics traffic-class-statistics\")";
                   junos:must-message "Traffic class can be configured only for traffic-class-statistics";
                 }
                 enum "tc-5" {
                   description "Traffic class 5";
                   junos:must "(\"protocols mpls statistics traffic-class-statistics\")";
                   junos:must-message "Traffic class can be configured only for traffic-class-statistics";
                 }
                 enum "tc-6" {
                   description "Traffic class 6";
                   junos:must "(\"protocols mpls statistics traffic-class-statistics\")";
                   junos:must-message "Traffic class can be configured only for traffic-class-statistics";
                 }
                 enum "tc-7" {
                   description "Traffic class 7";
                   junos:must "(\"protocols mpls statistics traffic-class-statistics\")";
                   junos:must-message "Traffic class can be configured only for traffic-class-statistics";
                 }
                 enum "all" {
                   description "All Traffic classes";
                   junos:must "(\"protocols mpls statistics traffic-class-statistics\")";
                   junos:must-message "Traffic class can be configured only for traffic-class-statistics";
                 }
                 enum "none" {
                   description "No Traffic class";
                 }
               }
             }
             uses apply-advanced;
             leaf query-interval {
               description "Minimum transmit interval";
               units "milliseconds";
               type union {
                 type string {
                   pattern "<.*>|$.*";
                 }
                 type uint32 {
                   range "1000 .. 4294967295";
                 }
               }
             }
             leaf measurement-quantity {
               description "Loss measurement quantity";
               default "packets";
               type enumeration {
                 enum "bytes" {
                   description "Byte loss measurement";
                 }
                 enum "packets" {
                   description "Packet loss measurement";
                 }
               }
             }
             leaf padding-size {
               description "Size of padding";
               type union {
                 type string {
                   pattern "<.*>|$.*";
                 }
                 type uint16 {
                   range "1 .. 1500";
                 }
               }
             }
             leaf average-sample-size {
               description "Number of samples used in average calculation";
               type union {
                 type string {
                   pattern "<.*>|$.*";
                 }
                 type uint16 {
                   range "1 .. 30";
                 }
               }
             }
             leaf loss-threshold {
               description "Loss threshold value";
               type union {
                 type string {
                   pattern "<.*>|$.*";
                 }
                 type uint32 {
                   range "1 .. 4294967295";
                 }
               }
             }
             leaf loss-threshold-window {
               description "Number of samples for loss threshold calculation";
               type union {
                 type string {
                   pattern "<.*>|$.*";
                 }
                 type uint32 {
                   range "1 .. 30";
                 }
               }
             }
             leaf twcd-delay-threshold {
               description "Two way channel delay threshold value";
               units "microseconds";
               type union {
                 type string {
                   pattern "<.*>|$.*";
                 }
                 type uint32 {
                   range "1 .. 4294967295";
                 }
               }
             }
             leaf rtt-delay-threshold {
               description "Round trip delay threshold value";
               units "microseconds";
               type union {
                 type string {
                   pattern "<.*>|$.*";
                 }
                 type uint32 {
                   range "1 .. 4294967295";
                 }
               }
             }
           }
         }
       }
       container responder {
         junos:must "(\".. .. .. ultimate-hop-popping\")";
         junos:must-message "Performance monitoring can be configured only on ultimate-hop-popping LSPs";
         junos:must "(\".. .. .. associate-lsp\")";
         junos:must-message "Performance monitoring can be configured only for associated LSPs";
         description "Responder options";
         uses apply-advanced;
         container loss {
           description "Loss measurement options";
           uses apply-advanced;
           leaf min-query-interval {
             description "Minimum query interval";
             units "milliseconds";
             type union {
               type string {
                 pattern "<.*>|$.*";
               }
               type uint32 {
                 range "1000 .. 4294967295";
               }
             }
           }
         }
         container delay {
           description "Delay measurement options";
           uses apply-advanced;
           leaf min-query-interval {
             description "Minimum query interval";
             units "milliseconds";
             type union {
               type string {
                 pattern "<.*>|$.*";
               }
               type uint32 {
                 range "1000 .. 4294967295";
               }
             }
           }
         }
       }
     }
     leaf lsp-ping-interval {
       description "Time interval between LSP ping messages";
       units "seconds";
       type union {
         type string {
           pattern "<.*>|$.*";
         }
         type uint16 {
           range "30 .. 3600";
         }
       }
     }
     leaf lsp-ping-multiplier {
       description "Number of ping reply missed before declaring BFD down";
       type union {
         type string {
           pattern "<.*>|$.*";
         }
         type uint8 {
           range "1 .. 5";
         }
       }
     }
     container traceoptions {
       description "Trace options for MPLSOAM process";
       uses apply-advanced;
       leaf no-remote-trace {
         description "Disable remote tracing";
         junos:must "(\"system tracing\")";
         junos:must-message "'no-remote-trace' is valid only when [system tracing] is configured";
         type empty;
       }
       container file {
         description "Trace file information";
         leaf filename {
           description "Name of file in which to write trace information";
           type string {
             length "1 .. 1024";
             junos:posix-pattern "![/ %]";
             junos:pattern-message "Must not contain '/', % or a space";
           }
         }
         leaf size {
           description "Maximum trace file size";
           type string;
         }
         leaf files {
           description "Maximum number of trace files";
           default "3";
           type union {
             type string {
               pattern "<.*>|$.*";
             }
             type uint32 {
               range "2 .. 1000";
             }
           }
         }
         choice world-readable-choice {
           leaf world-readable {
             description "Allow any user to read the log file";
             type empty;
           }
           leaf no-world-readable {
             description "Don't allow any user to read the log file";
             type empty;
           }
         }
         leaf match {
           description "Regular expression for lines to be logged";
           type jt:regular-expression;
         }
       }
       list flag {
         key name;
         ordered-by user;
         description "Tracing parameters";
         leaf name {
           type enumeration {
             enum "configuration" {
               description "Trace configuration events";
             }
             enum "pipe" {
               description "Trace pipe activity";
             }
             enum "rpc-packet-details" {
               description "Trace RPC packet details";
             }
             enum "database" {
               description "Trace database activity";
             }
             enum "network" {
               description "Trace network activity";
             }
             enum "traceroute" {
               description "Trace traceroute activity";
             }
             enum "all" {
               description "Trace everything";
             }
           }
         }
       }
     }
   }
   grouping pf_mapping {
     leaf name {
       description "Port Forwarding name";
       type string {
         length "1 .. 63";
         junos:posix-pattern "^[[:alnum:]][[:alnum:]_-]*$";
         junos:pattern-message "Must be a string beginning with a number or letter and consisting of letters, numbers, dashes and underscores.";
       }
     }
     uses apply-advanced;
     list destined-port {
       key "port translated-port";
       ordered-by user;
       description "Port forwarding mappings";
       max-elements 32;
       leaf port {
         description "Destination port";
         type union {
           type string {
             pattern "<.*>|$.*";
           }
           type uint16 {
             range "1 .. 65535";
           }
         }
       }
       leaf translated-port {
         description "Translated port";
         type union {
           type string {
             pattern "<.*>|$.*";
           }
           type uint16 {
             range "1 .. 65535";
           }
         }
       }
     }
   }
   grouping pim_bootstrap_options_type {
     uses apply-advanced;
     leaf priority {
       description "Eligibility to be the bootstrap router";
       type union {
         type string {
           pattern "<.*>|$.*";
         }
         type uint32 {
           range "0 .. 255";
         }
       }
     }
     leaf-list import {
       ordered-by user;
       description "Bootstrap import policy";
       type jt:policy-algebra;
     }
     leaf-list export {
       ordered-by user;
       description "Bootstrap export policy";
       type jt:policy-algebra;
     }
   }
   grouping pim_filter_obj {
     description "Filter to apply to tracing";
     leaf match-on {
       description "Argument on which to match";
       type enumeration {
         enum "prefix" {
           description "Filter based on prefix";
         }
       }
     }
     leaf-list policy {
       ordered-by user;
       description "Filter policy";
       type jt:policy-algebra;
     }
   }
   grouping pim_rp_group_range_type {
     leaf name {
       type jt:ipprefix;
     }
     uses apply-advanced;
     leaf nexthop-hold-time {
       description "Nexthop hold time in milliseconds";
       units "milliseconds";
       type union {
         type string {
           pattern "<.*>|$.*";
         }
         type uint32 {
           range "1 .. 1000";
         }
       }
     }
   }
   grouping pm-rspan-bridge-domain {
     description "RSPAN bridge-domain for pm";
     leaf name {
       description "Bridge domain name or VLAN id";
       junos:must "(!(\"vlans $$ forwarding-options filter\"))";
       junos:must-message "A vlan cannot both be an analyzer output vlan and have a filter applied to it.";
       type string {
       }
     }
     uses apply-advanced;
   }
   grouping pm-rspan-vlan {
     description "RSPAN vlan for pm";
     leaf name {
       description "VLAN name or VLAN id";
       junos:must "(!(\"vlans $$ forwarding-options filter\"))";
       junos:must-message "A vlan cannot both be an analyzer output vlan and have a filter applied to it.";
       type string {
       }
     }
     uses apply-advanced;
     leaf no-tag {
       description "Removes extra RSPAN tag from mirrored packets";
       type empty;
     }
   }
   grouping pm_family_input_type {
     description "Input options for port mirroring";
     uses apply-advanced;
     leaf rate {
       description "Ratio of packets to be sampled (1 out of N)";
       type union {
         type string {
           pattern "<.*>|$.*";
         }
         type uint32;
       }
     }
     leaf run-length {
       description "Number of samples after initial trigger";
       type union {
         type string {
           pattern "<.*>|$.*";
         }
         type uint32 {
           range "0 .. 20";
         }
       }
     }
     leaf maximum-packet-length {
       description "Maximum length of the mirrored packet";
       default "0";
       units "bytes";
       type union {
         type string {
           pattern "<.*>|$.*";
         }
         type uint32 {
           range "0 .. 9216";
         }
       }
     }
   }
   grouping policy-object-type {
     uses apply-advanced;
     container traceoptions {
       description "Network Security Policy Tracing Options";
       uses apply-advanced;
       leaf no-remote-trace {
         description "Disable remote tracing";
         junos:must "(\"system tracing\")";
         junos:must-message "'no-remote-trace' is valid only when [system tracing] is configured";
         type empty;
       }
       container file {
         description "Trace file information";
         leaf filename {
           description "Name of file in which to write trace information";
           type string {
             length "1 .. 1024";
             junos:posix-pattern "![/ %]";
             junos:pattern-message "Must not contain '/', % or a space";
           }
         }
         leaf size {
           description "Maximum trace file size";
           type string;
         }
         leaf files {
           description "Maximum number of trace files";
           default "3";
           type union {
             type string {
               pattern "<.*>|$.*";
             }
             type uint32 {
               range "2 .. 1000";
             }
           }
         }
         choice world-readable-choice {
           leaf world-readable {
             description "Allow any user to read the log file";
             type empty;
           }
           leaf no-world-readable {
             description "Don't allow any user to read the log file";
             type empty;
           }
         }
         leaf match {
           description "Regular expression for lines to be logged";
           type jt:regular-expression;
         }
       }
       list flag {
         key name;
         ordered-by user;
         description "Tracing parameters";
         leaf name {
           type enumeration {
             enum "configuration" {
               description "Trace configuration events";
             }
             enum "routing-socket" {
               description "Trace routing socket events";
             }
             enum "compilation" {
               description "Policy compilation events";
             }
             enum "ipc" {
               description "Inter-process communication events";
             }
             enum "rules" {
               description "Policy rules related events";
             }
             enum "lookup" {
               description "Policy lookup events";
             }
             enum "all" {
               description "Trace everything";
             }
           }
         }
       }
     }
     list policy {
       key "from-zone-name to-zone-name";
       ordered-by user;
       description "Define a policy context from this zone";
       leaf from-zone-name {
         description "Source zone";
         junos:must "((\".. .. .. .. security zones security-zone $$\" || \".. .. .. .. .. security zones security-zone $$\"))";
         junos:must-message "Security zone must be defined";
         type string {
           length "1 .. 63";
         }
       }
       leaf to-zone-name {
         description "Destination zone";
         junos:must "((\".. .. .. .. security zones security-zone $$\" || \".. .. .. .. .. security zones security-zone $$\"))";
         junos:must-message "Security zone must be defined";
         type string {
           length "1 .. 63";
         }
       }
       uses apply-advanced;
       list policy {
         key name;
         ordered-by user;
         description "Define security policy in specified zone-to-zone direction";
         uses policy_type;
       }
       container application-services {
         description "Application Services";
         uses context_application_services_type;
       }
     }
     container global {
       description "Define a global policy context";
       uses apply-advanced;
       list policy {
         key name;
         ordered-by user;
         description "Define security policy in global context";
         uses policy_type;
       }
     }
     list policy-set {
       key name;
       ordered-by user;
       description "Define a policy context for tunnel-inspection";
       leaf name {
         description "Policy-set name";
         type string {
           length "1 .. 63";
         }
       }
       uses apply-advanced;
       list policy {
         key name;
         ordered-by user;
         description "Define security policy in tunnel-inspection context";
         uses policy_type;
       }
     }
     container default-policy {
       description "Configure default action when no user-defined policy match";
       uses apply-advanced;
       leaf default-action {
         description "Default action";
         default "deny-all";
         type enumeration {
           enum "permit-all" {
             description "Permit all traffic if no policy match";
           }
           enum "deny-all" {
             description "Deny all traffic if no policy match";
           }
         }
       }
       leaf log-profile {
         description "Rtlog profile";
         junos:must "(\"security log profile $$\")";
         junos:must-message "RTLOG profile must be defined under [security log profile]";
         type string;
       }
     }
     container policy-rematch {
       presence "enable policy-rematch";
       description "Re-evaluate the policy when changed";
       leaf extensive {
         description "Perform policy extensive rematch";
         type empty;
       }
     }
     container policy-stats {
       presence "enable policy-stats";
       description "Parameters for policy statistics";
       uses apply-advanced;
       leaf system-wide {
         description "Enable/Disable system-wide policy statistics";
         type enumeration {
           enum "enable" {
             description "Enable policy system-wide statistics";
           }
           enum "disable" {
             description "Disable policy system-wide statistics";
           }
         }
       }
     }
     container pre-id-default-policy {
       description "Configure default policy action before dynamic application is finally identified";
       uses apply-advanced;
       container then {
         description "Specify policy action to take when packet match criteria";
         uses apply-advanced;
         container log {
           description "Enable log";
           uses log_type;
         }
         container session-timeout {
           description "Session timeout";
           uses session_timeout_type;
         }
       }
     }
     container unified-policy {
       description "Unified policies lookup limitations";
       uses apply-advanced;
       leaf max-lookups {
         description "Max lookup times upon micro-app transaction finals";
         type union {
           type string {
             pattern "<.*>|$.*";
           }
           type uint32 {
             range "0 .. 4294967295";
           }
         }
       }
     }
     container dns-cache {
       description "Define security policy dns-cache behaviors";
       uses apply-advanced;
       container error-response-delete-ip {
         presence "enable error-response-delete-ip";
         description "Clear DNS cache entry IP on error DNS response";
         uses apply-advanced;
         leaf retry-interval {
           description "Interval between deleting IP and resending DNS requests";
           default "300";
           units "seconds";
           type union {
             type string {
               pattern "<.*>|$.*";
             }
             type uint32 {
               range "5 .. 86400";
             }
           }
         }
       }
     }
     list stateful-firewall-rule {
       key name;
       ordered-by user;
       description "Define a stateful-firewall-rule";
       leaf name {
         description "Stateful-firewall-rule name";
         type string {
           length "1 .. 63";
           junos:posix-pattern "^[[:alnum:]][[:alnum:]/.:_-]*$";
           junos:pattern-message "Must be a string beginning with a number or letter and consisting of letters, numbers, dashes, underscores, forward slashes, colons and dots.";
         }
       }
       uses apply-advanced;
       leaf match-direction {
         description "Direction for which the rule match is applied";
         type enumeration {
           enum "input" {
             description "Match on input to interface";
           }
           enum "output" {
             description "Match on output from interface";
           }
           enum "input-output" {
             description "Match on input to or output from interface";
           }
         }
       }
       list policy {
         key name;
         ordered-by user;
         description "Define a stateful-firewall policy";
         uses policy_type;
       }
     }
     list stateful-firewall-rule-set {
       key name;
       ordered-by user;
       description "Defines a set of stateful firewall rules";
       leaf name {
         description "Name of the stateful firewall rule set";
         type string {
           length "1 .. 63";
           junos:posix-pattern "^[[:alnum:]][[:alnum:]/.:_-]*$";
           junos:pattern-message "Must be a string beginning with a number or letter and consisting of letters, numbers, dashes, underscores, forward slashes, colons and dots.";
         }
       }
       uses apply-advanced;
       list stateful-firewall-rule {
         key name;
         ordered-by user;
         description "Rule to be included in this stateful firewall rule set";
         leaf name {
           description "Stateful-firewall-rule name";
           junos:must "(\"services policies stateful-firewall-rule $$\")";
           junos:must-message "Undefined stateful-firewall-rule. Rule must be configured under policies";
           type string {
             junos:posix-pattern "^[[:alnum:]][[:alnum:]/.:_-]{0,62}$";
             junos:pattern-message "Must be a string beginning with a number or letter and consisting of no more than 63 total letters, numbers, dashes, underscores, forward slashes, colons and dots.";
           }
         }
         uses apply-advanced;
       }
     }
   }
   grouping context_application_services_type {
     uses apply-advanced;
     leaf security-metadata-streaming-policy {
       description "Specify security-metadata-streaming-policy";
       junos:must "(\"services security-metadata-streaming policy $$\")";
       junos:must-message "security-metadata-streaming policy must be defined";
       type string {
         length "1 .. 63";
       }
     }
   }
   grouping log_type {
     uses apply-advanced;
     leaf session-init {
       description "Log at session init time";
       type empty;
     }
     leaf session-close {
       description "Log at session close time";
       type empty;
     }
     leaf session-update {
       description "Log with specified interval (0 to disable this log)";
       default "0";
       units "minutes";
       type union {
         type string {
           pattern "<.*>|$.*";
         }
         type uint32 {
           range "0 .. 1440";
         }
       }
     }
     leaf sfw {
       description "Display Stateful-fire-wall SYSLOGs";
       type empty;
     }
     leaf profile {
       description "Name of rtlog profile";
       junos:must "(\"security log profile $$ stream-name\")";
       junos:must-message "RTLOG profile with stream must be defined under [security log profile]";
       type string;
     }
   }
   grouping policy_type {
     leaf name {
       description "Security policy name";
       type string {
         length "1 .. 63";
         junos:posix-pattern "^[[:alnum:]][[:alnum:]_-]*$";
         junos:pattern-message "Must be a string beginning with a number or letter and consisting of letters, numbers, dashes and underscores.";
       }
     }
     uses apply-advanced;
     leaf description {
       description "Text description of policy";
       type string {
         length "1 .. 900";
         junos:posix-pattern "^[^&<>\n]+$";
         junos:pattern-message "Must be a string excluding '&', '<', '>' and '\n'";
       }
     }
     container match {
       description "Specify security policy match-criteria";
       uses apply-advanced;
       choice source-address_choice {
         case case_1 {
           leaf-list source-address {
             ordered-by user;
             type string;
           }
         }
       }
       choice destination-address_choice {
         case case_1 {
           leaf-list destination-address {
             ordered-by user;
             type string;
           }
         }
       }
       leaf source-address-excluded {
         description "Exclude source addresses";
         type empty;
       }
       leaf destination-address-excluded {
         description "Exclude destination addresses";
         type empty;
       }
       choice application_type_choice {
         case case_1 {
           leaf-list application {
             ordered-by user;
             type string;
           }
         }
       }
       choice source_identity_choice {
         case case_1 {
           leaf-list source-identity {
             ordered-by user;
             type string;
           }
         }
       }
       choice source_identity_feed_choice {
         case case_1 {
           leaf-list source-identity-feed {
             ordered-by user;
             description "Specify source-identity-feed name from list to match";
             type string {
               length "1 .. 64";
             }
           }
         }
       }
       choice source_tenant_choice {
         case case_1 {
           list source-tenant {
             key name;
             ordered-by user;
             description "Source Tenant";
             uses match_source_tenant_type;
           }
         }
       }
       choice dest_service_choice {
         case case_1 {
           list destination-service {
             key name;
             ordered-by user;
             description "Destination Service";
             uses match_dest_service_type;
           }
         }
       }
       choice destination_identity_feed_choice {
         case case_1 {
           leaf-list destination-identity-feed {
             ordered-by user;
             description "Specify destination-identity-feed name from list to match";
             type string {
               length "1 .. 64";
             }
           }
         }
       }
       choice source_end_user_profile_choice {
         case case_1 {
           container source-end-user-profile {
             description "Match source end user profile";
             uses match_source_end_user_profile_value;
           }
         }
       }
       choice dynamic_application_type_choice {
         case case_1 {
           leaf-list dynamic-application {
             ordered-by user;
             type string;
           }
         }
       }
       choice url_category_type_choice {
         case case_1 {
           leaf-list url-category {
             ordered-by user;
             type string;
           }
         }
       }
       choice from_zone_choice {
         case case_1 {
           leaf-list from-zone {
             ordered-by user;
             type string;
           }
         }
       }
       choice to_zone_choice {
         case case_1 {
           leaf-list to-zone {
             ordered-by user;
             type string;
           }
         }
       }
       choice source_vrf_choice {
         case case_1 {
           leaf-list source-l3vpn-vrf-group {
             ordered-by user;
             description "L3VPN group name";
             junos:must "(\"security l3vpn vrf-group $$\")";
             junos:must-message "referenced vrf-group must configured";
             type string;
           }
         }
       }
       choice dst_vrf_choice {
         case case_1 {
           leaf-list destination-l3vpn-vrf-group {
             ordered-by user;
             description "L3VPN group name";
             junos:must "(\"security l3vpn vrf-group $$\")";
             junos:must-message "referenced vrf-group must configured";
             type string;
           }
         }
       }
     }
     container then {
       description "Specify policy action to take when packet match criteria";
       uses apply-advanced;
       choice action {
         case case_1 {
           container deny {
             presence "enable deny";
             description "Deny packets";
             uses apply-advanced;
             container application-services {
               description "Application Services";
               uses apply-advanced;
               container security-intelligence {
                 description "Generate security intellegence feeds";
                 uses security_intelligence_feeds;
               }
             }
           }
         }
         case case_2 {
           container reject {
             presence "enable reject";
             description "Reject packets";
             uses apply-advanced;
             leaf profile {
               description "Profile for redirect HTTP/S traffic";
               junos:must "(\"security dynamic-application profile $$\")";
               junos:must-message "Dynamic-application profile must be defined";
               type string;
             }
             container ssl-proxy {
               presence "enable ssl-proxy";
               description "SSL proxy services";
               uses apply-advanced;
               leaf profile-name {
                 description "Specify SSL proxy service profile name";
                 junos:must "(\"services ssl proxy profile $$\")";
                 junos:must-message "Referenced SSL proxy profile is not defined";
                 type string;
               }
             }
             container application-services {
               description "Application Services";
               uses apply-advanced;
               container security-intelligence {
                 description "Generate security intellegence feeds";
                 uses security_intelligence_feeds;
               }
             }
           }
         }
         case case_3 {
           container permit {
             presence "enable permit";
             description "Permit packets";
             uses apply-advanced;
             container tunnel {
               description "Tunnel packets";
               junos:must "(!(\".. .. .. match dynamic-application\"))";
               junos:must-message "Tunnel and dynamic-application can't be applied to same policy";
               uses tunnel_type;
             }
             container firewall-authentication {
               description "Enable authentication for this policy if permit or tunnel";
               uses firewall_authentication_type;
             }
             container destination-address {
               description "Enable destination address translation";
               presence "enable destination-address";
               uses destination_nat_enable_type;
             }
             container application-services {
               description "Application Services";
               uses application_services_type;
             }
             container tunnel-inspection {
               description "Enable tunnel inspection";
               uses apply-advanced;
               leaf profile-name {
                 description "Tunnel inspection profile";
                 junos:must "((\".. .. .. .. .. .. .. security tunnel-inspection inspection-profile $$\" || \" .. .. .. .. .. .. .. .. security tunnel-inspection inspection-profile $$\"))";
                 junos:must-message "tunnel-inspection profile must be configured";
                 type string {
                   length "1 .. 63";
                 }
               }
             }
             container tcp-options {
               description "Transmission Control Protocol session configuration";
               uses apply-advanced;
               leaf syn-check-required {
                 description "Enable per policy SYN-flag check";
                 type empty;
               }
               leaf sequence-check-required {
                 description "Enable per policy sequence-number checking";
                 type empty;
               }
               leaf initial-tcp-mss {
                 description "Override MSS value for initial direction";
                 type union {
                   type string {
                     pattern "<.*>|$.*";
                   }
                   type uint32 {
                     range "64 .. 65535";
                   }
                 }
               }
               leaf reverse-tcp-mss {
                 description "Override MSS value for reverse direction";
                 type union {
                   type string {
                     pattern "<.*>|$.*";
                   }
                   type uint32 {
                     range "64 .. 65535";
                   }
                 }
               }
               leaf window-scale {
                 description "Enable per policy window-scale";
                 type empty;
               }
             }
             leaf services-offload {
               description "Enable services offloading";
               type empty;
             }
             leaf no-services-offload {
               description "Disenable services offloading";
               type empty;
             }
             leaf advanced-connection-tracking {
               description "Lookup advanced-connection-tracking table on to-zone";
               type empty;
             }
           }
         }
       }
       container log {
         description "Enable log";
         uses log_type;
       }
       container count {
         description "Enable count";
         presence "enable count";
         uses count_type;
       }
     }
     leaf scheduler-name {
       description "Name of scheduler";
       junos:must "(\"schedulers scheduler $$\")";
       junos:must-message "scheduler must be defined";
       type string {
         length "1 .. 63";
         junos:posix-pattern "^[[:alnum:]][[:alnum:]_-]*$";
         junos:pattern-message "Must be a string beginning with a number or letter and consisting of letters, numbers, dashes and underscores.";
       }
     }
     leaf report-skip {
       description "Skip report for this policy";
       type empty;
     }
   }
   grouping application_services_type {
     description "Application Services";
     uses apply-advanced;
     leaf gtp-profile {
       description "Specify GPRS Tunneling Protocol profile name";
       junos:must "(!(\".. .. .. .. match dynamic-application\"))";
       junos:must-message "gtp and dynamic-application can't be applied to same policy";
       junos:must "(\"security gtp profile $$\")";
       junos:must-message "gtp profile must be defined";
       type string {
         length "1 .. 63";
       }
     }
     leaf sctp-profile {
       description "Specify Stream Control Protocol profile name";
       junos:must "(!(\".. .. .. .. match dynamic-application\"))";
       junos:must-message "sctp and dynamic-application can't be applied to same policy";
       junos:must "(\"security sctp profile $$\")";
       junos:must-message "sctp profile must be defined";
       type string {
         length "1 .. 63";
       }
     }
     leaf idp {
       description "Intrusion detection and prevention";
       type empty;
     }
     leaf packet-capture {
       description "Capturing traffic related to this policy";
       junos:must "(\".. .. .. .. match dynamic-application junos:UNKNOWN\")";
       junos:must-message "packet-capture action requires dynamic application junos:UNKNOWN in policy";
       type empty;
     }
     leaf idp-policy {
       description "Specify idp policy name";
       type string {
         length "1 .. 255";
       }
     }
     container ssl-proxy {
       presence "enable ssl-proxy";
       description "SSL proxy services";
       uses apply-advanced;
       leaf profile-name {
         description "Specify SSL proxy service profile name";
         junos:must "(\"services ssl proxy profile $$\")";
         junos:must-message "Referenced SSL proxy profile is not defined";
         type string;
       }
     }
     container web-proxy {
       presence "enable web-proxy";
       description "Web proxy services";
       uses apply-advanced;
       leaf profile-name {
         description "Specify Web proxy service profile name";
         junos:must "((\"services web-proxy secure-proxy profile $$\" || \"services web-proxy proxy-auto-configuration profile $$\"))";
         junos:must-message "Referenced Web proxy profile is not defined";
         type string;
       }
     }
     container uac-policy {
       presence "enable uac-policy";
       description "Enable unified access control enforcement of policy";
       uses apply-advanced;
       leaf captive-portal {
         junos:must "(\"services unified-access-control captive-portal $$\")";
         junos:must-message "Captive portal policy must be defined";
         type string {
           length "1 .. 128";
         }
       }
     }
     leaf utm-policy {
       description "Specify utm policy name";
       junos:must "(\"security utm utm-policy $$\")";
       junos:must-message "utm-policy must be defined";
       type string {
         length "1 .. 255";
       }
     }
     leaf icap-redirect {
       description "Specify icap redirect profile name";
       junos:must "(\"services icap-redirect profile $$\")";
       junos:must-message "icap-redirect profile must be defined";
       type string {
         length "1 .. 63";
       }
     }
     container application-firewall {
       description "Application firewall services";
       status deprecated;
       junos:must "((!(\".. .. .. .. match dynamic-application\") || (\".. .. .. .. match dynamic-application\" && \".. .. .. .. match dynamic-application none\")))";
       junos:must-message "Traditional AppFW and dynamic-application can't be applied to same policy";
       uses jsf_service_rule_set_type;
     }
     container application-traffic-control {
       description "Application traffic control services";
       uses jsf_application_traffic_control_rule_set_type;
     }
     choice wx-redirection {
       case case_1 {
         leaf redirect-wx {
           description "Set WX redirection";
           type empty;
         }
       }
       case case_2 {
         leaf reverse-redirect-wx {
           description "Set WX reverse redirection";
           type empty;
         }
       }
     }
     leaf security-intelligence-policy {
       description "Specify security-intelligence policy name";
       junos:must "(\"services security-intelligence policy $$\")";
       junos:must-message "security-intelligence policy must be defined";
       type string {
         length "1 .. 255";
       }
     }
     leaf advanced-anti-malware-policy {
       description "Specify advanced-anti-malware policy name";
       junos:must "(\"services advanced-anti-malware policy $$\")";
       junos:must-message "advanced-anti-malware policy must be defined";
       type string {
         length "1 .. 255";
       }
     }
     container security-intelligence {
       description "Generate security intellegence feeds";
       uses security_intelligence_feeds;
     }
   }
   grouping count_type {
     uses apply-advanced;
   }
   grouping destination_nat_enable_type {
     description "Enable Destination NAT";
     uses apply-advanced;
     choice destination_nat {
       case case_1 {
         leaf drop-translated {
           description "Drop the policy if NAT translated";
           type empty;
         }
       }
       case case_2 {
         leaf drop-untranslated {
           description "Drop the policy if NAT untranslated";
           type empty;
         }
       }
     }
   }
   grouping firewall_authentication_type {
     uses apply-advanced;
     choice auth-type {
       case case_1 {
         container pass-through {
           presence "enable pass-through";
           junos:must "((\".. .. .. .. .. .. .. access firewall-authentication pass-through\" || \".. .. .. .. .. .. .. .. access firewall-authentication pass-through\"))";
           junos:must-message "access firewall-authentication pass-through must be configured";
           description "Pass-through firewall authentication settings";
           uses apply-advanced;
           leaf access-profile {
             description "Specify access profile name";
             junos:must "((\"access profile $$\" || (\".. .. .. .. .. .. .. .. .. .. access profile $$\" && !(\".. .. .. .. .. .. .. .. .. .. access disable-tenant-access\"))))";
             junos:must-message "access-profile must be defined or access to profile is disabled for tenants";
             type string {
               length "1 .. 63";
             }
           }
           leaf-list client-match {
             ordered-by user;
             description "Name of user or group to match";
             type string {
               length "1 .. 63";
             }
           }
           leaf web-redirect {
             description "Redirect unauthenticated HTTP requests to the device's internal web server";
             type empty;
           }
           leaf web-redirect-to-https {
             description "Redirect unauthenticated HTTP requests to the device's internal HTTPS web server";
             type empty;
           }
           leaf web-authentication-server {
             description "Firewall web authentication server";
             type string {
               length "1 .. 128";
             }
           }
           leaf ssl-termination-profile {
             description "Specify SSL termination profile used to the SSL offload";
             type string {
               length "1 .. 63";
             }
           }
           leaf auth-only-browser {
             description "Authenticate only browser traffic";
             type empty;
           }
           list auth-user-agent {
             key name;
             ordered-by user;
             description "Authenticate HTTP traffic with specified user agent";
             leaf name {
               description "Authenticate HTTP traffic with specified user agent";
               type string {
                 length "1 .. 16";
               }
             }
             uses apply-advanced;
           }
         }
       }
       case case_2 {
         container web-authentication {
           presence "enable web-authentication";
           junos:must "((\".. .. .. .. .. .. .. access firewall-authentication web-authentication\" || \".. .. .. .. .. .. .. .. access firewall-authentication web-authentication\"))";
           junos:must-message "access firewall-authentication web-authentication must be configured";
           description "Web-authentication settings";
           uses apply-advanced;
           leaf-list client-match {
             ordered-by user;
             description "Name of user or group to match";
             type string {
               length "1 .. 63";
             }
           }
         }
       }
       case case_3 {
         container user-firewall {
           description "User-firewall firewall authentication settings";
           uses apply-advanced;
           leaf access-profile {
             description "Specify access profile name";
             junos:must "((\"access profile $$\" || (\".. .. .. .. .. .. .. .. .. .. access profile $$\" && !(\".. .. .. .. .. .. .. .. .. .. access disable-tenant-access\"))))";
             junos:must-message "access-profile must be defined or access to profile is disabled for tenants";
             type string {
               length "1 .. 63";
             }
           }
           leaf web-redirect {
             description "Redirect unauthenticated HTTP req to web server";
             type empty;
           }
           leaf web-redirect-to-https {
             description "Redirect unauthenticated HTTP req to HTTPS web server";
             type empty;
           }
           leaf web-authentication-server {
             description "Firewall web authentication server";
             type string {
               length "1 .. 128";
             }
           }
           leaf ssl-termination-profile {
             description "Specify SSL termination profile used to the SSL offload";
             type string {
               length "1 .. 63";
             }
           }
           leaf auth-only-browser {
             description "Authenticate only browser traffic";
             type empty;
           }
           list auth-user-agent {
             key name;
             ordered-by user;
             description "Authenticate HTTP traffic with specified user agent";
             leaf name {
               description "Authenticate HTTP traffic with specified user agent";
               type string {
                 length "1 .. 16";
               }
             }
             uses apply-advanced;
           }
           leaf domain {
             description "Specify domain name";
             type string {
               length "1 .. 64";
             }
           }
         }
       }
     }
     leaf push-to-identity-management {
       description "Push auth entry to identity management server";
       type empty;
     }
   }
   grouping jsf_service_rule_set_type {
     description "Define service rule set reference";
     uses apply-advanced;
     leaf rule-set {
       description "Service rule set name";
       junos:must "(\"security application-firewall rule-sets $$\")";
       junos:must-message "rule set must be defined";
       type string {
         length "1 .. 64";
       }
     }
   }
   grouping match_dest_service_type {
     leaf name {
       description "Destination Service for Vector Routing Policy";
       type string;
     }
   }
   grouping match_source_end_user_profile_value {
     uses apply-advanced;
     leaf source-end-user-profile-name {
       description "Specify source-end-user-profile name from list to match";
       junos:must "((\".. .. .. .. .. .. services user-identification device-information end-user-profile profile-name $$\" || \".. .. .. .. .. .. .. services user-identification device-information end-user-profile profile-name $$\"))";
       junos:must-message "Services user-identification device-information end-user-profile profile-name must be defined";
       type string;
     }
   }
   grouping match_source_tenant_type {
     leaf name {
       description "Source Tenant for Vector Routing Policy";
       type string;
     }
   }
   grouping port-range {
     description "Port ranges";
     leaf name {
       description "Single port/minimum port in the port range";
       type union {
         type string {
           pattern "<.*>|$.*";
         }
         type uint32 {
           range "0 .. 65535";
         }
       }
     }
     leaf maximum-port {
       description "Maximum port in the port range";
       type union {
         type string {
           pattern "<.*>|$.*";
         }
         type uint32 {
           range "0 .. 65535";
         }
       }
     }
   }
   grouping profile-radius-server-name-object {
     leaf name {
       description "Fully qualified domain name of the RADIUS server";
       type string {
         length "4 .. 255";
         junos:posix-pattern "^[[:alnum:]._-]+$";
         junos:pattern-message "Invalid FQDN";
       }
     }
     uses apply-advanced;
     leaf dns-query-interval {
       description "Frequency of RADIUS server name resolution";
       default "60";
       units "minutes";
       type union {
         type string {
           pattern "<.*>|$.*";
         }
         type uint16 {
           range "10 .. 1440";
         }
       }
     }
     leaf accounting-port {
       description "RADIUS server accounting port number";
       default "1813";
       type union {
         type string {
           pattern "<.*>|$.*";
         }
         type uint16 {
           range "1 .. 65535";
         }
       }
     }
     leaf radsec-destination {
       description "RADSEC destination";
       junos:must "(!(\".. preauthentication-order\"))";
       junos:must-message "RADSEC is mutually exclusive with preauthentication";
       junos:must "(\"access radsec destination $$\")";
       junos:must-message "RADSEC destination must be defined";
       type union {
         type uint32;
         type string {
           pattern "<.*>|$.*";
         }
       }
     }
     leaf port {
       description "RADIUS server authentication port number";
       default "1812";
       type union {
         type string {
           pattern "<.*>|$.*";
         }
         type uint16 {
           range "1 .. 65535";
         }
       }
     }
     leaf preauthentication-port {
       description "RADIUS server preauthentication port number";
       type union {
         type string {
           pattern "<.*>|$.*";
         }
         type uint16 {
           range "1 .. 65535";
         }
       }
     }
     leaf dynamic-request-port {
       description "RADIUS client dynamic request port number";
       default "3799";
       type union {
         type string {
           pattern "<.*>|$.*";
         }
         type uint16 {
           range "1 .. 65535";
         }
       }
     }
     leaf secret {
       description "Shared secret with the RADIUS server";
       type jt:unreadable;
     }
     leaf preauthentication-secret {
       description "Shared secret with the RADIUS server";
       type jt:unreadable;
     }
     leaf timeout {
       description "Request timeout period";
       default "3";
       units "seconds";
       type union {
         type string {
           pattern "<.*>|$.*";
         }
         type uint32 {
           range "1 .. 1000";
         }
       }
     }
     leaf retry {
       description "Retry attempts";
       default "3";
       type union {
         type string {
           pattern "<.*>|$.*";
         }
         type uint32 {
           range "1 .. 100";
         }
       }
     }
     leaf accounting-timeout {
       description "Accounting request timeout period";
       default "0";
       units "seconds";
       type union {
         type string {
           pattern "<.*>|$.*";
         }
         type uint32 {
           range "0 .. 1000";
         }
       }
     }
     leaf accounting-retry {
       description "Accounting retry attempts";
       default "0";
       type union {
         type string {
           pattern "<.*>|$.*";
         }
         type uint32 {
           range "0 .. 100";
         }
       }
     }
     leaf max-outstanding-requests {
       description "Maximum requests in flight to server";
       default "1000";
       type union {
         type string {
           pattern "<.*>|$.*";
         }
         type uint32 {
           range "0 .. 2000";
         }
       }
     }
     leaf source-address {
       description "Use specified address as source address";
       type jt:ipaddr;
     }
     leaf routing-instance {
       description "Use specified routing instance";
       junos:must "((\"routing-instances $$\" || any \"tenants <*> routing-instances $$\"))";
       junos:must-message "referenced routing-instance must be defined";
       type string;
     }
   }
   grouping profile-radius-server-object {
     leaf name {
       description "RADIUS server address";
       type jt:ipaddr;
     }
     uses apply-advanced;
     leaf port {
       description "RADIUS server authentication port number";
       default "1812";
       type union {
         type string {
           pattern "<.*>|$.*";
         }
         type uint16 {
           range "1 .. 65535";
         }
       }
     }
     leaf preauthentication-port {
       description "RADIUS server preauthentication port number";
       type union {
         type string {
           pattern "<.*>|$.*";
         }
         type uint16 {
           range "1 .. 65535";
         }
       }
     }
     leaf accounting-port {
       description "Port number to which to send RADIUS accounting messages";
       default "1813";
       type union {
         type string {
           pattern "<.*>|$.*";
         }
         type uint16 {
           range "1 .. 65535";
         }
       }
     }
     leaf dynamic-request-port {
       description "RADIUS client dynamic request port number";
       default "3799";
       type union {
         type string {
           pattern "<.*>|$.*";
         }
         type uint16 {
           range "1 .. 65535";
         }
       }
     }
     leaf secret {
       description "Shared secret with the RADIUS server";
       type jt:unreadable;
     }
     leaf preauthentication-secret {
       description "Shared secret with the RADIUS server";
       type jt:unreadable;
     }
     leaf timeout {
       description "Request timeout period";
       default "3";
       units "seconds";
       type union {
         type string {
           pattern "<.*>|$.*";
         }
         type uint32 {
           range "1 .. 1000";
         }
       }
     }
     leaf retry {
       description "Retry attempts";
       default "3";
       type union {
         type string {
           pattern "<.*>|$.*";
         }
         type uint32 {
           range "1 .. 100";
         }
       }
     }
     leaf accounting-timeout {
       description "Accounting request timeout period";
       default "0";
       units "seconds";
       type union {
         type string {
           pattern "<.*>|$.*";
         }
         type uint32 {
           range "0 .. 1000";
         }
       }
     }
     leaf accounting-retry {
       description "Accounting retry attempts";
       default "0";
       type union {
         type string {
           pattern "<.*>|$.*";
         }
         type uint32 {
           range "0 .. 100";
         }
       }
     }
     leaf max-outstanding-requests {
       description "Maximum requests in flight to server";
       default "1000";
       type union {
         type string {
           pattern "<.*>|$.*";
         }
         type uint32 {
           range "0 .. 2000";
         }
       }
     }
     leaf source-address {
       description "Use specified address as source address";
       type jt:ipaddr;
     }
     leaf routing-instance {
       description "Use specified routing instance";
       junos:must "((\"routing-instances $$\" || any \"tenants <*> routing-instances $$\"))";
       junos:must-message "referenced routing-instance must be defined";
       type string;
     }
     leaf radsec-destination {
       description "RADSEC destination";
       junos:must "(\"access radsec destination $$\")";
       junos:must-message "RADSEC destination must be defined";
       type union {
         type uint32;
         type string {
           pattern "<.*>|$.*";
         }
       }
     }
   }
   grouping profile-setting {
     description "UTM policy settings";
     leaf name {
       description "UTM policy name";
       type string {
         length "1 .. 29";
       }
     }
     uses apply-advanced;
     container anti-virus {
       description "UTM policy anti-virus profile";
       uses apply-advanced;
       leaf http-profile {
         description "Anti-virus profile";
         junos:must "((\"security utm feature-profile anti-virus sophos-engine profile $$\" || \"security utm feature-profile anti-virus profile $$\"))";
         junos:must-message "An anti-virus profile must be defined";
         type string;
       }
       container ftp {
         description "FTP profile";
         uses apply-advanced;
         leaf upload-profile {
           description "Anti-virus profile";
           junos:must "((\"security utm feature-profile anti-virus sophos-engine profile $$\" || \"security utm feature-profile anti-virus profile $$\"))";
           junos:must-message "An anti-virus profile must be defined";
           type string;
         }
         leaf download-profile {
           description "Anti-virus profile";
           junos:must "((\"security utm feature-profile anti-virus sophos-engine profile $$\" || \"security utm feature-profile anti-virus profile $$\"))";
           junos:must-message "An anti-virus profile must be defined";
           type string;
         }
       }
       leaf smtp-profile {
         description "Anti-virus profile";
         junos:must "((\"security utm feature-profile anti-virus sophos-engine profile $$\" || \"security utm feature-profile anti-virus profile $$\"))";
         junos:must-message "An anti-virus profile must be defined";
         type string;
       }
       leaf pop3-profile {
         description "Anti-virus profile";
         junos:must "((\"security utm feature-profile anti-virus sophos-engine profile $$\" || \"security utm feature-profile anti-virus profile $$\"))";
         junos:must-message "An anti-virus profile must be defined";
         type string;
       }
       leaf imap-profile {
         description "Anti-virus profile";
         junos:must "((\"security utm feature-profile anti-virus sophos-engine profile $$\" || \"security utm feature-profile anti-virus profile $$\"))";
         junos:must-message "An anti-virus profile must be defined";
         type string;
       }
     }
     container content-filtering {
       description "Content-filtering profile";
       uses apply-advanced;
       leaf http-profile {
         description "Content-filtering profile";
         status deprecated;
         junos:must "(\"security utm feature-profile content-filtering profile $$\")";
         junos:must-message "content-filtering profile must be defined";
         type string;
       }
       container ftp {
         description "FTP profile";
         status deprecated;
         uses apply-advanced;
         leaf upload-profile {
           description "Content-filtering FTP upload profile";
           junos:must "(\"security utm feature-profile content-filtering profile $$\")";
           junos:must-message "content-filtering profile must be defined";
           type string;
         }
         leaf download-profile {
           description "Content-filtering FTP download profile";
           junos:must "(\"security utm feature-profile content-filtering profile $$\")";
           junos:must-message "content-filtering profile must be defined";
           type string;
         }
       }
       leaf smtp-profile {
         description "Content-filtering SMTP profile";
         status deprecated;
         junos:must "(\"security utm feature-profile content-filtering profile $$\")";
         junos:must-message "content-filtering profile must be defined";
         type string;
       }
       leaf pop3-profile {
         description "Content-filtering POP3 profile";
         status deprecated;
         junos:must "(\"security utm feature-profile content-filtering profile $$\")";
         junos:must-message "content-filtering profile must be defined";
         type string;
       }
       leaf imap-profile {
         description "Content-filtering IMAP profile";
         status deprecated;
         junos:must "(\"security utm feature-profile content-filtering profile $$\")";
         junos:must-message "content-filtering profile must be defined";
         type string;
       }
       list rule-set {
         key name;
         ordered-by user;
         description "Configure UTM CF Rule Sets";
         uses cf-rule-set;
       }
     }
     container web-filtering {
       description "Web-filtering profile";
       uses apply-advanced;
       leaf http-profile {
         description "Web-filtering HTTP profile";
         junos:must "((\"security utm feature-profile web-filtering surf-control-integrated profile $$\" || (\"security utm feature-profile web-filtering websense-redirect profile $$\" || (\"security utm feature-profile web-filtering juniper-local profile $$\" || \"security utm feature-profile web-filtering juniper-enhanced profile $$\"))))";
         junos:must-message "websense-redirect profile or local profile or juniper-enhanced must be defined";
         type string;
       }
     }
     container anti-spam {
       description "Anti-spam profile";
       uses apply-advanced;
       leaf smtp-profile {
         description "Anti-spam profile";
         junos:must "(\"security utm feature-profile anti-spam sbl profile $$\")";
         junos:must-message "anti-spam sbl profile must be defined";
         type string;
       }
     }
     container traffic-options {
       description "Traffic options";
       status deprecated;
       uses apply-advanced;
       container sessions-per-client {
         description "Sessions per client";
         uses apply-advanced;
         leaf limit {
           description "Sessions limit";
           default "2000";
           type union {
             type string {
               pattern "<.*>|$.*";
             }
             type uint32 {
               range "0 .. 2000";
             }
           }
         }
         leaf over-limit {
           description "Over limit number";
           type enumeration {
             enum "log-and-permit" {
             }
             enum "block" {
             }
           }
         }
       }
     }
   }
   grouping programmable-rpd-type {
     uses apply-advanced;
     container traceoptions {
       description "Trace options";
       uses apply-advanced;
       container file {
         description "Trace file options";
         leaf filename {
           description "Name of file in which to write trace information";
           type string {
             length "1 .. 1024";
             junos:posix-pattern "![/ %]";
             junos:pattern-message "Must not contain '/', % or a space";
           }
         }
         leaf replace {
           description "Replace trace file rather than appending to it";
           status deprecated;
           type empty;
         }
         leaf size {
           description "Maximum trace file size";
           type string;
         }
         leaf files {
           description "Maximum number of trace files";
           default "10";
           type union {
             type string {
               pattern "<.*>|$.*";
             }
             type uint32 {
               range "2 .. 1000";
             }
           }
         }
         leaf no-stamp {
           description "Do not timestamp trace file";
           status deprecated;
           type empty;
         }
         choice world-readable-choice {
           leaf world-readable {
             description "Allow any user to read the log file";
             type empty;
           }
           leaf no-world-readable {
             description "Don't allow any user to read the log file";
             type empty;
           }
         }
       }
       list flag {
         key name;
         ordered-by user;
         description "Tracing parameters";
         leaf name {
           type enumeration {
             enum "client" {
               description "Client events";
             }
             enum "japi" {
               description "JAPI related traces";
             }
             enum "routing-interface" {
               description "Routing interface traces";
             }
             enum "route" {
               description "Trace routing information";
             }
             enum "normal" {
               description "Trace normal events";
             }
             enum "general" {
               description "Trace general events";
             }
             enum "state" {
               description "Trace state transitions";
             }
             enum "policy" {
               description "Trace policy processing";
             }
             enum "task" {
               description "Trace routing protocol task processing";
             }
             enum "timer" {
               description "Trace routing protocol timer processing";
             }
             enum "all" {
               description "Trace everything";
             }
           }
         }
       }
     }
     container purge-timeout {
       presence "enable purge-timeout";
       description "Purge timeout for all programmable-rpd clients in seconds";
       choice purge-parm {
         case case_1 {
           leaf never {
             description "Client programmed objects are never purged";
             type empty;
           }
         }
         case case_2 {
           leaf timeout {
             description "Timeout value, in seconds, for purging client programmed objects";
             units "seconds";
             type union {
               type string {
                 pattern "<.*>|$.*";
               }
               type uint32 {
                 range "1 .. 604800";
               }
             }
           }
         }
       }
     }
     list client {
       key name;
       ordered-by user;
       description "Programmable-rpd client options";
       leaf name {
         description "Client ID";
         type string {
           length "1 .. 255";
         }
       }
       uses apply-advanced;
       list interface-notification {
         key name;
         ordered-by user;
         description "Interfaces for notification";
         leaf name {
           description "Interface";
           type string {
             length "1 .. 32";
           }
         }
         uses apply-advanced;
       }
     }
     container rib-service {
       presence "enable rib-service";
       description "RIB service API options";
       uses apply-advanced;
       container dynamic-next-hop-interface {
         presence "enable dynamic-next-hop-interface";
         description "Update routes for next-hop interface changes";
         uses apply-advanced;
         choice enable-disable {
           case case_1 {
             leaf disable {
               description "Disable dynamic next-hop interface handling";
               type empty;
             }
           }
         }
       }
     }
   }
   grouping proto-object {
     leaf name {
       type string;
     }
     uses apply-advanced;
     list tunable-name {
       key name;
       ordered-by user;
       description "Protocol tunable name";
       uses tunable-object;
     }
   }
   grouping qualified_nh_obj {
     leaf name {
       description "Next hop to destination";
       type union {
         type jt:ipaddr-or-interface;
         type string {
           pattern "<.*>|$.*";
         }
       }
     }
     uses apply-advanced;
     leaf preference {
       description "Preference of qualified next hop";
       type union {
         type uint32;
         type string {
           pattern "<.*>|$.*";
         }
       }
     }
     leaf metric {
       description "Metric of qualified next hop";
       type union {
         type uint32;
         type string {
           pattern "<.*>|$.*";
         }
       }
     }
     leaf interface {
       description "Interface of qualified next hop";
       type union {
         type jt:interface-name;
         type string {
           pattern "<.*>|$.*";
         }
       }
     }
     leaf mac-address {
       description "Next-hop Mac Address";
       type jt:mac-unicast;
     }
     leaf tag {
       description "Tag string";
       type union {
         type uint32;
         type string {
           pattern "<.*>|$.*";
         }
       }
     }
     container bfd-liveness-detection {
       description "Bidirectional Forwarding Detection (BFD) options";
       uses apply-advanced;
       leaf version {
         description "BFD protocol version number";
         default "automatic";
         type enumeration {
           enum "0" {
             description "BFD version 0 (deprecated)";
           }
           enum "1" {
             description "BFD version 1";
           }
           enum "automatic" {
             description "Choose BFD version automatically";
           }
         }
       }
       leaf minimum-interval {
         description "Minimum transmit and receive interval";
         units "milliseconds";
         type union {
           type string {
             pattern "<.*>|$.*";
           }
           type uint32 {
             range "1 .. 255000";
           }
         }
       }
       leaf minimum-transmit-interval {
         description "Minimum transmit interval";
         status deprecated;
         units "milliseconds";
         type union {
           type string {
             pattern "<.*>|$.*";
           }
           type uint32 {
             range "1 .. 255000";
           }
         }
       }
       leaf minimum-receive-interval {
         description "Minimum receive interval";
         units "milliseconds";
         type union {
           type string {
             pattern "<.*>|$.*";
           }
           type uint32 {
             range "1 .. 255000";
           }
         }
       }
       leaf multiplier {
         description "Detection time multiplier";
         default "3";
         type union {
           type string {
             pattern "<.*>|$.*";
           }
           type uint32 {
             range "1 .. 255";
           }
         }
       }
       choice adaptation-choice {
         case case_1 {
           leaf no-adaptation {
             description "Disable adaptation";
             type empty;
           }
         }
       }
       container transmit-interval {
         description "Transmit-interval options";
         uses apply-advanced;
         leaf minimum-interval {
           description "Minimum transmit interval";
           units "milliseconds";
           type union {
             type string {
               pattern "<.*>|$.*";
             }
             type uint32 {
               range "1 .. 255000";
             }
           }
         }
         leaf threshold {
           description "High transmit interval triggering a trap";
           units "milliseconds";
           type union {
             type uint32;
             type string {
               pattern "<.*>|$.*";
             }
           }
         }
       }
       container detection-time {
         description "Detection-time options";
         uses apply-advanced;
         leaf threshold {
           description "High detection-time triggering a trap";
           units "milliseconds";
           type union {
             type uint32;
             type string {
               pattern "<.*>|$.*";
             }
           }
         }
       }
       container authentication {
         description "Authentication options";
         uses apply-advanced;
         leaf key-chain {
           description "Key chain name";
           junos:must "(\".. algorithm\")";
           junos:must-message "May not be configured without algorithm";
           junos:must "(\"security authentication-key-chains key-chain $$\")";
           junos:must-message "Referenced key-chain must be defined";
           type string;
         }
         leaf algorithm {
           description "Algorithm name";
           junos:must "(\".. key-chain\")";
           junos:must-message "May not be configured without key-chain";
           type enumeration {
             enum "simple-password" {
               description "Simple password";
             }
             enum "keyed-md5" {
               description "Keyed message Digest 5";
             }
             enum "meticulous-keyed-md5" {
               description "Meticulous keyed message Digest 5";
             }
             enum "keyed-sha-1" {
               description "Keyed secure hash algorithm (SHA1) ";
             }
             enum "meticulous-keyed-sha-1" {
               description "Meticulous keyed secure hash algorithm (SHA1) ";
             }
           }
         }
         leaf loose-check {
           description "Verify authentication only if authentication is negotiated";
           type empty;
         }
       }
       leaf neighbor {
         description "BFD neighbor address";
         type jt:ipaddr;
       }
       leaf local-address {
         description "BFD local address (for multihop only)";
         type jt:ipaddr;
       }
       leaf holddown-interval {
         description "Time to hold the session-UP notification to the client";
         units "milliseconds";
         type union {
           type string {
             pattern "<.*>|$.*";
           }
           type uint32 {
             range "0 .. 255000";
           }
         }
       }
       leaf minimum-receive-ttl {
         description "Minimum receive TTL below which to drop";
         type union {
           type string {
             pattern "<.*>|$.*";
           }
           type uint8 {
             range "1 .. 255";
           }
         }
       }
     }
   }
   grouping ragw-traceoptions {
     uses apply-advanced;
     leaf no-remote-trace {
       description "Disable remote tracing";
       junos:must "(\"system tracing\")";
       junos:must-message "'no-remote-trace' is valid only when [system tracing] is configured";
       type empty;
     }
     container file {
       description "Trace file information";
       leaf filename {
         description "Name of file in which to write trace information";
         type string {
           length "1 .. 1024";
           junos:posix-pattern "![/ %]";
           junos:pattern-message "Must not contain '/', % or a space";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     leaf level {
       description "Level of debugging output";
       default "brief";
       type enumeration {
         enum "brief" {
           description "Brief debugging output";
         }
         enum "detail" {
           description "Detailed debugging output";
         }
         enum "extensive" {
           description "Extensive debugging output";
         }
         enum "verbose" {
           description "Verbose debugging output";
         }
       }
     }
     list flag {
       key name;
       ordered-by user;
       description "Tracing parameters";
       leaf name {
         type enumeration {
           enum "configuration" {
             description "Trace CLI configuration events";
           }
           enum "tunnel" {
             description "Trace tunnel install/encap/decap events";
           }
           enum "session" {
             description "Trace session related events";
           }
           enum "all" {
             description "Trace everything";
           }
         }
       }
     }
   }
   grouping range-address-type {
     description "Range address";
     leaf name {
       description "Lower limit of address range";
       type jt:ipv4addr;
     }
     uses apply-advanced;
     container to {
       description "Port range upper limit";
       uses apply-advanced;
       leaf range-high {
         description "Upper limit of address range";
         type jt:ipv4addr;
       }
     }
   }
   grouping rate-limit-object {
     uses apply-advanced;
     leaf alarm-threshold {
       description "Set alarm threshold for rate-limit";
       type union {
         type string {
           pattern "<.*>|$.*";
         }
         type uint32 {
           range "1 .. 80000";
         }
       }
     }
     leaf drop-threshold {
       description "Set drop threshold for rate-limit";
       type union {
         type string {
           pattern "<.*>|$.*";
         }
         type uint32 {
           range "1 .. 80000";
         }
       }
     }
     container message {
       description "GTP limited message type";
       uses message-object;
     }
   }
   grouping reconfigure-trigger-type {
     description "DHCP reconfigure trigger";
     uses apply-advanced;
     leaf radius-disconnect {
       description "Trigger DHCP reconfigure by radius initiated disconnect";
       type empty;
     }
   }
   grouping reconfigure-type {
     description "DHCP reconfigure processing";
     uses apply-advanced;
     leaf clear-on-abort {
       description "Delete client on reconfiguration abort";
       type empty;
     }
     leaf attempts {
       description "Number of reconfigure attempts before aborting";
       type union {
         type string {
           pattern "<.*>|$.*";
         }
         type uint32 {
           range "1 .. 10";
         }
       }
     }
     leaf timeout {
       description "Initial timeout value for retry";
       type union {
         type string {
           pattern "<.*>|$.*";
         }
         type uint32 {
           range "1 .. 10";
         }
       }
     }
     leaf token {
       description "Reconfigure token";
       type string {
         length "1 .. 244";
       }
     }
     container trigger {
       description "DHCP reconfigure trigger";
       uses reconfigure-trigger-type;
     }
     leaf support-option-pd-exclude {
       description "Request prefix exclude option in reconfigure message";
       type empty;
     }
   }
   grouping relay-bulk-leasequery-v4-type {
     junos:must "(\".. overrides always-write-option-82\")";
     junos:must-message "Must configure [overrides always-write-option-82] to overwrite circuit-id for bulk-leasequery";
     junos:must "((\".. relay-option-82 circuit-id\" && !((\".. relay-option-82 circuit-id use-interface-description\" || \".. relay-option-82 circuit-id require-interface-description\"))))";
     junos:must-message "Must configure [relay-option-82 circuit-id] without description to insert circuit-id for bulk-leasequery";
     description "Configure bulk leasequery";
     uses apply-advanced;
     leaf attempts {
       description "Number of retry attempts";
       default "360";
       type union {
         type string {
           pattern "<.*>|$.*";
         }
         type uint32 {
           range "1 .. 720";
         }
       }
     }
     leaf timeout {
       description "Number of seconds";
       default "10";
       units "seconds";
       type union {
         type string {
           pattern "<.*>|$.*";
         }
         type uint32 {
           range "1 .. 10";
         }
       }
     }
   }
   grouping relay-bulk-leasequery-v6-type {
     junos:must "(\".. relay-agent-interface-id\")";
     junos:must-message "Must configure [relay-agent-interface-id] to insert interface-id for bulk-leasequery";
     description "Configure bulk leasequery";
     uses apply-advanced;
     leaf attempts {
       description "Number of retry attempts";
       default "6";
       type union {
         type string {
           pattern "<.*>|$.*";
         }
         type uint32 {
           range "1 .. 10";
         }
       }
     }
     leaf timeout {
       description "Number of seconds";
       default "10";
       units "seconds";
       type union {
         type string {
           pattern "<.*>|$.*";
         }
         type uint32 {
           range "1 .. 10";
         }
       }
     }
     container trigger {
       description "Trigger for bulk leasequery";
       leaf automatic {
         description "Trigger automatically";
         type empty;
       }
     }
   }
   grouping relay-leasequery-type {
     description "Configure leasequery";
     uses apply-advanced;
     leaf attempts {
       description "Number of retry attempts";
       default "6";
       type union {
         type string {
           pattern "<.*>|$.*";
         }
         type uint32 {
           range "1 .. 10";
         }
       }
     }
     leaf timeout {
       description "Number of seconds";
       default "10";
       units "seconds";
       type union {
         type string {
           pattern "<.*>|$.*";
         }
         type uint32 {
           range "1 .. 10";
         }
       }
     }
   }
   grouping relay-option-60-type-group {
     description "DHCP option-60 processing";
     uses apply-advanced;
     container vendor-option {
       description "Add vendor option";
       uses apply-advanced;
       container equals {
         description "Option 60 equals";
         uses relay-option-60-match-group;
       }
       container not-equals {
         description "Option 60 does not equal";
         status deprecated;
         uses relay-option-60-match-group;
       }
       container starts-with {
         description "Option 60 starts with";
         uses relay-option-60-match-group;
       }
       choice server-group-choice {
         case case_1 {
           leaf default-relay-server-group {
             description "Name of DHCP relay server group when match is not made";
             junos:must "(\".. .. .. .. server-group $$\")";
             junos:must-message "Referenced group must be defined under [edit dhcp-relay server-group]";
             type string {
               length "1 .. 64";
             }
           }
         }
         case case_2 {
           leaf default-local-server-group {
             description "Name of DHCP local server group when match is not made";
             junos:must "(\".. .. .. .. .. .. system services dhcp-local-server group $$\")";
             junos:must-message "Referenced group must be defined under [edit system services dhcp-local-server group]";
             type string {
               length "1 .. 64";
             }
           }
         }
         case case_3 {
           leaf drop {
             description "Discard when a match is not made";
             type empty;
           }
         }
         case case_4 {
           leaf forward-only {
             description "Forward without subscriber services when a match is not made";
             type empty;
           }
         }
       }
     }
   }
   grouping relay-option-60-match-group {
     uses apply-advanced;
     list ascii {
       key name;
       description "ASCII string";
       leaf name {
         description "ASCII string";
         type string {
           length "1 .. 256";
         }
       }
       uses apply-advanced;
       choice server-group-choice {
         case case_1 {
           leaf relay-server-group {
             description "Name of DHCP relay server group when match is made";
             junos:must "(\".. .. .. .. .. .. server-group $$\")";
             junos:must-message "Referenced group must be defined under [edit forwarding options dhcp-relay server-group]";
             type string {
               length "1 .. 64";
             }
           }
         }
         case case_2 {
           leaf local-server-group {
             description "Name of DHCP local server group when match is made";
             junos:must "(\".. .. .. .. .. .. .. .. system services dhcp-local-server group $$\")";
             junos:must-message "Referenced group must be defined under [edit system services dhcp-local-server group]";
             type string {
               length "1 .. 64";
             }
           }
         }
         case case_3 {
           leaf drop {
             description "Discard when a match is made";
             type empty;
           }
         }
         case case_4 {
           leaf forward-only {
             description "Forward without subscriber services when a match is made";
             type empty;
           }
         }
       }
     }
     list hexadecimal {
       key name;
       description "Hexadecimal string";
       leaf name {
         description "Hexadecimal string";
         type string {
           length "1 .. 512";
           junos:posix-pattern "^[[:xdigit:]]+$";
           junos:pattern-message "Must be hexadecimal digits (0-9, a-f, A-F)";
         }
       }
       uses apply-advanced;
       choice server-group-choice {
         case case_1 {
           leaf relay-server-group {
             description "Name of DHCP relay server group when match is made";
             junos:must "(\".. .. .. .. .. .. server-group $$\")";
             junos:must-message "Referenced group must be defined under [edit forwarding-options dhcp-relay server-group]";
             type string {
               length "1 .. 64";
             }
           }
         }
         case case_2 {
           leaf local-server-group {
             description "Name of DHCP local server group when match is made";
             junos:must "(\".. .. .. .. .. .. .. .. system services dhcp-local-server group $$\")";
             junos:must-message "Referenced group must be defined under [edit system services dhcp-local-server group]";
             type string {
               length "1 .. 64";
             }
           }
         }
         case case_3 {
           leaf drop {
             description "Discard when a match is made";
             type empty;
           }
         }
         case case_4 {
           leaf forward-only {
             description "Forward without subscriber services when a match is made";
             type empty;
           }
         }
       }
     }
   }
   grouping relay-option-60-type-top {
     description "DHCP option-60 processing";
     uses apply-advanced;
     container vendor-option {
       description "Add vendor option";
       uses apply-advanced;
       container equals {
         description "Option 60 equals";
         uses relay-option-60-match-top;
       }
       container not-equals {
         description "Option 60 does not equal";
         status deprecated;
         uses relay-option-60-match-top;
       }
       container starts-with {
         description "Option 60 starts with";
         uses relay-option-60-match-top;
       }
       choice server-group-choice {
         case case_1 {
           leaf default-relay-server-group {
             description "Name of DHCP relay server group when match is not made";
             junos:must "(\".. .. .. server-group $$\")";
             junos:must-message "Referenced group must be defined under [edit dhcp-relay server-group]";
             type string {
               length "1 .. 64";
             }
           }
         }
         case case_2 {
           leaf default-local-server-group {
             description "Name of DHCP local server group when match is not made";
             junos:must "(\".. .. .. .. .. system services dhcp-local-server group $$\")";
             junos:must-message "Referenced group must be defined under [edit system services dhcp-local-server group]";
             type string {
               length "1 .. 64";
             }
           }
         }
         case case_3 {
           leaf drop {
             description "Discard when a match is not made";
             type empty;
           }
         }
         case case_4 {
           leaf forward-only {
             description "Forward without subscriber services when a match is not made";
             type empty;
           }
         }
       }
     }
   }
   grouping relay-option-60-match-top {
     uses apply-advanced;
     list ascii {
       key name;
       description "ASCII string";
       leaf name {
         description "ASCII string";
         type string {
           length "1 .. 256";
         }
       }
       uses apply-advanced;
       choice server-group-choice {
         case case_1 {
           leaf relay-server-group {
             description "Name of DHCP relay server group when match is made";
             junos:must "(\".. .. .. .. .. server-group $$\")";
             junos:must-message "Referenced group must be defined under [edit forwarding options dhcp-relay server-group]";
             type string {
               length "1 .. 64";
             }
           }
         }
         case case_2 {
           leaf local-server-group {
             description "Name of DHCP local server group when match is made";
             junos:must "(\".. .. .. .. .. .. .. system services dhcp-local-server group $$\")";
             junos:must-message "Referenced group must be defined under [edit system services dhcp-local-server group]";
             type string {
               length "1 .. 64";
             }
           }
         }
         case case_3 {
           leaf drop {
             description "Discard when a match is made";
             type empty;
           }
         }
         case case_4 {
           leaf forward-only {
             description "Forward without subscriber services when a match is made";
             type empty;
           }
         }
       }
     }
     list hexadecimal {
       key name;
       description "Hexadecimal string";
       leaf name {
         description "Hexadecimal string";
         type string {
           length "1 .. 512";
           junos:posix-pattern "^[[:xdigit:]]+$";
           junos:pattern-message "Must be hexadecimal digits (0-9, a-f, A-F)";
         }
       }
       uses apply-advanced;
       choice server-group-choice {
         case case_1 {
           leaf relay-server-group {
             description "Name of DHCP relay server group when match is made";
             junos:must "(\".. .. .. .. .. server-group $$\")";
             junos:must-message "Referenced group must be defined under [edit forwarding-options dhcp-relay server-group]";
             type string {
               length "1 .. 64";
             }
           }
         }
         case case_2 {
           leaf local-server-group {
             description "Name of DHCP local server group when match is made";
             junos:must "(\".. .. .. .. .. .. .. system services dhcp-local-server group $$\")";
             junos:must-message "Referenced group must be defined under [edit system services dhcp-local-server group]";
             type string {
               length "1 .. 64";
             }
           }
         }
         case case_3 {
           leaf drop {
             description "Discard when a match is made";
             type empty;
           }
         }
         case case_4 {
           leaf forward-only {
             description "Forward without subscriber services when a match is made";
             type empty;
           }
         }
       }
     }
   }
   grouping relay-option-82-type {
     description "DHCP option-82 processing";
     uses apply-advanced;
     container circuit-id {
       presence "enable circuit-id";
       description "Add circuit identifier";
       uses apply-advanced;
       container prefix {
         description "Add prefix to circuit/interface-id or remote-id";
         uses apply-advanced;
         leaf host-name {
           description "Add router host name to circuit / interface-id or remote-id";
           type empty;
         }
         leaf logical-system-name {
           description "Add logical system name to circuit / interface-id or remote-id";
           type empty;
         }
         leaf routing-instance-name {
           description "Add routing instance name to circuit / interface-id or remote-id";
           type empty;
         }
       }
       leaf use-interface-description {
         description "Use interface description instead of circuit identifier";
         junos:must "(!(\".. require-interface-description\"))";
         junos:must-message "use-interface-description may not be set with require-interface-desciption";
         type enumeration {
           enum "logical" {
             description "Use the logical interface description";
           }
           enum "device" {
             description "Use the device interface description";
           }
         }
       }
       leaf use-vlan-id {
         description "Use VLAN id instead of name";
         junos:must "((!(\".. no-vlan-interface-name\") && (!(\".. use-interface-description\") && !(\".. require-interface-description\"))))";
         junos:must-message "Vlan-tag cannot be added as no-vlan-interface-name or interface-description is configured";
         type empty;
       }
       container vlan-id-only {
         presence "enable vlan-id-only";
         junos:must "(!((\".. include-irb-and-l2\" || (\".. keep-incoming-circuit-id\" || (\".. user-defined\" || (\".. no-vlan-interface-name\" || (\".. use-interface-description\" || (\".. use-vlan-id\" || (\".. prefix\" || \".. require-interface-description\")))))))))";
         junos:must-message "Vlan-id-only cannot be clubbed along with any other option-82 knob";
         description "Use only VLAN id";
         uses apply-advanced;
       }
       leaf no-vlan-interface-name {
         description "Not include vlan or interface name";
         type empty;
       }
       leaf include-irb-and-l2 {
         description "Include IRB and L2 interface name";
         type empty;
       }
       leaf user-defined {
         description "Include user defined string";
         junos:must "(!((\".. include-irb-and-l2\" || (\".. keep-incoming-circuit-id\" || (\".. no-vlan-interface-name\" || (\".. use-interface-description\" || (\".. use-vlan-id\" || (\".. prefix\" || \".. require-interface-description\"))))))))";
         junos:must-message "The user defined description for option 82 must be defined in order to see the usage and doesnt coexist with prefix";
         type empty;
       }
       leaf keep-incoming-circuit-id {
         description "Keep incoming circuit identifier";
         type empty;
       }
     }
     container remote-id {
       presence "enable remote-id";
       description "Add remote identifier";
       uses apply-advanced;
       container prefix {
         description "Add prefix to circuit/interface-id or remote-id";
         uses apply-advanced;
         leaf host-name {
           description "Add router host name to circuit / interface-id or remote-id";
           type empty;
         }
         leaf logical-system-name {
           description "Add logical system name to circuit / interface-id or remote-id";
           type empty;
         }
         leaf routing-instance-name {
           description "Add routing instance name to circuit / interface-id or remote-id";
           type empty;
         }
       }
       leaf use-interface-description {
         description "Use interface description instead of circuit identifier";
         junos:must "(!(\".. require-interface-description\"))";
         junos:must-message "use-interface-description may not be set with require-interface-desciption";
         type enumeration {
           enum "logical" {
             description "Use the logical interface description";
           }
           enum "device" {
             description "Use the device interface description";
           }
         }
       }
       leaf use-vlan-id {
         description "Use VLAN id instead of name";
         junos:must "((!(\".. no-vlan-interface-name\") && (!(\".. use-interface-description\") && !(\".. require-interface-description\"))))";
         junos:must-message "Vlan-tag cannot be added as no-vlan-interface-name or interface-description is configured";
         type empty;
       }
       leaf no-vlan-interface-name {
         description "Not include vlan or interface name";
         type empty;
       }
       leaf include-irb-and-l2 {
         description "Include IRB and L2 interface name";
         type empty;
       }
       container hostname-only {
         presence "enable hostname-only";
         junos:must "(!((\".. include-irb-and-l2\" || (\".. keep-incoming-remote-id\" || (\".. no-vlan-interface-name\" || (\".. use-interface-description\" || (\".. use-vlan-id\" || (\".. prefix\" || \".. use-string\"))))))))";
         junos:must-message "Hostname-only cannot be clubbed with any other sub-option";
         description "Include hostname only";
         uses apply-advanced;
       }
       leaf keep-incoming-remote-id {
         description "Keep incoming remote identifier";
         type empty;
       }
       leaf use-string {
         description "Use raw string instead of the default remote id";
         junos:must "(!((\".. use-interface-description\" || (\".. require-interface-description\" || (\".. include-irb-and-l2\" || (\".. keep-incoming-circuit-id\" || (\".. no-vlan-interface-name\" || \".. use-vlan-id\")))))))";
         junos:must-message "use-string can only coexist with prefix";
         type string;
       }
     }
     leaf server-id-override {
       description "Add link-selection and server-id sub-options on packets to server";
       junos:must "(!(\".. link-selection\"))";
       junos:must-message "server-id-override cannot be configured with link-selection";
       type empty;
     }
     leaf link-selection {
       description "Add link-selection suboption on packets to server";
       junos:must "(!(\".. server-id-override\"))";
       junos:must-message "link-selection cannot be configured with server-id-override";
       type empty;
     }
     leaf exclude-relay-agent-identifier {
       description "Exclude relay agent identifier from packets to server";
       type empty;
     }
     container vendor-specific {
       description "Add vendor-specific information";
       uses jdhcp-vendor-specific-type;
     }
   }
   grouping relay-v4-option-ascii-hex {
     uses apply-advanced;
     list ascii {
       key name;
       description "ASCII string";
       leaf name {
         description "ASCII string";
         type string {
           length "1 .. 256";
         }
       }
       uses apply-advanced;
       choice server-group-choice {
         case case_1 {
           leaf relay-server-group {
             description "Name of DHCP relay server group when match is made";
             junos:must "((\".. .. .. .. .. .. server-group $$\" || (\".. .. .. .. .. server-group $$\" || (\".. .. .. .. server-group $$\" || \".. .. .. server-group $$\"))))";
             junos:must-message "Referenced group must be defined under [edit forwarding dhcp-relay server-group]";
             type string {
               length "1 .. 64";
             }
           }
         }
         case case_2 {
           leaf local-server-group {
             description "Name of DHCP local server group when match is made";
             junos:must "((\".. .. .. .. .. .. .. .. system services dhcp-local-server group $$\" || (\".. .. .. .. .. .. .. system services dhcp-local-server group $$\" || (\".. .. .. .. .. .. system services dhcp-local-server group $$\" || \".. .. .. .. .. system services dhcp-local-server group $$\"))))";
             junos:must-message "Referenced group must be defined under [edit system services dhcp-local-server group]";
             type string {
               length "1 .. 64";
             }
           }
         }
         case case_3 {
           leaf drop {
             description "Discard when a match is made";
             type empty;
           }
         }
         case case_4 {
           leaf forward-only {
             description "Forward without subscriber services when a match is made";
             type empty;
           }
         }
       }
     }
     list hexadecimal {
       key name;
       description "Hexadecimal string";
       leaf name {
         description "Hexadecimal string";
         type string {
           length "1 .. 512";
           junos:posix-pattern "^[[:xdigit:]]+$";
           junos:pattern-message "Must be hexadecimal digits (0-9, a-f, A-F)";
         }
       }
       uses apply-advanced;
       choice server-group-choice {
         case case_1 {
           leaf relay-server-group {
             description "Name of DHCP relay server group when match is made";
             junos:must "((\".. .. .. .. .. .. server-group $$\" || (\".. .. .. .. .. server-group $$\" || (\".. .. .. .. server-group $$\" || \".. .. .. server-group $$\"))))";
             junos:must-message "Referenced group must be defined under [edit forwarding dhcp-relay server-group]";
             type string {
               length "1 .. 64";
             }
           }
         }
         case case_2 {
           leaf local-server-group {
             description "Name of DHCP local server group when match is made";
             junos:must "((\".. .. .. .. .. .. .. .. system services dhcp-local-server group $$\" || (\".. .. .. .. .. .. .. system services dhcp-local-server group $$\" || (\".. .. .. .. .. .. system services dhcp-local-server group $$\" || \".. .. .. .. .. system services dhcp-local-server group $$\"))))";
             junos:must-message "Referenced group must be defined under [edit system services dhcp-local-server group]";
             type string {
               length "1 .. 64";
             }
           }
         }
         case case_3 {
           leaf drop {
             description "Discard when a match is made";
             type empty;
           }
         }
         case case_4 {
           leaf forward-only {
             description "Forward without subscriber services when a match is made";
             type empty;
           }
         }
       }
     }
   }
   grouping relay-v6-option-ascii-hex {
     uses apply-advanced;
     list ascii {
       key name;
       description "ASCII string";
       leaf name {
         description "ASCII string";
         type string {
           length "1 .. 256";
         }
       }
       uses apply-advanced;
       choice server-group-choice {
         case case_1 {
           leaf relay-server-group {
             description "Name of DHCP relay server group when match is made";
             junos:must "((\".. .. .. .. .. .. server-group $$\" || (\".. .. .. .. .. server-group $$\" || (\".. .. .. .. server-group $$\" || \".. .. .. server-group $$\"))))";
             junos:must-message "Referenced group must be defined under [edit forwarding options dhcp-relay dhcpv6 server-group]";
             type string {
               length "1 .. 64";
             }
           }
         }
         case case_2 {
           leaf drop {
             description "Discard when a match is made";
             type empty;
           }
         }
         case case_3 {
           leaf forward-only {
             description "Forward without subscriber services when a match is made";
             type empty;
           }
         }
       }
     }
     list hexadecimal {
       key name;
       description "Hexadecimal string";
       leaf name {
         description "Hexadecimal string";
         type string {
           length "1 .. 512";
           junos:posix-pattern "^[[:xdigit:]]+$";
           junos:pattern-message "Must be hexadecimal digits (0-9, a-f, A-F)";
         }
       }
       uses apply-advanced;
       choice server-group-choice {
         case case_1 {
           leaf relay-server-group {
             description "Name of DHCP relay server group when match is made";
             junos:must "((\".. .. .. .. .. .. server-group $$\" || (\".. .. .. .. .. server-group $$\" || (\".. .. .. .. server-group $$\" || \".. .. .. server-group $$\"))))";
             junos:must-message "Referenced group must be defined under [edit forwarding options dhcp-relay dhcpv6 server-group]";
             type string {
               length "1 .. 64";
             }
           }
         }
         case case_2 {
           leaf drop {
             description "Discard when a match is made";
             type empty;
           }
         }
         case case_3 {
           leaf forward-only {
             description "Forward without subscriber services when a match is made";
             type empty;
           }
         }
       }
     }
   }
   grouping remote-access-client-config {
     leaf name {
       description "Name of config object name";
       type string {
         length "1 .. 32";
       }
     }
     uses apply-advanced;
     leaf connection-mode {
       description "Set connection-mode of client";
       default "manual";
       type enumeration {
         enum "manual" {
           description "Set to manual mode, default mode";
         }
         enum "always" {
           description "Set to always mode";
         }
       }
     }
     leaf biometric-authentication {
       description "Enable biometric authentication";
       type empty;
     }
     container windows-logon {
       presence "enable windows-logon";
       uses apply-advanced;
       leaf mode {
         description "Set windows logon mode";
         default "manual";
         type enumeration {
           enum "manual" {
             description "Manual Windows logon";
           }
           enum "automatic" {
             description "Automatic Windows logon with configured credentials";
           }
         }
       }
       leaf domain {
         description "Domain name for automatic windows logon";
         type string {
           length "1 .. 255";
         }
       }
       leaf disconnect-at-logoff {
         description "Disconnect after logoff";
         type empty;
       }
       leaf flush-credential-at-logoff {
         description "Flush cached credentials upon after logoff";
         type empty;
       }
       leaf lead-time-duration {
         description "Lead time duration for domain logon (seconds)";
         default "45";
         units "seconds";
         type union {
           type string {
             pattern "<.*>|$.*";
           }
           type uint32 {
             range "0 .. 120";
           }
         }
       }
       leaf eap-auth {
         description "EAP Authentication before profile selection";
         type empty;
       }
       leaf auto-dialog-open {
         description "Automatically open dialog for connection establishment";
         type empty;
       }
     }
     leaf no-dead-peer-detection {
       description "Disable dead-peer-detection on client";
       type empty;
     }
     container dead-peer-detection {
       description "Dead Peer Detection configuration";
       uses apply-advanced;
       leaf interval {
         description "The time between DPD probe messages (seconds) Default :60";
         default "60";
         units "seconds";
         type union {
           type string {
             pattern "<.*>|$.*";
           }
           type uint32 {
             range "1 .. 300";
           }
         }
       }
       leaf threshold {
         description "Maximum number of DPD retransmissions Default :5";
         default "5";
         type union {
           type string {
             pattern "<.*>|$.*";
           }
           type uint32 {
             range "1 .. 5";
           }
         }
       }
     }
     leaf no-tcp-encap {
       description "Disable tcp encapsulation";
       type empty;
     }
     leaf no-eap-tls {
       description "Disable EAP-TLS IKEV2 method";
       type empty;
     }
     container certificate {
       description "Certificate identifier";
       uses apply-advanced;
       leaf no-expiry-warning {
         description "Disable certificate expiry warning";
         junos:must "(!(\".. warn-before-expiry\"))";
         junos:must-message "Certificate must not have both no-expiry-warning or warn-before-expiry configured";
         type empty;
       }
       leaf no-pin-request-per-connection {
         description "Disable certificate pin request per connection";
         type empty;
       }
       leaf warn-before-expiry {
         description "Certificate expiration warning days (1 - 90)";
         default "60";
         units "days";
         junos:must "(!(\".. no-expiry-warning\"))";
         junos:must-message "Certificate must not have both no-expiry-warning or warn-before-expiry configured";
         type union {
           type string {
             pattern "<.*>|$.*";
           }
           type uint32 {
             range "1 .. 90";
           }
         }
       }
     }
     container credentials {
       description "Credentials saving option";
       uses apply-advanced;
       choice save-option {
         case case_1 {
           leaf password {
             description "Remember both username & password";
             type empty;
           }
         }
         case case_2 {
           leaf username {
             description "Remember username only";
             type empty;
           }
         }
       }
     }
   }
   grouping remote-access-profile-config {
     leaf name {
       description "Profile identifier";
       type string {
         length "1 .. 32";
       }
     }
     uses apply-advanced;
     leaf description {
       description "Text description of remote-access profile";
       type string {
         length "1 .. 255";
       }
     }
     leaf ipsec-vpn {
       description "Select the ipsec-vpn policy object";
       junos:must "(\"security ipsec vpn $$\")";
       junos:must-message "IPSec VPN object must be defined under [edit security ipsec vpn]";
       type string;
     }
     leaf access-profile {
       description "Select the access-profile";
       junos:must "(\"access profile $$\")";
       junos:must-message "Access profile must be defined under [edit access profile]";
       type string;
     }
     leaf client-config {
       description "Select the client config object";
       junos:must "(\"security remote-access client-config $$\")";
       junos:must-message "Referenced group must be defined under [edit security remote-access client-config]";
       type string;
     }
   }
   grouping remote-access-traceoptions {
     uses apply-advanced;
     leaf no-remote-trace {
       description "Disable remote tracing";
       junos:must "(\"system tracing\")";
       junos:must-message "'no-remote-trace' is valid only when [system tracing] is configured";
       type empty;
     }
     container file {
       description "Trace file information";
       leaf filename {
         description "Name of file in which to write trace information";
         type string {
           length "1 .. 1024";
           junos:posix-pattern "![/ %]";
           junos:pattern-message "Must not contain '/', % or a space";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     leaf level {
       description "Level of debugging output";
       default "brief";
       type enumeration {
         enum "brief" {
           description "Brief debugging output";
         }
         enum "detail" {
           description "Detailed debugging output";
         }
         enum "extensive" {
           description "Extensive debugging output";
         }
         enum "verbose" {
           description "Verbose debugging output";
         }
       }
     }
     list flag {
       key name;
       ordered-by user;
       description "Tracing parameters";
       leaf name {
         type enumeration {
           enum "cli-configuration" {
             description "Trace CLI configuration events";
           }
           enum "all" {
             description "Trace everything";
           }
         }
       }
     }
   }
   grouping rib-inet3 {
     uses apply-advanced;
     container inet.3 {
       presence "enable inet.3";
       description "Use inet.3 to exchange labeled unicast routes";
       uses apply-advanced;
     }
   }
   grouping rib_aggregate_type {
     uses apply-advanced;
     container defaults {
       description "Global route options";
       uses apply-advanced;
       container metric {
         description "Metric value";
         presence "enable metric";
         uses rib_static_metric_type;
       }
       container metric2 {
         description "Metric value 2";
         presence "enable metric2";
         uses rib_static_metric_type;
       }
       container metric3 {
         description "Metric value 3";
         presence "enable metric3";
         uses rib_static_metric_type;
       }
       container metric4 {
         description "Metric value 4";
         presence "enable metric4";
         uses rib_static_metric_type;
       }
       container tag {
         description "Tag string";
         presence "enable tag";
         uses rib_static_metric_type;
       }
       container tag2 {
         description "Tag string 2";
         presence "enable tag2";
         uses rib_static_metric_type;
       }
       container preference {
         description "Preference value";
         presence "enable preference";
         uses rib_static_metric_type;
       }
       container preference2 {
         description "Preference value 2";
         presence "enable preference2";
         uses rib_static_metric_type;
       }
       container color {
         description "Color (preference) value";
         presence "enable color";
         uses rib_static_metric_type;
       }
       container color2 {
         description "Color (preference) value 2";
         presence "enable color2";
         uses rib_static_metric_type;
       }
       leaf-list community {
         ordered-by user;
         description "BGP community identifier";
         type jt:community;
       }
       container as-path {
         description "Autonomous system path";
         uses apply-advanced;
         leaf path {
           description "Autonomous system path";
           type string;
         }
         leaf origin {
           type enumeration {
             enum "igp" {
               description "Path originated in the local IGP";
             }
             enum "egp" {
               description "Path originated in another AS";
             }
             enum "incomplete" {
               description "Path was learned by some other means";
             }
           }
         }
         leaf atomic-aggregate {
           description "Add ATOMIC_AGGREGATE path attribute to route";
           type empty;
         }
         container aggregator {
           presence "enable aggregator";
           description "Add AGGREGATOR path attribute to route";
         }
         leaf as-number {
           description " Autonomous system number in plain number or 'higher 16bits'.'Lower 16 bits' (asdot notation) format";
           type string {
             junos:posix-pattern "^[0-9]+(.[0-9]+)?$";
             junos:pattern-message "Use format 'x' or 'x.y' to specify number 'x' (Range 1 .. 4294967295) or number with higher 2 bytes 'x' (Range 0 .. 65535) and lower 2 bytes 'y' (Range 0 .. 65535) respectively";
           }
         }
         leaf address {
           description "Address of BGP system that formed the route";
           type jt:ipv4addr;
         }
       }
       leaf discard {
         description "Drop packets to destination; send no ICMP unreachables";
         type empty;
       }
       leaf next-table {
         description "Next hop to another table";
         type string;
       }
       choice brief_flag {
         case case_1 {
           leaf brief {
             description "Include longest common sequences from contributing paths";
             type empty;
           }
         }
         case case_2 {
           leaf full {
             description "Include all AS numbers from all contributing paths";
             type empty;
           }
         }
       }
       choice passive_flag {
         case case_1 {
           leaf active {
             description "Remove inactive route from forwarding table";
             type empty;
           }
         }
         case case_2 {
           leaf passive {
             description "Retain inactive route in forwarding table";
             type empty;
           }
         }
       }
     }
     list route {
       key name;
       ordered-by user;
       description "Individual route options";
       leaf name {
         description "Destination prefix";
         type jt:ipprefix;
       }
       uses apply-advanced;
       leaf-list policy {
         ordered-by user;
         description "Policy filter";
         type jt:policy-algebra;
       }
       container metric {
         description "Metric value";
         presence "enable metric";
         uses rib_static_metric_type;
       }
       container metric2 {
         description "Metric value 2";
         presence "enable metric2";
         uses rib_static_metric_type;
       }
       container metric3 {
         description "Metric value 3";
         presence "enable metric3";
         uses rib_static_metric_type;
       }
       container metric4 {
         description "Metric value 4";
         presence "enable metric4";
         uses rib_static_metric_type;
       }
       container tag {
         description "Tag string";
         presence "enable tag";
         uses rib_static_metric_type;
       }
       container tag2 {
         description "Tag string 2";
         presence "enable tag2";
         uses rib_static_metric_type;
       }
       container preference {
         description "Preference value";
         presence "enable preference";
         uses rib_static_metric_type;
       }
       container preference2 {
         description "Preference value 2";
         presence "enable preference2";
         uses rib_static_metric_type;
       }
       container color {
         description "Color (preference) value";
         presence "enable color";
         uses rib_static_metric_type;
       }
       container color2 {
         description "Color (preference) value 2";
         presence "enable color2";
         uses rib_static_metric_type;
       }
       leaf-list community {
         ordered-by user;
         description "BGP community identifier";
         type jt:community;
       }
       container as-path {
         description "Autonomous system path";
         uses apply-advanced;
         leaf path {
           description "Autonomous system path";
           type string;
         }
         leaf origin {
           type enumeration {
             enum "igp" {
               description "Path originated in the local IGP";
             }
             enum "egp" {
               description "Path originated in another AS";
             }
             enum "incomplete" {
               description "Path was learned by some other means";
             }
           }
         }
         leaf atomic-aggregate {
           description "Add ATOMIC_AGGREGATE path attribute to route";
           type empty;
         }
         container aggregator {
           presence "enable aggregator";
           description "Add AGGREGATOR path attribute to route";
         }
         leaf as-number {
           description " Autonomous system number in plain number or 'higher 16bits'.'Lower 16 bits' (asdot notation) format";
           type string {
             junos:posix-pattern "^[0-9]+(.[0-9]+)?$";
             junos:pattern-message "Use format 'x' or 'x.y' to specify number 'x' (Range 1 .. 4294967295) or number with higher 2 bytes 'x' (Range 0 .. 65535) and lower 2 bytes 'y' (Range 0 .. 65535) respectively";
           }
         }
         leaf address {
           description "Address of BGP system that formed the route";
           type jt:ipv4addr;
         }
       }
       leaf discard {
         description "Drop packets to destination; send no ICMP unreachables";
         type empty;
       }
       leaf next-table {
         description "Next hop to another table";
         type string;
       }
       choice brief_flag {
         case case_1 {
           leaf brief {
             description "Include longest common sequences from contributing paths";
             type empty;
           }
         }
         case case_2 {
           leaf full {
             description "Include all AS numbers from all contributing paths";
             type empty;
           }
         }
       }
       choice passive_flag {
         case case_1 {
           leaf active {
             description "Remove inactive route from forwarding table";
             type empty;
           }
         }
         case case_2 {
           leaf passive {
             description "Retain inactive route in forwarding table";
             type empty;
           }
         }
       }
     }
   }
   grouping rib_group_inet_type {
     description "Routing table group";
     leaf ribgroup-name {
       description "Name of the routing table group";
       type string;
     }
   }
   grouping rib_group_type {
     uses apply-advanced;
     leaf inet-old-style {
       description "Name of the IPv4 routing table group";
       status deprecated;
       type string;
     }
     leaf inet {
       description "Name of the IPv4 routing table group";
       type string;
     }
     leaf inet3 {
       description "Name of the IPv4 inet.3 routing table group";
       type string;
     }
     leaf inet6 {
       description "Name of the IPv6 routing table group";
       type string;
     }
     leaf inet63 {
       description "Name of the IPv6 inet6.3 routing table group";
       type string;
     }
   }
   grouping rib_static_metric_type {
     leaf metric-value {
       description "Metric value";
       type union {
         type uint32;
         type string {
           pattern "<.*>|$.*";
         }
       }
     }
     leaf type {
       description "Metric type";
       type union {
         type string {
           pattern "<.*>|$.*";
         }
         type uint32 {
           range "1 .. 16";
         }
       }
     }
   }
   grouping rip_filter_obj {
     description "Filter to apply to tracing";
     leaf match-on {
       description "Argument on which to match";
       type enumeration {
         enum "prefix" {
           description "Filter based on prefix";
         }
       }
     }
     leaf-list policy {
       ordered-by user;
       description "Filter policy";
       type jt:policy-algebra;
     }
   }
   grouping route_record_traceoptions {
     description "Traceoptions for sampling route record";
     uses apply-advanced;
     leaf no-remote-trace {
       description "Disable remote tracing";
       junos:must "(\"system tracing\")";
       junos:must-message "'no-remote-trace' is valid only when [system tracing] is configured";
       type empty;
     }
     container file {
       description "Trace file information";
       leaf filename {
         description "Name of file in which to write trace information";
         type string {
           length "1 .. 1024";
           junos:posix-pattern "![/ %]";
           junos:pattern-message "Must not contain '/', % or a space";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     leaf level {
       description "Level of debugging output";
       default "error";
       type enumeration {
         enum "error" {
           description "Match error conditions";
         }
         enum "warning" {
           description "Match warning messages";
         }
         enum "notice" {
           description "Match conditions that should be handled specially";
         }
         enum "info" {
           description "Match informational messages";
         }
         enum "verbose" {
           description "Match verbose messages";
         }
         enum "all" {
           description "Match all levels";
         }
       }
     }
     list flag {
       key name;
       ordered-by user;
       description "Area of route-record to enable debuging output";
       leaf name {
         type enumeration {
           enum "parse" {
             description "Trace parsing code";
           }
           enum "all" {
             description "Trace all area of jflow-service code";
           }
         }
       }
     }
   }
   grouping rpd_rib_group_type {
     description "Routing table group";
     leaf name {
       description "Routing table group";
       type string;
     }
     uses apply-advanced;
     leaf export-rib {
       description "Export routing table";
       type string;
     }
     leaf-list import-rib {
       ordered-by user;
       description "Import routing table";
       type string;
     }
     leaf-list import-policy {
       ordered-by user;
       description "Import policy";
       type jt:policy-algebra;
     }
   }
   grouping rpm-next-hop {
     leaf name {
       description "Next hop to destination";
       type jt:ipaddr;
     }
     uses apply-advanced;
     list rpm-probe {
       key name;
       ordered-by user;
       leaf name {
         description "RPM probe to track";
         junos:must "(\"services rpm probe $$\")";
         junos:must-message "Referenced RPM probe must be defined under 'services rpm probe'";
         type string;
       }
       leaf rpm-test {
         description "RPM test to track";
         junos:must "(\"services rpm probe ${rpm-probe} test $$\")";
         junos:must-message "Referenced RPM test must be defined under 'services rpm probe <probe> test '";
         type string;
       }
     }
   }
   grouping sampling_family_inet6_output_type {
     description "Configure output options for packet sampling";
     uses apply-advanced;
     leaf aggregate-export-interval {
       description "Interval of exporting aggregate accounting information";
       default "90";
       units "seconds";
       type union {
         type string {
           pattern "<.*>|$.*";
         }
         type uint32 {
           range "90 .. 1800";
         }
       }
     }
     leaf flow-inactive-timeout {
       description "Interval of inactivity that marks a flow inactive";
       default "60";
       units "seconds";
       type union {
         type string {
           pattern "<.*>|$.*";
         }
         type uint32 {
           range "15 .. 1800";
         }
       }
     }
     leaf flow-active-timeout {
       description "Interval after which an active flow is exported";
       default "1800";
       units "seconds";
       type union {
         type string {
           pattern "<.*>|$.*";
         }
         type uint32 {
           range "60 .. 1800";
         }
       }
     }
     list flow-server {
       key name;
       description "Configure sending traffic aggregates in cflowd format";
       max-elements 8;
       junos:must "((!(any \".. interface <*>\") || all \".. interface <*> source-address\"))";
       junos:must-message "'output interface source-address' must be specified with 'flow-server' and 'interface'";
       uses cflowd_sampling_inet6_sampling_type;
     }
     list interface {
       key name;
       description "Interfaces used to send monitored information";
       max-elements 1;
       junos:must "((any \".. flow-server <*>\" || any \".. extension-service <*>\"))";
       junos:must-message "'flow-server' or 'extension-service' must be specified with 'interface'";
       uses packet_export_intf_type;
     }
     container inline-jflow {
       description "Inline processing of sampled packets";
       presence "enable inline-jflow";
       junos:must "(any \".. flow-server <*>\")";
       junos:must-message "'flow-server' must be specified with the inline Jflow";
       uses packet_export_inline;
     }
     list extension-service {
       key name;
       ordered-by user;
       description "Define the customer specific sampling configuration";
       junos:must "(!(\".. flow-active-timeout\"))";
       junos:must-message "'.. flow-active-timeout' is not needed with 'extension-service'";
       junos:must "(!(\".. flow-inactive-timeout\"))";
       junos:must-message "'.. flow-inactive-timeout' is not valid for 'extension-service'";
       junos:must "(!(\".. aggregate-export-interval\"))";
       junos:must-message "'.. aggregate-export-interval' is not valid for 'extension-service'";
       junos:must "(!(any \".. flow-server <*>\"))";
       junos:must-message "'.. flow-server' is not needed with 'extension-service'";
       junos:must "(!(any \".. interface <*> source-address\"))";
       junos:must-message "'.. interface source-address' is not valid for 'extension-service'";
       junos:must "(!(any \".. interface <*> engine-id\"))";
       junos:must-message "'.. interface engine-id' is not valid for 'extension-service'";
       junos:must "(!(any \".. interface <*> engine-type\"))";
       junos:must-message "'.. interface engine-type' is not valid for 'extension-service'";
       junos:must "(any \".. interface <*>\")";
       junos:must-message "'.. interface' must be specified with 'extension-service'";
       leaf name {
         description "Customer prefixed sampling service name";
         type string {
           length "1 .. 63";
         }
       }
       uses apply-advanced;
     }
   }
   grouping cflowd_sampling_inet6_sampling_type {
     leaf name {
       description "Name of host collecting cflowd packets";
       type jt:ipaddr;
     }
     uses apply-advanced;
     leaf port {
       description "UDP port number on host collecting cflowd packets";
       type union {
         type uint16;
         type string {
           pattern "<.*>|$.*";
         }
       }
     }
     leaf dscp {
       description "Numeric DSCP value in the range 0 to 63";
       default "0";
       junos:must "(\".. .. inline-jflow\")";
       junos:must-message "DSCP can be configured for inline-jflow";
       type union {
         type string {
           pattern "<.*>|$.*";
         }
         type uint8 {
           range "0 .. 63";
         }
       }
     }
     leaf forwarding-class {
       description "Forwarding-class for exported jflow packets, applicable only for inline-jflow";
       junos:must "(\".. .. inline-jflow\")";
       junos:must-message "forwarding-class can be configured for inline-jflow";
       type string {
         length "1 .. 64";
       }
     }
     leaf routing-instance {
       description "Name of routing instance on which flow collector is reachable";
       junos:must "(\".. .. inline-jflow\")";
       junos:must-message "Routing Instances can be configured for inline-jflow";
       junos:must "(\"routing-instances $$ instance-type vrf\")";
       junos:must-message "routing instance should be defined and should be of type Virtual routing forwarding instance(VRF)";
       type string;
     }
     leaf autonomous-system-type {
       description "Type of autonomous system number to export";
       default "origin";
       type enumeration {
         enum "origin" {
           description "Export origin-AS numbers";
         }
         enum "peer" {
           description "Export peer-AS numbers";
         }
       }
     }
     container aggregation {
       description "Aggregations to perform for exported flows (version 8 only)";
       junos:must "(!(any \".. .. flow-server <*> version9\"))";
       junos:must-message "Select only one version";
       uses aggregation_type;
     }
     choice local-dump-choice {
       leaf local-dump {
         description "Dump cflowd records to log file before exporting";
         type empty;
       }
       leaf no-local-dump {
         description "Don't dump cflowd records to log file before exporting";
         type empty;
       }
     }
     leaf source-address {
       description "Source IPv4 address for cflowd packets";
       type jt:ipv4addr;
     }
     container version9 {
       presence "enable version9";
       junos:must "((!(any \".. .. .. .. inet output flow-server <*> version\") || !(any \".. .. .. .. inet output interface <*>\")))";
       junos:must-message "Select only one version or configure only RE based samping under family inet";
       junos:must "((any \".. .. interface <*>\" || \".. .. inline-jflow\"))";
       junos:must-message "Service PIC or inline-jflow (j-series and SRX only) must be specified for version9";
       description "Export data in version 9 format";
       uses apply-advanced;
       container template {
         description "Template configuration";
         uses apply-advanced;
         leaf template-name {
           description "Template name";
           junos:must "(\"services flow-monitoring version9 template $$ ipv6-template\")";
           junos:must-message "Template type must match input protocol";
           type string;
         }
       }
     }
   }
   grouping packet_export_inline {
     uses apply-advanced;
     leaf source-address {
       description "Address to use for generating monitored packets";
       type jt:ipaddr;
     }
     leaf flow-export-rate {
       description "Flow export rate of monitored packets in kpps";
       type union {
         type string {
           pattern "<.*>|$.*";
         }
         type uint32 {
           range "1 .. 3200";
         }
       }
     }
   }
   grouping sampling_family_input_type {
     description "Configure input options for packet sampling";
     uses apply-advanced;
     leaf rate {
       description "Ratio of packets to be sampled (1 out of N)";
       type union {
         type string {
           pattern "<.*>|$.*";
         }
         type uint32;
       }
     }
     leaf run-length {
       description "Number of samples after initial trigger";
       default "0";
       type union {
         type string {
           pattern "<.*>|$.*";
         }
         type uint32 {
           range "0 .. 20";
         }
       }
     }
     leaf max-packets-per-second {
       description "Threshold of samples per second before dropping";
       default "1000";
       type union {
         type uint16;
         type string {
           pattern "<.*>|$.*";
         }
       }
     }
     leaf maximum-packet-length {
       description "Maximum length of the sampled packet";
       default "0";
       units "bytes";
       type union {
         type string {
           pattern "<.*>|$.*";
         }
         type uint32 {
           range "0 .. 9192";
         }
       }
     }
   }
   grouping sampling_global_mpls_output_type {
     description "Configure output options for packet sampling";
     uses apply-advanced;
     leaf aggregate-export-interval {
       description "Interval of exporting aggregate accounting information";
       default "90";
       units "seconds";
       type union {
         type string {
           pattern "<.*>|$.*";
         }
         type uint32 {
           range "90 .. 1800";
         }
       }
     }
     leaf flow-inactive-timeout {
       description "Interval of inactivity that marks a flow inactive";
       default "60";
       units "seconds";
       type union {
         type string {
           pattern "<.*>|$.*";
         }
         type uint32 {
           range "15 .. 1800";
         }
       }
     }
     leaf flow-active-timeout {
       description "Interval after which an active flow is exported";
       default "1800";
       units "seconds";
       type union {
         type string {
           pattern "<.*>|$.*";
         }
         type uint32 {
           range "60 .. 1800";
         }
       }
     }
     list flow-server {
       key name;
       description "Configure sending traffic aggregates in cflowd format";
       max-elements 8;
       junos:must "((!(any \".. interface <*>\") || all \".. interface <*> source-address\"))";
       junos:must-message "'output interface source-address' must be specified with 'flow-server' and 'interface'";
       uses cflowd_global_mpls_sampling_type;
     }
     list interface {
       key name;
       description "Interfaces used to send monitored information";
       max-elements 1;
       junos:must "(any \".. flow-server <*>\")";
       junos:must-message "'flow-server' must be specified with 'interface'";
       uses packet_export_intf_type;
     }
   }
   grouping cflowd_global_mpls_sampling_type {
     leaf name {
       description "Name of host collecting cflowd packets";
       type jt:ipaddr;
     }
     uses apply-advanced;
     leaf port {
       description "UDP port number on host collecting cflowd packets";
       type union {
         type uint16;
         type string {
           pattern "<.*>|$.*";
         }
       }
     }
     leaf dscp {
       description "Numeric DSCP value in the range 0 to 63";
       default "0";
       junos:must "(\".. .. inline-jflow\")";
       junos:must-message "DSCP can be configured for inline-jflow";
       type union {
         type string {
           pattern "<.*>|$.*";
         }
         type uint8 {
           range "0 .. 63";
         }
       }
     }
     leaf forwarding-class {
       description "Forwarding-class for exported jflow packets, applicable only for inline-jflow";
       junos:must "(\".. .. inline-jflow\")";
       junos:must-message "forwarding-class can be configured for inline-jflow";
       type string {
         length "1 .. 64";
       }
     }
     leaf routing-instance {
       description "Name of routing instance on which flow collector is reachable";
       junos:must "(\".. .. inline-jflow\")";
       junos:must-message "Routing Instances can be configured for inline-jflow";
       junos:must "(\"routing-instances $$ instance-type vrf\")";
       junos:must-message "routing instance should be defined and should be of type Virtual routing forwarding instance(VRF)";
       type string;
     }
     leaf autonomous-system-type {
       description "Type of autonomous system number to export";
       default "origin";
       type enumeration {
         enum "origin" {
           description "Export origin-AS numbers";
         }
         enum "peer" {
           description "Export peer-AS numbers";
         }
       }
     }
     container aggregation {
       description "Aggregations to perform for exported flows (version 8 only)";
       junos:must "(!(any \".. .. flow-server <*> version9\"))";
       junos:must-message "Select only one version";
       uses aggregation_type;
     }
     choice local-dump-choice {
       leaf local-dump {
         description "Dump cflowd records to log file before exporting";
         type empty;
       }
       leaf no-local-dump {
         description "Don't dump cflowd records to log file before exporting";
         type empty;
       }
     }
     leaf source-address {
       description "Source IPv4 address for cflowd packets";
       type jt:ipv4addr;
     }
     container version9 {
       presence "enable version9";
       junos:must "((!(any \".. .. .. .. inet output flow-server <*> version\") || !(any \".. .. .. .. inet output interface <*>\")))";
       junos:must-message "Select only one version or configure only RE based samping under family inet";
       junos:must "((any \".. .. interface <*>\" || \".. .. inline-jflow\"))";
       junos:must-message "Service PIC or inline-jflow (j-series and SRX only) must be specified for version9";
       description "Export data in version 9 format";
       uses apply-advanced;
       container template {
         description "Template configuration";
         uses apply-advanced;
         leaf template-name {
           description "Template name";
           junos:must "((\"services flow-monitoring version9 template $$ mpls-template\" || (\"services flow-monitoring version9 template $$ mpls-ipv4-template\" || \"services flow-monitoring version9 template $$ mpls-ipvx-template\")))";
           junos:must-message "Template type must match input protocol";
           junos:must "((!(\".. .. .. .. inline-jflow source-address\") || (\".. .. .. .. inline-jflow source-address\" && all \".. .. .. .. flow-server <*> version9 template $$\")))";
           junos:must-message "All the collector under same family should share the same template in Inline-Jflow";
           type string;
         }
       }
     }
   }
   grouping sampling_input_type {
     description "Configure input options for packet sampling";
     uses apply-advanced;
     leaf rate {
       description "Ratio of packets to be sampled (1 out of N)";
       type union {
         type string {
           pattern "<.*>|$.*";
         }
         type uint32;
       }
     }
     leaf run-length {
       description "Number of samples after initial trigger";
       default "0";
       type union {
         type string {
           pattern "<.*>|$.*";
         }
         type uint32 {
           range "0 .. 20";
         }
       }
     }
     leaf max-packets-per-second {
       description "Threshold of samples per second before dropping";
       default "1000";
       type union {
         type uint16;
         type string {
           pattern "<.*>|$.*";
         }
       }
     }
     leaf maximum-packet-length {
       description "Maximum length of the sampled packet";
       default "0";
       units "bytes";
       type union {
         type string {
           pattern "<.*>|$.*";
         }
         type uint32 {
           range "0 .. 9192";
         }
       }
     }
     container family {
       presence "enable family";
       description "Protocol family";
       status deprecated;
       container inet {
         description "Sampling parameters for IPv4";
         uses apply-advanced;
         leaf rate {
           description "Ratio of packets to be sampled (1 out of N)";
           type union {
             type string {
               pattern "<.*>|$.*";
             }
             type uint32;
           }
         }
         leaf run-length {
           description "Number of samples after initial trigger";
           default "0";
           type union {
             type string {
               pattern "<.*>|$.*";
             }
             type uint32 {
               range "0 .. 20";
             }
           }
         }
         leaf max-packets-per-second {
           description "Threshold of samples per second before dropping";
           default "1000";
           type union {
             type uint16;
             type string {
               pattern "<.*>|$.*";
             }
           }
         }
         leaf maximum-packet-length {
           description "Maximum length of the sampled packet";
           default "0";
           units "bytes";
           type union {
             type string {
               pattern "<.*>|$.*";
             }
             type uint32 {
               range "0 .. 9192";
             }
           }
         }
       }
       container mpls {
         description "Sampling parameters for MPLS";
         uses apply-advanced;
         leaf rate {
           description "Ratio of packets to be sampled (1 out of N)";
           type union {
             type string {
               pattern "<.*>|$.*";
             }
             type uint32;
           }
         }
         leaf run-length {
           description "Number of samples after initial trigger";
           default "0";
           type union {
             type string {
               pattern "<.*>|$.*";
             }
             type uint32 {
               range "0 .. 20";
             }
           }
         }
         leaf max-packets-per-second {
           description "Threshold of samples per second before dropping";
           default "1000";
           type union {
             type uint16;
             type string {
               pattern "<.*>|$.*";
             }
           }
         }
         leaf maximum-packet-length {
           description "Maximum length of the sampled packet";
           default "0";
           units "bytes";
           type union {
             type string {
               pattern "<.*>|$.*";
             }
             type uint32 {
               range "0 .. 9192";
             }
           }
         }
       }
       container inet6 {
         description "Sampling parameters for IPv6";
         uses apply-advanced;
         leaf rate {
           description "Ratio of packets to be sampled (1 out of N)";
           type union {
             type string {
               pattern "<.*>|$.*";
             }
             type uint32;
           }
         }
         leaf run-length {
           description "Number of samples after initial trigger";
           default "0";
           type union {
             type string {
               pattern "<.*>|$.*";
             }
             type uint32 {
               range "0 .. 20";
             }
           }
         }
         leaf max-packets-per-second {
           description "Threshold of samples per second before dropping";
           default "1000";
           type union {
             type uint16;
             type string {
               pattern "<.*>|$.*";
             }
           }
         }
         leaf maximum-packet-length {
           description "Maximum length of the sampled packet";
           default "0";
           units "bytes";
           type union {
             type string {
               pattern "<.*>|$.*";
             }
             type uint32 {
               range "0 .. 9192";
             }
           }
         }
       }
     }
   }
   grouping sampling_instance_bridge_output_type {
     description "Configure output options for packet sampling";
     uses apply-advanced;
     list flow-server {
       key name;
       description "Configure sending traffic aggregates in cflowd format";
       max-elements 8;
       junos:must "(\".. inline-jflow\")";
       junos:must-message "Output 'inline Jflow' should be configured with flow-server";
       uses cflowd_instance_bridge_sampling_type;
     }
     container inline-jflow {
       description "Inline processing of sampled packets";
       presence "enable inline-jflow";
       junos:must "(any \".. flow-server <*>\")";
       junos:must-message "'flow-server' must be specified with the inline Jflow";
       uses packet_export_inline_instance;
     }
   }
   grouping cflowd_instance_bridge_sampling_type {
     leaf name {
       description "Name of host collecting cflowd packets";
       type jt:ipaddr;
     }
     uses apply-advanced;
     leaf port {
       description "UDP port number on host collecting cflowd packets";
       type union {
         type uint16;
         type string {
           pattern "<.*>|$.*";
         }
       }
     }
     leaf dscp {
       description "Numeric DSCP value in the range 0 to 63";
       default "0";
       junos:must "(\".. .. inline-jflow\")";
       junos:must-message "DSCP can be configured for inline-jflow";
       type union {
         type string {
           pattern "<.*>|$.*";
         }
         type uint8 {
           range "0 .. 63";
         }
       }
     }
     leaf forwarding-class {
       description "Forwarding-class for exported jflow packets, applicable only for inline-jflow";
       junos:must "(\".. .. inline-jflow\")";
       junos:must-message "forwarding-class can be configured for inline-jflow";
       type string {
         length "1 .. 64";
       }
     }
     leaf routing-instance {
       description "Name of routing instance on which flow collector is reachable";
       junos:must "(\".. .. inline-jflow\")";
       junos:must-message "Routing Instances can be configured for inline-jflow";
       junos:must "(\"routing-instances $$ instance-type vrf\")";
       junos:must-message "routing instance should be defined and should be of type Virtual routing forwarding instance(VRF)";
       type string;
     }
     container version9 {
       presence "enable version9";
       junos:must "(\".. .. inline-jflow\")";
       junos:must-message "inline Jflow must be specified for version9";
       description "Export data in version 9 format";
       uses apply-advanced;
       container template {
         description "Template configuration";
         uses apply-advanced;
         leaf template-name {
           description "Template name";
           junos:must "(\"services flow-monitoring version9 template $$ bridge-template\")";
           junos:must-message "Template type must match input protocol";
           junos:must "((!(\".. .. .. .. inline-jflow source-address\") || (\".. .. .. .. inline-jflow source-address\" && all \".. .. .. .. flow-server <*> version9 template $$\")))";
           junos:must-message "All the collector under same family should share the same template in Inline-Jflow";
           type string;
         }
       }
     }
     container version-ipfix {
       presence "enable version-ipfix";
       junos:must "(\".. .. inline-jflow\")";
       junos:must-message "inline Jflow must be specified for version-ipfix";
       description "Export data in version ipfix format";
       uses apply-advanced;
       container template {
         description "Template configuration";
         uses apply-advanced;
         leaf template-name {
           description "Template name";
           junos:must "(\"services flow-monitoring version-ipfix template $$ bridge-template\")";
           junos:must-message "Template type must match input protocol";
           junos:must "((!(\".. .. .. .. inline-jflow source-address\") || (\".. .. .. .. inline-jflow source-address\" && all \".. .. .. .. flow-server <*> version-ipfix template $$\")))";
           junos:must-message "All the collector under same family should share the same template in Inline-Jflow";
           type string;
         }
       }
     }
   }
   grouping packet_export_inline_instance {
     uses apply-advanced;
     leaf source-address {
       description "Address to use for generating monitored packets";
       type jt:ipaddr;
     }
     leaf flow-export-rate {
       description "Flow export rate of monitored packets in kpps";
       type union {
         type string {
           pattern "<.*>|$.*";
         }
         type uint32 {
           range "1 .. 3200";
         }
       }
     }
   }
   grouping sampling_instance_inet6_output_type {
     description "Configure output options for packet sampling";
     uses apply-advanced;
     leaf aggregate-export-interval {
       description "Interval of exporting aggregate accounting information";
       default "90";
       units "seconds";
       type union {
         type string {
           pattern "<.*>|$.*";
         }
         type uint32 {
           range "90 .. 1800";
         }
       }
     }
     leaf flow-inactive-timeout {
       description "Interval of inactivity that marks a flow inactive";
       default "60";
       units "seconds";
       type union {
         type string {
           pattern "<.*>|$.*";
         }
         type uint32 {
           range "15 .. 1800";
         }
       }
     }
     leaf flow-active-timeout {
       description "Interval after which an active flow is exported";
       default "1800";
       units "seconds";
       type union {
         type string {
           pattern "<.*>|$.*";
         }
         type uint32 {
           range "60 .. 1800";
         }
       }
     }
     list flow-server {
       key name;
       description "Configure sending traffic aggregates in cflowd format";
       max-elements 8;
       junos:must "((!(any \".. interface <*>\") || all \".. interface <*> source-address\"))";
       junos:must-message "'output interface source-address' must be specified with 'flow-server' and 'interface'";
       uses cflowd_instance_inet6_sampling_type;
     }
     list interface {
       key name;
       description "Interfaces used to send monitored information";
       max-elements 1;
       junos:must "((any \".. flow-server <*>\" || any \".. extension-service <*>\"))";
       junos:must-message "'flow-server' or 'extension-service' must be specified with 'interface'";
       uses packet_export_intf_type;
     }
     container inline-jflow {
       description "Inline processing of sampled packets";
       presence "enable inline-jflow";
       junos:must "(any \".. flow-server <*>\")";
       junos:must-message "'flow-server' must be specified with the inline Jflow";
       uses packet_export_inline_instance;
     }
     list extension-service {
       key name;
       ordered-by user;
       description "Define the customer specific sampling configuration";
       junos:must "(!(\".. flow-active-timeout\"))";
       junos:must-message "'.. flow-active-timeout' is not needed with 'extension-service'";
       junos:must "(!(\".. flow-inactive-timeout\"))";
       junos:must-message "'.. flow-inactive-timeout' is not valid for 'extension-service'";
       junos:must "(!(\".. aggregate-export-interval\"))";
       junos:must-message "'.. aggregate-export-interval' is not valid for 'extension-service'";
       junos:must "(!(any \".. flow-server <*>\"))";
       junos:must-message "'.. flow-server' is not needed with 'extension-service'";
       junos:must "(!(any \".. interface <*> source-address\"))";
       junos:must-message "'.. interface source-address' is not valid for 'extension-service'";
       junos:must "(!(any \".. interface <*> engine-id\"))";
       junos:must-message "'.. interface engine-id' is not valid for 'extension-service'";
       junos:must "(!(any \".. interface <*> engine-type\"))";
       junos:must-message "'.. interface engine-type' is not valid for 'extension-service'";
       junos:must "(any \".. interface <*>\")";
       junos:must-message "'.. interface' must be specified with 'extension-service'";
       leaf name {
         description "Customer prefixed sampling service name";
         type string {
           length "1 .. 63";
         }
       }
       uses apply-advanced;
     }
   }
   grouping cflowd_instance_inet6_sampling_type {
     leaf name {
       description "Name of host collecting cflowd packets";
       type jt:ipaddr;
     }
     uses apply-advanced;
     leaf port {
       description "UDP port number on host collecting cflowd packets";
       type union {
         type uint16;
         type string {
           pattern "<.*>|$.*";
         }
       }
     }
     leaf dscp {
       description "Numeric DSCP value in the range 0 to 63";
       default "0";
       junos:must "(\".. .. inline-jflow\")";
       junos:must-message "DSCP can be configured for inline-jflow";
       type union {
         type string {
           pattern "<.*>|$.*";
         }
         type uint8 {
           range "0 .. 63";
         }
       }
     }
     leaf forwarding-class {
       description "Forwarding-class for exported jflow packets, applicable only for inline-jflow";
       junos:must "(\".. .. inline-jflow\")";
       junos:must-message "forwarding-class can be configured for inline-jflow";
       type string {
         length "1 .. 64";
       }
     }
     leaf routing-instance {
       description "Name of routing instance on which flow collector is reachable";
       junos:must "(\".. .. inline-jflow\")";
       junos:must-message "Routing Instances can be configured for inline-jflow";
       junos:must "(\"routing-instances $$ instance-type vrf\")";
       junos:must-message "routing instance should be defined and should be of type Virtual routing forwarding instance(VRF)";
       type string;
     }
     leaf autonomous-system-type {
       description "Type of autonomous system number to export";
       default "origin";
       type enumeration {
         enum "origin" {
           description "Export origin-AS numbers";
         }
         enum "peer" {
           description "Export peer-AS numbers";
         }
       }
     }
     container aggregation {
       description "Aggregations to perform for exported flows (version 8 only)";
       junos:must "(!(any \".. .. flow-server <*> version9\"))";
       junos:must-message "Select only one version";
       uses aggregation_type;
     }
     choice local-dump-choice {
       leaf local-dump {
         description "Dump cflowd records to log file before exporting";
         type empty;
       }
       leaf no-local-dump {
         description "Don't dump cflowd records to log file before exporting";
         type empty;
       }
     }
     leaf source-address {
       description "Source IPv4 address for cflowd packets";
       type jt:ipv4addr;
     }
     container version9 {
       presence "enable version9";
       junos:must "((!(any \".. .. .. .. inet output flow-server <*> version\") || !(any \".. .. .. .. inet output interface <*>\")))";
       junos:must-message "Select only one version or configure only RE based samping under family inet";
       junos:must "((any \".. .. interface <*>\" || \".. .. inline-jflow\"))";
       junos:must-message "Service PIC or inline-jflow (j-series and SRX only) must be specified for version9";
       description "Export data in version 9 format";
       uses apply-advanced;
       container template {
         description "Template configuration";
         uses apply-advanced;
         leaf template-name {
           description "Template name";
           junos:must "(\"services flow-monitoring version9 template $$ ipv6-template\")";
           junos:must-message "Template type must match input protocol";
           junos:must "((!(\".. .. .. .. inline-jflow source-address\") || (\".. .. .. .. inline-jflow source-address\" && all \".. .. .. .. flow-server <*> version9 template $$\")))";
           junos:must-message "All the collector under same family should share the same template in Inline-Jflow";
           type string;
         }
       }
     }
     container version-ipfix {
       presence "enable version-ipfix";
       junos:must "(\".. .. inline-jflow\")";
       junos:must-message "inline Jflow must be specified for version-ipfix";
       description "Export data in version ipfix format";
       uses apply-advanced;
       container template {
         description "Template configuration";
         uses apply-advanced;
         leaf template-name {
           description "Template name";
           junos:must "(\"services flow-monitoring version-ipfix template $$ ipv6-template\")";
           junos:must-message "Template type must match input protocol";
           junos:must "((!(\".. .. .. .. inline-jflow source-address\") || (\".. .. .. .. inline-jflow source-address\" && all \".. .. .. .. flow-server <*> version-ipfix template $$\")))";
           junos:must-message "All the collector under same family should share the same template in Inline-Jflow";
           type string;
         }
       }
     }
   }
   grouping sampling_instance_inet_global_output_type {
     description "Configure output options for packet sampling";
     uses apply-advanced;
     leaf aggregate-export-interval {
       description "Interval of exporting aggregate accounting information";
       default "90";
       units "seconds";
       type union {
         type string {
           pattern "<.*>|$.*";
         }
         type uint32 {
           range "90 .. 1800";
         }
       }
     }
     leaf flow-inactive-timeout {
       description "Interval of inactivity that marks a flow inactive";
       default "60";
       units "seconds";
       type union {
         type string {
           pattern "<.*>|$.*";
         }
         type uint32 {
           range "15 .. 1800";
         }
       }
     }
     leaf flow-active-timeout {
       description "Interval after which an active flow is exported";
       default "1800";
       units "seconds";
       type union {
         type string {
           pattern "<.*>|$.*";
         }
         type uint32 {
           range "60 .. 1800";
         }
       }
     }
     container file {
       junos:must "(!(any \".. extension-service <*>\"))";
       junos:must-message "This configuration is not required with 'extension-service'";
       description "Configure parameters for dumping sampled packets";
       choice enable-disable {
         case case_1 {
           leaf disable {
             description "Disable sampled packet dumps";
             type empty;
           }
         }
       }
       leaf filename {
         description "Name of file to contain sampled packet dumps";
         type string {
           length "1 .. 1024";
           junos:posix-pattern "![/ %]";
           junos:pattern-message "Must not contain '/', % or a space";
         }
       }
       leaf files {
         description "Maximum number of sampled packet dump files";
         default "10";
         type union {
           type string {
             pattern "<.*>|$.*";
           }
           type uint32 {
             range "2 .. 10000";
           }
         }
       }
       leaf size {
         description "Maximum sample dump file size";
         type string;
       }
       choice world-readable-choice {
         leaf world-readable {
           description "Allow any user to read the sampled dump";
           type empty;
         }
         leaf no-world-readable {
           description "Don't allow any user to read the sampled dump";
           type empty;
         }
       }
       choice stamp-choice {
         leaf stamp {
           description "Timestamp every packet in the dump";
           type empty;
         }
         leaf no-stamp {
           description "Don't timestamp every packet in the dump";
           type empty;
         }
       }
     }
     container port-mirroring {
       description "Configure sending sampled traffic out through an interface";
       presence "enable port-mirroring";
       junos:must "(!(any \".. extension-service <*>\"))";
       junos:must-message "This configuration is not required with 'extension-service'";
       uses inet_pm_family_output_type;
     }
     list flow-server {
       key name;
       description "Configure sending traffic aggregates in cflowd format";
       max-elements 8;
       junos:must "((!(any \".. interface <*>\") || all \".. interface <*> source-address\"))";
       junos:must-message "'output interface source-address' must be specified with 'flow-server' and 'interface'";
       uses cflowd_sampling_inet_type;
     }
     list interface {
       key name;
       description "Interfaces used to send monitored information";
       max-elements 1;
       junos:must "((any \".. flow-server <*>\" || any \".. extension-service <*>\"))";
       junos:must-message "'flow-server' or 'extension-service' must be specified with 'interface'";
       uses packet_export_intf_type;
     }
     container inline-jflow {
       description "Inline processing of sampled packets";
       presence "enable inline-jflow";
       junos:must "(any \".. flow-server <*>\")";
       junos:must-message "'flow-server' must be specified with the inline Jflow";
       uses packet_export_inline;
     }
     list extension-service {
       key name;
       ordered-by user;
       description "Define the customer specific sampling configuration";
       junos:must "(!(\".. flow-active-timeout\"))";
       junos:must-message "'.. flow-active-timeout' is not needed with 'extension-service'";
       junos:must "(!(\".. flow-inactive-timeout\"))";
       junos:must-message "'.. flow-inactive-timeout' is not valid for 'extension-service'";
       junos:must "(!(\".. aggregate-export-interval\"))";
       junos:must-message "'.. aggregate-export-interval' is not valid for 'extension-service'";
       junos:must "(!(any \".. flow-server <*>\"))";
       junos:must-message "'.. flow-server' is not needed with 'extension-service'";
       junos:must "(!(any \".. interface <*> source-address\"))";
       junos:must-message "'.. interface source-address' is not valid for 'extension-service'";
       junos:must "(!(any \".. interface <*> engine-id\"))";
       junos:must-message "'.. interface engine-id' is not valid for 'extension-service'";
       junos:must "(!(any \".. interface <*> engine-type\"))";
       junos:must-message "'.. interface engine-type' is not valid for 'extension-service'";
       junos:must "(any \".. interface <*>\")";
       junos:must-message "'.. interface' must be specified with 'extension-service'";
       leaf name {
         description "Customer prefixed sampling service name";
         type string {
           length "1 .. 63";
         }
       }
       uses apply-advanced;
     }
   }
   grouping cflowd_sampling_inet_type {
     leaf name {
       description "Name of host collecting cflowd packets";
       type jt:ipaddr;
     }
     uses apply-advanced;
     leaf port {
       description "UDP port number on host collecting cflowd packets";
       type union {
         type uint16;
         type string {
           pattern "<.*>|$.*";
         }
       }
     }
     leaf dscp {
       description "Numeric DSCP value in the range 0 to 63";
       default "0";
       junos:must "(\".. .. inline-jflow\")";
       junos:must-message "DSCP can be configured for inline-jflow";
       type union {
         type string {
           pattern "<.*>|$.*";
         }
         type uint8 {
           range "0 .. 63";
         }
       }
     }
     leaf forwarding-class {
       description "Forwarding-class for exported jflow packets, applicable only for inline-jflow";
       junos:must "(\".. .. inline-jflow\")";
       junos:must-message "forwarding-class can be configured for inline-jflow";
       type string {
         length "1 .. 64";
       }
     }
     leaf routing-instance {
       description "Name of routing instance on which flow collector is reachable";
       junos:must "(\".. .. inline-jflow\")";
       junos:must-message "Routing Instances can be configured for inline-jflow";
       junos:must "(\"routing-instances $$ instance-type vrf\")";
       junos:must-message "routing instance should be defined and should be of type Virtual routing forwarding instance(VRF)";
       type string;
     }
     leaf autonomous-system-type {
       description "Type of autonomous system number to export";
       default "origin";
       type enumeration {
         enum "origin" {
           description "Export origin-AS numbers";
         }
         enum "peer" {
           description "Export peer-AS numbers";
         }
       }
     }
     container aggregation {
       description "Aggregations to perform for exported flows (version 8 only)";
       junos:must "(!(any \".. .. flow-server <*> version9\"))";
       junos:must-message "Select only one version";
       uses aggregation_type;
     }
     choice local-dump-choice {
       leaf local-dump {
         description "Dump cflowd records to log file before exporting";
         type empty;
       }
       leaf no-local-dump {
         description "Don't dump cflowd records to log file before exporting";
         type empty;
       }
     }
     leaf source-address {
       description "Source IPv4 address for cflowd packets";
       type jt:ipv4addr;
     }
     container version9 {
       presence "enable version9";
       junos:must "((!(any \".. .. .. .. inet output flow-server <*> version\") || !(any \".. .. .. .. inet output interface <*>\")))";
       junos:must-message "Select only one version or configure only RE based samping under family inet";
       junos:must "((any \".. .. interface <*>\" || \".. .. inline-jflow\"))";
       junos:must-message "Service PIC or inline-jflow (j-series and SRX only) must be specified for version9";
       description "Export data in version 9 format";
       uses apply-advanced;
       container template {
         description "Template configuration";
         uses apply-advanced;
         leaf template-name {
           description "Template name";
           junos:must "((\"services flow-monitoring version9 template $$ ipv4-template\" || \"services flow-monitoring version9 template $$ peer-as-billing-template\"))";
           junos:must-message "Template type must match input protocol";
           type string;
         }
       }
     }
     container version-ipfix {
       presence "enable version-ipfix";
       description "Export data in version ipfix format";
       status deprecated;
       uses apply-advanced;
       container template {
         description "Template configuration";
         uses apply-advanced;
         leaf template-name {
           description "Template name";
           type string;
         }
       }
     }
     leaf version {
       description "Format of exported cflowd aggregates";
       default "5";
       junos:must "(!(any \".. .. flow-server <*> version9\"))";
       junos:must-message "Select only one version";
       type enumeration {
         enum "5" {
           description "Export cflowd aggregates in version 5 format";
           junos:must "(\"system ntp\")";
           junos:must-message " NTP must be configured for sampling v5/8/500 to work properly";
         }
         enum "8" {
           description "Export cflowd aggregates in version 8 format";
           junos:must "(\"system ntp\")";
           junos:must-message " NTP must be configured for sampling v5/8/500 to work properly";
         }
         enum "500" {
           description "Export cflowd aggregates in ASN 500 format";
           junos:must "(!(\".. .. interface\"))";
           junos:must-message "This feature is only supported for RE based sampling";
           junos:must "(\"system ntp\")";
           junos:must-message " NTP must be configured for sampling v5/8/500 to work properly";
         }
       }
     }
   }
   grouping sampling_instance_inet_output_type {
     description "Configure output options for packet sampling";
     uses apply-advanced;
     leaf aggregate-export-interval {
       description "Interval of exporting aggregate accounting information";
       default "90";
       units "seconds";
       type union {
         type string {
           pattern "<.*>|$.*";
         }
         type uint32 {
           range "90 .. 1800";
         }
       }
     }
     leaf flow-inactive-timeout {
       description "Interval of inactivity that marks a flow inactive";
       default "60";
       units "seconds";
       type union {
         type string {
           pattern "<.*>|$.*";
         }
         type uint32 {
           range "15 .. 1800";
         }
       }
     }
     leaf flow-active-timeout {
       description "Interval after which an active flow is exported";
       default "1800";
       units "seconds";
       type union {
         type string {
           pattern "<.*>|$.*";
         }
         type uint32 {
           range "60 .. 1800";
         }
       }
     }
     list flow-server {
       key name;
       description "Configure sending traffic aggregates in cflowd format";
       max-elements 8;
       junos:must "((!(any \".. interface <*>\") || all \".. interface <*> source-address\"))";
       junos:must-message "'output interface source-address' must be specified with 'flow-server' and 'interface'";
       junos:must "((\".. interface\" || \".. inline-jflow\"))";
       junos:must-message "Output 'interface' or 'inline Jflow' should be configured with flow-server";
       uses cflowd_instance_inet_sampling_type;
     }
     list interface {
       key name;
       description "Interfaces used to send monitored information";
       max-elements 1;
       junos:must "((any \".. flow-server <*>\" || any \".. extension-service <*>\"))";
       junos:must-message "'flow-server' or 'extension-service' must be specified with 'interface'";
       uses packet_export_intf_type;
     }
     container inline-jflow {
       description "Inline processing of sampled packets";
       presence "enable inline-jflow";
       junos:must "(any \".. flow-server <*>\")";
       junos:must-message "'flow-server' must be specified with the inline Jflow";
       uses packet_export_inline_instance;
     }
     list extension-service {
       key name;
       ordered-by user;
       description "Define the customer specific sampling configuration";
       junos:must "(!(\".. flow-active-timeout\"))";
       junos:must-message "'.. flow-active-timeout' is not needed with 'extension-service'";
       junos:must "(!(\".. flow-inactive-timeout\"))";
       junos:must-message "'.. flow-inactive-timeout' is not valid for 'extension-service'";
       junos:must "(!(\".. aggregate-export-interval\"))";
       junos:must-message "'.. aggregate-export-interval' is not valid for 'extension-service'";
       junos:must "(!(any \".. flow-server <*>\"))";
       junos:must-message "'.. flow-server' is not needed with 'extension-service'";
       junos:must "(!(any \".. interface <*> source-address\"))";
       junos:must-message "'.. interface source-address' is not valid for 'extension-service'";
       junos:must "(!(any \".. interface <*> engine-id\"))";
       junos:must-message "'.. interface engine-id' is not valid for 'extension-service'";
       junos:must "(!(any \".. interface <*> engine-type\"))";
       junos:must-message "'.. interface engine-type' is not valid for 'extension-service'";
       junos:must "(any \".. interface <*>\")";
       junos:must-message "'.. interface' must be specified with 'extension-service'";
       leaf name {
         description "Customer prefixed sampling service name";
         type string {
           length "1 .. 63";
         }
       }
       uses apply-advanced;
     }
   }
   grouping cflowd_instance_inet_sampling_type {
     leaf name {
       description "Name of host collecting cflowd packets";
       type jt:ipaddr;
     }
     uses apply-advanced;
     leaf port {
       description "UDP port number on host collecting cflowd packets";
       type union {
         type uint16;
         type string {
           pattern "<.*>|$.*";
         }
       }
     }
     leaf dscp {
       description "Numeric DSCP value in the range 0 to 63";
       default "0";
       junos:must "(\".. .. inline-jflow\")";
       junos:must-message "DSCP can be configured for inline-jflow";
       type union {
         type string {
           pattern "<.*>|$.*";
         }
         type uint8 {
           range "0 .. 63";
         }
       }
     }
     leaf forwarding-class {
       description "Forwarding-class for exported jflow packets, applicable only for inline-jflow";
       junos:must "(\".. .. inline-jflow\")";
       junos:must-message "forwarding-class can be configured for inline-jflow";
       type string {
         length "1 .. 64";
       }
     }
     leaf routing-instance {
       description "Name of routing instance on which flow collector is reachable";
       junos:must "(\".. .. inline-jflow\")";
       junos:must-message "Routing Instances can be configured for inline-jflow";
       junos:must "(\"routing-instances $$ instance-type vrf\")";
       junos:must-message "routing instance should be defined and should be of type Virtual routing forwarding instance(VRF)";
       type string;
     }
     leaf autonomous-system-type {
       description "Type of autonomous system number to export";
       default "origin";
       type enumeration {
         enum "origin" {
           description "Export origin-AS numbers";
         }
         enum "peer" {
           description "Export peer-AS numbers";
         }
       }
     }
     container aggregation {
       description "Aggregations to perform for exported flows (version 8 only)";
       junos:must "(!(any \".. .. flow-server <*> version9\"))";
       junos:must-message "Select only one version";
       uses aggregation_type;
     }
     choice local-dump-choice {
       leaf local-dump {
         description "Dump cflowd records to log file before exporting";
         type empty;
       }
       leaf no-local-dump {
         description "Don't dump cflowd records to log file before exporting";
         type empty;
       }
     }
     leaf source-address {
       description "Source IPv4 address for cflowd packets";
       type jt:ipv4addr;
     }
     container version9 {
       presence "enable version9";
       junos:must "((!(any \".. .. .. .. inet output flow-server <*> version\") || !(any \".. .. .. .. inet output interface <*>\")))";
       junos:must-message "Select only one version or configure only RE based samping under family inet";
       junos:must "((any \".. .. interface <*>\" || \".. .. inline-jflow\"))";
       junos:must-message "Service PIC or inline-jflow (j-series and SRX only) must be specified for version9";
       description "Export data in version 9 format";
       uses apply-advanced;
       container template {
         description "Template configuration";
         uses apply-advanced;
         leaf template-name {
           description "Template name";
           junos:must "(\"services flow-monitoring version9 template $$ ipv4-template\")";
           junos:must-message "Template type must match input protocol";
           junos:must "((!(\".. .. .. .. inline-jflow source-address\") || (\".. .. .. .. inline-jflow source-address\" && all \".. .. .. .. flow-server <*> version9 template $$\")))";
           junos:must-message "All the collector under same family should share the same template in Inline-Jflow";
           type string;
         }
       }
     }
     container version-ipfix {
       presence "enable version-ipfix";
       junos:must "(\".. .. inline-jflow\")";
       junos:must-message "inline Jflow must be specified for version-ipfix";
       description "Export data in version ipfix format";
       uses apply-advanced;
       container template {
         description "Template configuration";
         uses apply-advanced;
         leaf template-name {
           description "Template name";
           junos:must "(\"services flow-monitoring version-ipfix template $$ ipv4-template\")";
           junos:must-message "Template type must match input protocol";
           junos:must "((!(\".. .. .. .. inline-jflow source-address\") || (\".. .. .. .. inline-jflow source-address\" && all \".. .. .. .. flow-server <*> version-ipfix template $$\")))";
           junos:must-message "All the collector under same family should share the same template in Inline-Jflow";
           type string;
         }
       }
     }
     leaf version {
       description "Format of exported cflowd aggregates";
       default "5";
       junos:must "(!(any \".. .. .. .. .. family mpls output flow-server <*> version9\"))";
       junos:must-message "Select only one version";
       junos:must "(!(any \".. .. .. .. .. family inet6 output flow-server <*> version9\"))";
       junos:must-message "Select only one version";
       junos:must "(!(any \".. .. .. .. .. family inet output flow-server <*> version9\"))";
       junos:must-message "Select only one version";
       junos:must "(!(any \".. .. flow-server <*> version-ipfix\"))";
       junos:must-message "Select only one version";
       junos:must "(!(any \".. .. flow-server <*> version9\"))";
       junos:must-message "Select only one version";
       type enumeration {
         enum "5" {
           description "Export cflowd aggregates in version 5 format";
           junos:must "(\"system ntp\")";
           junos:must-message " NTP must be configured for sampling v5/8/500 to work properly";
         }
         enum "8" {
           description "Export cflowd aggregates in version 8 format";
           junos:must "(\"system ntp\")";
           junos:must-message " NTP must be configured for sampling v5/8/500 to work properly";
         }
       }
     }
   }
   grouping sampling_instance_input_type {
     description "Configure input options for packet sampling";
     uses apply-advanced;
     leaf rate {
       description "Ratio of packets to be sampled (1 out of N)";
       type union {
         type string {
           pattern "<.*>|$.*";
         }
         type uint32;
       }
     }
     leaf run-length {
       description "Number of samples after initial trigger";
       default "0";
       type union {
         type string {
           pattern "<.*>|$.*";
         }
         type uint32 {
           range "0 .. 20";
         }
       }
     }
     leaf max-packets-per-second {
       description "Threshold of samples per second before dropping";
       default "1000";
       type union {
         type uint16;
         type string {
           pattern "<.*>|$.*";
         }
       }
     }
     leaf maximum-packet-length {
       description "Maximum length of the sampled packet";
       default "0";
       units "bytes";
       type union {
         type string {
           pattern "<.*>|$.*";
         }
         type uint32 {
           range "0 .. 9192";
         }
       }
     }
   }
   grouping sampling_instance_mpls_output_type {
     description "Configure output options for packet sampling";
     uses apply-advanced;
     leaf aggregate-export-interval {
       description "Interval of exporting aggregate accounting information";
       default "90";
       units "seconds";
       type union {
         type string {
           pattern "<.*>|$.*";
         }
         type uint32 {
           range "90 .. 1800";
         }
       }
     }
     leaf flow-inactive-timeout {
       description "Interval of inactivity that marks a flow inactive";
       default "60";
       units "seconds";
       type union {
         type string {
           pattern "<.*>|$.*";
         }
         type uint32 {
           range "15 .. 1800";
         }
       }
     }
     leaf flow-active-timeout {
       description "Interval after which an active flow is exported";
       default "1800";
       units "seconds";
       type union {
         type string {
           pattern "<.*>|$.*";
         }
         type uint32 {
           range "60 .. 1800";
         }
       }
     }
     list flow-server {
       key name;
       description "Configure sending traffic aggregates in cflowd format";
       max-elements 8;
       junos:must "((!(any \".. interface <*>\") || all \".. interface <*> source-address\"))";
       junos:must-message "'output interface source-address' must be specified with 'flow-server' and 'interface'";
       junos:must "((\".. interface\" || \".. inline-jflow\"))";
       junos:must-message "Output 'interface' or 'inline Jflow' should be configured with flow-server";
       uses cflowd_instance_mpls_sampling_type;
     }
     list interface {
       key name;
       description "Interfaces used to send monitored information";
       max-elements 1;
       junos:must "(any \".. flow-server <*>\")";
       junos:must-message "'flow-server' must be specified with 'interface'";
       uses packet_export_intf_type;
     }
     container inline-jflow {
       description "Inline processing of sampled packets";
       presence "enable inline-jflow";
       junos:must "(any \".. flow-server <*>\")";
       junos:must-message "'flow-server' must be specified with the inline Jflow";
       uses packet_export_inline_instance;
     }
   }
   grouping cflowd_instance_mpls_sampling_type {
     leaf name {
       description "Name of host collecting cflowd packets";
       type jt:ipaddr;
     }
     uses apply-advanced;
     leaf port {
       description "UDP port number on host collecting cflowd packets";
       type union {
         type uint16;
         type string {
           pattern "<.*>|$.*";
         }
       }
     }
     leaf dscp {
       description "Numeric DSCP value in the range 0 to 63";
       default "0";
       junos:must "(\".. .. inline-jflow\")";
       junos:must-message "DSCP can be configured for inline-jflow";
       type union {
         type string {
           pattern "<.*>|$.*";
         }
         type uint8 {
           range "0 .. 63";
         }
       }
     }
     leaf forwarding-class {
       description "Forwarding-class for exported jflow packets, applicable only for inline-jflow";
       junos:must "(\".. .. inline-jflow\")";
       junos:must-message "forwarding-class can be configured for inline-jflow";
       type string {
         length "1 .. 64";
       }
     }
     leaf routing-instance {
       description "Name of routing instance on which flow collector is reachable";
       junos:must "(\".. .. inline-jflow\")";
       junos:must-message "Routing Instances can be configured for inline-jflow";
       junos:must "(\"routing-instances $$ instance-type vrf\")";
       junos:must-message "routing instance should be defined and should be of type Virtual routing forwarding instance(VRF)";
       type string;
     }
     leaf autonomous-system-type {
       description "Type of autonomous system number to export";
       default "origin";
       type enumeration {
         enum "origin" {
           description "Export origin-AS numbers";
         }
         enum "peer" {
           description "Export peer-AS numbers";
         }
       }
     }
     container aggregation {
       description "Aggregations to perform for exported flows (version 8 only)";
       junos:must "(!(any \".. .. flow-server <*> version9\"))";
       junos:must-message "Select only one version";
       uses aggregation_type;
     }
     choice local-dump-choice {
       leaf local-dump {
         description "Dump cflowd records to log file before exporting";
         type empty;
       }
       leaf no-local-dump {
         description "Don't dump cflowd records to log file before exporting";
         type empty;
       }
     }
     leaf source-address {
       description "Source IPv4 address for cflowd packets";
       type jt:ipv4addr;
     }
     container version9 {
       presence "enable version9";
       junos:must "((!(any \".. .. .. .. inet output flow-server <*> version\") || !(any \".. .. .. .. inet output interface <*>\")))";
       junos:must-message "Select only one version or configure only RE based samping under family inet";
       junos:must "((any \".. .. interface <*>\" || \".. .. inline-jflow\"))";
       junos:must-message "Service PIC or inline-jflow (j-series and SRX only) must be specified for version9";
       description "Export data in version 9 format";
       uses apply-advanced;
       container template {
         description "Template configuration";
         uses apply-advanced;
         leaf template-name {
           description "Template name";
           junos:must "((\"services flow-monitoring version9 template $$ mpls-template\" || (\"services flow-monitoring version9 template $$ mpls-ipv4-template\" || \"services flow-monitoring version9 template $$ mpls-ipvx-template\")))";
           junos:must-message "Template type must match input protocol";
           junos:must "((!(\".. .. .. .. inline-jflow source-address\") || (\".. .. .. .. inline-jflow source-address\" && all \".. .. .. .. flow-server <*> version9 template $$\")))";
           junos:must-message "All the collector under same family should share the same template in Inline-Jflow";
           type string;
         }
       }
     }
     container version-ipfix {
       presence "enable version-ipfix";
       junos:must "(\".. .. inline-jflow\")";
       junos:must-message "inline Jflow must be specified for version-ipfix";
       description "Export data in version ipfix format";
       uses apply-advanced;
       container template {
         description "Template configuration";
         uses apply-advanced;
         leaf template-name {
           description "Template name";
           junos:must "((\"services flow-monitoring version-ipfix template $$ mpls-template\" || (\"services flow-monitoring version-ipfix template $$ mpls-ipv4-template\" || \"services flow-monitoring version-ipfix template $$ mpls-ipvx-template\")))";
           junos:must-message "Template type must match input protocol";
           junos:must "((!(\".. .. .. .. inline-jflow source-address\") || (\".. .. .. .. inline-jflow source-address\" && all \".. .. .. .. flow-server <*> version-ipfix template $$\")))";
           junos:must-message "All the collector under same family should share the same template in Inline-Jflow";
           type string;
         }
       }
     }
   }
   grouping sampling_instance_vpls_output_type {
     description "Configure output options for packet sampling";
     uses apply-advanced;
     list flow-server {
       key name;
       description "Configure sending traffic aggregates in cflowd format";
       max-elements 8;
       junos:must "(\".. inline-jflow\")";
       junos:must-message "Output 'inline Jflow' should be configured with flow-server";
       uses cflowd_instance_vpls_sampling_type;
     }
     container inline-jflow {
       description "Inline processing of sampled packets";
       presence "enable inline-jflow";
       junos:must "(any \".. flow-server <*>\")";
       junos:must-message "'flow-server' must be specified with the inline Jflow";
       uses packet_export_inline_instance;
     }
   }
   grouping cflowd_instance_vpls_sampling_type {
     leaf name {
       description "Name of host collecting cflowd packets";
       type jt:ipaddr;
     }
     uses apply-advanced;
     leaf port {
       description "UDP port number on host collecting cflowd packets";
       type union {
         type uint16;
         type string {
           pattern "<.*>|$.*";
         }
       }
     }
     leaf dscp {
       description "Numeric DSCP value in the range 0 to 63";
       default "0";
       junos:must "(\".. .. inline-jflow\")";
       junos:must-message "DSCP can be configured for inline-jflow";
       type union {
         type string {
           pattern "<.*>|$.*";
         }
         type uint8 {
           range "0 .. 63";
         }
       }
     }
     leaf forwarding-class {
       description "Forwarding-class for exported jflow packets, applicable only for inline-jflow";
       junos:must "(\".. .. inline-jflow\")";
       junos:must-message "forwarding-class can be configured for inline-jflow";
       type string {
         length "1 .. 64";
       }
     }
     leaf routing-instance {
       description "Name of routing instance on which flow collector is reachable";
       junos:must "(\".. .. inline-jflow\")";
       junos:must-message "Routing Instances can be configured for inline-jflow";
       junos:must "(\"routing-instances $$ instance-type vrf\")";
       junos:must-message "routing instance should be defined and should be of type Virtual routing forwarding instance(VRF)";
       type string;
     }
     container version9 {
       presence "enable version9";
       junos:must "(\".. .. inline-jflow\")";
       junos:must-message "inline Jflow must be specified for version9";
       description "Export data in version 9 format";
       uses apply-advanced;
       container template {
         description "Template configuration";
         uses apply-advanced;
         leaf template-name {
           description "Template name";
           junos:must "(\"services flow-monitoring version9 template $$ vpls-template\")";
           junos:must-message "Template type must match input protocol";
           junos:must "((!(\".. .. .. .. inline-jflow source-address\") || (\".. .. .. .. inline-jflow source-address\" && all \".. .. .. .. flow-server <*> version9 template $$\")))";
           junos:must-message "All the collector under same family should share the same template in Inline-Jflow";
           type string;
         }
       }
     }
     container version-ipfix {
       presence "enable version-ipfix";
       junos:must "(\".. .. inline-jflow\")";
       junos:must-message "inline Jflow must be specified for version-ipfix";
       description "Export data in version ipfix format";
       uses apply-advanced;
       container template {
         description "Template configuration";
         uses apply-advanced;
         leaf template-name {
           description "Template name";
           junos:must "(\"services flow-monitoring version-ipfix template $$ vpls-template\")";
           junos:must-message "Template type must match input protocol";
           junos:must "((!(\".. .. .. .. inline-jflow source-address\") || (\".. .. .. .. inline-jflow source-address\" && all \".. .. .. .. flow-server <*> version-ipfix template $$\")))";
           junos:must-message "All the collector under same family should share the same template in Inline-Jflow";
           type string;
         }
       }
     }
   }
   grouping sampling_output_type {
     description "Configure output options for packet sampling";
     uses apply-advanced;
     leaf aggregate-export-interval {
       description "Interval of exporting aggregate accounting information";
       default "90";
       units "seconds";
       type union {
         type string {
           pattern "<.*>|$.*";
         }
         type uint32 {
           range "90 .. 1800";
         }
       }
     }
     leaf flow-inactive-timeout {
       description "Interval of inactivity that marks a flow inactive";
       default "60";
       units "seconds";
       type union {
         type string {
           pattern "<.*>|$.*";
         }
         type uint32 {
           range "15 .. 1800";
         }
       }
     }
     leaf flow-active-timeout {
       description "Interval after which an active flow is exported";
       default "1800";
       units "seconds";
       type union {
         type string {
           pattern "<.*>|$.*";
         }
         type uint32 {
           range "60 .. 1800";
         }
       }
     }
     container file {
       junos:must "(!(any \".. extension-service <*>\"))";
       junos:must-message "This configuration is not required with 'extension-service'";
       description "Configure parameters for dumping sampled packets";
       choice enable-disable {
         case case_1 {
           leaf disable {
             description "Disable sampled packet dumps";
             type empty;
           }
         }
       }
       leaf filename {
         description "Name of file to contain sampled packet dumps";
         type string {
           length "1 .. 1024";
           junos:posix-pattern "![/ %]";
           junos:pattern-message "Must not contain '/', % or a space";
         }
       }
       leaf files {
         description "Maximum number of sampled packet dump files";
         default "10";
         type union {
           type string {
             pattern "<.*>|$.*";
           }
           type uint32 {
             range "2 .. 10000";
           }
         }
       }
       leaf size {
         description "Maximum sample dump file size";
         type string;
       }
       choice world-readable-choice {
         leaf world-readable {
           description "Allow any user to read the sampled dump";
           type empty;
         }
         leaf no-world-readable {
           description "Don't allow any user to read the sampled dump";
           type empty;
         }
       }
       choice stamp-choice {
         leaf stamp {
           description "Timestamp every packet in the dump";
           type empty;
         }
         leaf no-stamp {
           description "Don't timestamp every packet in the dump";
           type empty;
         }
       }
     }
     container port-mirroring {
       description "Configure sending sampled traffic out through an interface";
       presence "enable port-mirroring";
       junos:must "(!(any \".. extension-service <*>\"))";
       junos:must-message "This configuration is not required with 'extension-service'";
       uses inet_pm_family_output_type;
     }
     list flow-server {
       key name;
       description "Configure sending traffic aggregates in cflowd format";
       max-elements 8;
       junos:must "((!(any \".. interface <*>\") || all \".. interface <*> source-address\"))";
       junos:must-message "'output interface source-address' must be specified with 'flow-server' and 'interface'";
       uses cflowd_sampling_type;
     }
     list interface {
       key name;
       description "Interfaces used to send monitored information";
       max-elements 1;
       junos:must "((any \".. flow-server <*>\" || any \".. extension-service <*>\"))";
       junos:must-message "'flow-server' or 'extension-service' must be specified with 'interface'";
       uses packet_export_intf_type;
     }
     container inline-jflow {
       description "Inline processing of sampled packets";
       presence "enable inline-jflow";
       junos:must "(any \".. flow-server <*>\")";
       junos:must-message "'flow-server' must be specified with the inline Jflow";
       uses packet_export_inline;
     }
     list extension-service {
       key name;
       ordered-by user;
       description "Define the customer specific sampling configuration";
       junos:must "(!(\".. flow-active-timeout\"))";
       junos:must-message "'.. flow-active-timeout' is not needed with 'extension-service'";
       junos:must "(!(\".. flow-inactive-timeout\"))";
       junos:must-message "'.. flow-inactive-timeout' is not valid for 'extension-service'";
       junos:must "(!(\".. aggregate-export-interval\"))";
       junos:must-message "'.. aggregate-export-interval' is not valid for 'extension-service'";
       junos:must "(!(any \".. flow-server <*>\"))";
       junos:must-message "'.. flow-server' is not needed with 'extension-service'";
       junos:must "(!(any \".. interface <*> source-address\"))";
       junos:must-message "'.. interface source-address' is not valid for 'extension-service'";
       junos:must "(!(any \".. interface <*> engine-id\"))";
       junos:must-message "'.. interface engine-id' is not valid for 'extension-service'";
       junos:must "(!(any \".. interface <*> engine-type\"))";
       junos:must-message "'.. interface engine-type' is not valid for 'extension-service'";
       junos:must "(any \".. interface <*>\")";
       junos:must-message "'.. interface' must be specified with 'extension-service'";
       leaf name {
         description "Customer prefixed sampling service name";
         type string {
           length "1 .. 63";
         }
       }
       uses apply-advanced;
     }
   }
   grouping cflowd_sampling_type {
     leaf name {
       description "Name of host collecting cflowd packets";
       type jt:ipaddr;
     }
     uses apply-advanced;
     leaf port {
       description "UDP port number on host collecting cflowd packets";
       type union {
         type uint16;
         type string {
           pattern "<.*>|$.*";
         }
       }
     }
     leaf dscp {
       description "Numeric DSCP value in the range 0 to 63";
       default "0";
       junos:must "(\".. .. inline-jflow\")";
       junos:must-message "DSCP can be configured for inline-jflow";
       type union {
         type string {
           pattern "<.*>|$.*";
         }
         type uint8 {
           range "0 .. 63";
         }
       }
     }
     leaf forwarding-class {
       description "Forwarding-class for exported jflow packets, applicable only for inline-jflow";
       junos:must "(\".. .. inline-jflow\")";
       junos:must-message "forwarding-class can be configured for inline-jflow";
       type string {
         length "1 .. 64";
       }
     }
     leaf routing-instance {
       description "Name of routing instance on which flow collector is reachable";
       junos:must "(\".. .. inline-jflow\")";
       junos:must-message "Routing Instances can be configured for inline-jflow";
       junos:must "(\"routing-instances $$ instance-type vrf\")";
       junos:must-message "routing instance should be defined and should be of type Virtual routing forwarding instance(VRF)";
       type string;
     }
     leaf autonomous-system-type {
       description "Type of autonomous system number to export";
       default "origin";
       type enumeration {
         enum "origin" {
           description "Export origin-AS numbers";
         }
         enum "peer" {
           description "Export peer-AS numbers";
         }
       }
     }
     container aggregation {
       description "Aggregations to perform for exported flows (version 8 only)";
       junos:must "(!(any \".. .. flow-server <*> version9\"))";
       junos:must-message "Select only one version";
       uses aggregation_type;
     }
     choice local-dump-choice {
       leaf local-dump {
         description "Dump cflowd records to log file before exporting";
         type empty;
       }
       leaf no-local-dump {
         description "Don't dump cflowd records to log file before exporting";
         type empty;
       }
     }
     leaf source-address {
       description "Source IPv4 address for cflowd packets";
       type jt:ipv4addr;
     }
     container version9 {
       presence "enable version9";
       junos:must "(!(any \".. .. flow-server <*> version\"))";
       junos:must-message "Select only one version";
       junos:must "((any \".. .. interface <*>\" || \".. .. inline-jflow\"))";
       junos:must-message "Service PIC or inline-jflow (j-series and SRX only) must be specified for version9";
       description "Export data in version 9 format";
       uses apply-advanced;
       container template {
         description "Template configuration";
         uses apply-advanced;
         leaf template-name {
           description "Template name";
           junos:must "(((\"services flow-monitoring version9 template $$ ipv4-template\" && \"forwarding-options sampling input family inet\") || ((\"services flow-monitoring version9 template $$ ipv6-template\" && \"forwarding-options sampling input family inet6\") || ((\"services flow-monitoring version9 template $$ mpls-template\" && \"forwarding-options sampling input family mpls\") || ((\"services flow-monitoring version9 template $$ mpls-ipv4-template\" && \"forwarding-options sampling input family mpls\") || (\"services flow-monitoring version9 template $$ mpls-ipvx-template\" && \"forwarding-options sampling input family mpls\"))))))";
           junos:must-message "Template type must match input protocol";
           type string;
         }
       }
     }
     container version-ipfix {
       presence "enable version-ipfix";
       description "Export data in version ipfix format";
       status deprecated;
       uses apply-advanced;
       container template {
         description "Template configuration";
         uses apply-advanced;
         leaf template-name {
           description "Template name";
           type string;
         }
       }
     }
     leaf version {
       description "Format of exported cflowd aggregates";
       default "5";
       junos:must "(\"forwarding-options sampling input family inet\")";
       junos:must-message "input 'family inet' must be configured";
       junos:must "(!(any \".. .. flow-server <*> version9\"))";
       junos:must-message "Select only one version";
       type enumeration {
         enum "5" {
           description "Export cflowd aggregates in version 5 format";
           junos:must "(\"system ntp\")";
           junos:must-message " NTP must be configured for sampling v5/8/500 to work properly";
         }
         enum "8" {
           description "Export cflowd aggregates in version 8 format";
           junos:must "(\"system ntp\")";
           junos:must-message " NTP must be configured for sampling v5/8/500 to work properly";
         }
         enum "500" {
           description "Export cflowd aggregates in ASN 500 format";
           junos:must "(!(\".. .. interface\"))";
           junos:must-message "This feature is only supported for RE based sampling";
           junos:must "(\"system ntp\")";
           junos:must-message " NTP must be configured for sampling v5/8/500 to work properly";
         }
       }
     }
   }
   grouping sampling_traceoptions_type {
     description "Configure packet sampling traceoptions";
     uses apply-advanced;
     leaf no-remote-trace {
       description "Disable remote tracing";
       junos:must "(\"system tracing\")";
       junos:must-message "'no-remote-trace' is valid only when [system tracing] is configured";
       type empty;
     }
     container file {
       description "Trace file information";
       leaf filename {
         description "Name of file in which to write trace information";
         type string {
           length "1 .. 1024";
           junos:posix-pattern "![/ %]";
           junos:pattern-message "Must not contain '/', % or a space";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
   }
   grouping sbl-type {
     description "SBL type";
     uses apply-advanced;
     list profile {
       key name;
       ordered-by user;
       description "SBL profile";
       leaf name {
         description "SBL profile name";
         type string {
           length "1 .. 29";
         }
       }
       uses apply-advanced;
       choice sbl-default-server-choice {
         leaf sbl-default-server {
           description "Default SBL server";
           type empty;
         }
         leaf no-sbl-default-server {
           description "Don't default SBL server";
           type empty;
         }
       }
       leaf spam-action {
         description "Anti-spam actions";
         type enumeration {
           enum "block" {
             description "Block e-mail";
           }
           enum "tag-header" {
             description "Tag header of e-mail";
           }
           enum "tag-subject" {
             description "Tag subject of e-mail";
           }
         }
       }
       leaf custom-tag-string {
         description "Custom tag string";
         type string {
           length "1 .. 512";
         }
       }
       leaf address-whitelist {
         description "Anti-spam whitelist";
         junos:must "(\"security utm custom-objects url-pattern $$\")";
         junos:must-message "url-pattern must be defined";
         type string;
       }
       leaf address-blacklist {
         description "Anti-spam blacklist";
         junos:must "(\"security utm custom-objects url-pattern $$\")";
         junos:must-message "url-pattern must be defined";
         type string;
       }
     }
   }
   grouping scheduler_object_type {
     leaf name {
       description "Name of security scheduler";
       type string {
         length "1 .. 63";
         junos:posix-pattern "^[[:alnum:]][[:alnum:]_-]*$";
         junos:pattern-message "Must be a string beginning with a number or letter and consisting of letters, numbers, dashes and underscores.";
       }
     }
     uses apply-advanced;
     leaf description {
       description "Text description of scheduler";
       type string {
         length "1 .. 900";
         junos:posix-pattern "^[^&<>\n]+$";
         junos:pattern-message "Must be a string excluding '&', '<', '>' and '\n'";
       }
     }
     list start-date {
       key "start-date stop-date";
       ordered-by user;
       description "Start date and time ([YYYY-]MM-DD.hh:mm)";
       max-elements 2;
       leaf start-date {
         description "Start date and time ([YYYY-]MM-DD.hh:mm)";
         type string {
           junos:posix-pattern "^((2[0-9][0-9][0-9][-])?(0[1-9]|1[012])[-](0[1-9]|[12][0-9]|3[01])[.][0-9]{2,2}[:][0-9]{2,2})$";
           junos:pattern-message "Invalid date format [YYYY-]MM-DD.hh:mm";
         }
       }
       leaf stop-date {
         description "Stop date and time ([YYYY-]MM-DD.hh:mm)";
         type string {
           junos:posix-pattern "^((2[0-9][0-9][0-9][-])?(0[1-9]|1[012])[-](0[1-9]|[12][0-9]|3[01])[.][0-9]{2,2}[:][0-9]{2,2})$";
           junos:pattern-message "Invalid date format [YYYY-]MM-DD.hh:mm";
         }
       }
       uses apply-advanced;
     }
     container daily {
       description "Everyday; can be overwritten by specific weekday";
       uses daily-object;
     }
     container sunday {
       description "Every Sunday";
       uses daily-object;
     }
     container monday {
       description "Every Monday";
       uses daily-object;
     }
     container tuesday {
       description "Every Tuesday";
       uses daily-object;
     }
     container wednesday {
       description "Every Wednesday";
       uses daily-object;
     }
     container thursday {
       description "Every Thursday";
       uses daily-object;
     }
     container friday {
       description "Every Friday";
       uses daily-object;
     }
     container saturday {
       description "Every Saturday";
       uses daily-object;
     }
   }
   grouping daily-object {
     description "Daily schedule";
     uses apply-advanced;
     choice daily_type {
       case case_1 {
         list start-time {
           key "start-time-value stop-time";
           description "Time range for day";
           max-elements 2;
           leaf start-time-value {
             description "Start time for day (hh:mm)";
             type string {
               junos:posix-pattern "^((0[0-9]|1[0-9]|2[0-3])([:][0-5][0-9])?([:][0-5][0-9])?)$";
               junos:pattern-message "Must be a valid time in hh:mm format";
             }
           }
           leaf stop-time {
             description "Stop time for day (hh:mm)";
             type string {
               junos:posix-pattern "^((0[0-9]|1[0-9]|2[0-3])([:][0-5][0-9])?([:][0-5][0-9])?)$";
               junos:pattern-message "Must be a valid time in hh:mm format";
             }
           }
           uses apply-advanced;
         }
       }
       case case_2 {
         leaf exclude {
           description "Exclude day from week";
           type empty;
         }
       }
       case case_3 {
         leaf all-day {
           description "Include complete day";
           type empty;
         }
       }
     }
   }
   grouping sctp-object {
     uses apply-advanced;
     list profile {
       key name;
       description "Configure stream transmission protocol";
       leaf name {
         description "SCTP configuration name";
         type string {
           length "1 .. 31";
           junos:posix-pattern "^[0-9A-Za-z][_0-9A-Za-z-]{0,30}$";
           junos:pattern-message "Must be a string beginning with a letter or number, and consisting of no more than 31 total letters, numbers, dashes and underscores.";
         }
       }
       uses apply-advanced;
       leaf nat-only {
         description "Only do payload IPs translation for SCTP packet";
         type empty;
       }
       leaf association-timeout {
         description "SCTP association timeout length, in minutes";
         type union {
           type string {
             pattern "<.*>|$.*";
           }
           type uint32 {
             range "10 .. 1440";
           }
         }
       }
       leaf handshake-timeout {
         description "SCTP handshake timeout, in seconds";
         type union {
           type string {
             pattern "<.*>|$.*";
           }
           type uint32 {
             range "10 .. 30";
           }
         }
       }
       container drop {
         description "Disallowed SCTP payload message";
         uses apply-advanced;
         list m3ua-service {
           key name;
           ordered-by user;
           description "MTP level 3 (MTP3) user adaptation layer service";
           leaf name {
             type enumeration {
               enum "sccp" {
                 description "Signaling connection control part";
               }
               enum "tup" {
                 description "Telephone user part";
               }
               enum "isup" {
                 description "ISDN user part";
               }
             }
           }
         }
         list payload-protocol {
           key name;
           ordered-by user;
           description "SCTP payload protocol identifier";
           leaf name {
             type string;
           }
         }
       }
       container permit {
         description "Permit SCTP payload message";
         uses apply-advanced;
         list payload-protocol {
           key name;
           ordered-by user;
           description "SCTP payload protocol identifier";
           leaf name {
             type string;
           }
         }
       }
       container limit {
         description "Packet limits";
         uses apply-advanced;
         list payload-protocol {
           key name;
           ordered-by user;
           description "Payload Rate limit";
           leaf name {
             type string;
           }
           leaf rate {
             description "Rate limit";
             type union {
               type string {
                 pattern "<.*>|$.*";
               }
               type uint16 {
                 range "1 .. 12000";
               }
             }
           }
         }
         list address {
           key name;
           ordered-by user;
           description "Rate limit for a list of IP addresses";
           leaf name {
             description "IP address";
             type jt:ipaddr;
           }
           uses apply-advanced;
           list payload-protocol {
             key name;
             ordered-by user;
             description "Payload Rate limit";
             leaf name {
               type string;
             }
             leaf rate {
               description "Rate limit";
               type union {
                 type string {
                   pattern "<.*>|$.*";
                 }
                 type uint16 {
                   range "1 .. 12000";
                 }
               }
             }
           }
         }
         container rate {
           description "Rate limit";
           uses apply-advanced;
           leaf sccp {
             description "Global SCCP messages rate limit";
             type union {
               type string {
                 pattern "<.*>|$.*";
               }
               type uint16 {
                 range "1 .. 12000";
               }
             }
           }
           leaf ssp {
             description "Global SSP messages rate limit";
             type union {
               type string {
                 pattern "<.*>|$.*";
               }
               type uint16 {
                 range "1 .. 12000";
               }
             }
           }
           leaf sst {
             description "Global SST messages rate limit";
             type union {
               type string {
                 pattern "<.*>|$.*";
               }
               type uint16 {
                 range "1 .. 12000";
               }
             }
           }
           list address {
             key name;
             ordered-by user;
             description "Rate limit for a list of IP addresses";
             leaf name {
               description "IP address";
               type jt:ipaddr;
             }
             uses apply-advanced;
             leaf sccp {
               description "SCCP messages rate limit";
               type union {
                 type string {
                   pattern "<.*>|$.*";
                 }
                 type uint16 {
                   range "1 .. 12000";
                 }
               }
             }
             leaf ssp {
               description "SSP messages rate limit";
               type union {
                 type string {
                   pattern "<.*>|$.*";
                 }
                 type uint16 {
                   range "1 .. 12000";
                 }
               }
             }
             leaf sst {
               description "SST messages rate limit";
               type union {
                 type string {
                   pattern "<.*>|$.*";
                 }
                 type uint16 {
                   range "1 .. 12000";
                 }
               }
             }
           }
         }
       }
     }
     container multichunk-inspection {
       description "Configure for SCTP multi chunks inspection";
       uses apply-advanced;
       choice multichunk-flag {
         case case_1 {
           leaf disable {
             description "Set multichunk inspection flag to disable";
             type empty;
           }
         }
       }
     }
     container nullpdu {
       description "Configure for SCTP NULLPDU protocol value";
       uses apply-advanced;
       container protocol {
         description "SCTP NULLPDU payload protocol identifier";
         uses apply-advanced;
         choice nullpdu-protocol {
           case case_1 {
             leaf ID-0x0000 {
               description "Set 0x0000 to be NULLPDU ID value";
               type empty;
             }
           }
           case case_2 {
             leaf ID-0xFFFF {
               description "Set 0xFFFF to be NULLPDU ID value";
               type empty;
             }
           }
         }
       }
     }
     list log {
       key name;
       ordered-by user;
       description "GPRS stream control transmission protocol logs";
       leaf name {
         type enumeration {
           enum "configuration" {
             description "Log CLI configuration";
           }
           enum "rate-limit" {
             description "Log exceeding rate limits";
           }
           enum "association" {
             description "Log association event";
           }
           enum "data-message-drop" {
             description "Log the drop of SCTP data message";
           }
           enum "control-message-drop" {
             description "Log the drop of SCTP control message";
           }
           enum "control-message-all" {
             description "Log SCTP control message both drop and pass";
           }
         }
       }
     }
     container traceoptions {
       description "Trace options for GPRS stream control transmission protocol";
       uses apply-advanced;
       leaf no-remote-trace {
         description "Disable remote tracing";
         junos:must "(\"system tracing\")";
         junos:must-message "'no-remote-trace' is valid only when [system tracing] is configured";
         type empty;
       }
       container file {
         description "Trace file information";
         leaf filename {
           description "Name of file in which to write trace information";
           type string {
             length "1 .. 1024";
             junos:posix-pattern "![/ %]";
             junos:pattern-message "Must not contain '/', % or a space";
           }
         }
         leaf size {
           description "Maximum trace file size";
           type string;
         }
         leaf files {
           description "Maximum number of trace files";
           default "3";
           type union {
             type string {
               pattern "<.*>|$.*";
             }
             type uint32 {
               range "2 .. 1000";
             }
           }
         }
         choice world-readable-choice {
           leaf world-readable {
             description "Allow any user to read the log file";
             type empty;
           }
           leaf no-world-readable {
             description "Don't allow any user to read the log file";
             type empty;
           }
         }
         leaf match {
           description "Regular expression for lines to be logged";
           type jt:regular-expression;
         }
       }
       list flag {
         key name;
         ordered-by user;
         description "Tracing parameters";
         leaf name {
           type enumeration {
             enum "configuration" {
               description "Trace configuration events";
             }
             enum "detail" {
               description "Trace detail events";
             }
             enum "flow" {
               description "Trace flow events";
             }
             enum "parser" {
               description "Trace parser events";
             }
             enum "chassis-cluster" {
               description "Trace chassis cluster events";
             }
             enum "all" {
               description "Trace everything";
             }
           }
         }
       }
     }
   }
   grouping secintel-category-disable {
     description "Security intelligence category";
     leaf name {
       description "Name of security intelligence category";
       type enumeration {
         enum "IPFilter" {
           description "IPFilter";
         }
         enum "GeoIP" {
           description "GeoIP";
         }
         enum "CC" {
           description "Command and control";
         }
         enum "Blacklist" {
           description "Blacklist";
         }
         enum "Whitelist" {
           description "Whitelist";
         }
         enum "Infected-Hosts" {
           description "Infected-Hosts";
         }
         enum "SecProfiling" {
           description "SecProfiling";
         }
         enum "DNS" {
           description "DNS";
         }
       }
     }
     uses apply-advanced;
     container disable {
       presence "enable disable";
       description "To disable category for feed update";
     }
   }
   grouping secintel-policy-setting {
     description "Security intelligence policy setting";
     leaf name {
       description "Security intelligence policy name";
       type string {
         length "1 .. 63";
       }
     }
     uses apply-advanced;
     leaf description {
       description "Text description of policy";
       type string {
         length "1 .. 900";
         junos:posix-pattern "^[^&<>\n]+$";
         junos:pattern-message "Must be a string excluding '&', '<', '>' and '\n'";
       }
     }
     list category-profiles {
       key name;
       ordered-by user;
       description "Security intelligence category profiles";
       leaf name {
         description "Name of security intelligence category";
         type enumeration {
           enum "IPFilter" {
             description "IPFilter";
           }
           enum "GeoIP" {
             description "GeoIP";
           }
           enum "CC" {
             description "Command and control";
           }
           enum "Infected-Hosts" {
             description "Infected-Hosts";
           }
           enum "DNS" {
             description "DNS";
           }
         }
       }
       uses apply-advanced;
       leaf profile-name {
         description "Name of profile";
         junos:must "(\"services security-intelligence profile $$\")";
         junos:must-message "security intelligence profile must be defined";
         type string;
       }
     }
   }
   grouping secintel-profile-setting {
     description "Security intelligence profile settings";
     leaf name {
       description "Security intelligence profile name";
       type string {
         length "1 .. 63";
       }
     }
     uses apply-advanced;
     leaf description {
       description "Text description of profile";
       type string {
         length "1 .. 900";
         junos:posix-pattern "^[^&<>\n]+$";
         junos:pattern-message "Must be a string excluding '&', '<', '>' and '\n'";
       }
     }
     leaf category {
       description "Profile category name";
       type string;
     }
     list rule {
       key name;
       ordered-by user;
       description "Profile rule name";
       uses secintel-profile-rule;
     }
     container default-rule {
       presence "enable default-rule";
       description "Profile default rule";
       uses apply-advanced;
       container then {
         presence "enable then";
         description "Profile default rule action";
         uses apply-advanced;
         container action {
           description "Security intelligence profile action";
           uses apply-advanced;
           choice action {
             case case_1 {
               leaf permit {
                 description "Permit action";
                 type empty;
               }
             }
             case case_2 {
               container block {
                 description "Block action";
                 uses apply-advanced;
                 choice action {
                   case case_1 {
                     container drop {
                       presence "enable drop";
                       description "Drop packet";
                     }
                   }
                   case case_2 {
                     container close {
                       presence "enable close";
                       junos:must "(!(\".. .. .. .. .. category DNS\"))";
                       junos:must-message "close action not available on DNS profiles";
                       description "Close session";
                       uses apply-advanced;
                       container http {
                         description "Http content for block action";
                         uses apply-advanced;
                         choice http-choice {
                           case case_1 {
                             leaf file {
                               description "File name for http response to client";
                               type string;
                             }
                           }
                           case case_2 {
                             leaf message {
                               description "Block message to client";
                               type string;
                             }
                           }
                           case case_3 {
                             leaf redirect-url {
                               description "Redirect url to client";
                               type string {
                                 length "1 .. 1023";
                                 junos:posix-pattern "^https?://.*";
                                 junos:pattern-message "URL must begin with http:// or https://";
                               }
                             }
                           }
                         }
                       }
                     }
                   }
                 }
               }
             }
             case case_3 {
               container recommended {
                 presence "enable recommended";
                 junos:must "(!(\".. .. .. .. category DNS\"))";
                 junos:must-message "recommend action not available on DNS profiles";
                 description "Recommended action from feed server";
               }
             }
             case case_4 {
               leaf sinkhole {
                 description "DNS sinkhole for DNS profile";
                 junos:must "(\".. .. .. .. category DNS\")";
                 junos:must-message "Sinkhole action requires DNS category profile";
                 type empty;
               }
             }
           }
         }
         choice log-choice {
           leaf log {
             description "Log security intelligence block action";
             type empty;
           }
           leaf no-log {
             description "Don't log security intelligence block action";
             type empty;
           }
         }
       }
     }
   }
   grouping secintel-profile-rule {
     description "Security intelligence profile rule";
     leaf name {
       description "Profile rule name";
       type string {
         length "1 .. 63";
       }
     }
     uses apply-advanced;
     container match {
       description "Profile matching feed name and threat levels";
       uses apply-advanced;
       list feed-name {
         key name;
         ordered-by user;
         description "Profile matching feed name";
         max-elements 32;
         leaf name {
           type string {
             length "1 .. 63";
             junos:posix-pattern "^[^/;:|=,+*?&<>{}]*$";
             junos:pattern-message "Must not be double quotation marks and other special characters as / ; : | = , + * ? & < > { }";
           }
         }
         uses apply-advanced;
       }
       leaf-list threat-level {
         ordered-by user;
         description "Profile matching threat levels, higher number is more severe";
         type union {
           type uint32;
           type string {
             pattern "<.*>|$.*";
           }
         }
       }
     }
     container then {
       description "Profile action and log";
       uses apply-advanced;
       container action {
         description "Security intelligence profile action";
         uses apply-advanced;
         choice action {
           case case_1 {
             leaf permit {
               description "Permit action";
               type empty;
             }
           }
           case case_2 {
             container block {
               description "Block action";
               uses apply-advanced;
               choice action {
                 case case_1 {
                   container drop {
                     presence "enable drop";
                     description "Drop packet";
                   }
                 }
                 case case_2 {
                   container close {
                     presence "enable close";
                     junos:must "(!(\".. .. .. .. .. category DNS\"))";
                     junos:must-message "close action not available on DNS profiles";
                     description "Close session";
                     uses apply-advanced;
                     container http {
                       description "Http content for block action";
                       uses apply-advanced;
                       choice http-choice {
                         case case_1 {
                           leaf file {
                             description "File name for http response to client";
                             type string;
                           }
                         }
                         case case_2 {
                           leaf message {
                             description "Block message to client";
                             type string;
                           }
                         }
                         case case_3 {
                           leaf redirect-url {
                             description "Redirect url to client";
                             type string {
                               length "1 .. 1023";
                               junos:posix-pattern "^https?://.*";
                               junos:pattern-message "URL must begin with http:// or https://";
                             }
                           }
                         }
                       }
                     }
                   }
                 }
               }
             }
           }
           case case_3 {
             container recommended {
               presence "enable recommended";
               junos:must "(!(\".. .. .. .. category DNS\"))";
               junos:must-message "recommend action not available on DNS profiles";
               description "Recommended action from feed server";
             }
           }
           case case_4 {
             leaf sinkhole {
               description "DNS sinkhole for DNS profile";
               junos:must "(\".. .. .. .. category DNS\")";
               junos:must-message "Sinkhole action requires DNS category profile";
               type empty;
             }
           }
         }
       }
       container log {
         presence "enable log";
         description "Log security intelligence block action";
       }
     }
   }
   grouping secintel-traceoptions {
     description "Security intelligence trace options";
     uses apply-advanced;
     leaf no-remote-trace {
       description "Disable remote tracing";
       junos:must "(\"system tracing\")";
       junos:must-message "'no-remote-trace' is valid only when [system tracing] is configured";
       type empty;
     }
     container file {
       description "Trace file information";
       leaf filename {
         description "Name of file in which to write trace information";
         type string {
           length "1 .. 1024";
           junos:posix-pattern "![/ %]";
           junos:pattern-message "Must not contain '/', % or a space";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     leaf level {
       description "Level of debugging output";
       type enumeration {
         enum "error" {
           description "Match error conditions";
         }
         enum "warning" {
           description "Match warning messages";
         }
         enum "notice" {
           description "Match conditions that should be handled specially";
         }
         enum "info" {
           description "Match informational messages";
         }
         enum "verbose" {
           description "Match verbose messages";
         }
         enum "all" {
           description "Match all levels";
         }
       }
     }
     list flag {
       key name;
       ordered-by user;
       description "Trace flags";
       leaf name {
         type enumeration {
           enum "all" {
             description "Trace everything";
           }
           enum "feed" {
             description "Trace feed operation";
           }
           enum "ipc" {
             description "Trace ipc module";
           }
           enum "blacklist" {
             description "Trace security intelligence Blacklist category";
           }
           enum "cc" {
             description "Trace security intelligence CC category";
           }
           enum "infected-hosts" {
             description "Trace security intelligence Infected-Hosts category";
           }
           enum "control" {
             description "Trace control plane";
           }
           enum "infrastucture" {
             description "Trace infrastucture functions";
           }
           enum "jwas" {
             description "Trace security intelligence JWAS category";
           }
           enum "plugin" {
             description "Trace security intelligence plugin services";
           }
           enum "whitelist" {
             description "Trace security intelligence Whitelist category";
           }
           enum "secprofiling" {
             description "Trace security intelligence Secprofiling category";
           }
         }
       }
     }
   }
   grouping secure-wire-type {
     description "Secure-wire cross connection";
     leaf name {
       description "Secure-wire name";
       type string {
         length "1 .. 63";
       }
     }
     uses apply-advanced;
     leaf-list interface {
       description "Secure-wire logical interface";
       type union {
         type jt:interface-unit;
         type string {
           pattern "<.*>|$.*";
         }
       }
       max-elements 2;
     }
   }
   grouping security-authentication-key-chains {
     uses apply-advanced;
     list key-chain {
       key name;
       description "Key chain configuration";
       leaf name {
         description "Name of authentication key chain";
         type string {
           junos:posix-pattern "!^((__.*__)|(.*[ ].*)|(.{33,}))$";
           junos:pattern-message "Must be string of 32 characters or less with no spaces";
         }
       }
       uses apply-advanced;
       leaf description {
         description "Text description of this authentication-key-chain";
         type string {
           length "1 .. 80";
         }
       }
       leaf tolerance {
         description "Clock skew tolerance";
         default "3600";
         units "seconds";
         type union {
           type string {
             pattern "<.*>|$.*";
           }
           type uint32 {
             range "0 .. 4294967295";
           }
         }
       }
       list key {
         key name;
         description "Authentication element configuration";
         leaf name {
           description "Authentication element identifier";
           type union {
             type string {
               pattern "<.*>|$.*";
             }
             type uint32 {
               range "0 .. 63";
             }
           }
         }
         uses apply-advanced;
         leaf secret {
           description "Authentication key";
           type string {
             length "1 .. 126";
           }
         }
         leaf key-name {
           description "Key name in hexadecimal format used for macsec";
           type string {
             length "2 .. 64";
             junos:posix-pattern "^([0-9a-fA-F][0-9a-fA-F]){1,32}$";
             junos:pattern-message "Must be an even-length string up to 64 hexadecimal digits (0-9, a-f, A-F)";
           }
         }
         leaf start-time {
           description "Start time for key transmission (YYYY-MM-DD.HH:MM)";
           type jt:time;
         }
         leaf algorithm {
           description "Authentication algorithm";
           default "md5";
           type enumeration {
             enum "md5" {
               description "Message Digest 5";
             }
             enum "hmac-sha-1" {
               description "Hash-based Message Authentication Code (SHA1) (96 bits)";
               junos:must "(\".. options isis-enhanced\")";
               junos:must-message "sha algorithm required isis-enhanced";
             }
             enum "ao" {
               description "TCP Authentication Option";
             }
           }
         }
         leaf options {
           description "Protocol's transmission encoding format";
           default "basic";
           type enumeration {
             enum "basic" {
               description "Rudimentary encoding format";
             }
             enum "isis-enhanced" {
               description "RFC 5310 based encoding";
             }
           }
         }
         container ao-attribute {
           junos:must "(!(\".. authentication-key\"))";
           junos:must-message "Cannot be configured with authentication-key";
           junos:must "(\".. algorithm ao\")";
           junos:must-message "Can only be configured with authentication-algorithm ao";
           description "TCP Authentication option attributes";
           uses apply-advanced;
           leaf send-id {
             description "Send id for TCP-AO entry";
             type union {
               type string {
                 pattern "<.*>|$.*";
               }
               type uint32 {
                 range "0 .. 255";
               }
             }
           }
           leaf recv-id {
             description "Recv id for TCP-AO entry";
             type union {
               type string {
                 pattern "<.*>|$.*";
               }
               type uint32 {
                 range "0 .. 255";
               }
             }
           }
           leaf tcp-ao-option {
             description "Include TCP-AO option within message header";
             default "disabled";
             type enumeration {
               enum "enabled" {
                 description "Include the TCP-AO option";
               }
               enum "disabled" {
                 description "Not include the TCP-AO option";
               }
             }
           }
           leaf cryptographic-algorithm {
             description "Cryptographic algorithm for TCP-AO Traffic key and MAC digest generation";
             default "hmac-sha-1-96";
             type enumeration {
               enum "hmac-sha-1-96" {
                 description "Hash-based Message Authentication Code (SHA1) (96 bits)";
               }
               enum "aes-128-cmac-96" {
                 description "Cipher-based Message Authentication Code (AES128) (96 bits)";
               }
             }
           }
         }
       }
     }
   }
   grouping security-dhcpv6-options-type {
     description "Configure DHCPv6 options";
     uses apply-advanced;
     container option-37 {
       presence "enable option-37";
       description "Configure DHCPv6 remote identifier option";
       uses apply-advanced;
       container prefix {
         description "Configure DHCPv6 remote identifier prefix";
         uses apply-advanced;
         leaf host-name {
           description "Prefix router host name to DHCPv6 remote identifier";
           type empty;
         }
         leaf logical-system-name {
           description "Prefix logical system name to DHCPv6 remote identifier";
           type empty;
         }
         leaf routing-instance-name {
           description "Prefix routing instance name to DHCPv6 remote identifier";
           type empty;
         }
         leaf vlan-name {
           description "Prefix vlan name to DHCPv6 remote identifier";
           type empty;
         }
         leaf vlan-id {
           description "Prefix vlan tag to DHCPv6 remote identifier";
           type empty;
         }
       }
       leaf use-interface-mac {
         description "Add incoming interface's MAC address to DHCPv6 remote identifier";
         type empty;
       }
       leaf use-interface-index {
         description "Add interface index to DHCPv6 remote identifier";
         type enumeration {
           enum "logical" {
             description "Use the logical interface index";
           }
           enum "device" {
             description "Use the device interface index";
           }
         }
       }
       leaf use-interface-name {
         description "Add interface name to DHCPv6 remote identifier";
         type enumeration {
           enum "logical" {
             description "Use the logical interface name";
           }
           enum "device" {
             description "Use the device interface name";
           }
         }
       }
       leaf use-interface-description {
         description "Add interface description to DHCPv6 remote identifier";
         type enumeration {
           enum "logical" {
             description "Use the logical interface description";
           }
           enum "device" {
             description "Use the device interface description";
           }
         }
       }
       leaf use-string {
         description "Add custom string to DHCPv6 remote identifier";
         junos:must "(!(\".. use-interface-description\"))";
         junos:must-message "use-string and use-interface-description cannot be configured together";
         type string;
       }
     }
     container option-18 {
       presence "enable option-18";
       description "Configure DHCPv6 interface identifier option";
       uses apply-advanced;
       container prefix {
         description "Configure DHCPv6 interface identifier prefix";
         uses apply-advanced;
         leaf host-name {
           description "Prefix router host name to DHCPv6 interface identifier";
           type empty;
         }
         leaf logical-system-name {
           description "Prefix logical system name to DHCPv6 interface identifier";
           type empty;
         }
         leaf routing-instance-name {
           description "Prefix routing instance name to DHCPv6 interface identifier";
           type empty;
         }
         leaf vlan-name {
           description "Prefix vlan name to DHCPv6 interface identifier";
           type empty;
         }
         leaf vlan-id {
           description "Prefix vlan tag to DHCPv6 interface identifier";
           type empty;
         }
       }
       leaf use-interface-mac {
         description "Add incoming interface's MAC address to DHCPv6 circuit identifier";
         type empty;
       }
       leaf use-interface-index {
         description "Add interface index to DHCPv6 interface identifier";
         type enumeration {
           enum "logical" {
             description "Use the logical interface index";
           }
           enum "device" {
             description "Use the device interface index";
           }
         }
       }
       leaf use-interface-name {
         description "Add interface name to DHCPv6 remote identifier";
         type enumeration {
           enum "logical" {
             description "Use the logical interface name";
           }
           enum "device" {
             description "Use the device interface name";
           }
         }
       }
       leaf use-interface-description {
         description "Add interface description to DHCPv6 interface identifier";
         type enumeration {
           enum "logical" {
             description "Use the logical interface description";
           }
           enum "device" {
             description "Use the device interface description";
           }
         }
       }
       leaf use-string {
         description "Add custom string to DHCPv6 interface identifier";
         junos:must "(!(\".. use-interface-description\"))";
         junos:must-message "use-string and use-interface-description cannot be configured together";
         type string;
       }
     }
     container option-16 {
       presence "enable option-16";
       description "Configure DHCPv6 vendor class identifier option. Overwrite if exists";
       uses apply-advanced;
       leaf use-string {
         description "Add custom string to DHCPv6 vendor identifier";
         type string;
       }
     }
     leaf option-79 {
       description "Configure DHCPv6 client link layer address option";
       junos:must "(\".. .. light-weight-dhcpv6-relay\")";
       junos:must-message "Option-79 can be configured only on LDRAs";
       type empty;
     }
   }
   grouping security-distribution-profile {
     leaf name {
       description "Name of the distribution profile";
       type string {
         length "1 .. 32";
       }
     }
     uses apply-advanced;
     leaf description {
       description "Text description of Distribution Profile";
       type string {
         length "1 .. 80";
       }
     }
     list fpc {
       key name;
       description "Flexible PIC Concentrator parameters";
       uses fpc_type;
     }
   }
   grouping fpc_type {
     leaf name {
       description "FPC slot number";
       type union {
         type string {
           pattern "<.*>|$.*";
         }
         type uint32;
       }
     }
     uses apply-advanced;
     list pic {
       key name;
       description "Physical Interface Card number";
       uses pic_type;
     }
   }
   grouping pic_type {
     leaf name {
       description "PIC slot number";
       type union {
         type string {
           pattern "<.*>|$.*";
         }
         type uint32;
       }
     }
     uses apply-advanced;
     leaf-list thread-id {
       description "Thread-id";
       type union {
         type string {
           pattern "<.*>|$.*";
         }
         type uint32 {
           range "1 .. 27";
         }
       }
     }
   }
   grouping security-group-vpn {
     uses apply-advanced;
     container member {
       description "Group VPN member configuration";
       junos:must "(!(\".. server\"))";
       junos:must-message "Configuring both group-vpn server and group-vpn member is not supported";
       uses gvpn-member;
     }
     container server {
       description "Group VPN server configuration";
       junos:must "(!(\".. member\"))";
       junos:must-message "Configuring both group-vpn server and group-vpn member is not supported";
       uses gvpn-server;
     }
   }
   grouping gvpn-member {
     uses apply-advanced;
     container ike {
       description "Group VPN IKE configuration";
       uses gvpn-member-ike;
     }
     container ipsec {
       description "Group VPN IPsec configuration";
       uses gvpn-member-ipsec-vpn;
     }
   }
   grouping gvpn-member-ike {
     uses apply-advanced;
     container traceoptions {
       description "Trace options for Group VPN Member";
       uses apply-advanced;
       leaf no-remote-trace {
         description "Disable remote tracing";
         junos:must "(\"system tracing\")";
         junos:must-message "'no-remote-trace' is valid only when [system tracing] is configured";
         type empty;
       }
       container file {
         description "Trace file information";
         leaf filename {
           description "Name of file in which to write trace information";
           type string {
             length "1 .. 1024";
             junos:posix-pattern "![/ %]";
             junos:pattern-message "Must not contain '/', % or a space";
           }
         }
         leaf size {
           description "Maximum trace file size";
           type string;
         }
         leaf files {
           description "Maximum number of trace files";
           default "3";
           type union {
             type string {
               pattern "<.*>|$.*";
             }
             type uint32 {
               range "2 .. 1000";
             }
           }
         }
         choice world-readable-choice {
           leaf world-readable {
             description "Allow any user to read the log file";
             type empty;
           }
           leaf no-world-readable {
             description "Don't allow any user to read the log file";
             type empty;
           }
         }
         leaf match {
           description "Regular expression for lines to be logged";
           type jt:regular-expression;
         }
       }
       leaf level {
         description "Level of debugging output";
         default "error";
         type enumeration {
           enum "error" {
             description "Match error conditions";
           }
           enum "warning" {
             description "Match warning messages";
           }
           enum "notice" {
             description "Match conditions that should be handled specially";
           }
           enum "info" {
             description "Match informational messages";
           }
           enum "verbose" {
             description "Match verbose messages";
           }
           enum "all" {
             description "Match all levels";
           }
         }
       }
       list flag {
         key name;
         ordered-by user;
         description "Tracing parameters";
         leaf name {
           type enumeration {
             enum "timer" {
               description "Trace internal timer events";
             }
             enum "routing-socket" {
               description "Trace routing socket messages";
             }
             enum "parse" {
               description "Trace configuration processing";
             }
             enum "config" {
               description "Trace configuration download processing";
             }
             enum "ike" {
               description "Trace IKE module processing";
             }
             enum "policy-manager" {
               description "Trace policy manager processing";
             }
             enum "general" {
               description "Trace general events";
             }
             enum "database" {
               description "Trace security associations database events";
             }
             enum "certificates" {
               description "Trace certificate events";
             }
             enum "snmp" {
               description "Trace SNMP operations";
             }
             enum "thread" {
               description "Trace thread processing";
             }
             enum "high-availability" {
               description "Trace high-availability operations";
             }
             enum "next-hop-tunnels" {
               description "Trace next-hop-tunnels operations";
             }
             enum "all" {
               description "Trace everything";
             }
           }
         }
       }
       container gateway-filter {
         description "Set gateway filter for trace";
         uses apply-advanced;
         leaf local-address {
           description "Use an IP address to identify the local gateway";
           type jt:ipv4addr;
         }
         leaf remote-address {
           description "Use an IP address to identify the remote gateway";
           type jt:ipv4addr;
         }
       }
     }
     list proposal {
       key name;
       ordered-by user;
       description "Define an IKE proposal";
       uses gvpn-member-ike-proposal;
     }
     list policy {
       key name;
       ordered-by user;
       description "Define an IKE policy";
       uses gvpn-ike-policy;
     }
     list gateway {
       key name;
       ordered-by user;
       description "Define an IKE gateway";
       leaf name {
         description "Label for the remote (peer) gateway";
         junos:must "(!(\"security ike gateway $$\"))";
         junos:must-message "Gateway already defined under [security ike]";
         type string {
           length "1 .. 32";
         }
       }
       uses apply-advanced;
       leaf ike-policy {
         description "Name of the IKE policy";
         junos:must "(\"security group-vpn member ike policy $$\")";
         junos:must-message "Referenced IKE policy must be defined under [edit security group-vpn member ike policy]";
         type string {
           length "1 .. 32";
         }
       }
       leaf-list server-address {
         ordered-by user;
         description "Server Addresses upto 4";
         type jt:ipv4addr;
         max-elements 4;
       }
       container local-identity {
         description "Set the local IKE identity";
         choice identity-type {
           case case_1 {
             container inet {
               description "Use an IPv4 address";
               uses apply-advanced;
               leaf identity-ipv4 {
                 description "The local IPv4 identity";
                 type jt:ipv4addr;
               }
             }
           }
           case case_2 {
             container hostname {
               description "Use a fully-qualified domain name";
               uses apply-advanced;
               leaf identity-hostname {
                 description "The local hostname";
                 type string;
               }
             }
           }
           case case_3 {
             container user-at-hostname {
               description "Use an e-mail address";
               uses apply-advanced;
               leaf identity-user {
                 description "The local user-FQDN";
                 type string;
               }
             }
           }
         }
       }
       container remote-identity {
         description "Set the remote IKE identity";
         choice identity-type {
           case case_1 {
             container inet {
               description "Use an IPv4 address";
               uses apply-advanced;
               leaf identity-ipv4 {
                 description "The remote IPv4 identity";
                 type jt:ipv4addr;
               }
             }
           }
           case case_2 {
             container hostname {
               description "Use a fully-qualified domain name";
               uses apply-advanced;
               leaf identity-hostname {
                 description "The remote hostname";
                 type string;
               }
             }
           }
           case case_3 {
             container user-at-hostname {
               description "Use an e-mail address";
               uses apply-advanced;
               leaf identity-user {
                 description "The remote user-FQDN";
                 type string;
               }
             }
           }
         }
       }
       leaf local-address {
         description "Local IPv4 address for group member";
         junos:must "(!(any \"security group-vpn member ike gateway <*> server-address $$\"))";
         junos:must-message "Member can not have the same local address as server";
         type jt:ipv4addr;
       }
       leaf routing-instance {
         description "Name of routing instance that hosts local address";
         default "default";
         junos:must "(\"routing-instances $$\")";
         junos:must-message "Referenced routing-instance must be defined";
         type string;
       }
     }
   }
   grouping gvpn-ike-policy {
     leaf name {
       description "Name of policy";
       junos:must "((\".. proposals\" || \".. proposal-set\"))";
       junos:must-message "IKE policy must have either proposals or proposal-set configured";
       junos:must "(((\".. certificate local-certificate\" || \".. pre-shared-key\") && !((\".. certificate local-certificate\" && \".. pre-shared-key\"))))";
       junos:must-message "IKE policy must have either local certificate or pre-shared key configured";
       type string {
         length "1 .. 32";
       }
     }
     uses apply-advanced;
     leaf mode {
       description "Define the IKE mode for Phase 1";
       default "main";
       type enumeration {
         enum "main" {
           description "Main mode";
         }
         enum "aggressive" {
           description "Aggressive mode";
         }
       }
     }
     leaf description {
       description "Text description of IKE policy";
       type string {
         length "1 .. 80";
       }
     }
     leaf-list proposals {
       ordered-by user;
       description "Name of the proposal";
       junos:must "(\".. .. .. proposal $$\")";
       junos:must-message "Referenced proposal is not defined";
       type string {
         length "1 .. 32";
         junos:posix-pattern "^[[:alnum:]][[:alnum:]_-]*$";
         junos:pattern-message "Must be a string beginning with a number or letter and consisting of letters, numbers, dashes and underscores.";
       }
     }
     container pre-shared-key {
       description "Define a preshared key";
       choice key-choice {
         case case_1 {
           leaf ascii-text {
             description "Format as text";
             type string {
               length "1 .. 255";
             }
           }
         }
         case case_2 {
           leaf hexadecimal {
             description "Format as hexadecimal";
             type string {
               length "1 .. 255";
               junos:posix-pattern "^[[:xdigit:]]+$";
               junos:pattern-message "Must be hexadecimal digits (0-9, a-f, A-F)";
             }
           }
         }
       }
     }
   }
   grouping gvpn-member-ike-proposal {
     leaf name {
       description "Name of the IKE proposal";
       type string {
         length "1 .. 32";
       }
     }
     uses apply-advanced;
     leaf description {
       description "Text description of IKE proposal";
       type string {
         length "1 .. 80";
       }
     }
     leaf authentication-method {
       description "Define authentication method";
       type enumeration {
         enum "pre-shared-keys" {
           description "Preshared keys";
         }
       }
     }
     leaf dh-group {
       description "Define Diffie-Hellman group";
       type enumeration {
         enum "group14" {
           description "Diffie-Hellman Group 14";
         }
         enum "group24" {
           description "Diffie-Hellman Group 24";
         }
       }
     }
     leaf authentication-algorithm {
       description "Define authentication algorithm";
       type enumeration {
         enum "sha-256" {
           description "SHA 256-bit authentication algorithm";
         }
         enum "sha-384" {
           description "SHA 384-bit authentication algorithm";
         }
       }
     }
     leaf encryption-algorithm {
       description "Define encryption algorithm";
       type enumeration {
         enum "aes-128-cbc" {
           description "AES-CBC 128-bit encryption algorithm";
         }
         enum "aes-192-cbc" {
           description "AES-CBC 192-bit encryption algorithm";
         }
         enum "aes-256-cbc" {
           description "AES-CBC 256-bit encryption algorithm";
         }
       }
     }
     leaf lifetime-seconds {
       description "Lifetime, in seconds";
       default "180";
       units "seconds";
       type union {
         type string {
           pattern "<.*>|$.*";
         }
         type uint32 {
           range "180 .. 86400";
         }
       }
     }
   }
   grouping gvpn-member-ipsec-vpn {
     uses apply-advanced;
     list vpn {
       key name;
       ordered-by user;
       description "Define an IPSec VPN";
       uses ipsec-gvpn-member-template;
     }
   }
   grouping gvpn-server {
     uses apply-advanced;
     container traceoptions {
       description "Trace options for Group VPN debug";
       uses gvpn-server-traceoptions;
     }
     container ike {
       description "Group VPN IKE configuration";
       uses gvpn-server-ike;
     }
     container ipsec {
       description "Group VPN IPsec configuration";
       uses gvpn-server-ipsec-vpn;
     }
     list group {
       key name;
       ordered-by user;
       description "Define a Group VPN group";
       max-elements 50;
       uses gvpn-server-group-template;
     }
   }
   grouping gvpn-server-group-template {
     description "Configure a Group VPN group";
     leaf name {
       description "Name of the group";
       type string {
         length "1 .. 32";
       }
     }
     uses apply-advanced;
     leaf description {
       description "Text description of Group VPN group";
       type string {
         length "1 .. 80";
       }
     }
     leaf group-id {
       description "Enable Group VPN by defining group id";
       junos:must "((\".. no-group-check\" || unique \"security group-vpn server group <*> group-id $$\"))";
       junos:must-message "Group id must be unique among groups";
       type union {
         type string {
           pattern "<.*>|$.*";
         }
         type uint32 {
           range "1 .. 4294967295";
         }
       }
     }
     leaf member-threshold {
       description "Maximum number of members in this group";
       type union {
         type uint32;
         type string {
           pattern "<.*>|$.*";
         }
       }
     }
     container server-cluster {
       description "Enable server cluster for this group";
       uses gvpn-server-cluster;
     }
     list ike-gateway {
       key name;
       ordered-by user;
       description "Name of the IKE gateway";
       uses gvpn-server-ike-gateway;
     }
     leaf activation-time-delay {
       description "Configure delay in seconds for Group VPN key activation";
       status deprecated;
       default "15";
       type union {
         type string {
           pattern "<.*>|$.*";
         }
         type uint32 {
           range "10 .. 900";
         }
       }
     }
     leaf anti-replay-time-window {
       description "Configure Anti Replay time in milliseconds";
       type union {
         type string {
           pattern "<.*>|$.*";
         }
         type uint32 {
           range "1 .. 60000";
         }
       }
     }
     container server-member-communication {
       description "Configure Server to Member communication parameters";
       uses gvpn-server-member-communication;
     }
     list ipsec-sa {
       key name;
       ordered-by user;
       description "Define a Group VPN group SA";
       uses gvpn-server-group-ipsecsa;
     }
   }
   grouping gvpn-server-cluster {
     description "Server-Cluster for group VPN";
     uses apply-advanced;
     leaf server-role {
       description "Primary or backup server";
       type enumeration {
         enum "root-server" {
           description "Root-server";
         }
         enum "sub-server" {
           description "Sub-server";
         }
       }
     }
     list ike-gateway {
       key name;
       ordered-by user;
       description "Name of the IKE gateway";
       uses gvpn-server-ike-gateway-sc;
     }
     leaf retransmission-period {
       description "Configure retransmission period in seconds Default :10";
       default "10";
       type union {
         type string {
           pattern "<.*>|$.*";
         }
         type uint32 {
           range "2 .. 60";
         }
       }
     }
   }
   grouping gvpn-server-group-ipsecsa {
     description "Configure a Group VPN group SA";
     leaf name {
       description "Name of the SA";
       type string {
         length "1 .. 32";
       }
     }
     uses apply-advanced;
     leaf proposal {
       description "Name of the IPsec proposal";
       junos:must "(\"security group-vpn server ipsec proposal $$\")";
       junos:must-message "Referenced proposal is not defined";
       type string {
         length "1 .. 32";
       }
     }
     list match-policy {
       key name;
       ordered-by user;
       description "Configure a Group VPN group SA";
       max-elements 10;
       uses gvpn-server-group-ipsecsa-match;
     }
   }
   grouping gvpn-server-group-ipsecsa-match {
     description "Configure a Group VPN group SA policy";
     leaf name {
       description "Name of the policy";
       type string {
         length "1 .. 32";
       }
     }
     uses apply-advanced;
     leaf source {
       description "Specify the source IP address to be matched (0.0.0.0/0 for any)";
       type jt:ipv4prefix-mandatory;
     }
     leaf destination {
       description "Specify the destination IP address to be matched (0.0.0.0/0 for any)";
       type jt:ipv4prefix-mandatory;
     }
     leaf source-port {
       description "Specify the source port to be matched (0 for any)";
       type union {
         type string {
           pattern "<.*>|$.*";
         }
         type uint32 {
           range "0 .. 65535";
         }
       }
     }
     leaf destination-port {
       description "Specify the destination port to be matched (0 for any)";
       type union {
         type string {
           pattern "<.*>|$.*";
         }
         type uint32 {
           range "0 .. 65535";
         }
       }
     }
     leaf protocol {
       description "Specify the protocol number to be matched (0 for any)";
       type union {
         type string {
           pattern "<.*>|$.*";
         }
         type uint32 {
           range "0 .. 254";
         }
       }
     }
   }
   grouping gvpn-server-ike {
     uses apply-advanced;
     list proposal {
       key name;
       ordered-by user;
       description "Define an IKE proposal";
       uses gvpn-server-ike-proposal;
     }
     list policy {
       key name;
       ordered-by user;
       description "Define an IKE policy";
       uses gvpn-ike-policy;
     }
     list gateway {
       key name;
       ordered-by user;
       description "Define an IKE gateway";
       leaf name {
         description "Label for the remote (peer) gateway";
         type string {
           length "1 .. 32";
         }
       }
       uses apply-advanced;
       leaf ike-policy {
         description "Name of the IKE policy";
         junos:must "(!((\"security group-vpn server ike policy $$ mode main\" && (\"security group-vpn server ike policy $$ pre-shared-key\" && \".. dynamic\"))))";
         junos:must-message "Main mode for dynamic peer with Preshared key based authentication is not allowed";
         junos:must "(\"security group-vpn server ike policy $$\")";
         junos:must-message "Referenced IKE policy must be defined under [edit security group-vpn server ike policy]";
         type string {
           length "1 .. 32";
         }
       }
       choice remote-identifier {
         case case_1 {
           leaf address {
             description "IP address of peer";
             type string {
               length "1 .. 32";
             }
           }
         }
         case case_2 {
           container dynamic {
             description "Site to site peer with dynamic IP address";
             uses apply-advanced;
             choice remote-id-type {
               case case_1 {
                 leaf hostname {
                   description "Use a fully-qualified domain name";
                   type string;
                 }
               }
               case case_2 {
                 leaf inet {
                   description "Use an IPV4 address to identify the dynamic peer";
                   type jt:ipv4addr;
                 }
               }
               case case_3 {
                 leaf user-at-hostname {
                   description "Use an e-mail address";
                   type string;
                 }
               }
             }
           }
         }
       }
       container dead-peer-detection {
         presence "enable dead-peer-detection";
         description "Enable Dead Peer Detection between group-server-cluster servers";
         uses apply-advanced;
         choice mode {
           case case_1 {
             leaf always-send {
               description "Send probes periodically regardless of incoming and outgoing data traffic ";
               type empty;
             }
           }
         }
         leaf interval {
           description "The time between DPD probe messages  Default :10";
           default "10";
           units "seconds";
           type union {
             type string {
               pattern "<.*>|$.*";
             }
             type uint32 {
               range "10 .. 60";
             }
           }
         }
         leaf threshold {
           description "Maximum number of DPD retransmissions Default :5";
           default "5";
           type union {
             type string {
               pattern "<.*>|$.*";
             }
             type uint32 {
               range "1 .. 5";
             }
           }
         }
       }
       container local-identity {
         description "Set the local IKE identity";
         choice identity-type {
           case case_1 {
             container inet {
               description "Use an IPv4 address";
               uses apply-advanced;
               leaf identity-ipv4 {
                 description "The local IPv4 identity";
                 type jt:ipv4addr;
               }
             }
           }
           case case_2 {
             container hostname {
               description "Use a fully-qualified domain name";
               uses apply-advanced;
               leaf identity-hostname {
                 description "The local hostname";
                 type string;
               }
             }
           }
           case case_3 {
             container user-at-hostname {
               description "Use an e-mail address";
               uses apply-advanced;
               leaf identity-user {
                 description "The local user-FQDN";
                 type string;
               }
             }
           }
         }
       }
       container remote-identity {
         junos:must "(!(\".. dynamic\"))";
         junos:must-message "Since the remote gateway is dynamic, Define remote identity under dynamic";
         description "Set the remote IKE identity";
         choice identity-type {
           case case_1 {
             container inet {
               description "Use an IPv4 address";
               uses apply-advanced;
               leaf identity-ipv4 {
                 description "The remote IPv4 identity";
                 type jt:ipv4addr;
               }
             }
           }
           case case_2 {
             container hostname {
               description "Use a fully-qualified domain name";
               uses apply-advanced;
               leaf identity-hostname {
                 description "The remote hostname";
                 type string;
               }
             }
           }
           case case_3 {
             container user-at-hostname {
               description "Use an e-mail address";
               uses apply-advanced;
               leaf identity-user {
                 description "The remote user-FQDN";
                 type string;
               }
             }
           }
         }
       }
       leaf local-address {
         description "Local IP address for IKE negotiations";
         type jt:ipaddr;
       }
       leaf routing-instance {
         description "Name of routing instance that hosts local address";
         default "default";
         junos:must "(\"routing-instances $$\")";
         junos:must-message "Referenced routing-instance must be defined";
         type string;
       }
     }
   }
   grouping gvpn-server-ike-gateway {
     description "Configure a set of IKE gateways";
     leaf name {
       description "Name of the IKE gateway";
       junos:must "(!(\"security group-vpn server ike gateway $$ dead-peer-detection\"))";
       junos:must-message "Referenced IKE gateway must NOT be defined with dead-peer-detection";
       junos:must "(\"security group-vpn server ike gateway $$\")";
       junos:must-message "Referenced IKE gateway must be defined under [edit security group-vpn server ike gateway]";
       type string {
         length "1 .. 32";
       }
     }
     uses apply-advanced;
   }
   grouping gvpn-server-ike-gateway-sc {
     description "Configure a set of IKE gateways";
     leaf name {
       description "Name of the IKE gateway";
       junos:must "(!(\"security group-vpn server ike gateway $$ dynamic\"))";
       junos:must-message "Referenced IKE gateway must not be dynamic gateway";
       junos:must "(\"security group-vpn server ike gateway $$ dead-peer-detection always-send\")";
       junos:must-message "Referenced IKE gateway must be defined with dead-peer-detection always-send mode";
       type string {
         length "1 .. 32";
       }
     }
     uses apply-advanced;
   }
   grouping gvpn-server-ike-proposal {
     leaf name {
       description "Name of the IKE proposal";
       type string {
         length "1 .. 32";
       }
     }
     uses apply-advanced;
     leaf description {
       description "Text description of IKE proposal";
       type string {
         length "1 .. 80";
       }
     }
     leaf authentication-method {
       description "Define authentication method";
       type enumeration {
         enum "pre-shared-keys" {
           description "Preshared keys";
         }
       }
     }
     leaf authentication-algorithm {
       description "Define authentication algorithm";
       type enumeration {
         enum "sha-256" {
           description "SHA 256-bit authentication algorithm";
         }
         enum "sha-384" {
           description "SHA 384-bit authentication algorithm";
         }
       }
     }
     leaf dh-group {
       description "Define Diffie-Hellman group";
       type enumeration {
         enum "group14" {
           description "Diffie-Hellman Group 14";
         }
         enum "group24" {
           description "Diffie-Hellman Group 24";
         }
       }
     }
     leaf encryption-algorithm {
       description "Define encryption algorithm";
       type enumeration {
         enum "aes-128-cbc" {
           description "AES-CBC 128-bit encryption algorithm";
         }
         enum "aes-192-cbc" {
           description "AES-CBC 192-bit encryption algorithm";
         }
         enum "aes-256-cbc" {
           description "AES-CBC 256-bit encryption algorithm";
         }
       }
     }
   }
   grouping gvpn-server-ipsec-vpn {
     uses apply-advanced;
     list proposal {
       key name;
       ordered-by user;
       description "Define an IPSec proposal";
       uses gvpn-server-ipsec-proposal;
     }
   }
   grouping gvpn-server-ipsec-proposal {
     leaf name {
       description "Name of the IPSec proposal";
       type string {
         length "1 .. 32";
         junos:posix-pattern "^[[:alnum:]][[:alnum:]_-]*$";
         junos:pattern-message "Must be a string beginning with a number or letter and consisting of letters, numbers, dashes and underscores.";
       }
     }
     uses apply-advanced;
     leaf description {
       description "Text description of IPSec proposal";
       type string {
         length "1 .. 80";
       }
     }
     leaf authentication-algorithm {
       description "Define authentication algorithm";
       type enumeration {
         enum "hmac-sha-256-128" {
           description "HMAC-SHA-256-128 authentication algorithm";
         }
       }
     }
     leaf encryption-algorithm {
       description "Define encryption algorithm";
       type enumeration {
         enum "aes-128-cbc" {
           description "AES-CBC 128-bit encryption algorithm";
         }
         enum "aes-192-cbc" {
           description "AES-CBC 192-bit encryption algorithm";
         }
         enum "aes-256-cbc" {
           description "AES-CBC 256-bit encryption algorithm";
         }
       }
     }
     leaf lifetime-seconds {
       description "Lifetime, in seconds";
       units "seconds";
       type union {
         type string {
           pattern "<.*>|$.*";
         }
         type uint32 {
           range "180 .. 86400";
         }
       }
     }
   }
   grouping gvpn-server-member-communication {
     description "Group VPN Server to Member communication";
     uses apply-advanced;
     leaf communication-type {
       description "Define type of server member communication";
       type enumeration {
         enum "unicast" {
           description "Unicast";
         }
       }
     }
     leaf lifetime-seconds {
       description "Configure lifetime in seconds";
       default "3600";
       type union {
         type string {
           pattern "<.*>|$.*";
         }
         type uint32 {
           range "300 .. 86400";
         }
       }
     }
     leaf retransmission-period {
       description "Configure retransmission period in seconds";
       default "10";
       type union {
         type string {
           pattern "<.*>|$.*";
         }
         type uint32 {
           range "2 .. 60";
         }
       }
     }
     leaf number-of-retransmission {
       description "Configure maximum number of retransmission attempts";
       default "2";
       type union {
         type string {
           pattern "<.*>|$.*";
         }
         type uint32 {
           range "0 .. 60";
         }
       }
     }
     leaf heartbeat {
       description "Configure heartbeat period in seconds";
       status deprecated;
       default "300";
       type union {
         type string {
           pattern "<.*>|$.*";
         }
         type uint32 {
           range "60 .. 3600";
         }
       }
     }
     leaf encryption-algorithm {
       description "Define encryption algorithm";
       type enumeration {
         enum "aes-128-cbc" {
           description "AES-CBC 128-bit encryption algorithm";
         }
         enum "aes-192-cbc" {
           description "AES-CBC 192-bit encryption algorithm";
         }
         enum "aes-256-cbc" {
           description "AES-CBC 256-bit encryption algorithm";
         }
       }
     }
     leaf sig-hash-algorithm {
       description "Define sig-hash algorithm";
       type enumeration {
         enum "sha-256" {
           description "SHA 256-bit sig-hash algorithm";
         }
         enum "sha-384" {
           description "SHA 384-bit sig-hash algorithm";
         }
       }
     }
     leaf certificate {
       description "Certificate identifier";
       type string {
         junos:posix-pattern "^.{1,32}$";
         junos:pattern-message "Must be string of 32 characters or less";
       }
     }
   }
   grouping gvpn-server-traceoptions {
     description "Group VPN server tracing options";
     uses apply-advanced;
     leaf no-remote-trace {
       description "Disable remote tracing";
       junos:must "(\"system tracing\")";
       junos:must-message "'no-remote-trace' is valid only when [system tracing] is configured";
       type empty;
     }
     container file {
       description "Trace file information";
       leaf filename {
         description "Name of file in which to write trace information";
         type string {
           length "1 .. 1024";
           junos:posix-pattern "![/ %]";
           junos:pattern-message "Must not contain '/', % or a space";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     leaf level {
       description "Level of debugging output";
       default "error";
       type enumeration {
         enum "error" {
           description "Match error conditions";
         }
         enum "warning" {
           description "Match warning messages";
         }
         enum "notice" {
           description "Match conditions that should be handled specially";
         }
         enum "info" {
           description "Match informational messages";
         }
         enum "verbose" {
           description "Match verbose messages";
         }
         enum "all" {
           description "Match all levels";
         }
       }
     }
     list flag {
       key name;
       ordered-by user;
       description "Tracing parameters for GKSD";
       leaf name {
         type enumeration {
           enum "timer" {
             description "Trace internal timer events";
           }
           enum "routing-socket" {
             description "Trace routing socket messages";
           }
           enum "parse" {
             description "Trace configuration processing";
           }
           enum "config" {
             description "Trace configuration download processing";
           }
           enum "ike" {
             description "Trace IKE module processing";
           }
           enum "policy-manager" {
             description "Trace policy manager processing";
           }
           enum "general" {
             description "Trace general events";
           }
           enum "database" {
             description "Trace security associations database events";
           }
           enum "certificates" {
             description "Trace certificate events";
           }
           enum "snmp" {
             description "Trace SNMP operations";
           }
           enum "thread" {
             description "Trace thread processing";
           }
           enum "high-availability" {
             description "Trace high-availability operations";
           }
           enum "next-hop-tunnels" {
             description "Trace next-hop-tunnels operations";
           }
           enum "all" {
             description "Trace everything";
           }
         }
       }
     }
     container gateway-filter {
       description "Set gateway filter for trace";
       uses apply-advanced;
       leaf local-address {
         description "Use an IPV4 address to identify the local gateway";
         type jt:ipv4addr;
       }
       leaf remote-address {
         description "Use an IPV4 address to identify the remote gateway";
         type jt:ipv4addr;
       }
     }
   }
   grouping ipsec-gvpn-member-template {
     description "Configure a Group VPN";
     leaf name {
       description "Name of the VPN";
       junos:must "(!(\"security ipsec vpn $$\"))";
       junos:must-message "VPN already defined under [security ipsec]";
       type string {
         length "1 .. 32";
       }
     }
     uses apply-advanced;
     leaf ike-gateway {
       description "Name of IKE gateway";
       junos:must "(\"security group-vpn member ike gateway $$\")";
       junos:must-message "Referenced IKE gateway must be defined under [edit security group-vpn member ike gateway]";
       type string {
         length "1 .. 32";
       }
     }
     leaf group-vpn-external-interface {
       description "External interface for Group VPN";
       junos:must "(!(\"interfaces $$ family bridge\"))";
       junos:must-message "Bridge interface is not allowed as external-interface";
       junos:must "(\"interfaces $$-IFL\")";
       junos:must-message "Referenced interface must be configured under [edit interfaces] hierarchy";
       type union {
         type jt:interface-name;
         type string {
           pattern "<.*>|$.*";
         }
       }
     }
     leaf group {
       description "Enable Group VPN by defining group id";
       junos:must "((\".. no-group-check\" || unique \"security group-vpn member ipsec vpn <*> group $$\"))";
       junos:must-message "Group id must be unique among group vpns";
       type union {
         type string {
           pattern "<.*>|$.*";
         }
         type uint32 {
           range "1 .. 4294967295";
         }
       }
     }
     leaf heartbeat-threshold {
       description "Define heartbeat threshold for Group VPN";
       status deprecated;
       default "3";
       type union {
         type string {
           pattern "<.*>|$.*";
         }
         type uint32 {
           range "0 .. 10";
         }
       }
     }
     leaf match-direction {
       description "Direction for which the rule match is applied";
       type enumeration {
         enum "input" {
           description "Match on input to interface";
         }
         enum "output" {
           description "Match on output from interface";
         }
       }
     }
     leaf tunnel-mtu {
       description "Maximum transmit packet size";
       default "1500";
       type union {
         type string {
           pattern "<.*>|$.*";
         }
         type uint32 {
           range "256 .. 9192";
         }
       }
     }
     leaf recovery-probe {
       description "Enable triggering recovery probe mechanism";
       type empty;
     }
     leaf df-bit {
       description "Specifies how to handle the Don't Fragment bit";
       default "clear";
       type enumeration {
         enum "clear" {
           description "Clear DF bit of outer header";
         }
         enum "set" {
           description "Set DF bit of outer header";
         }
         enum "copy" {
           description "Copy DF bit from inner header";
         }
       }
     }
     container fail-open {
       description "List of fail open rules";
       uses ipsec_gvpn_fail_open_rule_object;
     }
     container exclude {
       description "List of exclude rules";
       uses ipsec_gvpn_exclude_rule_object;
     }
   }
   grouping ipsec_gvpn_exclude_rule_object {
     uses apply-advanced;
     list rule {
       key name;
       ordered-by user;
       description "Define exlude rules upto 10";
       max-elements 10;
       uses ipsec_gvpn_rule_address_object;
     }
   }
   grouping ipsec_gvpn_fail_open_rule_object {
     uses apply-advanced;
     list rule {
       key name;
       ordered-by user;
       description "Define fail open rules upto 10";
       max-elements 10;
       uses ipsec_gvpn_rule_address_object;
     }
   }
   grouping ipsec_gvpn_rule_address_object {
     leaf name {
       description "Rule name";
       type string {
         length "1 .. 63";
         junos:posix-pattern "^[[:alnum:]][[:alnum:]_-]*$";
         junos:pattern-message "Must be a string beginning with a number or letter and consisting of letters, numbers, dashes and underscores.";
       }
     }
     uses apply-advanced;
     container source-address {
       description "Match IP source address";
       presence "enable source-address";
       uses ipsec_gvpn_addr_object;
     }
     container destination-address {
       description "Match IP destination address";
       presence "enable destination-address";
       uses ipsec_gvpn_addr_object;
     }
     leaf application {
       description "Match application";
       junos:must "(\"applications application $$\")";
       junos:must-message "Application must be defined";
       type string;
     }
   }
   grouping ipsec_gvpn_addr_object {
     uses apply-advanced;
     leaf address {
       description "Prefix to match";
       type jt:ipv4prefix-only;
     }
   }
   grouping security-ike {
     uses apply-advanced;
     container traceoptions {
       description "Trace options for IPSec key management";
       uses security-traceoptions;
     }
     container trap {
       description "Controls the sending of SNMP traps";
       uses apply-advanced;
       leaf ipsec-tunnel-down {
         description "Send traps when peer is up and IPsec SA goes down";
         type empty;
       }
       leaf peer-down {
         description "Send traps when peer goes down";
         type empty;
       }
     }
     container respond-bad-spi {
       presence "enable respond-bad-spi";
       description "Respond to IPSec packets with bad SPI values";
       leaf max-responses {
         description "Maximum number of times to respond";
         default "5";
         type union {
           type string {
             pattern "<.*>|$.*";
           }
           type uint32 {
             range "1 .. 30";
           }
         }
       }
     }
     list proposal {
       key name;
       ordered-by user;
       description "Define an IKE proposal";
       uses ike-proposal;
     }
     list policy {
       key name;
       ordered-by user;
       description "Define an IKE policy";
       uses ike-policy;
     }
     list gateway {
       key name;
       ordered-by user;
       description "Define an IKE gateway";
       leaf name {
         description "Label for the remote (peer) gateway";
         type string {
           length "1 .. 32";
         }
       }
       uses apply-advanced;
       leaf ike-policy {
         description "Name of the IKE policy";
         junos:must "(!((\"security ike policy $$ reauth-frequency\" && \".. aaa access-profile\")))";
         junos:must-message "Reauth is not allowed with AAA access profile.";
         junos:must "(\"security ike policy $$\")";
         junos:must-message "Referenced IKE policy must be defined under [edit security ike policy]";
         junos:must "(!((\".. version v2-only\" && (\"security ike policy $$ pre-shared-key\" && \".. dynamic ike-user-type\"))))";
         junos:must-message "When dynamic ike-user-type is configured, IKEv2 with authentication-method pre-shared-key is not allowed";
         junos:must "(!((\"security ike policy $$ mode main\" && (\"security ike policy $$ pre-shared-key\" && \".. dynamic\"))))";
         junos:must-message "Main mode for dynamic peer with Preshared key based authentication is not allowed";
         type string {
           length "1 .. 32";
         }
       }
       choice remote-identifier {
         case case_1 {
           leaf-list address {
             ordered-by user;
             description "Addresses or hostnames of peer:1 primary, upto 4 backups";
             type string;
           }
         }
         case case_2 {
           container dynamic {
             description "Site to site peer with dynamic IP address";
             uses apply-advanced;
             choice remote-id-type {
               case case_1 {
                 container distinguished-name {
                   presence "enable distinguished-name";
                   description "Use a distinguished name: ";
                   uses apply-advanced;
                   choice name-type {
                     case case_1 {
                       leaf container {
                         description "Specify the container string";
                         type string;
                       }
                     }
                     case case_2 {
                       leaf wildcard {
                         description "Specify the wildcard string";
                         type string;
                       }
                     }
                   }
                 }
               }
               case case_2 {
                 leaf general-ikeid {
                   description "Disables IKE-ID validation";
                   junos:must "(\".. ike-user-type group-ike-id\")";
                   junos:must-message "dynamic general-ikeid is only supported with auto-vpn";
                   type empty;
                 }
               }
               case case_3 {
                 leaf hostname {
                   description "Use a fully-qualified domain name";
                   type string;
                 }
               }
               case case_4 {
                 leaf inet {
                   description "Use an IPV4 address to identify the dynamic peer";
                   type jt:ipv4addr;
                 }
               }
               case case_5 {
                 leaf inet6 {
                   description "Use an IPV6 address to identify the dynamic peer";
                   type jt:ipv6addr;
                 }
               }
               case case_6 {
                 leaf user-at-hostname {
                   description "Use an e-mail address";
                   type string;
                 }
               }
             }
             leaf connections-limit {
               description "Maximum number of users connected to gateway";
               type union {
                 type uint32;
                 type string {
                   pattern "<.*>|$.*";
                 }
               }
             }
             leaf ike-user-type {
               description "Type of the IKE ID";
               type enumeration {
                 enum "group-ike-id" {
                   description "Email address or FQDN shared as IKED ID by multiple users";
                 }
                 enum "shared-ike-id" {
                   description "Email address shared as IKED ID by multiple users";
                   junos:must "((\" .. .. xauth\" || \" .. .. aaa\"))";
                   junos:must-message "Need to configure aaa at [edit security ike gateway]";
                 }
               }
             }
             leaf reject-duplicate-connection {
               description "Reject new connection from duplicate IKE-id";
               junos:must "(((\".. ike-user-type shared-ike-id\" || \".. ike-user-type group-ike-id\") && !(\".. .. aaa\")))";
               junos:must-message "Supported for shared-ike or group-ike and with non-AAA";
               type empty;
             }
           }
         }
       }
       container dead-peer-detection {
         presence "enable dead-peer-detection";
         description "Enable Dead Peer Detection ";
         uses apply-advanced;
         choice mode {
           case case_1 {
             leaf optimized {
               description "Send probes only when there is outgoing and no incoming data traffic - RFC3706 (Default mode)";
               type empty;
             }
           }
           case case_2 {
             leaf probe-idle-tunnel {
               description "Send probes same as in optimized mode and also when there is no outgoing & incoming data traffic";
               type empty;
             }
           }
           case case_3 {
             leaf always-send {
               description "Send probes periodically regardless of incoming and outgoing data traffic ";
               type empty;
             }
           }
         }
         leaf interval {
           description "The time between DPD probe messages  Default :10";
           default "10";
           units "seconds";
           type union {
             type string {
               pattern "<.*>|$.*";
             }
             type uint32 {
               range "2 .. 60";
             }
           }
         }
         leaf threshold {
           description "Maximum number of DPD retransmissions Default :5";
           default "5";
           type union {
             type string {
               pattern "<.*>|$.*";
             }
             type uint32 {
               range "1 .. 5";
             }
           }
         }
       }
       leaf no-nat-traversal {
         description "Disable IPSec NAT traversal";
         type empty;
       }
       leaf nat-keepalive {
         description "Interval at which to send NAT keepalives";
         default "20";
         units "seconds";
         type union {
           type string {
             pattern "<.*>|$.*";
           }
           type uint32 {
             range "1 .. 300";
           }
         }
       }
       container local-identity {
         description "Set the local IKE identity";
         choice identity-type {
           case case_1 {
             container inet {
               description "Use an IPv4 address";
               uses apply-advanced;
               leaf identity-ipv4 {
                 description "The local IPv4 identity";
                 type jt:ipv4addr;
               }
             }
           }
           case case_2 {
             container inet6 {
               description "Use an IPv6 address";
               uses apply-advanced;
               leaf identity-ipv6 {
                 description "The local IPv6 identity";
                 type jt:ipv6addr;
               }
             }
           }
           case case_3 {
             container hostname {
               description "Use a fully-qualified domain name";
               uses apply-advanced;
               leaf identity-hostname {
                 description "The local hostname";
                 type string;
               }
             }
           }
           case case_4 {
             container user-at-hostname {
               description "Use an e-mail address";
               uses apply-advanced;
               leaf identity-user {
                 description "The local user-FQDN";
                 type string;
               }
             }
           }
           case case_5 {
             leaf distinguished-name {
               description "Use a distinguished name specified in local certificate";
               type empty;
             }
           }
           case case_6 {
             container key-id {
               description "Key ID identification values in ASCII string";
               uses apply-advanced;
               leaf string-key-id {
                 description "Key ID in ASCII string";
                 type string {
                   length "1 .. 127";
                 }
               }
             }
           }
         }
       }
       container remote-identity {
         junos:must "(!(\".. dynamic\"))";
         junos:must-message "Since the remote gateway is dynamic, Define remote identity under dynamic";
         description "Set the remote IKE identity";
         choice identity-type {
           case case_1 {
             container inet {
               description "Use an IPv4 address";
               uses apply-advanced;
               leaf identity-ipv4 {
                 description "The remote IPv4 identity";
                 type jt:ipv4addr;
               }
             }
           }
           case case_2 {
             container inet6 {
               description "Use an IPv6 address";
               uses apply-advanced;
               leaf identity-ipv6 {
                 description "The remote IPv6 identity";
                 type jt:ipv6addr;
               }
             }
           }
           case case_3 {
             container hostname {
               description "Use a fully-qualified domain name";
               uses apply-advanced;
               leaf identity-hostname {
                 description "The remote hostname";
                 type string;
               }
             }
           }
           case case_4 {
             container user-at-hostname {
               description "Use an e-mail address";
               uses apply-advanced;
               leaf identity-user {
                 description "The remote user-FQDN";
                 type string;
               }
             }
           }
           case case_5 {
             container distinguished-name {
               presence "enable distinguished-name";
               description "Use a distinguished name: ";
               uses apply-advanced;
               leaf container {
                 description "Specify the container string";
                 type string;
               }
               leaf wildcard {
                 description "Specify the wildcard string";
                 type string;
               }
             }
           }
           case case_6 {
             container key-id {
               description "Key ID identification values in string";
               uses apply-advanced;
               leaf string-key-id {
                 description "Key ID in ASCII string";
                 type string {
                   length "1 .. 127";
                 }
               }
             }
           }
         }
       }
       leaf external-interface {
         description "External interface for IKE negotiations";
         junos:must "(!(\"interfaces $$ family bridge\"))";
         junos:must-message "Bridge interface is not allowed as external-interface";
         junos:must "(\"interfaces $$-IFL\")";
         junos:must-message "Referenced interface must be configured under [edit interfaces] hierarchy";
         type union {
           type jt:interface-unit;
           type string {
             pattern "<.*>|$.*";
           }
         }
       }
       leaf local-address {
         description "Local IP address for IKE negotiations";
         type jt:ipaddr;
       }
       container aaa {
         junos:must "(!(\".. xauth\"))";
         junos:must-message "Keyword aaa is a replacement to xauth.";
         description "Use extended authentication";
         uses apply-advanced;
         list access-profile {
           key name;
           ordered-by user;
           description "Access profile information";
           max-elements 1;
           uses access-profile-template;
         }
         container client {
           description "AAA client info for authentication";
           leaf username {
             description "AAA client username with 1 to 128 characters";
             junos:must "(!(\" .. .. .. version v2-only\"))";
             junos:must-message "AAA client is supported for IKEv1 only, not IKEv2.";
             type string {
               length "1 .. 128";
             }
           }
           leaf password {
             description "AAA client password with 1 to 128 characters";
             junos:must "(\".. username\")";
             junos:must-message "Username must be defined";
             type string {
               length "1 .. 128";
             }
           }
         }
       }
       container xauth {
         description "Use extended authentication";
         status deprecated;
         uses apply-advanced;
         leaf access-profile {
           description "Access profile that contains authentication information";
           junos:must "(!(\" .. client\"))";
           junos:must-message "Cannot configure a gateway to be xauth server and client at the same time.";
           junos:must "(\"access profile $$\")";
           junos:must-message "access profile needs to be configured";
           type string;
         }
         container client {
           description "Xauth client info for authentication";
           leaf username {
             description "XAuth client username with 1 to 128 characters";
             junos:must "(!(\" .. .. .. version v2-only\"))";
             junos:must-message "Xauth is supported for IKEv1 only, not IKEv2.";
             type string {
               length "1 .. 128";
             }
           }
           leaf password {
             description "XAuth client password with 1 to 128 characters";
             junos:must "(\".. username\")";
             junos:must-message "username must be defined";
             type string {
               length "1 .. 128";
             }
           }
         }
       }
       leaf general-ikeid {
         description "Accept peer IKE-ID in general";
         junos:must "(!(\".. remote-identity\"))";
         junos:must-message "general-ikeid option is not allowed when remote-identity is configured";
         junos:must "(!(\".. dynamic\"))";
         junos:must-message "general-ikd-id option is not available for dynamic peer.";
         type empty;
       }
       container advpn {
         description "Enable Auto Discovery VPN";
         presence "enable advpn";
         junos:must "((!(\".. xauth\") && !(\".. aaa\")))";
         junos:must-message "AAA not available with advpn enabled gateway";
         uses advpn-suggester-partner;
       }
       leaf version {
         description "Negotiate using either IKE v1 or IKE v2 protocol";
         default "v1-only";
         type enumeration {
           enum "v1-only" {
             description "The connection must be initiated using IKE version 1";
           }
           enum "v2-only" {
             description "The connection must be initiated using IKE version 2";
           }
         }
       }
       container fragmentation {
         junos:must "(\".. version v2-only\")";
         junos:must-message "IKEv2 must be configured to use fragementation.";
         description "IKEv2 fragmentation configuration";
         uses apply-advanced;
         leaf disable {
           description "Disable IKEv2 fragmentation";
           type empty;
         }
         leaf size {
           description "Default 576 bytes for ipv4 and 1280 bytes for ipv6";
           type union {
             type string {
               pattern "<.*>|$.*";
             }
             type uint32 {
               range "570 .. 1320";
             }
           }
         }
       }
       leaf tcp-encap-profile {
         description "Ike over tcp profile name";
         junos:must "(\"security tcp-encap profile $$\")";
         junos:must-message "Referenced tcp-encap profile must be defined";
         type string;
       }
     }
   }
   grouping access-profile-template {
     description "Configure an access profile";
     leaf name {
       description "Access profile name used to authenticate with XAUTH/AAA server";
       junos:must "((!(\".. .. .. dynamic\") || \".. .. .. dynamic ike-user-type\"))";
       junos:must-message "DEP is not allowed with XAUTH/AAA access profile.";
       junos:must "(!(\".. .. .. address\"))";
       junos:must-message "For site-to-site tunnels, aaa access-profile configuration is not allowed";
       junos:must "(!(\" .. .. client\"))";
       junos:must-message "Cannot configure a gateway to be XAUTH/AAA server and client at the same time.";
       junos:must "(\"access profile $$\")";
       junos:must-message "Access profile needs to be configured";
       type string;
     }
     uses apply-advanced;
     leaf config-payload-password {
       description "Common client password for IKEv2 config-payload with 1 to 128 characters";
       type string {
         length "1 .. 128";
       }
     }
   }
   grouping advpn-suggester-partner {
     description "Configure ADVPN Suggester Partner";
     uses apply-advanced;
     container suggester {
       presence "enable suggester";
       description "Configure Shortcut Suggester parameters";
       uses apply-advanced;
       leaf disable {
         description "Disable Suggester capability";
         type empty;
       }
     }
     container partner {
       presence "enable partner";
       description "Configure Shortcut Partner parameters";
       uses apply-advanced;
       leaf connection-limit {
         description "Maximum number of shortcut connections (default: varies per platform)";
         junos:must "(!(\".. .. .. dynamic\"))";
         junos:must-message "ADVPN partner can only be configured on s2s gateway";
         type union {
           type uint32;
           type string {
             pattern "<.*>|$.*";
           }
         }
       }
       leaf idle-time {
         description "The duration (in sec) after which shortcut is torn down (default: 300 sec)";
         default "300";
         units "seconds";
         junos:must "(!(\".. .. .. dynamic\"))";
         junos:must-message "ADVPN partner can only be configured on s2s gateway";
         type union {
           type string {
             pattern "<.*>|$.*";
           }
           type uint32 {
             range "60 .. 86400";
           }
         }
       }
       leaf idle-threshold {
         description "The packet rate below which shortcut is torn down (default: 5 packets/sec)";
         default "5";
         junos:must "(!(\".. .. .. dynamic\"))";
         junos:must-message "ADVPN partner can only be configured on s2s gateway";
         type union {
           type string {
             pattern "<.*>|$.*";
           }
           type uint32 {
             range "3 .. 5000";
           }
         }
       }
       leaf disable {
         description "Disable Partner capability";
         type empty;
       }
     }
   }
   grouping ike-policy {
     leaf name {
       description "Name of policy";
       junos:must "(!((\".. certificate local-certificate\" && (\".. pre-shared-key\" || \".. seeded-pre-shared-key\"))))";
       junos:must-message "IKE policy must have either local certificate or pre-shared key configured";
       junos:must "(!((\".. seeded-pre-shared-key\" && \".. pre-shared-key\")))";
       junos:must-message "IKE policy must have either pre-shared key or seeded-pre-shared key configured";
       junos:must "(((\".. certificate local-certificate\" || (\".. seeded-pre-shared-key\" || \".. pre-shared-key\")) && !((\".. certificate local-certificate\" && (\".. pre-shared-key\" && \".. seeded-pre-shared-key\")))))";
       junos:must-message "IKE policy must have either local certificate or pre-shared key or seeded-pre-shared key configured";
       junos:must "(((\".. certificate local-certificate\" || \".. pre-shared-key\") && !((\".. certificate local-certificate\" && \".. pre-shared-key\"))))";
       junos:must-message "IKE policy must have either local certificate or pre-shared key configured";
       type string {
         length "1 .. 32";
       }
     }
     uses apply-advanced;
     leaf mode {
       description "Define the IKE mode for Phase 1";
       default "main";
       type enumeration {
         enum "main" {
           description "Main mode";
         }
         enum "aggressive" {
           description "Aggressive mode";
         }
       }
     }
     leaf reauth-frequency {
       description "Re-auth Peer after reauth-frequency times hard lifetime. (0-100) Default:0=Disabled";
       default "0";
       type union {
         type string {
           pattern "<.*>|$.*";
         }
         type uint32 {
           range "0 .. 100";
         }
       }
     }
     leaf description {
       description "Text description of IKE policy";
       type string {
         length "1 .. 80";
       }
     }
     leaf-list proposals {
       ordered-by user;
       description "Name of the proposal";
       junos:must "(\".. .. .. proposal $$\")";
       junos:must-message "Referenced proposal is not defined";
       type string {
         length "1 .. 32";
         junos:posix-pattern "^[[:alnum:]][[:alnum:]_-]*$";
         junos:pattern-message "Must be a string beginning with a number or letter and consisting of letters, numbers, dashes and underscores.";
       }
     }
     container certificate {
       description "Certificate configuration";
       uses apply-advanced;
       leaf local-certificate {
         description "Local certificate identifier";
         type string {
           junos:posix-pattern "^.{1,32}$";
           junos:pattern-message "Must be string of 32 characters or less";
         }
       }
       container trusted-ca {
         description "Specify the CA to use";
         choice ca {
           case case_1 {
             leaf ca-index {
               description "Index of the preferred CA to use";
               status deprecated;
               type union {
                 type uint32;
                 type string {
                   pattern "<.*>|$.*";
                 }
               }
             }
           }
           case case_2 {
             leaf use-all {
               description "Use all configured CAs";
               status deprecated;
               type empty;
             }
           }
           case case_3 {
             leaf ca-profile {
               description "Name of the preferred CA to use";
               junos:must "(\"security pki ca-profile $$\")";
               junos:must-message "Referenced profile must be defined under [edit security pki ca-profile]";
               type string;
             }
           }
           case case_4 {
             leaf trusted-ca-group {
               description "Name of the preferred CA group to use";
               junos:must "(\"security pki trusted-ca-group $$\")";
               junos:must-message "Referenced group must be defined under [edit security pki trusted-ca-group]";
               type string;
             }
           }
         }
       }
       leaf peer-certificate-type {
         description "Preferred type of certificate from peer";
         default "x509-signature";
         type enumeration {
           enum "pkcs7" {
             description "PKCS7 encoding";
           }
           enum "x509-signature" {
             description "X509 signature encoding";
           }
         }
       }
       leaf-list policy-oids {
         ordered-by user;
         description "Certificate policy object identifiers (maximum 5)";
         type string {
           length "1 .. 63";
         }
         max-elements 5;
       }
     }
     leaf proposal-set {
       description "Types of default IKE proposal-set";
       type enumeration {
         enum "basic" {
           description "IKE proposal-set for basic";
           junos:must "(!(\".. proposals\"))";
           junos:must-message "IKE policy must not have both proposals and proposal-set configured";
         }
         enum "compatible" {
           description "IKE proposal-set for compatible";
           junos:must "(!(\".. proposals\"))";
           junos:must-message "IKE policy must not have both proposals and proposal-set configured";
         }
         enum "standard" {
           description "IKE proposal-set for standard";
           junos:must "(!(\".. proposals\"))";
           junos:must-message "IKE policy must not have both proposals and proposal-set configured";
         }
         enum "suiteb-gcm-128" {
           description "IKE proposal-set for Suite-B-GCM-128";
           junos:must "((\".. certificate local-certificate\" && !(\".. pre-shared-key\")))";
           junos:must-message "Suite B proposal-sets require certificate-based authentication.";
           junos:must "(!(\".. proposals\"))";
           junos:must-message "IKE policy must not have both proposals and proposal-set configured";
         }
         enum "suiteb-gcm-256" {
           description "IKE proposal-set for Suite-B-GCM-256";
           junos:must "((\".. certificate local-certificate\" && !(\".. pre-shared-key\")))";
           junos:must-message "Suite B proposal-sets require certificate-based authentication.";
           junos:must "(!(\".. proposals\"))";
           junos:must-message "IKE policy must not have both proposals and proposal-set configured";
         }
         enum "prime-128" {
           description "IKE proposal-set for PRIME-128";
           junos:must "((\".. certificate local-certificate\" && !(\".. pre-shared-key\")))";
           junos:must-message "PRIME proposal-sets require certificate-based authentication.";
           junos:must "(!(\".. proposals\"))";
           junos:must-message "IKE policy must not have both proposals and proposal-set configured";
         }
         enum "prime-256" {
           description "IKE proposal-set for PRIME-256";
           junos:must "((\".. certificate local-certificate\" && !(\".. pre-shared-key\")))";
           junos:must-message "PRIME proposal-sets require certificate-based authentication.";
           junos:must "(!(\".. proposals\"))";
           junos:must-message "IKE policy must not have both proposals and proposal-set configured";
         }
       }
     }
     container pre-shared-key {
       description "Define a preshared key";
       choice key-choice {
         case case_1 {
           leaf ascii-text {
             description "Format as text";
             type string {
               length "1 .. 255";
             }
           }
         }
         case case_2 {
           leaf hexadecimal {
             description "Format as hexadecimal";
             type string {
               length "1 .. 255";
               junos:posix-pattern "^[[:xdigit:]]+$";
               junos:pattern-message "Must be hexadecimal digits (0-9, a-f, A-F)";
             }
           }
         }
       }
     }
     container seeded-pre-shared-key {
       description "Define a preshared key";
       choice key-choice {
         case case_1 {
           leaf ascii-text {
             description "Format as text";
             type string {
               length "1 .. 255";
             }
           }
         }
         case case_2 {
           leaf hexadecimal {
             description "Format as hexadecimal";
             type string {
               length "1 .. 255";
               junos:posix-pattern "^[[:xdigit:]]+$";
               junos:pattern-message "Must be hexadecimal digits (0-9, a-f, A-F)";
             }
           }
         }
       }
     }
   }
   grouping ike-proposal {
     leaf name {
       description "Name of the IKE proposal";
       type string {
         length "1 .. 32";
       }
     }
     uses apply-advanced;
     leaf description {
       description "Text description of IKE proposal";
       type string {
         length "1 .. 80";
       }
     }
     leaf authentication-method {
       description "Define authentication method";
       type enumeration {
         enum "pre-shared-keys" {
           description "Preshared keys";
         }
         enum "rsa-signatures" {
           description "RSA signatures";
         }
         enum "dsa-signatures" {
           description "DSA signatures";
         }
         enum "ecdsa-signatures-256" {
           description "ECDSA signatures (256 bit modulus)";
         }
         enum "ecdsa-signatures-384" {
           description "ECDSA signatures (384 bit modulus)";
         }
         enum "ecdsa-signatures-521" {
           description "ECDSA signatures (521 bit modulus)";
         }
       }
     }
     leaf dh-group {
       description "Define Diffie-Hellman group";
       type enumeration {
         enum "group1" {
           description "Diffie-Hellman Group 1";
         }
         enum "group2" {
           description "Diffie-Hellman Group 2";
         }
         enum "group5" {
           description "Diffie-Hellman Group 5";
         }
         enum "group14" {
           description "Diffie-Hellman Group 14";
         }
         enum "group15" {
           description "Diffie-Hellman Group 15";
         }
         enum "group16" {
           description "Diffie-Hellman Group 16";
         }
         enum "group19" {
           description "Diffie-Hellman Group 19";
         }
         enum "group20" {
           description "Diffie-Hellman Group 20";
         }
         enum "group21" {
           description "Diffie-Hellman Group 21";
         }
         enum "group24" {
           description "Diffie-Hellman Group 24";
         }
       }
     }
     leaf authentication-algorithm {
       description "Define authentication algorithm";
       type enumeration {
         enum "md5" {
           description "MD5 authentication algorithm";
         }
         enum "sha1" {
           description "SHA1 authentication algorithm";
         }
         enum "sha-256" {
           description "SHA 256-bit authentication algorithm";
         }
         enum "sha-384" {
           description "SHA 384-bit authentication algorithm";
         }
         enum "sha-512" {
           description "SHA 512-bit authentication algorithm";
         }
       }
     }
     leaf encryption-algorithm {
       description "Define encryption algorithm";
       type enumeration {
         enum "des-cbc" {
           description "DES-CBC encryption algorithm";
         }
         enum "3des-cbc" {
           description "3DES-CBC encryption algorithm";
         }
         enum "aes-128-cbc" {
           description "AES-CBC 128-bit encryption algorithm";
         }
         enum "aes-192-cbc" {
           description "AES-CBC 192-bit encryption algorithm";
         }
         enum "aes-256-cbc" {
           description "AES-CBC 256-bit encryption algorithm";
         }
         enum "aes-128-gcm" {
           description "AES-GCM 128-bit encryption algorithm";
           junos:must "(!(\".. authentication-algorithm\"))";
           junos:must-message "When using aes-gcm for Encryption the Authentication Algorithm must not be set.";
         }
         enum "aes-256-gcm" {
           description "AES-GCM 256-bit encryption algorithm";
           junos:must "(!(\".. authentication-algorithm\"))";
           junos:must-message "When using aes-gcm for Encryption the Authentication Algorithm must not be set.";
         }
       }
     }
     leaf lifetime-seconds {
       description "Lifetime, in seconds";
       units "seconds";
       type union {
         type string {
           pattern "<.*>|$.*";
         }
         type uint32 {
           range "180 .. 86400";
         }
       }
     }
   }
   grouping security-ipsec-policies {
     uses apply-advanced;
     list from-zone {
       key "from-zone-name to-zone";
       ordered-by user;
       description "Define ipsec policy context";
       uses security-ipsec-policy;
     }
   }
   grouping security-ipsec-policy {
     leaf from-zone-name {
       description "Incoming zone";
       junos:must "(\"security zones security-zone $$\")";
       junos:must-message "Security zone must be defined";
       type string {
         length "1 .. 63";
       }
     }
     leaf to-zone {
       description "Outgoing zone";
       junos:must "(\"security zones security-zone $$\")";
       junos:must-message "Security zone must be defined";
       type string {
         length "1 .. 63";
       }
     }
     uses apply-advanced;
     leaf ipsec-group-vpn {
       description "Group VPN name";
       junos:must "(unique \"security ipsec-policy from-zone <*> to-zone <*> ipsec-group-vpn $$\")";
       junos:must-message "Group VPN can only be referenced by one pair of from-zone and to-zone";
       junos:must "(\"security group-vpn member ipsec vpn $$\")";
       junos:must-message "Group VPN must be defined";
       type string {
         length "1 .. 32";
       }
     }
   }
   grouping security-ipsec-vpn {
     uses apply-advanced;
     container internal {
       presence "enable internal";
       description "Define an IPSec SA for internal RE-RE communication";
       uses apply-advanced;
       container security-association {
         description "Define an IPsec security association";
         presence "enable security-association";
         uses ipsec-internal-sa;
       }
     }
     container traceoptions {
       description "Trace options for IPSec data-plane debug";
       uses ipsec-traceoptions;
     }
     container vpn-monitor-options {
       description "Global options for VPN liveliness monitoring";
       presence "enable vpn-monitor-options";
       uses ipsec-vpn-monitor;
     }
     list proposal {
       key name;
       ordered-by user;
       description "Define an IPSec proposal";
       uses ipsec-proposal;
     }
     list policy {
       key name;
       ordered-by user;
       description "Define an IPSec policy";
       uses ipsec-policy;
     }
     list vpn {
       key name;
       ordered-by user;
       description "Define an IPSec VPN";
       uses ipsec-vpn-template;
     }
     list security-association {
       key name;
       ordered-by user;
       description "Define a manual control plane SA ";
       uses ipsec-sa;
     }
     leaf anti-replay-window-size {
       description "Anti-replay window size Default 64";
       type union {
         type string {
           pattern "<.*>|$.*";
         }
         type uint32 {
           range "64 .. 8192";
         }
       }
     }
   }
   grouping ipsec-internal-sa {
     uses apply-advanced;
     container manual {
       description "Define a manual security association";
       uses apply-advanced;
       container encryption {
         description "Define encryption parameters";
         uses apply-advanced;
         leaf algorithm {
           description "Define encryption algorithm";
           type enumeration {
             enum "3des-cbc" {
               description "3DES-CBC encryption algorithm";
             }
             enum "aes-128-cbc" {
               description "AES-CBC 128-bit encryption algorithm";
             }
           }
         }
         leaf ike-ha-link-encryption {
           description "Enable HA link encryption IKE internal messages";
           type enumeration {
             enum "enable" {
               description "Enable HA link encryption IKE internal messages";
             }
           }
         }
         container key {
           description "Define an encryption key";
           choice key-choice {
             case case_1 {
               leaf ascii-text {
                 description "Format as text";
                 type jt:unreadable;
               }
             }
           }
         }
       }
     }
   }
   grouping ipsec-policy {
     leaf name {
       description "Name of the IPSec policy";
       type string {
         length "1 .. 32";
         junos:posix-pattern "^[[:alnum:]][[:alnum:]_-]*$";
         junos:pattern-message "Must be a string beginning with a number or letter and consisting of letters, numbers, dashes and underscores.";
       }
     }
     uses apply-advanced;
     leaf description {
       description "Text description of IPSec policy";
       type string {
         length "1 .. 80";
       }
     }
     container perfect-forward-secrecy {
       description "Define perfect forward secrecy";
       uses apply-advanced;
       leaf keys {
         description "Define Diffie-Hellman group";
         type enumeration {
           enum "group1" {
             description "Diffie-Hellman Group 1";
           }
           enum "group2" {
             description "Diffie-Hellman Group 2";
           }
           enum "group5" {
             description "Diffie-Hellman Group 5";
           }
           enum "group14" {
             description "Diffie-Hellman Group 14";
           }
           enum "group15" {
             description "Diffie-Hellman Group 15";
           }
           enum "group16" {
             description "Diffie-Hellman Group 16";
           }
           enum "group19" {
             description "Diffie-Hellman Group 19";
           }
           enum "group20" {
             description "Diffie-Hellman Group 20";
           }
           enum "group21" {
             description "Diffie-Hellman Group 21";
           }
           enum "group24" {
             description "Diffie-Hellman Group 24";
           }
         }
       }
     }
     leaf-list proposals {
       ordered-by user;
       description "Name of the proposal";
       junos:must "(\".. .. .. proposal $$\")";
       junos:must-message "Referenced proposal is not defined";
       type string {
         length "1 .. 32";
         junos:posix-pattern "^[[:alnum:]][[:alnum:]_-]*$";
         junos:pattern-message "Must be a string beginning with a number or letter and consisting of letters, numbers, dashes and underscores.";
       }
     }
     leaf proposal-set {
       description "Types of default IPSEC proposal-set";
       type enumeration {
         enum "basic" {
           description "IPSEC basic proposal-set";
           junos:must "(!(\".. proposals\"))";
           junos:must-message "IPSec policy must not have both proposals and proposal-set configured";
         }
         enum "compatible" {
           description "IPSEC compatible proposal-set";
           junos:must "(!(\".. proposals\"))";
           junos:must-message "IPSec policy must not have both proposals and proposal-set configured";
         }
         enum "standard" {
           description "IPSEC standard proposal-set";
           junos:must "(!(\".. proposals\"))";
           junos:must-message "IPSec policy must not have both proposals and proposal-set configured";
         }
         enum "suiteb-gcm-128" {
           description "IPSec proposal-set for Suite-B-GCM-128";
           junos:must "(!(\".. proposals\"))";
           junos:must-message "IPSec policy must not have both proposals and proposal-set configured";
         }
         enum "suiteb-gcm-256" {
           description "IPSec proposal-set for Suite-B-GCM-256";
           junos:must "(!(\".. proposals\"))";
           junos:must-message "IPSec policy must not have both proposals and proposal-set configured";
         }
         enum "prime-128" {
           description "IPSec proposal-set for PRIME-128";
           junos:must "(!(\".. proposals\"))";
           junos:must-message "IPSec policy must not have both proposals and proposal-set configured";
         }
         enum "prime-256" {
           description "IPSec proposal-set for PRIME-256";
           junos:must "(!(\".. proposals\"))";
           junos:must-message "IPSec policy must not have both proposals and proposal-set configured";
         }
       }
     }
   }
   grouping ipsec-proposal {
     leaf name {
       description "Name of the IPSec proposal";
       type string {
         length "1 .. 32";
         junos:posix-pattern "^[[:alnum:]][[:alnum:]_-]*$";
         junos:pattern-message "Must be a string beginning with a number or letter and consisting of letters, numbers, dashes and underscores.";
       }
     }
     uses apply-advanced;
     leaf extended-sequence-number {
       description "Extended Sequence Number enabled";
       type empty;
     }
     leaf description {
       description "Text description of IPSec proposal";
       type string {
         length "1 .. 80";
       }
     }
     leaf protocol {
       description "Define an IPSec protocol for the proposal";
       type enumeration {
         enum "ah" {
           description "Authentication header";
           junos:must "(!(\".. encryption-algorithm\"))";
           junos:must-message "Encryption algorithm must not be defined for AH";
         }
         enum "esp" {
           description "Encapsulated Security Payload header";
         }
       }
     }
     leaf authentication-algorithm {
       description "Define authentication algorithm";
       type enumeration {
         enum "hmac-md5-96" {
           description "HMAC-MD5-96 authentication algorithm";
         }
         enum "hmac-sha1-96" {
           description "HMAC-SHA1-96 authentication algorithm";
         }
         enum "hmac-sha-256-128" {
           description "HMAC-SHA-256-128 authentication algorithm";
         }
         enum "hmac-sha-256-96" {
           description "HMAC-SHA-256-96 authentication algorithm (non-RFC compliant)";
         }
         enum "hmac-sha-384" {
           description "HMAC-SHA-384 authentication algorithm";
         }
         enum "hmac-sha-512" {
           description "HMAC-SHA-512 authentication algorithm";
         }
       }
     }
     leaf encryption-algorithm {
       description "Define encryption algorithm";
       type enumeration {
         enum "des-cbc" {
           description "DES-CBC encryption algorithm";
         }
         enum "3des-cbc" {
           description "3DES-CBC encryption algorithm";
         }
         enum "aes-128-cbc" {
           description "AES-CBC 128-bit encryption algorithm";
         }
         enum "aes-192-cbc" {
           description "AES-CBC 192-bit encryption algorithm";
         }
         enum "aes-256-cbc" {
           description "AES-CBC 256-bit encryption algorithm";
         }
         enum "aes-128-gcm" {
           description "AES-GCM 128-bit encryption algorithm";
           junos:must "(!(\".. authentication-algorithm\"))";
           junos:must-message "HMAC Authentication is not compatible with AES-GCM";
         }
         enum "aes-192-gcm" {
           description "AES-GCM 192-bit encryption algorithm";
           junos:must "(!(\".. authentication-algorithm\"))";
           junos:must-message "HMAC Authentication is not compatible with AES-GCM";
         }
         enum "aes-256-gcm" {
           description "AES-GCM 256-bit encryption algorithm";
           junos:must "(!(\".. authentication-algorithm\"))";
           junos:must-message "HMAC Authentication is not compatible with AES-GCM";
         }
       }
     }
     leaf lifetime-seconds {
       description "Lifetime, in seconds";
       units "seconds";
       type union {
         type string {
           pattern "<.*>|$.*";
         }
         type uint32 {
           range "180 .. 86400";
         }
       }
     }
   }
   grouping ipsec-sa {
     leaf name {
       description "Name of IPSec security association";
       junos:must "(\".. manual\")";
       junos:must-message "Type must be defined for security-association";
       type string {
         length "1 .. 32";
         junos:posix-pattern "^[[:alnum:]][[:alnum:]_-]*$";
         junos:pattern-message "Must be a string beginning with a number or letter and consisting of letters, numbers, dashes and underscores.";
       }
     }
     uses apply-advanced;
     leaf description {
       description "Text description of security association";
       type string {
         length "1 .. 80";
       }
     }
     leaf mode {
       description "Define security association mode";
       default "transport";
       type enumeration {
         enum "transport" {
           description "Transport mode";
           junos:must "(\".. manual\")";
           junos:must-message "Manual block must be configured for transport mode security association";
         }
       }
     }
     choice sa_choice {
       case case_1 {
         container manual {
           description "Define a manual security association";
           uses security-association-manual;
         }
       }
     }
   }
   grouping ipsec-traceoptions {
     description "Data-plane IPSec tracing options";
     uses apply-advanced;
     leaf no-remote-trace {
       description "Disable remote tracing";
       junos:must "(\"system tracing\")";
       junos:must-message "'no-remote-trace' is valid only when [system tracing] is configured";
       type empty;
     }
     container file {
       description "Trace file information";
       leaf filename {
         description "Name of file in which to write trace information";
         type string {
           length "1 .. 1024";
           junos:posix-pattern "![/ %]";
           junos:pattern-message "Must not contain '/', % or a space";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     list flag {
       key name;
       ordered-by user;
       description "Events to include in data-plane IPSec trace output";
       leaf name {
         type enumeration {
           enum "packet-processing" {
             description "Trace data packet processing events";
           }
           enum "packet-drops" {
             description "Trace packet drops";
           }
           enum "security-associations" {
             description "Trace security association management events";
           }
           enum "next-hop-tunnel-binding" {
             description "Trace next-hop tunnel binding events";
           }
           enum "all" {
             description "Trace with all flags enabled";
           }
         }
       }
     }
   }
   grouping ipsec-vpn-monitor {
     description "Configure VPN monitoring";
     uses apply-advanced;
     leaf interval {
       description "Monitor interval in seconds";
       default "10";
       units "seconds";
       type union {
         type string {
           pattern "<.*>|$.*";
         }
         type uint32 {
           range "2 .. 3600";
         }
       }
     }
     leaf threshold {
       description "Number of consecutive failures to determine connectivity";
       default "10";
       type union {
         type string {
           pattern "<.*>|$.*";
         }
         type uint32 {
           range "1 .. 65536";
         }
       }
     }
   }
   grouping ipsec-vpn-template {
     description "Configure an IPSec VPN";
     leaf name {
       description "Name of the VPN";
       type string {
         length "1 .. 32";
       }
     }
     uses apply-advanced;
     leaf ha-link-encryption {
       description "Enable HA link encryption";
       junos:must "(!(\".. ike proxy-identity\"))";
       junos:must-message "When ha-link-encryption is enabled, ike proxy-identity configuration is not allowed";
       junos:must "(!(\".. ike idle-time\"))";
       junos:must-message "When ha-link-encryption is enabled, ike idle-time configuration is not allowed";
       junos:must "(!(\".. ike install-interval\"))";
       junos:must-message "When ha-link-encryption is enabled, ike install-interval configuration is not allowed";
       junos:must "(!(\".. distribution-profile\"))";
       junos:must-message "When ha-link-encryption is enabled, distribution-profile configuration is not allowed";
       junos:must "(!(\".. establish-tunnels responder-only-no-rekey\"))";
       junos:must-message "When ha-link-encryption is enabled, establish-tunnels responder-only-no-rekey configuration is not allowed";
       junos:must "(!(\".. establish-tunnels responder-only\"))";
       junos:must-message "When ha-link-encryption is enabled, establish-tunnels responder-only configuration is not allowed";
       junos:must "(!(\".. establish-tunnels on-traffic\"))";
       junos:must-message "When ha-link-encryption is enabled, establish-tunnels on-traffic configuration is not allowed";
       junos:must "(!(\".. establish-tunnels immediately\"))";
       junos:must-message "When ha-link-encryption is enabled, establish-tunnels immediately configuration is not allowed";
       junos:must "(!(\".. traffic-selector\"))";
       junos:must-message "When ha-link-encryption is enabled, traffic-selector configuration is not allowed";
       junos:must "(!(\".. vpn-monitor\"))";
       junos:must-message "When ha-link-encryption is enabled, vpn-monitor configuration is not allowed";
       junos:must "(!(\".. copy-outer-dscp\"))";
       junos:must-message "When ha-link-encryption is enabled, copy-outer-dscp configuration is not allowed";
       junos:must "(!(\".. multi-sa\"))";
       junos:must-message "When ha-link-encryption is enabled, multi-sa configuration is not allowed";
       junos:must "(!(\".. bind-interface\"))";
       junos:must-message "When ha-link-encryption is enabled, bind-interface configuration is not allowed";
       junos:must "(!(\".. manual\"))";
       junos:must-message "When ha-link-encryption is enabled, manual sa configuration is not allowed";
       junos:must "(!(\".. df-bit\"))";
       junos:must-message "When ha-link-encryption is enabled, df-bit configuration is not allowed";
       junos:must "(!(\".. udp-encapsulate\"))";
       junos:must-message "When ha-link-encryption is enabled, udp-encapsulate configuration is not allowed";
       junos:must "(!(\".. ike no-anti-replay\"))";
       junos:must-message "When ha-link-encryption is enabled, no-anti-replay configuration is not allowed";
       type empty;
     }
     leaf bind-interface {
       description "Bind to tunnel interface (route-based VPN)";
       junos:must "(!((\"interfaces $$-IFL multipoint\" && \".. aaa access-profile\")))";
       junos:must-message "When aaa access-profile is configured under security ike gateway, vpn-monitor configuration is not allowed";
       junos:must "((\"interfaces $$-IFL\" || any \"logical-systems <*> interfaces $$-IFL\"))";
       junos:must-message "Referenced interface must be configured under [edit interfaces] hierarchy";
       type union {
         type jt:interface-name;
         type string {
           pattern "<.*>|$.*";
         }
       }
     }
     leaf df-bit {
       description "Specifies how to handle the Don't Fragment bit";
       type enumeration {
         enum "clear" {
           description "Clear DF bit of outer header";
         }
         enum "set" {
           description "Set DF bit of outer header";
         }
         enum "copy" {
           description "Copy DF bit from inner header";
         }
       }
     }
     container multi-sa {
       presence "enable multi-sa";
       junos:must "(!(\".. vpn-monitor\"))";
       junos:must-message "vpn-monitor with multi-sa is not supported";
       description "Negotiate multiple SAs based on configuration choice";
       uses apply-advanced;
       choice sa_map {
         case case_1 {
           list forwarding-class {
             key name;
             ordered-by user;
             leaf name {
               description "Name of forwarding classes";
               type string {
                 length "1 .. 32";
               }
             }
             uses apply-advanced;
           }
         }
       }
     }
     leaf copy-outer-dscp {
       description "Enable copying outer IP header DSCP and ECN to inner IP header";
       type empty;
     }
     container vpn-monitor {
       description "Monitor VPN liveliness";
       presence "enable vpn-monitor";
       uses ipsec-template-monitor;
     }
     choice negotiation {
       case case_1 {
         container manual {
           junos:must "(!(\".. traffic-selector\"))";
           junos:must-message "Manual vpn with traffic selector is not allowed";
           description "Define a manual security association";
           uses apply-advanced;
           leaf gateway {
             description "Define the IPSec peer";
             type jt:hostname;
           }
           leaf external-interface {
             description "External interface for the security association";
             junos:must "(!(\"interfaces $$ family bridge\"))";
             junos:must-message "Bridge interface is not allowed as external-interface";
             junos:must "(\"interfaces $$-IFL\")";
             junos:must-message "Referenced interface must be configured under [edit interfaces] hierarchy";
             type union {
               type jt:interface-unit;
               type string {
                 pattern "<.*>|$.*";
               }
             }
           }
           leaf protocol {
             description "Define an IPSec protocol for the security association";
             type enumeration {
               enum "ah" {
                 description "Authentication header";
                 junos:must "(!(\".. encryption\"))";
                 junos:must-message "Encryption must not be defined for AH";
                 junos:must "(\".. authentication\")";
                 junos:must-message "Authentication must be defined for AH";
               }
               enum "esp" {
                 description "Encapsulated Security Payload header";
                 junos:must "((\".. authentication\" || \".. encryption\"))";
                 junos:must-message "Either authentication or encryption must be defined for ESP";
               }
             }
           }
           leaf spi {
             description "Define security parameter index";
             type union {
               type string {
                 pattern "<.*>|$.*";
               }
               type uint32 {
                 range "256 .. 16639";
               }
             }
           }
           container authentication {
             description "Define authentication parameters";
             uses apply-advanced;
             leaf algorithm {
               description "Define authentication algorithm";
               type enumeration {
                 enum "hmac-md5-96" {
                   description "HMAC-MD5-96 authentication algorithm";
                 }
                 enum "hmac-sha1-96" {
                   description "HMAC-SHA1-96 authentication algorithm";
                 }
                 enum "hmac-sha-256-128" {
                   description "HMAC-SHA-256-128 authentication algorithm";
                 }
                 enum "hmac-sha-256-96" {
                   description "HMAC-SHA-256-96 authentication algorithm (non-RFC compliant)";
                 }
                 enum "hmac-sha-384" {
                   description "HMAC-SHA-384 authentication algorithm";
                 }
                 enum "hmac-sha-512" {
                   description "HMAC-SHA-512 authentication algorithm";
                 }
               }
             }
             container key {
               description "Define an authentication key";
               choice key-choice {
                 case case_1 {
                   leaf ascii-text {
                     description "Format as text";
                     type string {
                       length "1 .. 255";
                     }
                   }
                 }
                 case case_2 {
                   leaf hexadecimal {
                     description "Format as hexadecimal";
                     type string {
                       length "1 .. 255";
                       junos:posix-pattern "^[[:xdigit:]]+$";
                       junos:pattern-message "Must be hexadecimal digits (0-9, a-f, A-F)";
                     }
                   }
                 }
               }
             }
           }
           container encryption {
             description "Define encryption parameters";
             uses apply-advanced;
             leaf algorithm {
               description "Define encryption algorithm";
               type enumeration {
                 enum "des-cbc" {
                   description "DES-CBC encryption algorithm";
                 }
                 enum "3des-cbc" {
                   description "3DES-CBC encryption algorithm";
                 }
                 enum "aes-128-cbc" {
                   description "AES-CBC 128-bit encryption algorithm";
                 }
                 enum "aes-192-cbc" {
                   description "AES-CBC 192-bit encryption algorithm";
                 }
                 enum "aes-256-cbc" {
                   description "AES-CBC 256-bit encryption algorithm";
                 }
                 enum "aes-128-gcm" {
                   description "AES-GCM 128-bit encryption algorithm";
                   junos:must "(!(\".. authentication-algorithm\"))";
                   junos:must-message "When using aes-gcm for Encryption the Authentication Algorithm must not be set.";
                 }
                 enum "aes-256-gcm" {
                   description "AES-GCM 256-bit encryption algorithm";
                   junos:must "(!(\".. authentication-algorithm\"))";
                   junos:must-message "When using aes-gcm for Encryption the Authentication Algorithm must not be set.";
                 }
               }
             }
             container key {
               description "Define an encryption key";
               choice key-choice {
                 case case_1 {
                   leaf ascii-text {
                     description "Format as text";
                     type string {
                       length "1 .. 255";
                     }
                   }
                 }
                 case case_2 {
                   leaf hexadecimal {
                     description "Format as hexadecimal";
                     type string {
                       length "1 .. 255";
                       junos:posix-pattern "^[[:xdigit:]]+$";
                       junos:pattern-message "Must be hexadecimal digits (0-9, a-f, A-F)";
                     }
                   }
                 }
               }
             }
           }
         }
       }
       case case_2 {
         container ike {
           description "Define an IKE-keyed IPSec vpn";
           uses apply-advanced;
           leaf gateway {
             description "Name of remote gateway";
             junos:must "(!((\".. .. ha-link-encryption\" && \"security ike gateway $$ external-interface\")))";
             junos:must-message "When ha-link-encryption is enabled, external-interface is pre-defined and cannot be configured in associated IKE Gateway";
             junos:must "(!((\".. .. ha-link-encryption\" && \"security ike gateway $$ address\")))";
             junos:must-message "When ha-link-encryption is enabled, peer address is pre-defined and cannot be configured in associated IKE Gateway";
             junos:must "(!((\".. .. ha-link-encryption\" && \"security ike gateway $$ no-nat-traversal\")))";
             junos:must-message "When ha-link-encryption is enabled, Disable NAT-Traversal is not applicable in associated IKE Gateway";
             junos:must "(!((\".. .. ha-link-encryption\" && \"security ike gateway $$ general-ikeid\")))";
             junos:must-message "When ha-link-encryption is enabled, General-IKEID is not applicable in associated IKE Gateway";
             junos:must "(!((\".. .. ha-link-encryption\" && \"security ike gateway $$ dynamic\")))";
             junos:must-message "When ha-link-encryption is enabled, Dynamic is not applicable in associated IKE Gateway";
             junos:must "(!((\".. .. ha-link-encryption\" && \"security ike gateway $$ advpn\")))";
             junos:must-message "When ha-link-encryption is enabled, ADVPN is not applicable in associated IKE Gateway";
             junos:must "(!((\".. .. ha-link-encryption\" && \"security ike gateway $$ tcp-encap-profile\")))";
             junos:must-message "When ha-link-encryption is enabled, tcp-encap-profile is not applicable on associated IKE Gateway";
             junos:must "(!((\".. .. ha-link-encryption\" && \"security ike gateway $$ nat-keepalive\")))";
             junos:must-message "When ha-link-encryption is enabled,  nat-keepalive is not applicable on associated IKE Gateway";
             junos:must "(!((\".. .. ha-link-encryption\" && \"security ike gateway $$ local-address\")))";
             junos:must-message "When ha-link-encryption is enabled, local-address is pre-defined and cannot be configured in associated IKE Gateway";
             junos:must "(!((\".. .. ha-link-encryption\" && \"security ike gateway $$ dead-peer-detection\")))";
             junos:must-message "When ha-link-encryption is enabled, dead-peer-detection (mode:always-send, Interval: 3 sec, Threshold:10) is pre-defined and cannot be configured in associated IKE Gateway";
             junos:must "(!((\".. .. ha-link-encryption\" && \"security ike gateway $$ aaa\")))";
             junos:must-message "When ha-link-encryption is enabled, AAA is not applicable in associated IKE Gateway";
             junos:must "(!((!(\".. .. ha-link-encryption\") && (!(\".. .. bind-interface\") && \"security ike gateway $$ version v2-only\"))))";
             junos:must-message "IKEv2 requires bind-interface configuration as only route-based is supported";
             junos:must "(!((\"security ike gateway $$ advpn\" && \".. proxy-identity\")))";
             junos:must-message "No proxy-identity support on an advpn enabled gateway";
             junos:must "(!((\"security ike gateway $$ aaa access-profile\" && \".. .. vpn-monitor\")))";
             junos:must-message "When aaa access-profile is configured under security ike gateway, vpn-monitor configuration is not allowed";
             junos:must "(!((\"security ike gateway $$ advpn\" && \".. .. vpn-monitor destination-ip\")))";
             junos:must-message "No destination ip support for vpn-monitor in vpn referring to an advpn enabled gateway";
             junos:must "(!((\"security ike gateway $$ dynamic ike-user-type\" && \".. .. vpn-monitor destination-ip\")))";
             junos:must-message "No destination ip support for vpn-monitor in vpn using shared or group ike";
             junos:must "(\"security ike gateway $$\")";
             junos:must-message "Referenced IKE gateway must be defined under [edit security ike gateway]";
             junos:must "(!((\".. .. ha-link-encryption\" && \"security ike gateway $$ local-identity\")))";
             junos:must-message "When ha-link-encryption is enabled, local-identity cannot be configured in associated IKE Gateway";
             junos:must "(!((\".. .. ha-link-encryption\" && \"security ike gateway $$ remote-identity\")))";
             junos:must-message "When ha-link-encryption is enabled, remote-identity cannot be configured in associated IKE Gateway";
             junos:must "(!((\".. .. ha-link-encryption\" && !(\"security ike gateway $$ version v2-only\"))))";
             junos:must-message "When ha-link-encryption is enabled, associated IKE Gateway must be version 2";
             type string {
               length "1 .. 32";
               junos:posix-pattern "^[[:alnum:]][[:alnum:]_-]*$";
               junos:pattern-message "Must be a string beginning with a number or letter and consisting of letters, numbers, dashes and underscores.";
             }
           }
           leaf anti-replay-window-size {
             description "Anti-replay window size Default 64";
             junos:must "(!(\".. no-anti-replay\"))";
             junos:must-message "no-anti-replay must not be defined";
             type union {
               type string {
                 pattern "<.*>|$.*";
               }
               type uint32 {
                 range "64 .. 8192";
               }
             }
           }
           leaf no-anti-replay {
             description "Disable the anti-replay check";
             junos:must "(!(\".. anti-replay-window-size\"))";
             junos:must-message "anti-replay-window-size must not be defined";
             type empty;
           }
           container proxy-identity {
             description "IPSec proxy-id to use in IKE negotiations";
             presence "enable proxy-identity";
             uses ipsec-template-proxy-id;
           }
           leaf ipsec-policy {
             description "Name of the IPSec policy";
             junos:must "(\"security ipsec policy $$\")";
             junos:must-message "Referenced IPSec policy must be defined under [edit security ipsec policy]";
             type string {
               length "1 .. 32";
               junos:posix-pattern "^[[:alnum:]][[:alnum:]_-]*$";
               junos:pattern-message "Must be a string beginning with a number or letter and consisting of letters, numbers, dashes and underscores.";
             }
           }
           leaf install-interval {
             description "Delay installation of rekeyed outbound SAs on initiator";
             default "1";
             units "seconds";
             type union {
               type string {
                 pattern "<.*>|$.*";
               }
               type uint32 {
                 range "0 .. 10";
               }
             }
           }
         }
       }
     }
     list traffic-selector {
       key name;
       ordered-by user;
       description "Traffic selector";
       junos:must "(!(\".. ike proxy-identity\"))";
       junos:must-message "Proxy-identity must not be configured with traffic-selector";
       junos:must "(\".. bind-interface\")";
       junos:must-message "Bind-interface must be configured under [edit security ipsec vpn] hierarchy";
       max-elements 200;
       leaf name {
         description "Name of traffic selector";
         type string {
           length "1 .. 31";
         }
       }
       uses apply-advanced;
       list term {
         key name;
         ordered-by user;
         description "Define a set of traffic selector rules";
         max-elements 200;
         uses traffic-selector-term-object;
       }
       leaf local-ip {
         description "IP address of local traffic-selector";
         type jt:ipprefix-mandatory;
       }
       leaf remote-ip {
         description "IP address of remote traffic-selector";
         type jt:ipprefix-mandatory;
       }
       leaf protocol {
         description "Define protocol";
         junos:must "((\" .. local-ip\" || \" .. remote-ip\"))";
         junos:must-message "Either local-ip or remote-ip must be defined for protocol";
         type string;
       }
       leaf source-port {
         description "Hyphenated source port range";
         junos:must "((\" .. local-ip\" && \" .. protocol\"))";
         junos:must-message "local-ip and protocol must be defined for source-port";
         type string;
       }
       leaf destination-port {
         description "Hyphenated destination port range";
         junos:must "((\" .. remote-ip\" && \" .. protocol\"))";
         junos:must-message "remote-ip and protocol must be defined for destination-port";
         type string;
       }
       leaf metric {
         description "Metric value for st0 route";
         type union {
           type string {
             pattern "<.*>|$.*";
           }
           type uint32 {
             range "1 .. 4294967295";
           }
         }
       }
       leaf description {
         description "Describe the traffic selector";
         type string {
           length "1 .. 80";
         }
       }
     }
     leaf establish-tunnels {
       description "Define the criteria to establish tunnels";
       default "on-traffic";
       junos:must "(\".. ike\")";
       junos:must-message "VPN must be IKE-keyed to define establish-tunnel method";
       type enumeration {
         enum "immediately" {
           description "Establish tunnels immediately";
         }
         enum "on-traffic" {
           description "Establish tunnels on traffic";
         }
         enum "responder-only" {
           description "Establish tunnels only on receiving negotiation from peer";
         }
         enum "responder-only-no-rekey" {
           description "Disable rekey in responder-only mode";
         }
       }
     }
     leaf distribution-profile {
       description "Specify a distribution-profile to distribute tunnel";
       type string;
     }
     leaf tunnel-mtu {
       description "Maximum transmit packet size";
       type union {
         type string {
           pattern "<.*>|$.*";
         }
         type uint32 {
           range "256 .. 9192";
         }
       }
     }
     leaf no-icmp-packet-too-big {
       description "Disable ICMP packet too big notifications for IPv6 packets only";
       type empty;
     }
     leaf passive-mode-tunneling {
       description "No active IP packet checks before IPSec encapsulation";
       type empty;
     }
     leaf match-direction {
       description "Direction for which the rule match is applied";
       type enumeration {
         enum "input" {
           description "Match on input to interface";
         }
         enum "output" {
           description "Match on output from interface";
         }
       }
     }
     container udp-encapsulate {
       presence "enable udp-encapsulate";
       description "UDP encapsulation of IPsec data traffic";
       leaf dest-port {
         description "UDP destination port";
         default "4565";
         type union {
           type string {
             pattern "<.*>|$.*";
           }
           type uint32 {
             range "1025 .. 65536";
           }
         }
       }
     }
   }
   grouping ipsec-template-monitor {
     junos:must "(!(\".. traffic-selector\"))";
     junos:must-message "vpn-monitor with traffic selector is not supported";
     description "Configure VPN monitoring";
     uses apply-advanced;
     leaf optimized {
       description "Optimize for scalability";
       type empty;
     }
     leaf source-interface {
       description "Source interface for monitor message";
       type union {
         type jt:interface-unit;
         type string {
           pattern "<.*>|$.*";
         }
       }
     }
     leaf destination-ip {
       description "Destination IP addres for monitor message";
       type jt:ipaddr;
     }
     container verify-path {
       presence "enable verify-path";
       description "Verify IPSec path using vpn-monitor before bring up st0 state";
       uses apply-advanced;
       leaf destination-ip {
         description "Destination IP addres for verify IPSec path";
         type jt:ipaddr;
       }
       leaf packet-size {
         description "Size of the packet";
         default "64";
         type union {
           type string {
             pattern "<.*>|$.*";
           }
           type uint32 {
             range "64 .. 1350";
           }
         }
       }
     }
   }
   grouping ipsec-template-proxy-id {
     description "Proxy identity settings";
     uses apply-advanced;
     leaf local {
       description "Local IP address/prefix length";
       type jt:ipprefix-mandatory;
     }
     leaf remote {
       description "Remote IP address/prefix length";
       type jt:ipprefix-mandatory;
     }
     leaf service {
       description "Name of serivce that passes through, any enables all services";
       type string {
         length "1 .. 32";
       }
     }
   }
   grouping security-association-manual {
     uses apply-advanced;
     list direction {
       key name;
       ordered-by user;
       description "Define the direction of the security association";
       leaf name {
         type enumeration {
           enum "bidirectional" {
             description "Bidirectional security association";
             junos:must "((!(\".. .. direction $$={inbound}\") && !(\".. .. direction $$={outbound}\")))";
             junos:must-message "Outbound or inbound blocks must not be configured";
           }
         }
       }
       uses apply-advanced;
       leaf protocol {
         description "Define an IPSec protocol for the security association";
         type enumeration {
           enum "ah" {
             description "Authentication header";
             junos:must "(!(\".. encryption\"))";
             junos:must-message "Encryption must not be defined for AH";
             junos:must "(\".. authentication\")";
             junos:must-message "Authentication must be defined for AH";
           }
           enum "esp" {
             description "Encapsulated Security Payload header";
             junos:must "((\".. authentication\" || \".. encryption\"))";
             junos:must-message "Either authentication or encryption must be defined for ESP";
           }
         }
       }
       leaf spi {
         description "Define security parameter index";
         type union {
           type string {
             pattern "<.*>|$.*";
           }
           type uint32 {
             range "256 .. 16639";
           }
         }
       }
       container authentication {
         description "Define authentication parameters";
         uses apply-advanced;
         leaf algorithm {
           description "Define authentication algorithm";
           type enumeration {
             enum "hmac-md5-96" {
               description "HMAC-MD5-96 authentication algorithm";
             }
             enum "hmac-sha1-96" {
               description "HMAC-SHA1-96 authentication algorithm";
             }
           }
         }
         container key {
           description "Define an authentication key";
           choice key-choice {
             case case_1 {
               leaf ascii-text {
                 description "Format as text";
                 type string {
                   length "1 .. 255";
                 }
               }
             }
             case case_2 {
               leaf hexadecimal {
                 description "Format as hexadecimal";
                 type string {
                   length "1 .. 255";
                   junos:posix-pattern "^[[:xdigit:]]+$";
                   junos:pattern-message "Must be hexadecimal digits (0-9, a-f, A-F)";
                 }
               }
             }
           }
         }
       }
       container encryption {
         description "Define encryption parameters";
         uses apply-advanced;
         leaf algorithm {
           description "Define encryption algorithm";
           type enumeration {
             enum "des-cbc" {
               description "DES-CBC encryption algorithm";
             }
             enum "3des-cbc" {
               description "3DES-CBC encryption algorithm";
             }
           }
         }
         container key {
           description "Define an encryption key";
           choice key-choice {
             case case_1 {
               leaf ascii-text {
                 description "Format as text";
                 type string {
                   length "1 .. 255";
                 }
               }
             }
             case case_2 {
               leaf hexadecimal {
                 description "Format as hexadecimal";
                 type string {
                   length "1 .. 255";
                   junos:posix-pattern "^[[:xdigit:]]+$";
                   junos:pattern-message "Must be hexadecimal digits (0-9, a-f, A-F)";
                 }
               }
             }
           }
         }
       }
     }
   }
   grouping security-macsec {
     uses apply-advanced;
     container traceoptions {
       description "Tracing options for debugging protocol operation";
       presence "enable traceoptions";
       uses macsec-trace-options;
     }
     list connectivity-association {
       key name;
       ordered-by user;
       description "Configure connectivity association properties";
       leaf name {
         description "Connectivity association name";
         type string {
           length "1 .. 32";
         }
       }
       uses apply-advanced;
       leaf cipher-suite {
         description "Cipher suite to be used for encryption";
         type enumeration {
           enum "gcm-aes-128" {
             description "GCM-AES-128 cipher suite";
           }
           enum "gcm-aes-256" {
             description "GCM-AES-256 cipher suite";
             junos:must "(!(\".. security-mode static-sak\"))";
             junos:must-message "GCM-AES-256 cipher suite not allowed for static-sak mode";
           }
           enum "gcm-aes-xpn-128" {
             description "GCM-AES-XPN-128 cipher suite";
             junos:must "(!(\".. security-mode static-sak\"))";
             junos:must-message "GCM-AES-XPN-128 cipher suite not allowed for static-sak mode";
           }
           enum "gcm-aes-xpn-256" {
             description "GCM-AES-XPN-256 cipher suite";
             junos:must "(!(\".. security-mode static-sak\"))";
             junos:must-message "GCM-AES-XPN-256 cipher suite not allowed for static-sak mode";
           }
         }
       }
       leaf security-mode {
         description "Connectivity association mode";
         junos:must "((!(\".. security-mode static-cak\") || (\".. pre-shared-key cak\" || (\".. pre-shared-key-chain\" || \".. fallback-key cak\"))))";
         junos:must-message "Pre-shared key or fallback-key or pre-shared-key-chain required for static-cak mode";
         type enumeration {
           enum "dynamic" {
             description "Dynamic connectivity and secure association mode (MKA and dot1x)";
           }
           enum "static-sak" {
             description "Static secure association key mode (no MKA)";
           }
           enum "static-cak" {
             description "Static connectivity association key mode (MKA and Pre-shared key)";
           }
         }
       }
       leaf sak-hash-128 {
         description "Configure to generate 128bit SAK hash to program HW";
         junos:must "((\".. cipher-suite gcm-aes-256\" || \".. cipher-suite gcm-aes-xpn-256\"))";
         junos:must-message "Allowed only for cipher-suite gcm-aes-256 or gcm-aes-xpn-256";
         type empty;
       }
       list secure-channel {
         key name;
         ordered-by user;
         description "Configure secure channel properties";
         junos:must "(\".. security-mode static-sak\")";
         junos:must-message "Secure-channel configuration allowed only for static-sak mode";
         leaf name {
           description "Secure channel name";
           type string;
         }
         uses apply-advanced;
         container id {
           description "Secure channel identifier";
           uses apply-advanced;
           leaf mac-address {
             description "MAC addresses";
             type jt:mac-addr;
           }
           leaf port-id {
             description "Port identifier";
             type union {
               type string {
                 pattern "<.*>|$.*";
               }
               type uint32 {
                 range "1 .. 65535";
               }
             }
           }
         }
         leaf direction {
           description "Secure channel direction";
           type enumeration {
             enum "inbound" {
             }
             enum "outbound" {
             }
           }
         }
         leaf encryption {
           description "Enable Encryption";
           type empty;
         }
         leaf offset {
           description "Confidentiality offset";
           type enumeration {
             enum "0" {
               description "Confidentiality protected for all octets of MACSec PDU data";
             }
             enum "30" {
               description "Confidentiality not protected for initial 30 octets of MACSec PDU data";
             }
             enum "50" {
               description "Confidentiality not protected for initial 50 octets of MACSec PDU data";
             }
           }
         }
         leaf include-sci {
           description "Include secure channel identifier in MAC Security PDU";
           type empty;
         }
         list security-association {
           key name;
           ordered-by user;
           description "Security association";
           leaf name {
             description "Security association number";
             type union {
               type string {
                 pattern "<.*>|$.*";
               }
               type uint32 {
                 range "0 .. 3";
               }
             }
           }
           uses apply-advanced;
           leaf key {
             description "Security association key in hexadecimal format of length 32";
             type string {
               length 32;
               junos:posix-pattern "^[[:xdigit:]]+$";
               junos:pattern-message "Must be hexadecimal digits (0-9, a-f, A-F) of length 32";
             }
           }
         }
       }
       container mka {
         presence "enable mka";
         junos:must "((\".. security-mode static-cak\" || \".. security-mode dynamic\"))";
         junos:must-message "MKA configuration can be set only for dynamic/static-cak modes";
         description "Configure MAC Security Key Agreement protocol properties";
         uses apply-advanced;
         leaf transmit-interval {
           description "Configure MKA periodic transmit interval";
           default "2000";
           units "milliseconds";
           junos:must "(!(\".. bounded-delay\"))";
           junos:must-message "Might not be configured with bounded-delay";
           type union {
             type string {
               pattern "<.*>|$.*";
             }
             type uint32 {
               range "2000 .. 6000";
             }
           }
         }
         leaf sak-rekey-interval {
           description "Configure SAK rekeying interval";
           units "seconds";
           type union {
             type string {
               pattern "<.*>|$.*";
             }
             type uint32 {
               range "60 .. 86400";
             }
           }
         }
         leaf bounded-delay {
           description "Configure Bounded Hello Time";
           junos:must "(\".. .. replay-protect replay-window-size\")";
           junos:must-message "replay-window-size must be configured with bounded-delay";
           type empty;
         }
         leaf suspend-on-request {
           description "Configure on key-server to accept suspend-on-request during gres or issu";
           type empty;
         }
         leaf suspend-for {
           description "Configure to suspend MKA during gres or issu";
           junos:must "(\"system commit synchronize\")";
           junos:must-message "Synchronized commits must be configured with warm-standby";
           junos:must "(\"chassis redundancy graceful-switchover\")";
           junos:must-message "Graceful switchover needs to be configured";
           type empty;
         }
         leaf key-server-priority {
           description "Configure MKA key server priority";
           default "16";
           junos:must "(\".. .. security-mode static-cak\")";
           junos:must-message "Allowed only for static-cak mode";
           type union {
             type string {
               pattern "<.*>|$.*";
             }
             type uint32 {
               range "0 .. 255";
             }
           }
         }
         leaf must-secure {
           description "Allow only secure dot1x traffic";
           junos:must "(\".. .. security-mode dynamic\")";
           junos:must-message "Allowed only for dynamic mode";
           type empty;
         }
         leaf should-secure {
           description "Configure fail open mode for MKA protocol";
           junos:must "(\".. .. security-mode static-cak\")";
           junos:must-message "Allowed only for static mode";
           type empty;
         }
         leaf eapol-address {
           description "Configure EAPOL destination group address";
           default "pae";
           junos:must "(\".. .. security-mode static-cak\")";
           junos:must-message "Allowed only for static-cak mode";
           type string;
         }
       }
       container replay-protect {
         junos:must "((\".. security-mode static-cak\" || \".. security-mode dynamic\"))";
         junos:must-message "Not allowed for static-sak mode";
         description "Configure replay protection";
         uses apply-advanced;
         leaf replay-window-size {
           description "Configure replay protection window size";
           units "packets";
           type union {
             type string {
               pattern "<.*>|$.*";
             }
             type uint32 {
               range "0 .. 65535";
             }
           }
         }
       }
       leaf no-encryption {
         description "Disable encryption";
         junos:must "(!(\".. offset\"))";
         junos:must-message "Offset can be configured only with encryption";
         junos:must "((\".. security-mode static-cak\" || \".. security-mode dynamic\"))";
         junos:must-message "Encryption for static-sak mode should be configured under secure-channel";
         type empty;
       }
       leaf disable-preceding-key {
         description "Disable CA preceding key duing key switch-over";
         junos:must "(\".. security-mode static-cak\")";
         junos:must-message "Enabling configuration allowed only in static-cak mode";
         type empty;
       }
       leaf offset {
         description "Confidentiality offset";
         default "0";
         junos:must "((\".. security-mode static-cak\" || \".. security-mode dynamic\"))";
         junos:must-message "Offset for static-sak mode should be configured under secure-channel";
         type enumeration {
           enum "0" {
             description "Confidentiality provided for all octets of data";
           }
           enum "30" {
             description "Confidentiality not provided for initial 30 octets of data";
           }
           enum "50" {
             description "Confidentiality not provided for initial 50 octets of data";
           }
         }
       }
       leaf include-sci {
         description "Include secure channel identifier in MAC Security PDU";
         junos:must "((\".. security-mode static-cak\" || \".. security-mode dynamic\"))";
         junos:must-message "Not allowed for static-sak mode";
         type empty;
       }
       container pre-shared-key {
         presence "enable pre-shared-key";
         junos:must "(\".. security-mode static-cak\")";
         junos:must-message "Pre-shared key configuration allowed only in static-cak mode";
         description "Configure pre-shared connectivity association key";
         uses apply-advanced;
         leaf ckn {
           description "Connectivity association key name in hexadecimal format";
           type string {
             length "2 .. 64";
             junos:posix-pattern "^([0-9a-fA-F][0-9a-fA-F]){1,32}$";
             junos:pattern-message "Must be an even-length string up to 64 hexadecimal digits (0-9, a-f, A-F)";
           }
         }
         leaf cak {
           description "Connectivity association key in hexadecimal format";
           type string {
             length "1 .. 64";
             junos:posix-pattern "^[[:xdigit:]]+$";
             junos:pattern-message "Must be hexadecimal digits (0-9, a-f, A-F)";
           }
         }
       }
       container fallback-key {
         presence "enable fallback-key";
         junos:must "(\".. security-mode static-cak\")";
         junos:must-message "Fallback key configuration allowed only in static-cak mode";
         description "Configure fallback key for connectivity association";
         uses apply-advanced;
         leaf ckn {
           description "Connectivity association fallback key name in hexadecimal format";
           junos:must "(!(\".. .. pre-shared-key ckn $$\"))";
           junos:must-message "fallback-key CKN cannot be same as pre-shared-key CKN";
           type string {
             length "2 .. 64";
             junos:posix-pattern "^([0-9a-fA-F][0-9a-fA-F]){1,32}$";
             junos:pattern-message "Must be an even-length string up to 64 hexadecimal digits (0-9, a-f, A-F)";
           }
         }
         leaf cak {
           description "Connectivity association fallback key secret in hexadecimal format";
           type string {
             length "1 .. 64";
             junos:posix-pattern "^[[:xdigit:]]+$";
             junos:pattern-message "Must be hexadecimal digits (0-9, a-f, A-F)";
           }
         }
       }
       leaf pre-shared-key-chain {
         description "Pre-shared key chain name for connectivity association";
         junos:must "(!(\".. pre-shared-key\"))";
         junos:must-message "May not be configured with pre-shared-key";
         junos:must "(\"security authentication-key-chains key-chain $$\")";
         junos:must-message "authentication-key-chains not defined !!";
         type string {
           junos:posix-pattern "^.{1,32}$";
           junos:pattern-message "Must be string of 32 characters or less";
         }
       }
       list exclude-protocol {
         key name;
         ordered-by user;
         description "Configure protocols to exclude from MAC Security";
         junos:must "((\".. security-mode static-cak\" || \".. security-mode dynamic\"))";
         junos:must-message "Not allowed for static-sak mode";
         leaf name {
           type enumeration {
             enum "cdp" {
               description "Cisco Discovery Protocol";
             }
             enum "lldp" {
               description "Link Level Discovery Protocol";
             }
             enum "lacp" {
               description "Link Aggregation Control Protocol";
             }
           }
         }
       }
     }
     list interfaces {
       key name;
       description "Interfaces on which macsec configuration is applied";
       leaf name {
         type union {
           type jt:interface-device;
           type string {
             pattern "<.*>|$.*";
           }
         }
       }
       uses apply-advanced;
       list unit {
         key name;
         description "Logical interface";
         leaf name {
           description "Logical unit number";
           junos:must "(!(\".. .. connectivity-association\"))";
           junos:must-message "Cannot configure connectivity association on both physical and logical interface";
           type union {
             type string {
               pattern "<.*>|$.*";
             }
             type uint32 {
               range "0 .. 16385";
             }
           }
         }
         uses apply-advanced;
         leaf connectivity-association {
           description "Connectivity association name";
           junos:must "(!(\"security macsec connectivity-association $$ pre-shared-key-chain\"))";
           junos:must-message "Pre-shared keychain not supported for IFL macsec";
           junos:must "(\"security macsec connectivity-association $$\")";
           junos:must-message "Connectivity association not defined";
           type string;
         }
         container traceoptions {
           description "Tracing options of MKA protocol";
           presence "enable traceoptions";
           junos:must "(!(\".. .. traceoptions\"))";
           junos:must-message "Cannot configure traceoptions on both IFD and IFL";
           uses mka-trace-options;
         }
       }
       leaf connectivity-association {
         description "Connectivity association name";
         junos:must "(\"security macsec connectivity-association $$\")";
         junos:must-message "Connectivity association not defined";
         type string;
       }
       container traceoptions {
         description "Tracing options of MKA protocol";
         presence "enable traceoptions";
         junos:must "(\".. connectivity-association\")";
         junos:must-message "Connectivity association should be configured on interface to enable traceoptions";
         uses mka-trace-options;
       }
     }
     list cluster-control-port {
       key name;
       description "Cluster control port on which macsec configuration is applied";
       leaf name {
         description "Port identifier";
         type union {
           type string {
             pattern "<.*>|$.*";
           }
           type uint32 {
             range "0 .. 1";
           }
         }
       }
       uses apply-advanced;
       leaf connectivity-association {
         description "Connectivity association name";
         junos:must "(!(\"security macsec connectivity-association $$ pre-shared-key-chain\"))";
         junos:must-message "Pre-shared keychain is not supported on cluster control port";
         junos:must "(\"security macsec connectivity-association $$\")";
         junos:must-message "Connectivity association not defined";
         type string;
       }
       container traceoptions {
         description "Tracing options of MKA protocol";
         presence "enable traceoptions";
         uses mka-trace-options;
       }
     }
     list cluster-data-port {
       key name;
       description "Cluster data port on which macsec configuration is applied";
       leaf name {
         junos:must "(!(\"security macsec connectivity-association $$ pre-shared-key-chain\"))";
         junos:must-message "Pre-shared keychain is not supported on cluster data port";
         type union {
           type jt:interface-device;
           type string {
             pattern "<.*>|$.*";
           }
         }
       }
       uses apply-advanced;
       leaf connectivity-association {
         description "Connectivity association name";
         junos:must "(\"security macsec connectivity-association $$\")";
         junos:must-message "Connectivity association not defined";
         type string;
       }
       container traceoptions {
         description "Tracing options of MKA protocol";
         presence "enable traceoptions";
         uses mka-trace-options;
       }
     }
   }
   grouping macsec-trace-options {
     description "Trace options for MACSec Protocol";
     uses apply-advanced;
     container file {
       description "Trace file options";
       leaf filename {
         description "Name of file in which to write trace information";
         type string {
           length "1 .. 1024";
           junos:posix-pattern "![/ %]";
           junos:pattern-message "Must not contain '/', % or a space";
         }
       }
       leaf replace {
         description "Replace trace file rather than appending to it";
         status deprecated;
         type empty;
       }
       leaf size {
         description "Maximum trace file size";
         type string;
       }
       leaf files {
         description "Maximum number of trace files";
         default "10";
         type union {
           type string {
             pattern "<.*>|$.*";
           }
           type uint32 {
             range "2 .. 1000";
           }
         }
       }
       leaf no-stamp {
         description "Do not timestamp trace file";
         status deprecated;
         type empty;
       }
       choice world-readable-choice {
         leaf world-readable {
           description "Allow any user to read the log file";
           type empty;
         }
         leaf no-world-readable {
           description "Don't allow any user to read the log file";
           type empty;
         }
       }
     }
     list flag {
       key name;
       ordered-by user;
       description "Tracing parameters";
       junos:must "(\".. file\")";
       junos:must-message "Trace file name required to enable tracing";
       leaf name {
         type enumeration {
           enum "config" {
             description "Trace configuration messages";
           }
           enum "debug" {
             description "Trace debug messages";
           }
           enum "telemetry" {
             description "Trace telemetry messages";
           }
           enum "normal" {
             description "Trace normal messages";
           }
           enum "all" {
             description "Trace all";
           }
         }
       }
     }
   }
   grouping mka-trace-options {
     description "Trace options for MKA protocol";
     uses apply-advanced;
     container file {
       description "Trace file options";
       leaf filename {
         description "Name of file in which to write trace information";
         type string {
           length "1 .. 1024";
           junos:posix-pattern "![/ %]";
           junos:pattern-message "Must not contain '/', % or a space";
         }
       }
       leaf replace {
         description "Replace trace file rather than appending to it";
         status deprecated;
         type empty;
       }
       leaf size {
         description "Maximum trace file size";
         type string;
       }
       leaf files {
         description "Maximum number of trace files";
         default "10";
         type union {
           type string {
             pattern "<.*>|$.*";
           }
           type uint32 {
             range "2 .. 1000";
           }
         }
       }
       leaf no-stamp {
         description "Do not timestamp trace file";
         status deprecated;
         type empty;
       }
       choice world-readable-choice {
         leaf world-readable {
           description "Allow any user to read the log file";
           type empty;
         }
         leaf no-world-readable {
           description "Don't allow any user to read the log file";
           type empty;
         }
       }
     }
     list flag {
       key name;
       ordered-by user;
       description "Tracing parameters";
       junos:must "(\".. file\")";
       junos:must-message "Trace file name required to enable tracing";
       leaf name {
         type enumeration {
           enum "mka-packets" {
             description "Trace MKA input and output packets";
           }
           enum "state" {
             description "Trace MKA state information";
           }
           enum "to-secy" {
             description "Trace MKA to SecY state changes";
           }
           enum "keys" {
             description "Trace key creation/generation information";
           }
           enum "normal" {
             description "Trace normal events";
           }
           enum "all" {
             description "Trace all";
           }
         }
       }
     }
   }
   grouping security-option-82-type {
     description "DHCP option-82 processing";
     uses apply-advanced;
     container circuit-id {
       presence "enable circuit-id";
       description "Configure DHCP option 82 circuit id";
       uses apply-advanced;
       container prefix {
         description "Configure DHCP option 82 circuit id prefix";
         uses apply-advanced;
         leaf host-name {
           description "Add router host name to DHCP option-82 circuit id";
           type empty;
         }
         leaf logical-system-name {
           description "Add logical system name to DHCP option-82 circuit id";
           type empty;
         }
         leaf routing-instance-name {
           description "Add routing instance name to DHCP option-82 circuit id";
           type empty;
         }
       }
       leaf use-interface-description {
         description "Use interface description instead of circuit identifier";
         type enumeration {
           enum "logical" {
             description "Use the logical interface description";
           }
           enum "device" {
             description "Use the device interface description";
           }
         }
       }
       leaf use-vlan-id {
         description "Use VLAN id instead of name";
         type empty;
       }
     }
     container remote-id {
       presence "enable remote-id";
       description "Configure DHCP option 82 remote id";
       uses apply-advanced;
       leaf host-name {
         description "Add router host name to DHCP option-82 remote id";
         type empty;
       }
       leaf use-interface-description {
         description "Use interface description instead of interface name";
         type enumeration {
           enum "logical" {
             description "Use the logical interface description";
           }
           enum "device" {
             description "Use the device interface description";
           }
         }
       }
       leaf use-string {
         description "Use raw string instead of the default remote id";
         junos:must "(!(\".. use-interface-description\"))";
         junos:must-message "use-string and use-interface-description cannot be configured together";
         type string;
       }
       leaf mac {
         description "Add chassis MAC Address to DHCP option-82 remote id";
         type empty;
       }
     }
     container vendor-id {
       presence "enable vendor-id";
       description "Configure DHCP option 82 vendor id";
       uses apply-advanced;
       leaf use-string {
         description "Use raw string instead of the default vendor id";
         default "Juniper Networks";
         type string;
       }
     }
   }
   grouping security-pki {
     uses apply-advanced;
     list ca-profile {
       key name;
       ordered-by user;
       description "Certificate authority profile configuration";
       leaf name {
         description "Name of certificate authority profile";
         type string {
           length "1 .. 32";
           junos:posix-pattern "![/%. ]";
           junos:pattern-message "Must not contain '/', %, '.' or a space";
         }
       }
       uses apply-advanced;
       leaf ca-identity {
         description "Certificate authority identifier";
         type string;
       }
       leaf source-address {
         description "Use specified address as source address";
         type jt:ipaddr;
       }
       leaf proxy-profile {
         description "Use specified proxy server";
         junos:must "(\"services proxy profile $$\")";
         junos:must-message "Referenced Proxy profile must be defined under [edit services proxy profile]";
         type string;
       }
       leaf routing-instance {
         description "Use specified routing instance";
         junos:must "((\"routing-instances $$\" || any \"tenants <*> routing-instances $$\"))";
         junos:must-message "referenced routing-instance must be defined";
         type string;
       }
       container enrollment {
         description "Enrollment parameters for certificate authority";
         uses apply-advanced;
         leaf url {
           description "Enrollment URL of certificate authority";
           type string;
         }
         leaf retry {
           description "Number of enrollment retry attempts before aborting";
           default "1000";
           type union {
             type string {
               pattern "<.*>|$.*";
             }
             type uint32 {
               range "0 .. 1080";
             }
           }
         }
         leaf retry-interval {
           description "Interval in seconds between the enrollment retries";
           default "600";
           type union {
             type string {
               pattern "<.*>|$.*";
             }
             type uint32 {
               range "0 .. 3600";
             }
           }
         }
       }
       container revocation-check {
         description "Method for checking certificate revocations";
         uses apply-advanced;
         choice revocation-check-options {
           case case_1 {
             leaf use-crl {
               description "Use CRL for revocation check";
               type empty;
             }
           }
           case case_2 {
             leaf use-ocsp {
               description "Use OCSP for revocation check";
               type empty;
             }
           }
           case case_3 {
             leaf disable {
               description "Disable revocation check";
               type empty;
             }
           }
         }
         container ocsp {
           presence "enable ocsp";
           description "Online Certificate Status Protocol (OCSP) configuration";
           uses apply-advanced;
           list url {
             key name;
             ordered-by user;
             leaf name {
               description "HTTP URL for OCSP access location";
               type string {
                 length "1 .. 500";
               }
             }
             uses apply-advanced;
           }
           leaf nonce-payload {
             description "Include nonce payload in OCSP requests";
             type enumeration {
               enum "enable" {
                 description "Send nonce paylod in OCSP request";
               }
               enum "disable" {
                 description "Do not send nonce payload in OCSP request";
               }
             }
           }
           leaf disable-responder-revocation-check {
             description "Disable OCSP responder certificate revocation check";
             type empty;
           }
           leaf accept-unknown-status {
             description "Accept certificates with unknown status";
             type empty;
           }
           container connection-failure {
             presence "enable connection-failure";
             description "Actions on failure to connect to OCSP Responder";
             uses apply-advanced;
             choice connection-failure-options {
               case case_1 {
                 leaf fallback-crl {
                   description "Use CRL for revocation check";
                   type empty;
                 }
               }
               case case_2 {
                 leaf disable {
                   description "Disable OCSP check on connection failure";
                   type empty;
                 }
               }
             }
           }
         }
         container crl {
           description "Certificate revocation list configuration";
           uses apply-advanced;
           container disable {
             leaf on-download-failure {
               description "Check revocation status with existing CRL file if present, otherwise skip. This feature must be enabled for manual CRL download.";
               type empty;
             }
           }
           list url {
             key name;
             ordered-by user;
             leaf name {
               description "URL of CRL distribution point for certificate authority";
               type string {
                 length "1 .. 500";
               }
             }
             uses apply-advanced;
             leaf password {
               description "Password for authentication with the server";
               type jt:unreadable;
             }
           }
           leaf refresh-interval {
             description "CRL refresh interval";
             units "hours";
             type union {
               type string {
                 pattern "<.*>|$.*";
               }
               type uint32 {
                 range "0 .. 8784";
               }
             }
           }
         }
       }
       container administrator {
         description "Administrator information";
         uses apply-advanced;
         leaf email-address {
           description "Administrator e-mail to which to send certificate requests";
           type string;
         }
       }
     }
     list trusted-ca-group {
       key name;
       ordered-by user;
       description "Trusted Certificate Authority group configuration";
       leaf name {
         description "Name of the trusted CA group";
         type string {
           length "1 .. 63";
         }
       }
       uses apply-advanced;
       leaf-list ca-profiles {
         ordered-by user;
         description "Name of the CA profiles (maximum 20)";
         type string {
           length "1 .. 63";
         }
         max-elements 20;
       }
     }
     container trap {
       presence "enable trap";
       description "Trap options for PKI certificates";
       uses apply-advanced;
       list certificate-id {
         key name;
         ordered-by user;
         description "Local certificate identifier";
         leaf name {
           description "Local cert id";
           type string;
         }
         uses apply-advanced;
         leaf days {
           description "Number of days to generate trap (default 60)";
           default "60";
           type union {
             type string {
               pattern "<.*>|$.*";
             }
             type uint32 {
               range "1 .. 100";
             }
           }
         }
       }
       list ca-identity {
         key name;
         ordered-by user;
         description "CA identity";
         leaf name {
           description "CA profile";
           junos:must "(\"security pki ca-profile $$\")";
           junos:must-message "Referenced ca-profile must be defined under [edit security pki ca-profile]";
           type string;
         }
         uses apply-advanced;
         leaf days {
           description "Number of days to generate trap (default 60)";
           default "60";
           type union {
             type string {
               pattern "<.*>|$.*";
             }
             type uint32 {
               range "1 .. 100";
             }
           }
         }
       }
       container all-certificates {
         presence "enable all-certificates";
         description "Trap config for all certificates";
         uses apply-advanced;
         leaf days {
           description "Number of days to generate trap (default 60)";
           default "60";
           type union {
             type string {
               pattern "<.*>|$.*";
             }
             type uint32 {
               range "1 .. 100";
             }
           }
         }
       }
     }
     container auto-re-enrollment {
       description "Auto re-enroll of certificate";
       uses apply-advanced;
       container cmpv2 {
         presence "enable cmpv2";
         description "CMPv2 auto re-enrollment configuration";
         uses apply-advanced;
         list certificate-id {
           key name;
           ordered-by user;
           description "CMPv2 auto re-enrollment configuration for certificate-id";
           leaf name {
             description "Certificate identifier that needs auto re-enrollment";
             type string {
               junos:posix-pattern "^.{1,32}$";
               junos:pattern-message "Must be string of 32 characters or less";
             }
           }
           uses apply-advanced;
           container re-enroll-time {
             presence "enable re-enroll-time";
             description "Re-enroll trigger time in days <value> | hours <value> | percentage <value>";
             uses apply-advanced;
             choice re-enroll-time-options {
               case case_1 {
                 leaf days {
                   description "Re-enrollment trigger time in days from now";
                   type union {
                     type uint32;
                     type string {
                       pattern "<.*>|$.*";
                     }
                   }
                 }
               }
               case case_2 {
                 leaf hours {
                   description "Re-enrollment trigger time in hours from now";
                   type union {
                     type uint32;
                     type string {
                       pattern "<.*>|$.*";
                     }
                   }
                 }
               }
               case case_3 {
                 leaf percent {
                   description "Re-enrollment trigger time before expiration as percentage";
                   type union {
                     type string {
                       pattern "<.*>|$.*";
                     }
                     type uint32 {
                       range "1 .. 99";
                     }
                   }
                 }
               }
             }
           }
           leaf ca-profile-name {
             description "Name of certificate authority profile";
             junos:must "(\"security pki ca-profile $$ enrollment url\")";
             junos:must-message "Referenced ca-profile must have enrollment url configured under [edit security pki ca-profile <ca-profile-name> enrollment url]";
             junos:must "(\"security pki ca-profile $$\")";
             junos:must-message "Referenced ca-profile must be defined under [edit security pki ca-profile]";
             type string {
               junos:posix-pattern "^.{1,32}$";
               junos:pattern-message "Must be string of 32 characters or less";
             }
           }
           leaf re-enroll-trigger-time-percentage {
             description "Re-enrollment trigger time before expiration as percentage";
             type union {
               type string {
                 pattern "<.*>|$.*";
               }
               type uint32 {
                 range "1 .. 99";
               }
             }
           }
           leaf re-generate-keypair {
             description "Generate new key-pair for auto-re-enrollment";
             type empty;
           }
         }
       }
       container scep {
         presence "enable scep";
         description "SCEP auto re-enrollment configuration";
         uses apply-advanced;
         list certificate-id {
           key name;
           ordered-by user;
           description "SCEP auto re-enrollment configuration for certificate-id";
           leaf name {
             description "Certificate identifier that needs auto re-enrollment";
             type string {
               junos:posix-pattern "^.{1,32}$";
               junos:pattern-message "Must be string of 32 characters or less";
             }
           }
           uses apply-advanced;
           container re-enroll-time {
             presence "enable re-enroll-time";
             description "Re-enroll time in days <value> | hours <value> | percentage <value>";
             uses apply-advanced;
             choice re-enroll-time-options {
               case case_1 {
                 leaf days {
                   description "Re-enrollment trigger time in days from now";
                   type union {
                     type uint32;
                     type string {
                       pattern "<.*>|$.*";
                     }
                   }
                 }
               }
               case case_2 {
                 leaf hours {
                   description "Re-enrollment trigger time in hours from now";
                   type union {
                     type uint32;
                     type string {
                       pattern "<.*>|$.*";
                     }
                   }
                 }
               }
               case case_3 {
                 leaf percent {
                   description "Re-enrollment trigger time before expiration as percentage";
                   type union {
                     type string {
                       pattern "<.*>|$.*";
                     }
                     type uint32 {
                       range "1 .. 99";
                     }
                   }
                 }
               }
             }
           }
           leaf ca-profile-name {
             description "Name of certificate authority profile";
             junos:must "(\"security pki ca-profile $$ enrollment url\")";
             junos:must-message "Referenced ca-profile must have enrollment url configured under [edit security pki ca-profile <ca-profile-name> enrollment url]";
             junos:must "(\"security pki ca-profile $$\")";
             junos:must-message "Referenced ca-profile must be defined under [edit security pki ca-profile]";
             type string {
               junos:posix-pattern "^.{1,32}$";
               junos:pattern-message "Must be string of 32 characters or less";
             }
           }
           leaf re-generate-keypair {
             description "Generate new key-pair for auto-re-enrollment";
             type empty;
           }
           leaf re-enroll-trigger-time-percentage {
             description "Re-enrollment trigger time before expiration as percentage";
             type union {
               type string {
                 pattern "<.*>|$.*";
               }
               type uint32 {
                 range "1 .. 99";
               }
             }
           }
           leaf challenge-password {
             description "Password used by CA for enrollment and revocation";
             type jt:unreadable;
           }
           container scep-encryption-algorithm {
             presence "enable scep-encryption-algorithm";
             description "SCEP encryption algorithm";
             uses apply-advanced;
             choice scep-encryption-algorithm-options {
               case case_1 {
                 leaf des {
                   description "Use DES as SCEP encryption algorithm";
                   type empty;
                 }
               }
               case case_2 {
                 leaf des3 {
                   description "Use DES3 as SCEP encryption algorithm";
                   type empty;
                 }
               }
             }
           }
           container scep-digest-algorithm {
             presence "enable scep-digest-algorithm";
             description "SCEP digest algorithm";
             uses apply-advanced;
             choice scep-digest-algorithm-options {
               case case_1 {
                 leaf md5 {
                   description "Use MD5 as SCEP digest algorithm";
                   type empty;
                 }
               }
               case case_2 {
                 leaf sha1 {
                   description "Use SHA1 as SCEP digest algorithm";
                   type empty;
                 }
               }
             }
           }
         }
       }
       list certificate-id {
         key name;
         ordered-by user;
         description "Auto re-enrollment configuration for certificate-id";
         leaf name {
           description "Certificate identifier that needs auto re-enrollment";
           type string {
             junos:posix-pattern "^.{1,32}$";
             junos:pattern-message "Must be string of 32 characters or less";
           }
         }
         uses apply-advanced;
         container re-enroll-time {
           presence "enable re-enroll-time";
           description "Re-enroll trigger time in days <value> | hours <value> | percentage <value>";
           uses apply-advanced;
           choice re-enroll-time-options {
             case case_1 {
               leaf days {
                 description "Re-enrollment trigger time in days from now";
                 type union {
                   type uint32;
                   type string {
                     pattern "<.*>|$.*";
                   }
                 }
               }
             }
             case case_2 {
               leaf hours {
                 description "Re-enrollment trigger time in hours from now";
                 type union {
                   type uint32;
                   type string {
                     pattern "<.*>|$.*";
                   }
                 }
               }
             }
             case case_3 {
               leaf percent {
                 description "Re-enrollment trigger time before expiration as percentage";
                 type union {
                   type string {
                     pattern "<.*>|$.*";
                   }
                   type uint32 {
                     range "1 .. 99";
                   }
                 }
               }
             }
           }
         }
         leaf ca-profile-name {
           description "Name of certificate authority profile";
           junos:must "(\"security pki ca-profile $$ enrollment url\")";
           junos:must-message "Referenced ca-profile must have enrollment url configured under [edit security pki ca-profile <ca-profile-name> enrollment url]";
           junos:must "(\"security pki ca-profile $$\")";
           junos:must-message "Referenced ca-profile must be defined under [edit security pki ca-profile]";
           type string {
             junos:posix-pattern "^.{1,32}$";
             junos:pattern-message "Must be string of 32 characters or less";
           }
         }
         leaf re-generate-keypair {
           description "Generate new key-pair for auto-re-enrollment";
           type empty;
         }
         leaf re-enroll-trigger-time-percentage {
           description "Re-enrollment trigger time before expiration as percentage";
           type union {
             type string {
               pattern "<.*>|$.*";
             }
             type uint32 {
               range "1 .. 99";
             }
           }
         }
         leaf challenge-password {
           description "Password used by CA for enrollment and revocation";
           type jt:unreadable;
         }
         container scep-encryption-algorithm {
           presence "enable scep-encryption-algorithm";
           description "SCEP encryption algorithm";
           uses apply-advanced;
           choice scep-encryption-algorithm-options {
             case case_1 {
               leaf des {
                 description "Use DES as SCEP encryption algorithm";
                 type empty;
               }
             }
             case case_2 {
               leaf des3 {
                 description "Use DES3 as SCEP encryption algorithm";
                 type empty;
               }
             }
           }
         }
         container scep-digest-algorithm {
           presence "enable scep-digest-algorithm";
           description "SCEP digest algorithm";
           uses apply-advanced;
           choice scep-digest-algorithm-options {
             case case_1 {
               leaf md5 {
                 description "Use MD5 as SCEP digest algorithm";
                 type empty;
               }
             }
             case case_2 {
               leaf sha1 {
                 description "Use SHA1 as SCEP digest algorithm";
                 type empty;
               }
             }
           }
         }
         leaf validity-period {
           description "Certificate validity period in days from enrollment start date";
           status deprecated;
           type union {
             type string {
               pattern "<.*>|$.*";
             }
             type uint32 {
               range "1 .. 4095";
             }
           }
         }
       }
     }
     container traceoptions {
       description "PKI trace options";
       uses apply-advanced;
       leaf no-remote-trace {
         description "Disable remote tracing";
         junos:must "(\"system tracing\")";
         junos:must-message "'no-remote-trace' is valid only when [system tracing] is configured";
         type empty;
       }
       container file {
         description "Trace file information";
         leaf filename {
           description "Name of file in which to write trace information";
           type string {
             length "1 .. 1024";
             junos:posix-pattern "![/ %]";
             junos:pattern-message "Must not contain '/', % or a space";
           }
         }
         leaf size {
           description "Maximum trace file size";
           type string;
         }
         leaf files {
           description "Maximum number of trace files";
           default "3";
           type union {
             type string {
               pattern "<.*>|$.*";
             }
             type uint32 {
               range "2 .. 1000";
             }
           }
         }
         choice world-readable-choice {
           leaf world-readable {
             description "Allow any user to read the log file";
             type empty;
           }
           leaf no-world-readable {
             description "Don't allow any user to read the log file";
             type empty;
           }
         }
         leaf match {
           description "Regular expression for lines to be logged";
           type jt:regular-expression;
         }
       }
       list flag {
         key name;
         ordered-by user;
         description "Tracing parameters";
         leaf name {
           type enumeration {
             enum "certificate-verification" {
               description "PKI certificate verification tracing";
             }
             enum "online-crl-check" {
               description "PKI online crl tracing";
             }
             enum "enrollment" {
               description "PKI certificate enrollment tracing";
             }
             enum "all" {
               description "Trace with all flags enabled";
             }
           }
         }
       }
     }
   }
   grouping security-traceoptions {
     description "Trace options for key management process";
     uses apply-advanced;
     leaf no-remote-trace {
       description "Disable remote tracing";
       junos:must "(\"system tracing\")";
       junos:must-message "'no-remote-trace' is valid only when [system tracing] is configured";
       type empty;
     }
     container file {
       description "Trace file information";
       leaf filename {
         description "Name of file in which to write trace information";
         type string {
           length "1 .. 1024";
           junos:posix-pattern "![/ %]";
           junos:pattern-message "Must not contain '/', % or a space";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     leaf rate-limit {
       description "Limit the incoming rate of trace messages";
       default "0";
       type union {
         type string {
           pattern "<.*>|$.*";
         }
         type uint32 {
           range "0 .. 4294967295";
         }
       }
     }
     container filter {
       description "Filter parameters for IKE traceoptions";
       uses apply-advanced;
       leaf fpc {
         description "FPC slot number";
         type union {
           type string {
             pattern "<.*>|$.*";
           }
           type uint32;
         }
       }
       leaf pic {
         description "PIC slot number";
         type union {
           type string {
             pattern "<.*>|$.*";
           }
           type uint32;
         }
       }
     }
     list flag {
       key name;
       ordered-by user;
       description "Tracing parameters for IKE";
       leaf name {
         type enumeration {
           enum "timer" {
             description "Trace internal timer events";
           }
           enum "routing-socket" {
             description "Trace routing socket messages";
           }
           enum "parse" {
             description "Trace configuration processing";
           }
           enum "config" {
             description "Trace configuration download processing";
           }
           enum "ike" {
             description "Trace IKE module processing";
           }
           enum "policy-manager" {
             description "Trace policy manager processing";
           }
           enum "general" {
             description "Trace general events";
           }
           enum "database" {
             description "Trace security associations database events";
           }
           enum "certificates" {
             description "Trace certificate events";
           }
           enum "snmp" {
             description "Trace SNMP operations";
           }
           enum "thread" {
             description "Trace thread processing";
           }
           enum "high-availability" {
             description "Trace high-availability operations";
           }
           enum "next-hop-tunnels" {
             description "Trace next-hop-tunnels operations";
           }
           enum "all" {
             description "Trace everything";
           }
         }
       }
     }
   }
   grouping security-zone-type {
     description "Security zone";
     leaf name {
       description "Name of the zone";
       type string {
         length "1 .. 63";
         junos:posix-pattern "^[[:alnum:]._-]+$";
         junos:pattern-message "Must be a string consisting of letters, numbers, dashes and underscores";
       }
     }
     uses apply-advanced;
     leaf description {
       description "Text description of zone";
       type string {
         length "1 .. 900";
         junos:posix-pattern "^[^&<>\n]+$";
         junos:pattern-message "Must be a string excluding '&', '<', '>' and '\n'";
       }
     }
     leaf tcp-rst {
       description "Send RST for NON-SYN packet not matching TCP session";
       type empty;
     }
     container address-book {
       description "Address book entries";
       junos:must "(!(\"security address-book\"))";
       junos:must-message "Zone specific address books are not allowed when there are global address books defined";
       uses address-book-type;
     }
     leaf screen {
       description "Name of ids option object applied to the zone";
       junos:must "(\"security screen ids-option $$\")";
       junos:must-message "referenced ids-object must be defined under [security screen ids-option]";
       type string {
         length "1 .. 32";
       }
     }
     container host-inbound-traffic {
       description "Allowed system services & protocols";
       uses zone_host_inbound_traffic_t;
     }
     list interfaces {
       key name;
       ordered-by user;
       description "Interfaces that are part of this zone";
       uses zone-interface-list-type;
     }
     leaf application-tracking {
       description "Enable Application tracking support for this zone";
       type empty;
     }
     leaf source-identity-log {
       description "Show user and group info in session log for this zone";
       type empty;
     }
     container advance-policy-based-routing-profile {
       description "Enable Advance Policy Based Routing on this zone";
       uses apply-advanced;
       leaf profile {
         description "Advance policy based routing profile name";
         type string {
           length "1 .. 63";
         }
       }
     }
     leaf enable-reverse-reroute {
       description "Enable Reverse route lookup when there is change in ingress interface";
       type empty;
     }
     leaf unidirectional-session-refreshing {
       description "Enable unidirectional session refreshing on this zone";
       type empty;
     }
     container advanced-connection-tracking {
       description "Enable Advance Policy Based Routing on this zone";
       uses apply-advanced;
       leaf timeout {
         description "Timeout value in seconds for advanced-connection-tracking table for this zone";
         type union {
           type uint32;
           type string {
             pattern "<.*>|$.*";
           }
         }
       }
       leaf mode {
         type enumeration {
           enum "allow-any-host" {
             description "Create allow-any-host table, thus policies whose to-zone is this zone can lookup";
           }
           enum "allow-target-host" {
             description "Create allow-target-host table, thus policies whose to-zone is this zone can lookup";
           }
           enum "allow-target-host-port" {
             description "Create allow-target-host-port table, thus policies whose to-zone is this zone can lookup";
           }
         }
       }
       leaf track-all-policies-to-this-zone {
         description "Mandate all policies with to-zone set to this zone to do connection track table lookup";
         type empty;
       }
     }
   }
   grouping address-book-type {
     description "Configure security address book for the zone";
     uses apply-advanced;
     list address {
       key name;
       ordered-by user;
       description "Define a security address";
       uses address_type;
     }
     list address-set {
       key name;
       ordered-by user;
       description "Define a security address set";
       uses address_set_type;
     }
   }
   grouping security_intelligence_feeds {
     description "Specify the feed post action";
     uses apply-advanced;
     container add-source-ip-to-feed {
       description "Add Source IP to Feed";
       uses apply-advanced;
       leaf name-of-feed {
         description "Specify the desired feed-name";
         type string {
           length "1 .. 64";
         }
       }
     }
     container add-destination-ip-to-feed {
       description "Add Destination IP to Feed";
       uses apply-advanced;
       leaf name-of-feed {
         description "Specify the desired feed-name";
         type string {
           length "1 .. 64";
         }
       }
     }
     container add-source-identity-to-feed {
       description "Add Source Identity to Feed";
       uses apply-advanced;
       leaf name-of-feed {
         description "Specify the desired feed-name";
         type string {
           length "1 .. 64";
         }
       }
     }
     container add-destination-identity-to-feed {
       description "Add Destination Identity to Feed";
       uses apply-advanced;
       leaf name-of-feed {
         description "Specify the desired feed-name";
         type string {
           length "1 .. 64";
         }
       }
     }
   }
   grouping server {
     description "Server settings";
     uses apply-advanced;
     leaf host {
       description "Server host IP address or string host name";
       type string;
     }
     leaf port {
       description "Server port";
       type union {
         type string {
           pattern "<.*>|$.*";
         }
         type uint32 {
           range "1024 .. 65535";
         }
       }
     }
     leaf routing-instance {
       description "Routing instance name";
       junos:must "(\"routing-instances $$\")";
       junos:must-message "Routing-instance must be defined";
       type string;
     }
     leaf source-address {
       description "Source ip address used to connect server";
       type jt:ipaddr;
     }
   }
   grouping server-active-leasequery-type {
     description "Allow active leasequery";
     uses apply-advanced;
     leaf timeout {
       description "Read/write timeout in seconds";
       default "120";
       units "seconds";
       type union {
         type string {
           pattern "<.*>|$.*";
         }
         type uint32 {
           range "10 .. 3600";
         }
       }
     }
     leaf idle-timeout {
       description "Idle-timeout in seconds";
       default "60";
       units "seconds";
       type union {
         type string {
           pattern "<.*>|$.*";
         }
         type uint32 {
           range "10 .. 3600";
         }
       }
     }
   }
   grouping server-bulk-leasequery-type {
     description "Allow bulk leasequery";
     uses apply-advanced;
     leaf max-connections {
       description "Max TCP connections allowed at a time";
       default "3";
       type union {
         type string {
           pattern "<.*>|$.*";
         }
         type uint32 {
           range "1 .. 10";
         }
       }
     }
     leaf timeout {
       description "Timeout for blocked connection";
       default "120";
       units "seconds";
       type union {
         type string {
           pattern "<.*>|$.*";
         }
         type uint32 {
           range "1 .. 1000";
         }
       }
     }
     leaf max-empty-replies {
       description "Maximum number of empty replies for a connection";
       default "5";
       units "seconds";
       type union {
         type string {
           pattern "<.*>|$.*";
         }
         type uint32 {
           range "1 .. 100";
         }
       }
     }
     leaf restricted-requestor {
       description "Allow bulk leasequery only from restricted requestors";
       type empty;
     }
   }
   grouping server-connection-type {
     description "Connection parameters per server";
     uses apply-advanced;
     leaf address {
       description "IP address";
       type jt:ipaddr;
     }
     leaf ca-certificate {
       description "Ca-certificate file name";
       type string {
         length "1 .. 256";
       }
     }
     leaf client-id {
       description "Client ID for OAuth2 grant";
       type string {
         length "1 .. 64";
       }
     }
     leaf client-secret {
       description "Client secret for OAuth2 grant";
       type string {
         length "1 .. 128";
       }
     }
   }
   grouping server-group-type {
     uses apply-advanced;
     list server-group {
       key name;
       ordered-by user;
       description "One or more server groups";
       leaf name {
         description "Server group name";
         type string {
           length "1 .. 64";
           junos:posix-pattern "^[A-Za-z0-9][_0-9A-Za-z-]*$";
           junos:pattern-message "Must be a non-reserved string of 64 characters or less";
         }
       }
       uses apply-advanced;
       list address {
         key name;
         ordered-by user;
         description "IP Address of one or more DHCP servers";
         max-elements 32;
         leaf name {
           description "IP Address of DHCP server";
           type jt:ipaddr;
         }
         uses apply-advanced;
       }
     }
   }
   grouping server-leasequery-type {
     description "Allow leasequery";
     uses apply-advanced;
     leaf restricted-requestor {
       description "Allow leasequery only from restricted requestors";
       type empty;
     }
   }
   grouping server-match-action-choice {
     uses apply-advanced;
     choice v4-action-choice {
       case case_1 {
         leaf forward-only {
           description "Forward without subscriber services";
           type empty;
         }
       }
       case case_2 {
         leaf create-relay-entry {
           description "Create relay entry and allow subscriber services";
           type empty;
         }
       }
     }
   }
   grouping server-match-v6-ascii-hex {
     uses apply-advanced;
     list ascii {
       key name;
       description "ASCII string";
       leaf name {
         description "ASCII string";
         type string {
           length "1 .. 256";
         }
       }
       uses apply-advanced;
       choice server-match-action-choice {
         case case_1 {
           leaf forward-only {
             description "Forward without subscriber services when a match is made";
             type empty;
           }
         }
         case case_2 {
           leaf create-relay-entry {
             description "Create relay entry and allow subscriber services";
             type empty;
           }
         }
       }
     }
     list hexadecimal {
       key name;
       description "Hexadecimal string";
       leaf name {
         description "Hexadecimal string";
         type string {
           length "1 .. 512";
           junos:posix-pattern "^[[:xdigit:]]+$";
           junos:pattern-message "Must be hexadecimal digits (0-9, a-f, A-F)";
         }
       }
       uses apply-advanced;
       choice server-match-action-choice {
         case case_1 {
           leaf forward-only {
             description "Forward without subscriber services when a match is made";
             type empty;
           }
         }
         case case_2 {
           leaf create-relay-entry {
             description "Create relay entry and allow subscriber services";
             type empty;
           }
         }
       }
     }
   }
   grouping server-v6-option-ascii-hex {
     uses apply-advanced;
     list ascii {
       key name;
       description "ASCII string";
       leaf name {
         description "ASCII string";
         type string {
           length "1 .. 256";
         }
       }
       uses apply-advanced;
     }
     list hexadecimal {
       key name;
       description "Hexadecimal string";
       leaf name {
         description "Hexadecimal string";
         type string {
           length "1 .. 512";
           junos:posix-pattern "^[[:xdigit:]]+$";
           junos:pattern-message "Must be hexadecimal digits (0-9, a-f, A-F)";
         }
       }
       uses apply-advanced;
     }
   }
   grouping service-device-object {
     leaf name {
       description "Service device name";
       type string {
         length "1 .. 64";
       }
     }
     uses apply-advanced;
     leaf address {
       description "Service device ip address";
       type jt:ipv4addr;
     }
     container access-domain {
       description "Subscriber access configuration";
       uses apply-advanced;
       leaf-list vlan-id-list {
         description "List of access VLAN identifiers";
         type jt:vlan-range;
       }
     }
     container provisioning-method {
       description "Provisioning method configuration";
       uses apply-advanced;
       choice prov_method {
         case case_1 {
           container netconf {
             description "Netconf provisioning method";
             presence "enable netconf";
             uses netconf-object;
           }
         }
       }
     }
     container dictionary {
       description "Dictionary file path";
       uses apply-advanced;
       leaf dictionary-path {
         description "Complete path with dictionary name";
         type jt:filename;
       }
     }
   }
   grouping netconf-object {
     uses apply-advanced;
     leaf user-name {
       description "User name for netconf";
       type string {
         length "1 .. 64";
       }
     }
     leaf password {
       description "Password for netconf";
       type string {
         length "1 .. 64";
       }
     }
     leaf connection-retry-interval {
       description "Retry interval for connection establishment";
       default "3";
       units "seconds";
       type union {
         type string {
           pattern "<.*>|$.*";
         }
         type uint16 {
           range "1 .. 10";
         }
       }
     }
     leaf response-timeout {
       description "Timeout for provisioning response";
       default "10";
       units "seconds";
       type union {
         type string {
           pattern "<.*>|$.*";
         }
         type uint16 {
           range "1 .. 180";
         }
       }
     }
     leaf response-timeout-count {
       description "Consecutive timeout failures before taking action";
       default "3";
       type union {
         type string {
           pattern "<.*>|$.*";
         }
         type uint16 {
           range "1 .. 10";
         }
       }
     }
     leaf bulk-interval {
       description "Bulked services time interval per commit";
       default "1000";
       units "milliseconds";
       type union {
         type string {
           pattern "<.*>|$.*";
         }
         type uint16 {
           range "500 .. 50000";
         }
       }
     }
     leaf bulk-limit {
       description "Maximum number of bulked services per commit";
       default "1";
       type union {
         type string {
           pattern "<.*>|$.*";
         }
         type uint16 {
           range "1 .. 1000";
         }
       }
     }
     leaf reconfigure-bulk-limit {
       description "Maximum number of bulked services per reconfiguration";
       default "100";
       type union {
         type string {
           pattern "<.*>|$.*";
         }
         type uint16 {
           range "1 .. 1000";
         }
       }
     }
     leaf port {
       description "Tcp port number for netconf";
       default "830";
       type union {
         type string {
           pattern "<.*>|$.*";
         }
         type uint32 {
           range "1 .. 65535";
         }
       }
     }
   }
   grouping session_timeout_type {
     uses apply-advanced;
     leaf tcp {
       description "Timeout value for tcp sessions";
       units "seconds";
       type union {
         type string {
           pattern "<.*>|$.*";
         }
         type uint32 {
           range "4 .. 86400";
         }
       }
     }
     leaf udp {
       description "Timeout value for udp sessions";
       units "seconds";
       type union {
         type string {
           pattern "<.*>|$.*";
         }
         type uint32 {
           range "4 .. 86400";
         }
       }
     }
     leaf ospf {
       description "Timeout value for ospf sessions";
       units "seconds";
       type union {
         type string {
           pattern "<.*>|$.*";
         }
         type uint32 {
           range "4 .. 86400";
         }
       }
     }
     leaf icmp {
       description "Timeout value for icmp sessions";
       units "seconds";
       type union {
         type string {
           pattern "<.*>|$.*";
         }
         type uint32 {
           range "4 .. 86400";
         }
       }
     }
     leaf icmp6 {
       description "Timeout value for icmp6 sessions";
       units "seconds";
       type union {
         type string {
           pattern "<.*>|$.*";
         }
         type uint32 {
           range "4 .. 86400";
         }
       }
     }
     leaf others {
       description "Timeout value for other sessions";
       units "seconds";
       type union {
         type string {
           pattern "<.*>|$.*";
         }
         type uint32 {
           range "4 .. 86400";
         }
       }
     }
   }
   grouping sfw_match_object {
     uses apply-advanced;
     list source-address {
       key name;
       ordered-by user;
       description "Match IP source address";
       uses sfw_addr_object;
     }
     list destination-address {
       key name;
       ordered-by user;
       description "Match IP destination address";
       uses sfw_addr_object;
     }
     container destination-port {
       presence "enable destination-port";
       uses apply-advanced;
       choice port_choice {
         case case_1 {
           container range {
             description "Range of ports";
             leaf low {
               description "Lower limit of port range";
               type union {
                 type string {
                   pattern "<.*>|$.*";
                 }
                 type uint16 {
                   range "1 .. 65535";
                 }
               }
             }
             leaf high {
               description "Upper limit of port range";
               type union {
                 type string {
                   pattern "<.*>|$.*";
                 }
                 type uint16 {
                   range "1 .. 65535";
                 }
               }
             }
           }
         }
       }
     }
     list source-address-range {
       key "low high";
       ordered-by user;
       description "Match IP source address range";
       leaf low {
         description "Lower limit of address range";
         type jt:ipaddr;
       }
       leaf high {
         description "Upper limit of address range";
         type jt:ipaddr;
       }
       leaf except {
         description "Match address not in this prefix";
         type empty;
       }
     }
     list source-prefix-list {
       key name;
       ordered-by user;
       description "One or more named lists of source prefixes to match";
       leaf name {
         description "Name of prefix list to match against";
         type string;
       }
       leaf except {
         description "Name of prefix list not to match against";
         type empty;
       }
     }
     list destination-address-range {
       key "low high";
       ordered-by user;
       description "Match IP destination address range";
       leaf low {
         description "Lower limit of address range";
         type jt:ipaddr;
       }
       leaf high {
         description "Upper limit of address range";
         type jt:ipaddr;
       }
       leaf except {
         description "Match address not in this prefix";
         type empty;
       }
     }
     list destination-prefix-list {
       key name;
       ordered-by user;
       description "One or more named lists of destination prefixes to match";
       leaf name {
         description "Name of prefix list to match against";
         type string;
       }
       leaf except {
         description "Name of prefix list not to match against";
         type empty;
       }
     }
     leaf-list applications {
       ordered-by user;
       description "Match one or more applications";
       type string;
     }
     list application-sets {
       key name;
       ordered-by user;
       description "Match one or more application sets";
       leaf name {
         type string {
           length "1 .. 63";
           junos:posix-pattern "^[[:alnum:]][[:alnum:]_-]*$";
           junos:pattern-message "Must be a string beginning with a number or letter and consisting of letters, numbers, dashes and underscores.";
         }
       }
       uses apply-advanced;
     }
     leaf-list application {
       ordered-by user;
       type string;
     }
   }
   grouping sfw_addr_object {
     leaf name {
       description "Match IP address";
       type string;
     }
     leaf except {
       description "Match address not in this prefix";
       type empty;
     }
   }
   grouping sla_policy_type {
     leaf name {
       description "APBR policy name";
       type string {
         length "1 .. 63";
         junos:posix-pattern "^[[:alnum:]][[:alnum:]_-]*$";
         junos:pattern-message "Must be a string beginning with a number or letter and consisting of letters, numbers, dashes and underscores.";
       }
     }
     uses apply-advanced;
     leaf description {
       description "Text description of policy";
       type string {
         length "1 .. 900";
         junos:posix-pattern "^[^&<>\n]+$";
         junos:pattern-message "Must be a string excluding '&', '<', '>' and '\n'";
       }
     }
     container match {
       description "Specify sla policy match-criteria";
       uses apply-advanced;
       choice source-address_choice {
         case case_1 {
           leaf-list source-address {
             ordered-by user;
             type string;
           }
         }
       }
       choice destination-address_choice {
         case case_1 {
           leaf-list destination-address {
             ordered-by user;
             type string;
           }
         }
       }
       leaf source-address-excluded {
         description "Exclude source addresses";
         type empty;
       }
       leaf destination-address-excluded {
         description "Exclude destination addresses";
         type empty;
       }
       choice application_type_choice {
         case case_1 {
           leaf-list application {
             ordered-by user;
             description "Specify application or application-set name to match";
             junos:must "((\".. .. .. .. .. .. .. applications application $$\" || (\".. .. .. .. .. .. .. applications application-set $$\" || (\".. .. .. .. .. .. .. .. applications application $$\" || \".. .. .. .. .. .. .. .. applications application-set $$\"))))";
             junos:must-message "application or application-set must be defined";
             type string {
               length "1 .. 63";
             }
           }
         }
       }
       choice source_identity_choice {
         case case_1 {
           leaf-list source-identity {
             ordered-by user;
             type string;
           }
         }
       }
     }
     container then {
       description "Specify policy action to take when packet match criteria";
       uses apply-advanced;
       choice action {
         case case_1 {
           container application-services {
             description "Application Services";
             uses sla_application_services_type;
           }
         }
       }
     }
     leaf scheduler-name {
       description "Name of scheduler";
       junos:must "(\"schedulers scheduler $$\")";
       junos:must-message "scheduler must be defined";
       type string {
         length "1 .. 63";
         junos:posix-pattern "^[[:alnum:]][[:alnum:]_-]*$";
         junos:pattern-message "Must be a string beginning with a number or letter and consisting of letters, numbers, dashes and underscores.";
       }
     }
   }
   grouping sla_application_services_type {
     description "Application Services";
     uses apply-advanced;
     leaf advance-policy-based-routing-profile {
       description "Specify APBR profile name";
       junos:must "(\"security advance-policy-based-routing profile $$\")";
       junos:must-message "advance-policy-based-routing profile must be defined";
       type string {
         length "1 .. 63";
       }
     }
   }
   grouping slaacd-config-type {
     description "Slaacd configuration options";
     uses apply-advanced;
     container vlans {
       description "Slaac config on vlan";
       uses apply-advanced;
       list vlan-config {
         key name;
         description "Virtual LAN configuration";
         uses vlan-slaacd;
       }
     }
     container interface {
       description "Slaac config on interface";
       uses apply-advanced;
       list intf-config {
         key name;
         description "Interface configuration";
         uses slaacd-interface;
       }
     }
     container link-local-expiry-interval {
       description "Link local address expiry interval";
       uses apply-advanced;
       leaf interval {
         description "Expiry interval";
         default "86400";
         units "seconds";
         type union {
           type string {
             pattern "<.*>|$.*";
           }
           type uint32 {
             range "60 .. 86400";
           }
         }
       }
     }
     container traceoptions {
       description "Slaac Snooping trace options";
       uses apply-advanced;
       leaf no-remote-trace {
         description "Disable remote tracing";
         junos:must "(\"system tracing\")";
         junos:must-message "'no-remote-trace' is valid only when [system tracing] is configured";
         type empty;
       }
       container file {
         description "Trace file information";
         leaf filename {
           description "Name of file in which to write trace information";
           type string {
             length "1 .. 1024";
             junos:posix-pattern "![/ %]";
             junos:pattern-message "Must not contain '/', % or a space";
           }
         }
         leaf size {
           description "Maximum trace file size";
           type string;
         }
         leaf files {
           description "Maximum number of trace files";
           default "3";
           type union {
             type string {
               pattern "<.*>|$.*";
             }
             type uint32 {
               range "2 .. 1000";
             }
           }
         }
         choice world-readable-choice {
           leaf world-readable {
             description "Allow any user to read the log file";
             type empty;
           }
           leaf no-world-readable {
             description "Don't allow any user to read the log file";
             type empty;
           }
         }
         leaf match {
           description "Regular expression for lines to be logged";
           type jt:regular-expression;
         }
       }
       list flag {
         key name;
         description "Tracing parameters";
         leaf name {
           type enumeration {
             enum "configuration" {
               description "Log configuration events";
             }
             enum "init" {
               description "Trace init message events";
             }
             enum "state" {
               description "Trace state message events";
             }
             enum "rtsock" {
               description "Trace rtsock message events";
             }
             enum "packet" {
               description "Trace packet events";
             }
             enum "fsm" {
               description "Trace fsm update events";
             }
             enum "io" {
               description "Trace io events";
             }
             enum "verbose" {
               description "Trace verbose events";
             }
             enum "task" {
               description "Trace TASK related events";
             }
             enum "all" {
               description "Trace all events";
             }
           }
         }
       }
     }
   }
   grouping slaacd-interface {
     description "Interface name";
     leaf name {
       description "Interface name";
       type string;
     }
     uses apply-advanced;
     container mark-interface {
       description "Mark interface";
       uses apply-advanced;
       leaf trusted {
         description "Mark interface trusted";
         type empty;
       }
     }
     container max-allowed-contention {
       description "Maximum allowed contention count(will be valid only for un-trusted ports)";
       uses apply-advanced;
       leaf count {
         description "Contention count";
         junos:must "(\".. duration\")";
         junos:must-message "Duration cannot be zero for non-zero count.";
         type union {
           type string {
             pattern "<.*>|$.*";
           }
           type uint16 {
             range "1 .. 10";
           }
         }
       }
       leaf duration {
         description "Contention duration";
         units "seconds";
         junos:must "(\".. count\")";
         junos:must-message "Count cannot be zero for non-zero duration.";
         type union {
           type string {
             pattern "<.*>|$.*";
           }
           type uint16 {
             range "60 .. 3600";
           }
         }
       }
     }
     container auto-dad {
       description "Auto duplicate address detection";
       uses apply-advanced;
       leaf retries {
         description "DAD retry value";
         default "1";
         type union {
           type string {
             pattern "<.*>|$.*";
           }
           type uint16 {
             range "1 .. 3";
           }
         }
       }
       leaf retrans-interval {
         description "DAD re-transmission interval";
         default "1";
         units "seconds";
         type union {
           type string {
             pattern "<.*>|$.*";
           }
           type uint16 {
             range "1 .. 6";
           }
         }
       }
     }
   }
   grouping sm-ippool-pool {
     description "Address pool configuration";
     leaf name {
       description "Address pool name";
       type string {
         length "1 .. 64";
       }
     }
     uses apply-advanced;
     leaf service-mode {
       description "Service mode";
       type enumeration {
         enum "maintenance" {
           description "Maintenance mode";
         }
       }
     }
     container family {
       presence "enable family";
       description "Address family";
       choice family_type {
         case case_1 {
           container inet {
             presence "enable inet";
             description "IPv4 address pool configuration";
             uses apply-advanced;
             list network {
               key name;
               ordered-by user;
               description "Specify IPv4 network prefix";
               leaf name {
                 description "IPv4 network prefix";
                 type jt:ipv4prefix-only;
               }
               uses apply-advanced;
               leaf external-assigned {
                 description "Assigned by an external authority";
                 junos:must "(!(\".. allocation-prefix-length\"))";
                 junos:must-message "external assigned addresses do not support allocation-prefix-length";
                 junos:must "(!(any \".. range <*> external-assigned\"))";
                 junos:must-message "This can be defined for the network prefix or range";
                 type empty;
               }
               leaf allocation-prefix-length {
                 description "Size of address allocation block";
                 junos:must "(!(\".. external-assigned\"))";
                 junos:must-message "allocation-prefix-length not valid for external assigned addresses";
                 type union {
                   type string {
                     pattern "<.*>|$.*";
                   }
                   type uint8 {
                     range "22 .. 32";
                   }
                 }
               }
               list range {
                 key name;
                 ordered-by user;
                 description "Specify ranges within the prefix";
                 leaf name {
                   description "Range name";
                   junos:must "(unique \".. .. .. network <*> range $$\")";
                   junos:must-message "Range name has to be unique in the pool";
                   type string {
                     length "1 .. 64";
                   }
                 }
                 uses apply-advanced;
                 leaf low {
                   description "Lower limit of the range";
                   type jt:ipv4addr;
                 }
                 leaf high {
                   description "Upper limit of the range";
                   type jt:ipv4addr;
                 }
                 leaf external-assigned {
                   description "Assigned by an external authority";
                   junos:must "(!(\".. .. allocation-prefix-length\"))";
                   junos:must-message "external assigned addresses do not support allocation-prefix-length";
                   junos:must "(!(\".. .. external-assigned\"))";
                   junos:must-message "This can be defined for the network prefix or range";
                   type empty;
                 }
               }
             }
           }
         }
         case case_2 {
           container inet6 {
             presence "enable inet6";
             description "IPv6 address pool configuration";
             uses apply-advanced;
             list network {
               key name;
               ordered-by user;
               description "Specify IPv6 network prefix";
               leaf name {
                 description "IPv6 network prefix";
                 type jt:ipv6prefix-only;
               }
               uses apply-advanced;
               leaf external-assigned {
                 description "Assigned by an external authority";
                 junos:must "(!(\".. allocation-prefix-length\"))";
                 junos:must-message "external assigned addresses do not support allocation-prefix-length";
                 junos:must "(!(any \".. range <*> external-assigned\"))";
                 junos:must-message "This can be defined for the network prefix or range";
                 type empty;
               }
               leaf allocation-prefix-length {
                 description "Size of address allocation block";
                 junos:must "(!(\".. external-assigned\"))";
                 junos:must-message "allocation-prefix-length not valid for external assigned addresses";
                 type union {
                   type string {
                     pattern "<.*>|$.*";
                   }
                   type uint8 {
                     range "54 .. 64";
                   }
                 }
               }
               list range {
                 key name;
                 ordered-by user;
                 description "Specify ranges within the prefix";
                 leaf name {
                   description "Range name";
                   junos:must "(unique \".. .. .. network <*> range $$\")";
                   junos:must-message "Range name has to be unique in the pool";
                   type string {
                     length "1 .. 64";
                   }
                 }
                 uses apply-advanced;
                 leaf low {
                   description "Lower limit of the range";
                   type jt:ipv6prefix-only;
                 }
                 leaf high {
                   description "Upper limit of the range";
                   type jt:ipv6prefix-only;
                 }
                 leaf external-assigned {
                   description "Addresses in this range are assigned to the client by an external authority";
                   junos:must "(!(\".. .. allocation-prefix-length\"))";
                   junos:must-message "external assigned addresses do not support allocation-prefix-length";
                   junos:must "(!(\".. .. external-assigned\"))";
                   junos:must-message "This can be defined for the network prefix or range";
                   type empty;
                 }
               }
             }
           }
         }
       }
     }
     leaf ageing-window {
       description "Time in sec when the address should not be re-used";
       default "2";
       units "seconds";
       type union {
         type string {
           pattern "<.*>|$.*";
         }
         type uint16 {
           range "1 .. 65535";
         }
       }
     }
     leaf pool-prefetch-threshold {
       description "Pool usage threshold to prefetch more addresses";
       default "80";
       units "percent";
       type union {
         type string {
           pattern "<.*>|$.*";
         }
         type uint8 {
           range "1 .. 100";
         }
       }
     }
     leaf pool-snmp-trap-threshold {
       description "Pool usage threshold to generate SNMP trap";
       default "80";
       units "percent";
       type union {
         type string {
           pattern "<.*>|$.*";
         }
         type uint8 {
           range "1 .. 100";
         }
       }
     }
     leaf default-pool {
       description "Pool usage as one of default pools or APN(s) specific";
       type empty;
     }
   }
   grouping smpl-analyzer-type {
     leaf name {
       description "Analyzer name";
       junos:must "(!(\"forwarding-options sampling instance $$\"))";
       junos:must-message "analyzer must not have the same name as of any other sampling instance";
       junos:must "(!(\"forwarding-options port-mirroring instance $$\"))";
       junos:must-message "analyzer must not have the same name as of any other port mirror instance";
       type string {
         length "1 .. 63";
         junos:posix-pattern "^[[:alpha:]][[:alnum:]_-]+$";
         junos:pattern-message "Must be a string beginning with a letter and consisting of letters, numbers, dashes, and underscores";
       }
     }
     uses apply-advanced;
     container input {
       description "Ports and VLANs to monitor";
       uses smpl-analyzer-input-type;
     }
     container output {
       description "Outgoing port or VLAN for mirrored packets";
       uses smpl-analyzer-output-type;
     }
   }
   grouping smpl-analyzer-input-type {
     uses apply-advanced;
     leaf rate {
       description "Ratio of packets to be sampled (1 out of N)";
       type union {
         type string {
           pattern "<.*>|$.*";
         }
         type uint32 {
           range "1 .. 65535";
         }
       }
     }
     leaf maximum-packet-length {
       description "Maximum length of the mirrored packet";
       units "bytes";
       type union {
         type string {
           pattern "<.*>|$.*";
         }
         type uint32 {
           range "0 .. 9216";
         }
       }
     }
     container ingress {
       description "Ports and VLANs to monitor incoming traffic";
       uses smpl-analyzer-ingress-type;
     }
     container egress {
       description "Ports and VLANs to monitor outgoing traffic";
       uses smpl-analyzer-egress-type;
     }
   }
   grouping smpl-analyzer-egress-type {
     uses apply-advanced;
     list interface {
       key name;
       ordered-by user;
       description "Port to monitor outgoing traffic";
       uses analyzer-egress-interface-type;
     }
     list routing-instance {
       key name;
       description "Routing instances";
       uses analyzer-egress-routing-instance-type;
     }
     list vlan {
       key name;
       ordered-by user;
       description "VLAN to monitor outgoing traffic";
       uses analyzer-egress-vlan-type;
     }
     list bridge-domain {
       key name;
       ordered-by user;
       description "Bridge-domain to monitor outgoing traffic";
       uses analyzer-egress-bridge-domain-type;
     }
   }
   grouping analyzer-egress-bridge-domain-type {
     leaf name {
       description "Bridge domain name, VLAN id or VLAN range string";
       junos:must "(!(any \"forwarding-options analyzer <*> output bridge-domain $$\"))";
       junos:must-message "bridge-domain must not be output of any analyzer session";
       junos:must "(unique \"forwarding-options analyzer <*> input egress bridge-domain $$\")";
       junos:must-message "bridge-domain must not be input egress to any other analyzer";
       type string;
     }
     uses apply-advanced;
   }
   grouping analyzer-egress-interface-type {
     leaf name {
       description "Logical interface name";
       type string;
     }
     uses apply-advanced;
   }
   grouping analyzer-egress-routing-instance-type {
     leaf name {
       description "Routing instance name";
       type string {
         junos:posix-pattern "!^((__.*__)|(all)|(.*[ ].*)|(\"\")|(.{129,}))$";
         junos:pattern-message "Must be a non-reserved string of 128 characters or less with no spaces.";
       }
     }
     uses apply-advanced;
     list vlan {
       key name;
       ordered-by user;
       description "VLAN to monitor outgoing traffic";
       uses analyzer-egress-vlan-type;
     }
     list bridge-domain {
       key name;
       ordered-by user;
       description "Bridge-domain to monitor outgoing traffic";
       uses analyzer-egress-bridge-domain-type;
     }
   }
   grouping analyzer-egress-vlan-type {
     leaf name {
       description "VLAN name, VLAN id or VLAN range string";
       junos:must "(!(any \"forwarding-options analyzer <*> output vlan $$\"))";
       junos:must-message "vlan must not be output of any analyzer session";
       junos:must "(unique \"forwarding-options analyzer <*> input egress vlan $$\")";
       junos:must-message "vlan must not be input egress to any other analyzer";
       type string;
     }
     uses apply-advanced;
   }
   grouping smpl-analyzer-ingress-type {
     uses apply-advanced;
     list interface {
       key name;
       ordered-by user;
       description "Port to monitor incoming traffic";
       uses analyzer-ingress-interface-type;
     }
     list routing-instance {
       key name;
       description "Routing instances";
       uses analyzer-ingress-routing-instance-type;
     }
     list vlan {
       key name;
       ordered-by user;
       description "VLAN to monitor incoming traffic";
       uses analyzer-ingress-vlan-type;
     }
     list bridge-domain {
       key name;
       ordered-by user;
       description "Bridge-domain to monitor incoming traffic";
       uses analyzer-ingress-bridge-domain-type;
     }
   }
   grouping analyzer-ingress-bridge-domain-type {
     leaf name {
       description "Bridge domain name, VLAN id or VLAN range string";
       junos:must "(!(any \"forwarding-options analyzer <*> output bridge-domain $$\"))";
       junos:must-message "vlan must not be output of any analyzer session";
       junos:must "(unique \"forwarding-options analyzer <*> input ingress bridge-domain $$\")";
       junos:must-message "vlan must not be input ingress to any other analyzer";
       junos:must "(!(\"vlans $$ vlan-id-list\"))";
       junos:must-message "vlan-id-list cannot be configured on forwarding-options analyzer";
       type string;
     }
     uses apply-advanced;
   }
   grouping analyzer-ingress-interface-type {
     leaf name {
       description "Logical interface name";
       type string;
     }
     uses apply-advanced;
   }
   grouping analyzer-ingress-routing-instance-type {
     leaf name {
       description "Routing instance name";
       type string {
         junos:posix-pattern "!^((__.*__)|(all)|(.*[ ].*)|(\"\")|(.{129,}))$";
         junos:pattern-message "Must be a non-reserved string of 128 characters or less with no spaces.";
       }
     }
     uses apply-advanced;
     list vlan {
       key name;
       ordered-by user;
       description "VLAN to monitor incoming traffic";
       uses analyzer-ingress-vlan-type;
     }
     list bridge-domain {
       key name;
       ordered-by user;
       description "Bridge-domain to monitor incoming traffic";
       uses analyzer-ingress-bridge-domain-type;
     }
   }
   grouping analyzer-ingress-vlan-type {
     leaf name {
       description "VLAN name, VLAN id or VLAN range string";
       junos:must "(!(any \"forwarding-options analyzer <*> output vlan $$\"))";
       junos:must-message "vlan must not be output of any analyzer session";
       junos:must "(unique \"forwarding-options analyzer <*> input ingress vlan $$\")";
       junos:must-message "vlan must not be input ingress to any other analyzer";
       junos:must "(!(\"vlans $$ vlan-id-list\"))";
       junos:must-message "vlan-id-list cannot be configured on forwarding-options analyzer";
       type string;
     }
     uses apply-advanced;
   }
   grouping smpl-analyzer-output-type {
     uses apply-advanced;
     choice interface_or_vlan {
       case case_1 {
         leaf interface {
           description "Outgoing port for mirrored packets";
           junos:must "(!(\"interfaces $$-IFL family inet\"))";
           junos:must-message "An interface configured as family inet cannot be configured as analyzer output interface";
           junos:must "(!((\"interfaces $$-IFL family inet\" || \"interfaces $$-IFL family inet6\")))";
           junos:must-message "An interface configured as family inet/inet6 cannot be configured as analyzer output interface";
           junos:must "(!((\"interfaces $$-IFL family ethernet-switching filter\" || (\"interfaces $$-IFL family inet filter\" || \"interfaces $$-IFL family inet6 filter\"))))";
           junos:must-message "An interface cannot both be an analyzer output interface and have a filter applied to it.";
           type union {
             type jt:interface-name;
             type string {
               pattern "<.*>|$.*";
             }
           }
         }
       }
       case case_2 {
         leaf ip-address {
           description "ERSPAN Destination IP Address";
           type jt:ipv4addr;
         }
       }
       case case_3 {
         leaf ipv6-address {
           description "ERSPAN Destination IPv6 Address";
           type jt:ipv6addr;
         }
       }
       case case_4 {
         leaf next-hop-group {
           description "Next-hop-group through which to send port-mirror traffic";
           junos:must "(\"forwarding-options next-hop-group $$ group-type layer-2\")";
           junos:must-message "Referenced next-hop-group must be defined as layer-2 group";
           type string;
         }
       }
       case case_5 {
         list routing-instance {
           key name;
           description "Routing instances";
           max-elements 1;
           uses output-routing-instance-type;
         }
       }
       case case_6 {
         list vlan {
           key name;
           description "Outgoing VLAN for mirrored packets";
           max-elements 1;
           uses pm-rspan-vlan;
         }
       }
       case case_7 {
         list bridge-domain {
           key name;
           description "Outgoing bridge-domain for mirrored packets";
           max-elements 1;
           uses pm-rspan-bridge-domain;
         }
       }
     }
   }
   grouping output-routing-instance-type {
     leaf name {
       description "Routing instance name";
       type string {
         junos:posix-pattern "!^((__.*__)|(all)|(.*[ ].*)|(\"\")|(.{129,}))$";
         junos:pattern-message "Must be a non-reserved string of 128 characters or less with no spaces.";
       }
     }
     uses apply-advanced;
     choice ipaddr_or_vlan {
       case case_1 {
         leaf ip-address {
           description "ERSPAN Destination IP Address";
           type jt:ipv4addr;
         }
       }
       case case_2 {
         leaf ipv6-address {
           description "ERSPAN Destination IPv6 Address";
           type jt:ipv6addr;
         }
       }
       case case_3 {
         list vlan {
           key name;
           description "Outgoing VLAN for mirrored packets";
           max-elements 1;
           uses pm-rspan-vlan;
         }
       }
       case case_4 {
         list bridge-domain {
           key name;
           description "Outgoing bridge-domain for mirrored packets";
           max-elements 1;
           uses pm-rspan-bridge-domain;
         }
       }
     }
   }
   grouping softwires-object {
     description "Configure softwire feature";
     uses apply-advanced;
     list softwire-name {
       key name;
       description "Configure softwire object";
       uses softwire-option-type;
     }
     container softwire-types {
       description "Configure softwire objects";
       uses apply-advanced;
       list v6rd {
         key name;
         description "Configure v6rd object";
         uses softwire-option-type;
       }
       list ds-lite {
         key name;
         description "Configure ds-lite object";
         uses softwire-option-type;
       }
       list map-e {
         key name;
         ordered-by user;
         description "Configure Map-e object";
         uses map-e-domain;
       }
     }
     list map-e {
       key name;
       ordered-by user;
       description "Configure a MAP-E domain and domain rules";
       max-elements 1;
       uses map-e-domain;
     }
     container traceoptions {
       description "Trace options for Network Security DS-Lite";
       uses apply-advanced;
       leaf no-remote-trace {
         description "Disable remote tracing";
         junos:must "(\"system tracing\")";
         junos:must-message "'no-remote-trace' is valid only when [system tracing] is configured";
         type empty;
       }
       container file {
         description "Trace file information";
         leaf filename {
           description "Name of file in which to write trace information";
           type string {
             length "1 .. 1024";
             junos:posix-pattern "![/ %]";
             junos:pattern-message "Must not contain '/', % or a space";
           }
         }
         leaf size {
           description "Maximum trace file size";
           type string;
         }
         leaf files {
           description "Maximum number of trace files";
           default "3";
           type union {
             type string {
               pattern "<.*>|$.*";
             }
             type uint32 {
               range "2 .. 1000";
             }
           }
         }
         choice world-readable-choice {
           leaf world-readable {
             description "Allow any user to read the log file";
             type empty;
           }
           leaf no-world-readable {
             description "Don't allow any user to read the log file";
             type empty;
           }
         }
         leaf match {
           description "Regular expression for lines to be logged";
           type jt:regular-expression;
         }
       }
       list flag {
         key name;
         ordered-by user;
         description "Tracing parameters";
         leaf name {
           type enumeration {
             enum "configuration" {
               description "Trace configuration events";
             }
             enum "flow" {
               description "Trace flow events";
             }
             enum "all" {
               description "Trace everything";
             }
           }
         }
       }
     }
     list rule-set {
       key name;
       ordered-by user;
       description "Define a softwire rule set";
       uses sw-rule-set-object;
     }
   }
   grouping map-e-domain {
     description "Configure a MAP-E domain";
     leaf name {
       description "MAP-E domain name";
       type string {
         length "1 .. 11";
         junos:posix-pattern "![_]";
         junos:pattern-message "A special character _ is not allowed";
       }
     }
     uses apply-advanced;
     leaf confidentiality {
       description "Configure JUNOS MAP-E confidentiality";
       type empty;
     }
     leaf br-address {
       description "Ipv6 address of BR";
       type jt:unreadable;
     }
     container end-user-prefix {
       description "Configure end-user-prefix value or source interface for obtaining end-user-prefix";
       uses apply-advanced;
       leaf prefix-value {
         description "End user prefix";
         junos:must "(!(\".. auto\"))";
         junos:must-message "Explicit end-user-prefix is not allowed when auto is configured";
         type jt:ipv6prefix;
       }
     }
     list rule {
       key name;
       ordered-by user;
       description "Configure a BMR or FMR rule for map-e ";
       max-elements 101;
       uses map-e-rule;
     }
     leaf role {
       description "Define a role of the MAP-E";
       type enumeration {
         enum "CE" {
           description "CE deployment";
         }
       }
     }
     leaf version {
       description "Define version of the MAP-E";
       type enumeration {
         enum "3" {
           description "Version 3: draft-ietf-softwire-map-03";
         }
       }
     }
   }
   grouping map-e-rule {
     description "Configure a MAP-E rule";
     leaf name {
       description "MAP-E rule name";
       type string {
         length "1 .. 11";
         junos:posix-pattern "![_]";
         junos:pattern-message "A special character _ is not allowed";
       }
     }
     uses apply-advanced;
     leaf rule-type {
       description "Define a rule type of MAP-E";
       type enumeration {
         enum "BMR" {
           description "Define BMR rule type";
         }
         enum "FMR" {
           description "Define FMR rule type";
         }
       }
     }
     leaf ipv4-prefix {
       description "Ipv4 prefix";
       type jt:unreadable;
     }
     leaf ipv6-prefix {
       description "Ipv6 prefix";
       type jt:unreadable;
     }
     leaf ea-bits-length {
       description "EA bits length";
       type union {
         type string {
           pattern "<.*>|$.*";
         }
         type uint32 {
           range "0 .. 48";
         }
       }
     }
     leaf psid-offset {
       description "PSID offset";
       type jt:unreadable;
     }
     leaf psid-len {
       description "PSID length";
       type union {
         type string {
           pattern "<.*>|$.*";
         }
         type uint32 {
           range "0 .. 16";
         }
       }
     }
     leaf mtu-v6 {
       description "MTU for the softwire tunnel";
       default "9192";
       type union {
         type string {
           pattern "<.*>|$.*";
         }
         type uint32 {
           range "1280 .. 9192";
         }
       }
     }
     leaf v4-reassembly {
       description "MAP-E IPv4 reassembly support";
       type empty;
     }
     leaf v6-reassembly {
       description "MAP-E IPv6 reassembly support";
       type empty;
     }
     leaf disable-auto-route {
       description "MAP-E Disable Auto Route";
       type empty;
     }
   }
   grouping softwire-option-type {
     description "Configure softwire object";
     leaf name {
       description "DS-Lite/Softwire object name";
       type string {
         length "1 .. 23";
       }
     }
     uses apply-advanced;
     leaf softwire-concentrator {
       description "Concentrator address";
       type jt:ipaddr;
     }
     leaf softwire-type {
       description "Softwire-type";
       default "IPv4-in-IPv6";
       type enumeration {
         enum "IPv4-in-IPv6" {
           description "Ipv4-in-IPv6";
         }
         enum "v6rd" {
           description "V6rd";
         }
       }
     }
     leaf ipv4-prefix {
       description "6rd customer edge IPV4 prefix";
       type jt:ipv4prefix;
     }
     leaf v6rd-prefix {
       description "6rd domain's IPV6 prefix";
       type jt:ipv6prefix;
     }
     leaf mtu-v4 {
       description "MTU for the softwire tunnel";
       type union {
         type string {
           pattern "<.*>|$.*";
         }
         type uint32 {
           range "576 .. 9192";
         }
       }
     }
     leaf mtu-v6 {
       description "MTU for the softwire tunnel";
       type union {
         type string {
           pattern "<.*>|$.*";
         }
         type uint32 {
           range "1280 .. 9192";
         }
       }
     }
     leaf auto-update-mtu {
       description "Auto update MTU from received ICMPv6 messages";
       type empty;
     }
     leaf copy-dscp {
       description "Copy DSCP (type of service) from IPv6 to IPv4 header";
       type empty;
     }
     leaf flow-limit {
       description "Max Number of IPv4 flows per Softwire";
       default "0";
       type union {
         type string {
           pattern "<.*>|$.*";
         }
         type uint32 {
           range "0 .. 16384";
         }
       }
     }
     leaf session-limit-per-prefix {
       description "Max number of sessions allowed per Softwire prefix";
       default "0";
       junos:must "(!(\".. flow-limit\"))";
       junos:must-message "Cannot configure both flow-limit and session-limit-per-prefix in same softwire-concentrator";
       type union {
         type string {
           pattern "<.*>|$.*";
         }
         type uint32 {
           range "0 .. 16384";
         }
       }
     }
   }
   grouping sophos-scan-options {
     description "Anti-virus scan options";
     uses apply-advanced;
     choice uri-check-choice {
       leaf uri-check {
         description "Anti-virus uri-check";
         type empty;
       }
       leaf no-uri-check {
         description "Don't anti-virus uri-check";
         type empty;
       }
     }
     leaf content-size-limit {
       description "Content size limit";
       units "kilobytes";
       type string;
     }
     leaf timeout {
       description "Scan engine timeout";
       units "seconds";
       type union {
         type string {
           pattern "<.*>|$.*";
         }
         type uint32 {
           range "1 .. 1800";
         }
       }
     }
   }
   grouping source-class-filters {
     leaf name {
       description "Source class name";
       junos:must "((any \"policy-options policy-statement <*> then source-class $$\" || (any \"policy-options policy-statement <*> term <*> then source-class $$\" || (any \"policy-options policy-statement <*> from route-filter <*> <*> source-class $$\" || (any \"policy-options policy-statement <*> term <*> from route-filter <*> <*> source-class $$\" || (any \"policy-options policy-statement <*> then forwarding-class $$\" || (any \"policy-options policy-statement <*> term <*> then forwarding-class $$\" || (any \"policy-options policy-statement <*> from route-filter <*> <*> forwarding-class $$\" || (any \"logical-systems <*> policy-options policy-statement <*> then source-class $$\" || (any \"logical-systems <*> policy-options policy-statement <*> term <*> then source-class $$\" || (any \"logical-systems <*> policy-options policy-statement <*> from route-filter <*> <*> source-class $$\" || (any \"logical-systems <*> policy-options policy-statement <*> term <*> from route-filter <*> <*> source-class $$\" || (any \"logical-systems <*> policy-options policy-statement <*> then forwarding-class $$\" || (any \"logical-systems <*> policy-options policy-statement <*> term <*> then forwarding-class $$\" || any \"logical-systems <*> policy-options policy-statement <*> from route-filter <*> <*> forwarding-class $$\"))))))))))))))";
       junos:must-message "referenced source-class must be defined";
       type string;
     }
     uses apply-advanced;
     container family {
       description "Protocol family";
       container inet {
         description "Protocol family IPv4 for firewall filter";
         uses apply-advanced;
         container filter {
           description "Packet filtering";
           uses apply-advanced;
           leaf filter-name {
             description "Inet Filter name";
             type string;
           }
         }
       }
       container inet6 {
         description "Protocol family IPv6 for firewall filter";
         uses apply-advanced;
         container filter {
           description "Packet filtering";
           uses apply-advanced;
           leaf filter-name {
             description "Inet6 Filter name";
             type string;
           }
         }
       }
     }
   }
   grouping spring-te-template-map {
     description "SPRING-TE template color map";
     leaf name {
       description "Name of SPRING-TE template";
       junos:must "(\"protocols source-packet-routing source-routing-path-template $$ primary\")";
       junos:must-message "Referenced spring-te template doesn't exist or primary not configured in it";
       type string;
     }
     uses apply-advanced;
     choice colors {
       case case_1 {
         leaf-list color {
           description "Set of color list to be mapped to corresponding SPRING-TE template";
           type union {
             type uint32;
             type string {
               pattern "<.*>|$.*";
             }
           }
         }
       }
       case case_2 {
         leaf color-any {
           description "Map any color to corresponding SPRING-TE template";
           type empty;
         }
       }
     }
   }
   grouping springte_lsp_nh_obj {
     uses apply-advanced;
     leaf nexthop {
       description "SPRING-TE LSP to use to reach destination";
       type string {
         length "1 .. 128";
       }
     }
     container lsp-source {
       description "Source of tunnel creation";
       uses apply-advanced;
       choice lsp-src-choice {
         case case_1 {
           leaf pcep {
             description "Path computation element protocol";
             type empty;
           }
         }
         case case_2 {
           leaf static {
             description "Static configuration";
             type empty;
           }
         }
         case case_3 {
           leaf dtm {
             description "Dynamic tunnel module";
             type empty;
           }
         }
         case case_4 {
           leaf bgp {
             description "BGP SRTE";
             type empty;
           }
         }
       }
     }
   }
   grouping ssg-destination-nat-object {
     uses apply-advanced;
     list pool {
       key name;
       ordered-by user;
       description "Define a destination address pool";
       leaf name {
         description "Pool name";
         type string {
           length "1 .. 63";
           junos:posix-pattern "^[[:alnum:]][[:alnum:]_-]*$";
           junos:pattern-message "Must be a string beginning with a number or letter and consisting of letters, numbers, dashes and underscores.";
         }
       }
       uses apply-advanced;
       leaf description {
         description "Text description of pool";
         type string {
           length "1 .. 900";
           junos:posix-pattern "^[^&<>\n]+$";
           junos:pattern-message "Must be a string excluding '&', '<', '>' and '\n'";
         }
       }
       container routing-instance {
         description "Routing instance";
         uses apply-advanced;
         choice ri-name-choice {
           case case_1 {
             leaf default {
               description "Default routing-instance";
               type empty;
             }
           }
           case case_2 {
             leaf ri-name {
               description "Routing-instance name";
               junos:must "((\"routing-instances $$ instance-type virtual-router\" || \"routing-instances $$ instance-type vrf\"))";
               junos:must-message "Instance-type virtual-router or vrf must be defined under [routing-instances]";
               junos:must "(\"routing-instances $$\")";
               junos:must-message "Routing-instance must be defined";
               type string {
                 junos:posix-pattern "^[[:alnum:]][[:alnum:]_-]*$";
                 junos:pattern-message "Must be a string beginning with a number or letter and consisting of letters, numbers, dashes and underscores.";
               }
             }
           }
         }
       }
       container address {
         description "Add address or address range to pool";
         leaf ipaddr {
           description "IPv4 or IPv6 address or address range";
           type jt:ipprefix;
         }
         choice range-port-choice {
           case case_1 {
             container to {
               description "Upper limit of address range";
               uses apply-advanced;
               leaf ipaddr {
                 description "IPv4 or IPv6 upper limit of address range";
                 type jt:ipprefix;
               }
             }
           }
           case case_2 {
             leaf port {
               description "Specify the port value";
               type union {
                 type uint16;
                 type string {
                   pattern "<.*>|$.*";
                 }
               }
             }
           }
         }
       }
     }
     list port-forwarding {
       key name;
       ordered-by user;
       description "Define a port-forwarding mapping pool";
       leaf name {
         description "Port Forwarding mapping name";
         type string {
           length "1 .. 31";
           junos:posix-pattern "^[[:alnum:]][[:alnum:]_-]*$";
           junos:pattern-message "Must be a string beginning with a number or letter and consisting of letters, numbers, dashes and underscores.";
         }
       }
       uses apply-advanced;
       leaf description {
         description "Text description of port forwarding mapping";
         type string {
           length "1 .. 900";
           junos:posix-pattern "^[^&<>\n]+$";
           junos:pattern-message "Must be a string excluding '&', '<', '>' and '\n'";
         }
       }
       list destined-port {
         key "port translated-port";
         ordered-by user;
         description "Port forwarding mappings";
         max-elements 32;
         leaf port {
           description "Destination port";
           type union {
             type string {
               pattern "<.*>|$.*";
             }
             type uint16 {
               range "1 .. 65535";
             }
           }
         }
         leaf translated-port {
           description "Translated port";
           type union {
             type string {
               pattern "<.*>|$.*";
             }
             type uint16 {
               range "1 .. 65535";
             }
           }
         }
       }
     }
     list rule-set {
       key name;
       ordered-by user;
       description "Configurate a set of rules";
       leaf name {
         description "Rule-set name";
         junos:must "((!(\"services nat source rule-set $$\") && !(\"services nat static rule-set $$\")))";
         junos:must-message "the rule set name should be unique across all types of nat";
         type string {
           length "1 .. 63";
           junos:posix-pattern "^[[:alnum:]][[:alnum:]_-]*$";
           junos:pattern-message "Must be a string beginning with a number or letter and consisting of letters, numbers, dashes and underscores.";
         }
       }
       uses apply-advanced;
       leaf description {
         description "Text description of rule set";
         type string {
           length "1 .. 900";
           junos:posix-pattern "^[^&<>\n]+$";
           junos:pattern-message "Must be a string excluding '&', '<', '>' and '\n'";
         }
       }
       container from {
         description "Where is the traffic from";
         choice from-context-choice {
           case case_1 {
             leaf-list routing-instance {
               description "Source routing instance list";
               type string;
               max-elements 8;
             }
           }
           case case_2 {
             leaf-list routing-group {
               description "Source routing group list";
               type string;
               max-elements 8;
             }
           }
           case case_3 {
             leaf-list zone {
               description "Source zone list";
               type string;
               max-elements 8;
             }
           }
           case case_4 {
             leaf-list interface {
               description "Source interface list";
               type union {
                 type jt:interface-name;
                 type string {
                   pattern "<.*>|$.*";
                 }
               }
               max-elements 8;
             }
           }
         }
       }
       list rule {
         key name;
         ordered-by user;
         description "Destination NAT rule";
         uses dest-nat-rule-object;
       }
       leaf match-direction {
         description "Match direction";
         type enumeration {
           enum "input" {
             description "Match on input to interface";
           }
           enum "output" {
             description "Match on output from interface";
           }
         }
       }
     }
   }
   grouping dest-nat-rule-object {
     leaf name {
       description "Rule name";
       type string {
         length "1 .. 63";
         junos:posix-pattern "^[[:alnum:]][[:alnum:]_-]*$";
         junos:pattern-message "Must be a string beginning with a number or letter and consisting of letters, numbers, dashes and underscores.";
       }
     }
     uses apply-advanced;
     leaf description {
       description "Text description of rule";
       type string {
         length "1 .. 900";
         junos:posix-pattern "^[^&<>\n]+$";
         junos:pattern-message "Must be a string excluding '&', '<', '>' and '\n'";
       }
     }
     container dest-nat-rule-match {
       description "Specify Destination NAT rule match criteria";
       uses apply-advanced;
       leaf-list source-address {
         ordered-by user;
         description "Source address";
         type string;
         max-elements 8;
       }
       leaf-list source-address-name {
         ordered-by user;
         description "Address/address-set from address book";
         type string;
         max-elements 8;
       }
       choice dst-choice {
         case case_1 {
           container destination-address {
             description "Destination address";
             choice dst-addr-choice {
               case case_1 {
                 leaf dst-addr {
                   description "IPv4 or IPv6 destination address";
                   type jt:ipprefix;
                 }
               }
               case case_2 {
                 leaf any-unicast {
                   description "Match any unicast address";
                   type empty;
                 }
               }
             }
           }
         }
         case case_2 {
           container destination-address-name {
             description "Address from address book";
             leaf dst-addr-name {
               description "Address from address book";
               type string {
                 length "1 .. 63";
               }
             }
           }
         }
       }
       list destination-port {
         key name;
         ordered-by user;
         description "Destination port";
         max-elements 8;
         leaf name {
           description "Port or lower limit of port range";
           type union {
             type uint16;
             type string {
               pattern "<.*>|$.*";
             }
           }
         }
         container to {
           description "Port range upper limit";
           uses apply-advanced;
           leaf high {
             description "Upper limit of port range";
             type union {
               type uint16;
               type string {
                 pattern "<.*>|$.*";
               }
             }
           }
         }
       }
       leaf-list protocol {
         ordered-by user;
         description "IP Protocol";
         type string;
         max-elements 4;
       }
       leaf-list application {
         ordered-by user;
         type string;
       }
     }
     container then {
       description "Then action";
       uses apply-advanced;
       container destination-nat {
         description "Destination NAT action";
         uses apply-advanced;
         choice action {
           case case_1 {
             leaf off {
               description "No action";
               type empty;
             }
           }
           case case_2 {
             container pool {
               description "Use Destination NAT pool";
               uses apply-advanced;
               leaf pool-name {
                 description "Name of Destination NAT pool";
                 junos:must "(\".. .. .. .. .. .. .. .. nat destination pool $$\")";
                 junos:must-message "Destination NAT pool name must be defined";
                 type string {
                   length "1 .. 63";
                 }
               }
             }
           }
           case case_3 {
             leaf destination-prefix {
               description "Destination prefix to be used for NAT64 and 464 translation type";
               type jt:ipprefix-only;
             }
           }
         }
         container xlat-source-rule {
           junos:must "(\".. destination-prefix\")";
           junos:must-message "'xlat-source-rule' can be configured only for NAT464 destination rule";
           description "Set source nat rule to match for NAT464";
           uses apply-advanced;
           list rule-set {
             key name;
             ordered-by user;
             description "Source nat rule-set";
             max-elements 1;
             leaf name {
               description "Source nat rule-set name";
               junos:must "(\"services nat source rule-set $$\")";
               junos:must-message "source rule-set must be defined under 'services nat'";
               type string {
                 length "1 .. 63";
                 junos:posix-pattern "^[[:alnum:]][[:alnum:]_-]*$";
                 junos:pattern-message "Must be a string beginning with a number or letter and consisting of letters, numbers, dashes and underscores.";
               }
             }
             uses apply-advanced;
             leaf rule {
               description "Source NAT rule name";
               type string {
                 length "1 .. 63";
                 junos:posix-pattern "^[[:alnum:]][[:alnum:]_-]*$";
                 junos:pattern-message "Must be a string beginning with a number or letter and consisting of letters, numbers, dashes and underscores.";
               }
             }
           }
         }
         container port-forwarding-mappings {
           description "Use Destination NAT port forwarding mapping pool";
           uses apply-advanced;
           leaf pf-name {
             description "Name of Port forwarding mappings";
             junos:must "(\".. .. .. .. .. .. .. .. nat destination port-forwarding $$\")";
             junos:must-message "Port forwarding pool mappings must be defined";
             type string {
               length "1 .. 31";
             }
           }
         }
         container rule-session-count-alarm {
           description "Config rule-session-count-alarm to destination rule";
           uses nat-rule-session-count-alarm-object;
         }
       }
       leaf syslog {
         description "System log information about the packet";
         type empty;
       }
     }
   }
   grouping nat-rule-session-count-alarm-object {
     uses apply-advanced;
     leaf raise-threshold {
       description "Raise threshold for rule session count alarm";
       type union {
         type string {
           pattern "<.*>|$.*";
         }
         type uint32 {
           range "1 .. 4294967295";
         }
       }
     }
     leaf clear-threshold {
       description "Clear threshold for session count hit alarm";
       type union {
         type string {
           pattern "<.*>|$.*";
         }
         type uint32 {
           range "1 .. 4294967295";
         }
       }
     }
   }
   grouping ssg-proxy-arp-object {
     uses apply-advanced;
     list interface {
       key name;
       ordered-by user;
       description "Interface with proxy arp configured";
       uses ssg-interface-object;
     }
   }
   grouping ssg-interface-object {
     leaf name {
       description "Interface name";
       type union {
         type jt:interface-name;
         type string {
           pattern "<.*>|$.*";
         }
       }
     }
     uses apply-advanced;
     list address {
       key name;
       ordered-by user;
       description "Proxy ARP address";
       leaf name {
         description "Address or address range";
         type jt:ipv4prefix;
       }
       container to {
         description "Upper limit of address range";
         uses apply-advanced;
         leaf ipaddr {
           description "Upper limit of address range";
           type jt:ipv4prefix;
         }
       }
     }
   }
   grouping ssg-proxy-ndp-object {
     uses apply-advanced;
     list interface {
       key name;
       ordered-by user;
       description "Interface with proxy arp configured";
       uses ssg-proxy-ndp-interface-object;
     }
   }
   grouping ssg-proxy-ndp-interface-object {
     leaf name {
       description "Interface name";
       type union {
         type jt:interface-name;
         type string {
           pattern "<.*>|$.*";
         }
       }
     }
     uses apply-advanced;
     list address {
       key name;
       ordered-by user;
       description "Proxy ndp address";
       leaf name {
         description "Address or address range";
         type jt:ipv6prefix;
       }
       container to {
         description "Upper limit of address range";
         uses apply-advanced;
         leaf ipv6addr {
           description "Upper limit of address range";
           type jt:ipv6addr;
         }
       }
     }
   }
   grouping ssg-source-nat-object {
     uses apply-advanced;
     container persistent-nat {
       description "Persistent NAT info";
       container log {
         description "Configure persistent NAT log";
         choice enable-disable {
           case case_1 {
             leaf disable {
               description "Disable Persistent NAT log";
               type empty;
             }
           }
         }
       }
     }
     list pool {
       key name;
       ordered-by user;
       description "Define a source address pool";
       leaf name {
         description "Pool name";
         type string {
           length "1 .. 63";
           junos:posix-pattern "^[[:alnum:]][[:alnum:]_-]*$";
           junos:pattern-message "Must be a string beginning with a number or letter and consisting of letters, numbers, dashes and underscores.";
         }
       }
       uses apply-advanced;
       leaf description {
         description "Text description of pool";
         type string {
           length "1 .. 900";
           junos:posix-pattern "^[^&<>\n]+$";
           junos:pattern-message "Must be a string excluding '&', '<', '>' and '\n'";
         }
       }
       container routing-instance {
         description "Routing instance";
         uses apply-advanced;
         leaf ri-name {
           description "Routing instance name";
           junos:must "(\"routing-instances $$ instance-type virtual-router\")";
           junos:must-message "Instance-type virtual-router must be defined under [routing-instances]";
           junos:must "(\"routing-instances $$\")";
           junos:must-message "Routing-instance must be defined";
           type string {
             junos:posix-pattern "^[[:alnum:]][[:alnum:]_-]*$";
             junos:pattern-message "Must be a string beginning with a number or letter and consisting of letters, numbers, dashes and underscores.";
           }
         }
       }
       list address {
         key name;
         ordered-by user;
         description "Add address to pool";
         max-elements 64;
         leaf name {
           description "IPv4 or IPv6 address or address range";
           type jt:ipprefix;
         }
         container to {
           description "Upper limit of address range";
           uses apply-advanced;
           leaf ipaddr {
             description "IPv4 or IPv6 upper limit of address range";
             type jt:ipprefix;
           }
         }
       }
       container host-address-base {
         description "The base of host address";
         leaf ipaddr {
           description "IPv4 or IPv6 base address";
           junos:must "(!(\".. .. port range\"))";
           junos:must-message "'port range...' must not be configured when configure host-address-base";
           type jt:ipprefix;
         }
       }
       container port {
         description "Config port attribute to pool";
         uses apply-advanced;
         choice port-choice {
           case case_1 {
             leaf no-translation {
               description "Do not perform port translation";
               junos:must "(!(\".. automatic\"))";
               junos:must-message "'automatic' must not be configured when configure port no-translation";
               junos:must "(!(\".. preserve-range\"))";
               junos:must-message "'preserve-range' must not be configured when configure port no-translation";
               junos:must "(!(\".. preserve-parity\"))";
               junos:must-message "'preserve-parity' must not be configured when configure port no-translation";
               type empty;
             }
           }
           case case_2 {
             container range {
               description "Port range";
               uses apply-advanced;
               choice port-assign-choice {
                 case case_1 {
                   leaf random-allocation {
                     description "Allocate port randomly";
                     junos:must "(!(\".. .. .. .. .. .. source pool $$ port no-translation\"))";
                     junos:must-message "'port no-translation' must not be configured when configure port assignment as random";
                     type empty;
                   }
                 }
                 case case_2 {
                   leaf round-robin {
                     description "Allocate port round-robin";
                     junos:must "(!(\".. .. .. .. .. .. source pool $$ port no-translation\"))";
                     junos:must-message "'port no-translation' must not be configured when configure port assignment as round-robin";
                     type empty;
                   }
                 }
               }
               leaf low {
                 description "Lower limit of port range";
                 junos:must "(!(\".. .. .. host-address-base\"))";
                 junos:must-message "'host-address-base' must not be configured when configure port range";
                 type union {
                   type string {
                     pattern "<.*>|$.*";
                   }
                   type uint16 {
                     range "1024 .. 65535";
                   }
                 }
               }
               container to {
                 description "Port range upper limit";
                 uses apply-advanced;
                 leaf high {
                   description "Upper limit of port range";
                   junos:must "(!(\".. .. .. .. host-address-base\"))";
                   junos:must-message "'host-address-base' must not be configured when configure port range";
                   type union {
                     type string {
                       pattern "<.*>|$.*";
                     }
                     type uint16 {
                       range "1024 .. 65535";
                     }
                   }
                 }
               }
               container twin-port {
                 description "Twin port range";
                 uses apply-advanced;
                 leaf low {
                   description "Lower limit of twin port range";
                   junos:must "(!(\".. .. .. .. host-address-base\"))";
                   junos:must-message "'host-address-base' must not be configured when configure twin port range";
                   type union {
                     type string {
                       pattern "<.*>|$.*";
                     }
                     type uint16 {
                       range "63488 .. 65535";
                     }
                   }
                 }
                 container to {
                   description "Twin port range upper limit";
                   uses apply-advanced;
                   leaf high {
                     description "Upper limit of twin port range";
                     junos:must "(!(\".. .. .. .. .. host-address-base\"))";
                     junos:must-message "'host-address-base' must not be configured when configure twin port range";
                     type union {
                       type string {
                         pattern "<.*>|$.*";
                       }
                       type uint16 {
                         range "63488 .. 65535";
                       }
                     }
                   }
                 }
               }
             }
           }
           case case_3 {
             container automatic {
               description "Port assignment";
               uses apply-advanced;
               choice port-assign-choice {
                 case case_1 {
                   leaf random-allocation {
                     description "Allocate port randomly";
                     junos:must "(!(\".. .. .. .. .. .. source pool $$ port no-translation\"))";
                     junos:must-message "'port no-translation' must not be configured when configure port assignment as random";
                     type empty;
                   }
                 }
                 case case_2 {
                   leaf round-robin {
                     description "Allocate port by round-robin";
                     junos:must "(!(\".. .. .. .. .. .. source pool $$ port no-translation\"))";
                     junos:must-message "'port no-translation' must not be configured when configure port assignment as round-robin";
                     type empty;
                   }
                 }
               }
             }
           }
         }
         leaf port-overloading-factor {
           description "Port overloading factor for each IP";
           type union {
             type string {
               pattern "<.*>|$.*";
             }
             type uint16 {
               range "2 .. 32";
             }
           }
         }
         container block-allocation {
           description "Port block allocation";
           presence "enable block-allocation";
           uses block-allocation-object;
         }
         container deterministic {
           description "Deterministic nat allocation";
           presence "enable deterministic";
           uses deterministic-object;
         }
         leaf preserve-parity {
           description "Allocate port as the same parity as incoming port";
           junos:must "(!(\".. .. .. .. .. source pool $$ port no-translation\"))";
           junos:must-message "'port no-translation' must not be configured when configure preserve-parity";
           type empty;
         }
         leaf preserve-range {
           description "Allocate port from the same port range as incoming port";
           junos:must "(!(\".. .. .. .. .. source pool $$ port no-translation\"))";
           junos:must-message "'port no-translation' must not be configured when configure preserve-range";
           type empty;
         }
       }
       container overflow-pool {
         junos:must "(\".. .. .. source pool ${pool} port no-translation\")";
         junos:must-message "'port no-translation' must be configured on original address pool";
         description "Specify an overflow pool";
         choice overflow-pool-choice {
           case case_1 {
             leaf pool-name {
               description "Name of source address pool";
               junos:must "(!(\".. .. .. .. source pool $$ host-address-base\"))";
               junos:must-message "'host-address-base' must not be configured on overflow address pool";
               junos:must "(!(\".. .. .. .. source pool $$ port no-translation\"))";
               junos:must-message "'port no-translation' must not be configured on overflow address pool";
               junos:must "(!(\".. .. .. .. source pool ${pool} overflow-pool ${pool}\"))";
               junos:must-message "Overflow address pool must not be original address pool";
               junos:must "(\".. .. .. .. source pool $$\")";
               junos:must-message "Overflow address pool must be defined under [nat source pool]";
               type string {
                 length "1 .. 63";
                 junos:posix-pattern "^[[:alnum:]][[:alnum:]_-]*$";
                 junos:pattern-message "Must be a string beginning with a number or letter and consisting of letters, numbers, dashes and underscores.";
               }
             }
           }
           case case_2 {
             leaf interface {
               description "Allow interface pool to support overflow";
               type empty;
             }
           }
         }
       }
       leaf address-shared {
         description "Allow multiple hosts to share an externel address";
         type empty;
       }
       container address-pooling {
         description "Specify the address-pooling behavior";
         choice pooling-choice {
           case case_1 {
             leaf paired {
               description "Allow address-pooling paired for a source pool with port translation";
               type empty;
             }
           }
           case case_2 {
             leaf no-paired {
               description "Allow address-pooling no-paired for a source pool without port translation";
               type empty;
             }
           }
         }
       }
       container address-persistent {
         description "Specify the address-persistent behavior";
         container subscriber {
           description "Configure address persistent for subscriber";
           leaf ipv6-prefix-length {
             description "Ipv6 prefix length for address persistent";
             type union {
               type string {
                 pattern "<.*>|$.*";
               }
               type uint16 {
                 range "8 .. 128";
               }
             }
           }
         }
       }
       container pool-utilization-alarm {
         description "Config pool-utilization-alarm to pool";
         uses source-nat-pool-utilization-alarm-object;
       }
       leaf ei-mapping-timeout {
         description "Endpoint-independent mapping timeout";
         units "second";
         type union {
           type string {
             pattern "<.*>|$.*";
           }
           type uint32 {
             range "120 .. 86400";
           }
         }
       }
       leaf mapping-timeout {
         description "Address-pooling paired and endpoint-independent mapping timeout";
         units "second";
         type union {
           type string {
             pattern "<.*>|$.*";
           }
           type uint32 {
             range "120 .. 86400";
           }
         }
       }
       leaf limit-ports-per-host {
         description "Number of ports allocated per host";
         type union {
           type string {
             pattern "<.*>|$.*";
           }
           type uint16 {
             range "2 .. 65535";
           }
         }
       }
       container allocation-domain {
         description "Specify map-e domain name for pool";
         leaf mape-domain-name {
           description "Name of map-e domain";
           junos:must "(!(\".. .. address\"))";
           junos:must-message "'address...' must not be configured when configure allocation-domain";
           junos:must "(\"security softwires map-e $$\")";
           junos:must-message "mape domain must be defined";
           type string {
             length "1 .. 63";
           }
         }
         container allocation-rule {
           description "Specify map-e rule name for pool";
           leaf mape-rule-name {
             description "Name of map-e rule";
             type string {
               length "1 .. 63";
             }
           }
         }
       }
     }
     leaf address-persistent {
       description "Allow source address to maintain same translation";
       type empty;
     }
     leaf session-persistence-scan {
       description "Allow source to maintain session when session scan";
       type empty;
     }
     leaf session-drop-hold-down {
       description "Session drop hold down time";
       type union {
         type string {
           pattern "<.*>|$.*";
         }
         type uint16 {
           range "30 .. 28800";
         }
       }
     }
     container pool-utilization-alarm {
       description "Configure pool utilization alarm";
       uses source-nat-pool-utilization-alarm-object;
     }
     container port-randomization {
       description "Configure Source NAT port randomization";
       choice enable-disable {
         case case_1 {
           leaf disable {
             description "Disable Source NAT port randomization";
             type empty;
           }
         }
       }
     }
     container port-round-robin {
       description "Configure Source NAT port randomization";
       choice enable-disable {
         case case_1 {
           leaf disable {
             description "Disable Source NAT port randomization";
             type empty;
           }
         }
       }
     }
     leaf port-scaling-enlargement {
       description "Configure source port scaling to 2.4G only for NGSPC";
       type empty;
     }
     leaf pool-distribution {
       description "Configure Source pool distribution, the APPCP bottleneck of NAT CPS can be alleviated.";
       type empty;
     }
     container pool-default-port-range {
       description "Configure Source NAT default port range";
       leaf low {
         description "Lower limit of port range";
         junos:must "(!(any \"security nat source pool <*> host-address-base\"))";
         junos:must-message "'host-address-base' must not be configured when configure port range";
         type union {
           type string {
             pattern "<.*>|$.*";
           }
           type uint16;
         }
       }
       container to {
         description "Port range upper limit";
         uses apply-advanced;
         leaf high {
           description "Upper limit of port range";
           junos:must "(!(any \"security nat source pool <*> host-address-base\"))";
           junos:must-message "'host-address-base' must not be configured when configure port range";
           type union {
             type string {
               pattern "<.*>|$.*";
             }
             type uint16;
           }
         }
       }
     }
     container pool-default-twin-port-range {
       description "Configure Source NAT default twin port range";
       leaf low {
         description "Lower limit of twin port range";
         type union {
           type string {
             pattern "<.*>|$.*";
           }
           type uint16 {
             range "63488 .. 65535";
           }
         }
       }
       container to {
         description "Twin port range upper limit";
         uses apply-advanced;
         leaf high {
           description "Upper limit of twin port range";
           type union {
             type string {
               pattern "<.*>|$.*";
             }
             type uint16 {
               range "63488 .. 65535";
             }
           }
         }
       }
     }
     container interface {
       description "Configure interface port overloading for persistent NAT";
       uses apply-advanced;
       choice interface-choice {
         case case_1 {
           container port-overloading {
             description "Configure port overloading";
             leaf off {
               description "Turn off interface port over-loading";
               type empty;
             }
           }
         }
         case case_2 {
           leaf port-overloading-factor {
             description "Port overloading factor for interface NAT";
             type union {
               type uint16;
               type string {
                 pattern "<.*>|$.*";
               }
             }
           }
         }
       }
     }
     list rule-set {
       key name;
       ordered-by user;
       description "Configurate a set of rules";
       leaf name {
         description "Rule-set name";
         junos:must "((!(\"services nat destination rule-set $$\") && !(\"services nat static rule-set $$\")))";
         junos:must-message "the rule set name should be unique across all types of nat";
         type string {
           length "1 .. 63";
           junos:posix-pattern "^[[:alnum:]][[:alnum:]_-]*$";
           junos:pattern-message "Must be a string beginning with a number or letter and consisting of letters, numbers, dashes and underscores.";
         }
       }
       uses apply-advanced;
       leaf description {
         description "Text description of rule set";
         type string {
           length "1 .. 900";
           junos:posix-pattern "^[^&<>\n]+$";
           junos:pattern-message "Must be a string excluding '&', '<', '>' and '\n'";
         }
       }
       container from {
         description "Where is the traffic from";
         choice from-context-choice {
           case case_1 {
             leaf-list routing-instance {
               description "Source routing instance list";
               type string;
               max-elements 8;
             }
           }
           case case_2 {
             leaf-list routing-group {
               description "Source routing group list";
               type string;
               max-elements 8;
             }
           }
           case case_3 {
             leaf-list zone {
               description "Source zone list";
               type string;
               max-elements 8;
             }
           }
           case case_4 {
             leaf-list interface {
               description "Source interface list";
               type union {
                 type jt:interface-name;
                 type string {
                   pattern "<.*>|$.*";
                 }
               }
               max-elements 8;
             }
           }
         }
       }
       container to {
         description "Where is the traffic to";
         choice from-context-choice {
           case case_1 {
             leaf-list routing-instance {
               description "Destination routing instance list";
               type string;
               max-elements 8;
             }
           }
           case case_2 {
             leaf-list routing-group {
               description "Destination routing group list";
               type string;
               max-elements 8;
             }
           }
           case case_3 {
             leaf-list zone {
               description "Destination zone list";
               type string;
               max-elements 8;
             }
           }
           case case_4 {
             leaf-list interface {
               description "Destination interface list";
               type union {
                 type jt:interface-name;
                 type string {
                   pattern "<.*>|$.*";
                 }
               }
               max-elements 8;
             }
           }
         }
       }
       list rule {
         key name;
         ordered-by user;
         description "Source NAT rule";
         uses src-nat-rule-object;
       }
       leaf match-direction {
         description "Match direction";
         type enumeration {
           enum "input" {
             description "Match on input to interface";
           }
           enum "output" {
             description "Match on output from interface";
           }
         }
       }
     }
   }
   grouping block-allocation-object {
     description "Port block allocation";
     uses apply-advanced;
     leaf block-size {
       description "Block size";
       type union {
         type string {
           pattern "<.*>|$.*";
         }
         type uint16 {
           range "1 .. 64512";
         }
       }
     }
     leaf maximum-blocks-per-host {
       description "Maximum block number per host";
       type union {
         type string {
           pattern "<.*>|$.*";
         }
         type uint16 {
           range "1 .. 512";
         }
       }
     }
     leaf active-block-timeout {
       description "Active block timeout interval";
       type union {
         type string {
           pattern "<.*>|$.*";
         }
         type uint32;
       }
     }
     leaf interim-logging-interval {
       description "Interim Logging interval";
       type union {
         type string {
           pattern "<.*>|$.*";
         }
         type uint32 {
           range "1800 .. 86400";
         }
       }
     }
     leaf last-block-recycle-timeout {
       description "Last Block recycle timeout interval";
       type union {
         type string {
           pattern "<.*>|$.*";
         }
         type uint32 {
           range "120 .. 864000";
         }
       }
     }
     container log {
       description "Configure port block log";
       choice enable-disable {
         case case_1 {
           leaf disable {
             description "Disable PBA port block log";
             type empty;
           }
         }
       }
     }
   }
   grouping deterministic-object {
     description "Deterministic nat allocation";
     uses apply-advanced;
     leaf block-size {
       description "Block size";
       type union {
         type string {
           pattern "<.*>|$.*";
         }
         type uint16;
       }
     }
     leaf det-nat-configuration-log-interval {
       description "Deterministic nat configuration logging interval";
       type union {
         type string {
           pattern "<.*>|$.*";
         }
         type uint32 {
           range "1800 .. 86400";
         }
       }
     }
     container host {
       description "Host address";
       leaf-list address {
         ordered-by user;
         description "Host ip address";
         type jt:ipprefix;
         max-elements 8;
       }
       leaf-list address-name {
         ordered-by user;
         description "Host address/address-set from address book";
         type string;
         max-elements 8;
       }
     }
     leaf include-boundary-addresses {
       description "Include network and broadcast in 'match' source address";
       type empty;
     }
   }
   grouping source-nat-pool-utilization-alarm-object {
     uses apply-advanced;
     leaf raise-threshold {
       description "Raise threshold for pool utilization alarm";
       type union {
         type string {
           pattern "<.*>|$.*";
         }
         type uint16 {
           range "50 .. 100";
         }
       }
     }
     leaf clear-threshold {
       description "Clear threshold for pool utilization alarm";
       type union {
         type string {
           pattern "<.*>|$.*";
         }
         type uint16 {
           range "40 .. 100";
         }
       }
     }
   }
   grouping src-nat-rule-object {
     leaf name {
       description "Source NAT Rule name";
       type string {
         length "1 .. 63";
         junos:posix-pattern "^[[:alnum:]][[:alnum:]_-]*$";
         junos:pattern-message "Must be a string beginning with a number or letter and consisting of letters, numbers, dashes and underscores.";
       }
     }
     uses apply-advanced;
     leaf description {
       description "Text description of rule";
       type string {
         length "1 .. 900";
         junos:posix-pattern "^[^&<>\n]+$";
         junos:pattern-message "Must be a string excluding '&', '<', '>' and '\n'";
       }
     }
     container src-nat-rule-match {
       description "Specify Source NAT rule match criteria";
       uses apply-advanced;
       leaf-list source-address {
         ordered-by user;
         description "Source address";
         type string;
         max-elements 8;
       }
       leaf-list source-address-name {
         ordered-by user;
         description "Address/address-set from address book";
         type string;
         max-elements 8;
       }
       list source-port {
         key name;
         ordered-by user;
         description "Source port";
         max-elements 8;
         leaf name {
           description "Port or lower limit of port range";
           type union {
             type uint16;
             type string {
               pattern "<.*>|$.*";
             }
           }
         }
         container to {
           description "Port range upper limit";
           uses apply-advanced;
           leaf high {
             description "Upper limit of port range";
             type union {
               type uint16;
               type string {
                 pattern "<.*>|$.*";
               }
             }
           }
         }
       }
       leaf-list destination-address {
         ordered-by user;
         description "Destination address";
         type string;
         max-elements 8;
       }
       leaf-list destination-address-name {
         ordered-by user;
         description "Address/address-set from address book";
         type string;
         max-elements 8;
       }
       list destination-port {
         key name;
         ordered-by user;
         description "Destination port";
         max-elements 8;
         leaf name {
           description "Port or lower limit of port range";
           type union {
             type uint16;
             type string {
               pattern "<.*>|$.*";
             }
           }
         }
         container to {
           description "Port range upper limit";
           uses apply-advanced;
           leaf high {
             description "Upper limit of port range";
             type union {
               type uint16;
               type string {
                 pattern "<.*>|$.*";
               }
             }
           }
         }
       }
       leaf-list protocol {
         ordered-by user;
         description "IP Protocol";
         type string;
         max-elements 4;
       }
       leaf-list application {
         ordered-by user;
         type string;
       }
     }
     container then {
       description "Then action";
       uses apply-advanced;
       container source-nat {
         description "Source NAT action";
         uses apply-advanced;
         choice action {
           case case_1 {
             leaf off {
               description "No action";
               type empty;
             }
           }
           case case_2 {
             container pool {
               description "Use Source NAT pool";
               uses apply-advanced;
               leaf pool-name {
                 description "Name of Source NAT pool";
                 junos:must "(\".. .. .. .. .. .. .. .. nat source pool $$\")";
                 junos:must-message "Source NAT pool name must be defined";
                 type string {
                   length "1 .. 63";
                 }
               }
               container persistent-nat {
                 description "Persistent NAT info";
                 presence "enable persistent-nat";
                 uses persistent-nat-object;
               }
             }
           }
           case case_3 {
             container interface {
               presence "enable interface";
               description "Use egress interface address";
               uses apply-advanced;
               container persistent-nat {
                 description "Persistent NAT info";
                 presence "enable persistent-nat";
                 uses persistent-nat-object;
               }
             }
           }
         }
         leaf clat-prefix {
           description "An IPv6 prefix to be used for XLAT464 and prefix length can only be 32/40/48/56/64/96";
           junos:must "((\".. .. .. match source-address\" || \".. .. .. match source-address-name\"))";
           junos:must-message "source-address or source-address-name is required for Clat-prefix";
           type jt:ipprefix-only;
         }
         leaf clat-ipv6-prefix-length {
           description "The ipv6 prefix length for CLAT source address";
           junos:must "(!(\".. .. .. match\"))";
           junos:must-message "'match' criteria is not applicable when 'clat-ipv6-prefix-length' is configured.";
           junos:must "(!(\".. clat-prefix\"))";
           junos:must-message "clat-ipv6-prefix-length cannot be configured along with clat-prefix. Either clat-prefix or clat-ipv6-prefix-length can be configured.";
           type enumeration {
             enum "32" {
               description "The ipv6 prefix length of 32";
             }
             enum "40" {
               description "The ipv6 prefix length of 40";
             }
             enum "48" {
               description "The ipv6 prefix length of 48";
             }
             enum "56" {
               description "The ipv6 prefix length of 56";
             }
             enum "64" {
               description "The ipv6 prefix length of 64";
             }
             enum "96" {
               description "The ipv6 prefix length of 96";
             }
           }
         }
         container rule-session-count-alarm {
           description "Config rule-session-count-alarm to source rule";
           uses nat-rule-session-count-alarm-object;
         }
         container mapping-type {
           description "Source nat mapping type";
           leaf endpoint-independent {
             description "Endpoint independent mapping";
             type empty;
           }
           leaf address-pooling-paired {
             description "Address pooling paired mapping";
             type empty;
           }
         }
         container secure-nat-mapping {
           description "Mapping options for enhanced security";
           leaf eif-flow-limit {
             description "Number of inbound flows to be allowed for a EIF mapping";
             junos:must "(\".. .. filtering-type\")";
             junos:must-message "eif-flow-limit applies only to filtering-type";
             type union {
               type string {
                 pattern "<.*>|$.*";
               }
               type uint16 {
                 range "0 .. 65534";
               }
             }
           }
           container mapping-refresh {
             description "Enable timer refresh option";
             choice refresh-choice {
               case case_1 {
                 leaf inbound {
                   description "Enable timer refresh for inbound connections only";
                   type empty;
                 }
               }
               case case_2 {
                 leaf outbound {
                   description "Enable timer refresh for outbound connections only";
                   type empty;
                 }
               }
               case case_3 {
                 leaf inbound-outbound {
                   description "Enable timer refresh for inbound & outbound connections";
                   type empty;
                 }
               }
             }
           }
         }
         container filtering-type {
           junos:must "(\".. mapping-type endpoint-independent\")";
           junos:must-message "endpoint independent filtering can not be configured with endpoint-independent mapping only";
           description "Source NAT filtering type";
           uses apply-advanced;
           container endpoint-independent {
             presence "enable endpoint-independent";
             description "Endpoint independent filtering";
             uses apply-advanced;
             list prefix-list {
               key name;
               ordered-by user;
               description "One or more named lists of source prefixes to match";
               leaf name {
                 description "Name of prefix list to match against";
                 type string {
                   length "1 .. 63";
                 }
               }
               leaf except {
                 description "Name of prefix list not to match against";
                 type empty;
               }
             }
           }
         }
       }
       leaf syslog {
         description "System log information about the packet";
         type empty;
       }
     }
   }
   grouping persistent-nat-object {
     uses apply-advanced;
     container permit {
       description "Persistent NAT permit configure";
       choice persistent-nat-type-choice {
         case case_1 {
           leaf any-remote-host {
             description "Permit any remote host";
             type empty;
           }
         }
         case case_2 {
           leaf target-host {
             description "Permit target host";
             type empty;
           }
         }
         case case_3 {
           leaf target-host-port {
             description "Permit target host port";
             type empty;
           }
         }
       }
     }
     leaf block-ext-session {
       description "Block sessions from external hosts";
       type empty;
     }
     leaf address-mapping {
       description "Address-to-address mapping";
       type empty;
     }
     leaf inactivity-timeout {
       description "Inactivity timeout value";
       type union {
         type string {
           pattern "<.*>|$.*";
         }
         type uint16 {
           range "60 .. 7200";
         }
       }
     }
     leaf max-session-number {
       description "The maximum session number value";
       type union {
         type string {
           pattern "<.*>|$.*";
         }
         type uint32 {
           range "8 .. 65536";
         }
       }
     }
   }
   grouping ssg-static-nat-object {
     uses apply-advanced;
     list rule-set {
       key name;
       ordered-by user;
       description "Configurate a set of rules";
       leaf name {
         description "Rule-set name";
         type string {
           length "1 .. 63";
           junos:posix-pattern "^[[:alnum:]][[:alnum:]_-]*$";
           junos:pattern-message "Must be a string beginning with a number or letter and consisting of letters, numbers, dashes and underscores.";
         }
       }
       uses apply-advanced;
       leaf description {
         description "Text description of rule set";
         type string {
           length "1 .. 900";
           junos:posix-pattern "^[^&<>\n]+$";
           junos:pattern-message "Must be a string excluding '&', '<', '>' and '\n'";
         }
       }
       container from {
         description "Where is the traffic from";
         choice from-context-choice {
           case case_1 {
             leaf-list routing-instance {
               description "Source routing instance list";
               type string;
               max-elements 8;
             }
           }
           case case_2 {
             leaf-list routing-group {
               description "Source routing group list";
               type string;
               max-elements 8;
             }
           }
           case case_3 {
             leaf-list zone {
               description "Source zone list";
               type string;
               max-elements 8;
             }
           }
           case case_4 {
             leaf-list interface {
               description "Source interface list";
               type union {
                 type jt:interface-name;
                 type string {
                   pattern "<.*>|$.*";
                 }
               }
               max-elements 8;
             }
           }
         }
       }
       list rule {
         key name;
         ordered-by user;
         description "Static NAT rule";
         uses static-nat-rule-object;
       }
       leaf match-direction {
         description "Match direction";
         type enumeration {
           enum "input" {
             description "Match on input to interface";
           }
           enum "output" {
             description "Match on output from interface";
           }
         }
       }
     }
   }
   grouping static-nat-rule-object {
     leaf name {
       description "Static Rule name";
       type string {
         length "1 .. 63";
         junos:posix-pattern "^[[:alnum:]][[:alnum:]_-]*$";
         junos:pattern-message "Must be a string beginning with a number or letter and consisting of letters, numbers, dashes and underscores.";
       }
     }
     uses apply-advanced;
     leaf description {
       description "Text description of rule";
       type string {
         length "1 .. 900";
         junos:posix-pattern "^[^&<>\n]+$";
         junos:pattern-message "Must be a string excluding '&', '<', '>' and '\n'";
       }
     }
     container static-nat-rule-match {
       description "Specify Static NAT rule match criteria";
       uses apply-advanced;
       leaf-list source-address {
         ordered-by user;
         description "Source address";
         type jt:ipprefix;
         max-elements 8;
       }
       leaf-list source-address-name {
         ordered-by user;
         description "Address from address book";
         type string;
         max-elements 8;
       }
       list source-port {
         key name;
         ordered-by user;
         description "Source port";
         max-elements 8;
         leaf name {
           description "Port or lower limit of port range";
           type union {
             type uint16;
             type string {
               pattern "<.*>|$.*";
             }
           }
         }
         container to {
           description "Port range upper limit";
           uses apply-advanced;
           leaf high {
             description "Upper limit of port range";
             type union {
               type uint16;
               type string {
                 pattern "<.*>|$.*";
               }
             }
           }
         }
       }
       choice dst-choice {
         case case_1 {
           container destination-address {
             description "Destination address";
             leaf dst-addr {
               description "IPv4 or IPv6 Destination address prefix";
               type jt:ipprefix;
             }
           }
         }
         case case_2 {
           container destination-address-name {
             description "Address from address book";
             leaf dst-addr-name {
               description "Address from address book";
               type string {
                 length "1 .. 63";
               }
             }
           }
         }
       }
       container destination-port {
         description "Destination port";
         leaf low {
           description "Port or lower limit of port range";
           junos:must "((\".. .. .. then static-nat prefix mapped-port\" || \".. .. .. then static-nat prefix-name mapped-port\"))";
           junos:must-message "'then static-nat prefix mapped-port ...' or 'then static-nat prefix-name mapped-port' must be configured when configure 'destination-port'";
           type union {
             type uint16;
             type string {
               pattern "<.*>|$.*";
             }
           }
         }
         container to {
           description "Port range upper limit";
           uses apply-advanced;
           leaf high {
             description "Upper limit of port range";
             type union {
               type uint16;
               type string {
                 pattern "<.*>|$.*";
               }
             }
           }
         }
       }
     }
     container then {
       description "Then action";
       uses apply-advanced;
       container static-nat {
         description "Static NAT action";
         uses apply-advanced;
         choice prefix-choice {
           case case_1 {
             container inet {
               presence "enable inet";
               description "Translated to IPv4 address";
               uses apply-advanced;
               leaf routing-instance {
                 description "Routing instance";
                 type string;
               }
             }
           }
           case case_2 {
             container prefix {
               description "Address prefix";
               uses apply-advanced;
               leaf addr-prefix {
                 description "IPv4 or IPv6 address prefix value";
                 type jt:ipprefix;
               }
               container mapped-port {
                 description "Mapped port";
                 uses static-nat-rule-mapped-port-object;
               }
               leaf routing-instance {
                 description "Routing instance";
                 type string;
               }
             }
           }
           case case_3 {
             container prefix-name {
               description "Address from address book";
               uses apply-advanced;
               leaf addr-prefix-name {
                 description "Address from address book";
                 type string {
                   length "1 .. 63";
                 }
               }
               container mapped-port {
                 description "Mapped port";
                 uses static-nat-rule-mapped-port-object;
               }
               leaf routing-instance {
                 description "Routing instance";
                 type string;
               }
             }
           }
           case case_4 {
             container nptv6-prefix {
               description "NPTv6 address prefix, the longest prefix will be supported is /64";
               uses apply-advanced;
               leaf addr-prefix {
                 description "IPv6 address prefix value, the longest prefix will be supported is /64";
                 type jt:ipprefix;
               }
               leaf routing-instance {
                 description "Routing instance";
                 type string;
               }
             }
           }
           case case_5 {
             container nptv6-prefix-name {
               description "NPTv6 address from address book";
               uses apply-advanced;
               leaf addr-prefix-name {
                 description "IPv6 address from address book";
                 type string {
                   length "1 .. 63";
                 }
               }
               leaf routing-instance {
                 description "Routing instance";
                 type string;
               }
             }
           }
         }
         container rule-session-count-alarm {
           description "Config rule-session-count-alarm to static rule";
           uses nat-rule-session-count-alarm-object;
         }
       }
     }
   }
   grouping static-nat-rule-mapped-port-object {
     uses apply-advanced;
     leaf low {
       description "Port or lower limit of port range";
       junos:must "(\".. .. .. .. .. match destination-port\")";
       junos:must-message "'match destination-port ...' must be configured when configure 'mapped-port'";
       type union {
         type uint16;
         type string {
           pattern "<.*>|$.*";
         }
       }
     }
     container to {
       description "Port range upper limit";
       uses apply-advanced;
       leaf high {
         description "Upper limit of port range";
         type union {
           type uint16;
           type string {
             pattern "<.*>|$.*";
           }
         }
       }
     }
   }
   grouping stp-interface {
     leaf name {
       type string;
     }
     uses apply-advanced;
     leaf priority {
       description "Interface priority (in increments of 16 - 0,16,..240)";
       type union {
         type string {
           pattern "<.*>|$.*";
         }
         type uint16 {
           range "0 .. 255";
         }
       }
     }
     leaf cost {
       description "Cost of the interface";
       type union {
         type string {
           pattern "<.*>|$.*";
         }
         type uint32 {
           range "1 .. 200000000";
         }
       }
     }
     leaf mode {
       description "Interface mode (P2P or shared)";
       type enumeration {
         enum "point-to-point" {
           description "Interface mode is point-to-point";
         }
         enum "shared" {
           description "Interface mode is shared";
         }
       }
     }
     leaf edge {
       description "Port is an edge port";
       type empty;
     }
     leaf access-trunk {
       description "Send/Receive untagged RSTP BPDUs on this interface";
       type empty;
     }
     container bpdu-timeout-action {
       presence "enable bpdu-timeout-action";
       description "Define action on BPDU expiry (Loop Protect)";
       uses apply-advanced;
       leaf block {
         description "Block the interface";
         type empty;
       }
       leaf alarm {
         description "Generate an alarm";
         type empty;
       }
     }
     leaf no-root-port {
       description "Do not allow the interface to become root (Root Protect)";
       type empty;
     }
     leaf disable {
       description "Disable Spanning Tree on port";
       type empty;
     }
   }
   grouping stp-trace-options {
     description "Trace options for Spanning Tree Protocol";
     uses apply-advanced;
     container file {
       description "Trace file options";
       leaf filename {
         description "Name of file in which to write trace information";
         type string {
           length "1 .. 1024";
           junos:posix-pattern "![/ %]";
           junos:pattern-message "Must not contain '/', % or a space";
         }
       }
       leaf replace {
         description "Replace trace file rather than appending to it";
         status deprecated;
         type empty;
       }
       leaf size {
         description "Maximum trace file size";
         type string;
       }
       leaf files {
         description "Maximum number of trace files";
         default "10";
         type union {
           type string {
             pattern "<.*>|$.*";
           }
           type uint32 {
             range "2 .. 1000";
           }
         }
       }
       leaf no-stamp {
         description "Do not timestamp trace file";
         status deprecated;
         type empty;
       }
       choice world-readable-choice {
         leaf world-readable {
           description "Allow any user to read the log file";
           type empty;
         }
         leaf no-world-readable {
           description "Don't allow any user to read the log file";
           type empty;
         }
       }
     }
     list flag {
       key name;
       ordered-by user;
       description "Tracing parameters";
       junos:must "(\".. file\")";
       junos:must-message "Trace file name required to enable tracing";
       leaf name {
         type enumeration {
           enum "events" {
             description "Trace events to the protocol state machine";
           }
           enum "bpdu" {
             description "Trace BPDU reception and transmission";
           }
           enum "timers" {
             description "Trace protocol timers";
           }
           enum "port-information-state-machine" {
             description "Trace port information state machine";
           }
           enum "port-receive-state-machine" {
             description "Trace port receive state machine";
           }
           enum "port-role-select-state-machine" {
             description "Trace port role selection state machine";
           }
           enum "port-role-transit-state-machine" {
             description "Trace port role transit state machine";
           }
           enum "port-state-transit-state-machine" {
             description "Trace port state transit state machine";
           }
           enum "port-migration-state-machine" {
             description "Trace port migration state machine";
           }
           enum "port-transmit-state-machine" {
             description "Trace port transmit state machine";
           }
           enum "topology-change-state-machine" {
             description "Trace topology change state machine";
           }
           enum "bridge-detection-state-machine" {
             description "Trace Bridge detection state machine";
           }
           enum "state-machine-variables" {
             description "Trace when state machine variables change";
           }
           enum "ppmd" {
             description "Trace state and events for ppmd process";
           }
           enum "all-failures" {
             description "Trace all failure conditions";
           }
           enum "all" {
             description "Trace all";
           }
         }
       }
       leaf disable {
         description "Disable this trace flag";
         type empty;
       }
     }
   }
   grouping subscription-type {
     uses apply-advanced;
     leaf link-subscription {
       description "Link bandwidth percentage for RSVP reservation";
       default "100";
       type string;
     }
     leaf ct0 {
       description "Subscription percentage for traffic class 0";
       default "100";
       junos:must "(\"protocols mpls diffserv-te bandwidth-model\")";
       junos:must-message "Must have a diffserv-te bandwidth model configured when configuring subscription per traffic class";
       type string;
     }
     leaf ct1 {
       description "Subscription percentage for traffic class 1";
       default "100";
       junos:must "(\"protocols mpls diffserv-te bandwidth-model\")";
       junos:must-message "Must have a diffserv-te bandwidth model configured when configuring subscription per traffic class";
       type string;
     }
     leaf ct2 {
       description "Subscription percentage for traffic class 2";
       default "100";
       junos:must "(\"protocols mpls diffserv-te bandwidth-model\")";
       junos:must-message "Must have a diffserv-te bandwidth model configured when configuring subscription per traffic class";
       type string;
     }
     leaf ct3 {
       description "Subscription percentage for traffic class 3";
       default "100";
       junos:must "(\"protocols mpls diffserv-te bandwidth-model\")";
       junos:must-message "Must have a diffserv-te bandwidth model configured when configuring subscription per traffic class";
       type string;
     }
     list priority {
       key priority-value;
       ordered-by user;
       description "Subscription percentage for a specific priority";
       leaf priority-value {
         description "Priority for which subscription percent is being configured";
         junos:must "(!(\"protocols mpls diffserv-te\"))";
         junos:must-message "Cannot configure per-priority subscription alongside diffserv-te";
         type union {
           type string {
             pattern "<.*>|$.*";
           }
           type uint32 {
             range "0 .. 7";
           }
         }
       }
       uses apply-advanced;
       leaf percent {
         description "Subscription percent for the specific priority";
         junos:must "(!(\"protocols mpls diffserv-te\"))";
         junos:must-message "Cannot configure per-priority subscription alongside diffserv-te";
         type string;
       }
     }
   }
   grouping svr-cipher-suite-list-type {
     leaf name {
       description "Cipher-suite name";
       type string {
         length "1 .. 63";
         junos:posix-pattern "^[[:alnum:]][[:alnum:]_-]*$";
         junos:pattern-message "Must be a string beginning with a number or letter and consisting of letters, numbers, dashes and underscores.";
       }
     }
     uses apply-advanced;
     leaf authentication-algorithm {
       description "Define authentication algorithm";
       type enumeration {
         enum "hmac-sha1" {
           description "HMAC-SHA1 authentication algorithm";
         }
         enum "hmac-sha2-256" {
           description "HMAC-SHA-256 authentication algorithm";
         }
         enum "hmac-sha-256-128" {
           description "HMAC-SHA-256-128 authentication algorithm";
         }
       }
     }
     leaf authentication-disabled {
       description "Disable authentication";
       type empty;
     }
     leaf encryption-algorithm {
       description "Define encryption algorithm";
       type enumeration {
         enum "aes-128-cbc" {
           description "AES-CBC 128-bit encryption algorithm";
         }
         enum "aes-256-cbc" {
           description "AES-CBC 256-bit encryption algorithm";
         }
       }
     }
     leaf encryption-disabled {
       description "Disable encryption";
       type empty;
     }
     leaf adaptive-encryption-disabled {
       description "Disable adaptive encryption";
       type empty;
     }
     container authentication-key {
       description "Define an authentication key";
       choice key-choice {
         case case_1 {
           leaf ascii-text {
             description "Format as text";
             type string {
               length "1 .. 255";
             }
           }
         }
         case case_2 {
           leaf hexadecimal {
             description "Format as hexadecimal";
             type string {
               length "1 .. 255";
               junos:posix-pattern "^[[:xdigit:]]+$";
               junos:pattern-message "Must be hexadecimal digits (0-9, a-f, A-F)";
             }
           }
         }
       }
     }
     container encryption-key {
       description "Define an encryption key";
       choice key-choice {
         case case_1 {
           leaf ascii-text {
             description "Format as text";
             type string {
               length "1 .. 255";
             }
           }
         }
         case case_2 {
           leaf hexadecimal {
             description "Format as hexadecimal";
             type string {
               length "1 .. 255";
               junos:posix-pattern "^[[:xdigit:]]+$";
               junos:pattern-message "Must be hexadecimal digits (0-9, a-f, A-F)";
             }
           }
         }
       }
     }
     leaf encryption-vector {
       description "Encryption-vector string";
       type string {
         length "1 .. 63";
         junos:posix-pattern "^[[:alnum:]][[:alnum:]_-]*$";
         junos:pattern-message "Must be a string beginning with a number or letter and consisting of letters, numbers, dashes and underscores.";
       }
     }
   }
   grouping svr-destination-service-list-type {
     leaf name {
       description "Destination service name";
       type string {
         length "1 .. 63";
         junos:posix-pattern "^[[:alnum:]][[:alnum:]_-]*$";
         junos:pattern-message "Must be a string beginning with a number or letter and consisting of letters, numbers, dashes and underscores.";
       }
     }
     leaf-list ip-prefix {
       ordered-by user;
       description "Destination-service IP prefix";
       type jt:ipprefix;
       max-elements 32;
     }
     container transport {
       description "Transport layer protocol and port";
       uses apply-advanced;
       container tcp {
         presence "enable tcp";
         description "TCP protocol";
         uses apply-advanced;
         list port-range {
           key name;
           ordered-by user;
           description "Port range";
           max-elements 8;
           uses port-range-list-type;
         }
       }
       container udp {
         presence "enable udp";
         description "UDP protocol";
         uses apply-advanced;
         list port-range {
           key name;
           ordered-by user;
           description "Port range";
           max-elements 8;
           uses port-range-list-type;
         }
       }
       leaf icmp {
         description "ICMP protocol";
         type empty;
       }
       leaf gre {
         description "GRE protocol";
         type empty;
       }
     }
     list access-policy {
       key name;
       ordered-by user;
       description "Access policy";
       max-elements 32;
       uses access-policy-list-type;
     }
     leaf cipher-suite {
       description "Cipher-suite";
       junos:must "(\"services vector-routing cipher-suites $$\")";
       junos:must-message "'cipher-suite' must be configured";
       type string {
         length "1 .. 63";
       }
     }
   }
   grouping access-policy-list-type {
     leaf name {
       description "From source-tenant";
       junos:must "(\"services vector-routing source-tenants $$\")";
       junos:must-message "Referenced 'source-tenant' must be configured";
       type string {
         length "1 .. 63";
         junos:posix-pattern "^[[:alnum:]][[:alnum:]_-]*$";
         junos:pattern-message "Must be a string beginning with a number or letter and consisting of letters, numbers, dashes and underscores.";
       }
     }
     uses apply-advanced;
     leaf permission {
       description "Permission with allow as default";
       default "allow";
       type enumeration {
         enum "allow" {
           description "Permit";
         }
         enum "deny" {
           description "Deny";
         }
       }
     }
   }
   grouping port-range-list-type {
     leaf name {
       description "Lower limit of port range";
       type union {
         type uint32;
         type string {
           pattern "<.*>|$.*";
         }
       }
     }
     uses apply-advanced;
     container to {
       description "Port range upper limit";
       leaf range-high {
         description "Upper limit of port range";
         type union {
           type uint32;
           type string {
             pattern "<.*>|$.*";
           }
         }
       }
     }
   }
   grouping svr-meta-bfd-type {
     description "Vector routing meta-bfd configuration";
     uses apply-advanced;
     leaf desired-tx-interval {
       description "Represents the frequency with which BFD asynchronous control packets (milliseconds)";
       default "1000";
       type union {
         type string {
           pattern "<.*>|$.*";
         }
         type uint32 {
           range "50 .. 600000";
         }
       }
     }
     leaf required-min-rx-interval {
       description "Represents the minimum interval between BFD asynchronous control packets (milliseconds)";
       default "500";
       type union {
         type string {
           pattern "<.*>|$.*";
         }
         type uint32 {
           range "50 .. 600000";
         }
       }
     }
     leaf dscp {
       description "The DSCP value to use with BFD packets";
       default "0";
       type union {
         type string {
           pattern "<.*>|$.*";
         }
         type uint32 {
           range "0 .. 63";
         }
       }
     }
     leaf link-test-interval {
       description "This represents the interval between BFD echo tests sent to the peer (seconds)";
       default "10";
       type union {
         type string {
           pattern "<.*>|$.*";
         }
         type uint32 {
           range "1 .. 86400";
         }
       }
     }
     leaf multiplier {
       description "Number of consecutive missed messages deciding the link between them is unusable";
       default "3";
       type union {
         type string {
           pattern "<.*>|$.*";
         }
         type uint32 {
           range "3 .. 20";
         }
       }
     }
   }
   grouping svr-router-list-type {
     leaf name {
       description "Router name";
       type string {
         length "1 .. 63";
         junos:posix-pattern "^[[:alnum:]][[:alnum:]_-]*$";
         junos:pattern-message "Must be a string beginning with a number or letter and consisting of letters, numbers, dashes and underscores.";
       }
     }
     uses apply-advanced;
     list node {
       key name;
       ordered-by user;
       description "Router's node name";
       max-elements 1;
       uses svr-node-list-type;
     }
     list peer {
       key name;
       ordered-by user;
       description "Router's peer configuration";
       uses svr-peer-list-type;
     }
     list service-routes {
       key name;
       ordered-by user;
       description "Router's service route";
       uses svr-service-route-list-type;
     }
   }
   grouping svr-node-list-type {
     leaf name {
       description "Service node name";
       type string {
         length "1 .. 63";
         junos:posix-pattern "^[[:alnum:]][[:alnum:]_-]*$";
         junos:pattern-message "Must be a string beginning with a number or letter and consisting of letters, numbers, dashes and underscores.";
       }
     }
     uses apply-advanced;
     list interfaces {
       key name;
       ordered-by user;
       description "Service node interfaces";
       uses svr-router-node-interface-list-type;
     }
   }
   grouping svr-peer-list-type {
     leaf name {
       description "Peer name";
       type string {
         length "1 .. 63";
         junos:posix-pattern "^[[:alnum:]][[:alnum:]_-]*$";
         junos:pattern-message "Must be a string beginning with a number or letter and consisting of letters, numbers, dashes and underscores.";
       }
     }
     uses apply-advanced;
     leaf authority {
       description "Peer authority";
       junos:must "(\".. .. .. authority-name $$\")";
       junos:must-message "'authority-name' must be configured";
       type string {
         length "1 .. 63";
       }
     }
     leaf router {
       description "Peer router";
       type string {
         length "1 .. 63";
       }
     }
   }
   grouping svr-router-node-interface-list-type {
     leaf name {
       description "Vector-routing logical interface";
       junos:must "(!((\"protocols l2-learning global-mode switching\" && \"interfaces $$ family ethernet-switching\")))";
       junos:must-message "Referenced interface must not be ethernet-switching interface of switching mode";
       type union {
         type jt:interface-name;
         type string {
           pattern "<.*>|$.*";
         }
       }
     }
     uses apply-advanced;
     list adjacency {
       key name;
       ordered-by user;
       description "Configure vector routing interface adjacency";
       uses svr-adjacency-list-type;
     }
     leaf cipher-suite {
       description "Cipher-suite";
       junos:must "(\".. .. .. .. cipher-suites $$\")";
       junos:must-message "'cipher-suite' must be configured";
       type string {
         length "1 .. 63";
       }
     }
   }
   grouping svr-adjacency-list-type {
     leaf name {
       description "Adjacency name";
       type string {
         length "1 .. 63";
         junos:posix-pattern "^[[:alnum:]][[:alnum:]_-]*$";
         junos:pattern-message "Must be a string beginning with a number or letter and consisting of letters, numbers, dashes and underscores.";
       }
     }
     uses apply-advanced;
     leaf address {
       description "Adjacency IP address";
       type jt:ipaddr;
     }
     leaf peer {
       description "Adjacency peer name";
       junos:must "(\".. .. .. .. peer $$\")";
       junos:must-message "'peer' must be configured";
       type string {
         length "1 .. 63";
       }
     }
     leaf cipher-suite {
       description "Security policy";
       junos:must "(\".. .. .. .. .. cipher-suites $$\")";
       junos:must-message "'cipher-suite' must be configured";
       type string {
         length "1 .. 63";
       }
     }
     leaf cost {
       description "Link cost";
       default "1";
       type union {
         type string {
           pattern "<.*>|$.*";
         }
         type uint32 {
           range "1 .. 255";
         }
       }
     }
     leaf peer-connectivity {
       description "Peer-connectivity type (bidirectional/outbound-only)";
       default "bidirectional";
       type enumeration {
         enum "bidirectional" {
           description "Bidirectional";
         }
         enum "outbound-only" {
           description "Outbound-only";
         }
       }
     }
   }
   grouping svr-service-route-list-type {
     leaf name {
       description "Service route name";
       type string {
         length "1 .. 63";
         junos:posix-pattern "^[[:alnum:]][[:alnum:]_-]*$";
         junos:pattern-message "Must be a string beginning with a number or letter and consisting of letters, numbers, dashes and underscores.";
       }
     }
     uses apply-advanced;
     leaf peer {
       description "Service peer name";
       junos:must "(\".. .. peer $$\")";
       junos:must-message "'peer' must be configured";
       type string {
         length "1 .. 63";
       }
     }
     leaf destination-service {
       description "Destination service name";
       junos:must "(\"services vector-routing destination-services $$\")";
       junos:must-message "'destination-services' must be configured";
       type string {
         length "1 .. 63";
       }
     }
   }
   grouping svr-source-tenant-list-type {
     leaf name {
       description "Source tenant name";
       type string {
         length "1 .. 63";
         junos:posix-pattern "^[[:alnum:]][[:alnum:]_-]*$";
         junos:pattern-message "Must be a string beginning with a number or letter and consisting of letters, numbers, dashes and underscores.";
       }
     }
     leaf-list ip-prefix {
       ordered-by user;
       description "Source-tenant IP prefix";
       type jt:ipprefix;
       max-elements 32;
     }
     list interfaces {
       key name;
       ordered-by user;
       description "Incoming interfaces";
       max-elements 32;
       uses source-tenant-interface-list-type;
     }
   }
   grouping source-tenant-interface-list-type {
     description "Logical interfaces in this source-tenant";
     leaf name {
       description "Logical interface";
       junos:must "(any \"services vector-routing router <*> node <*> interfaces $$\")";
       junos:must-message "Referenced 'interface' must be configured under services vector-routing router <router-name> node <node-name> interfaces";
       type union {
         type jt:interface-name;
         type string {
           pattern "<.*>|$.*";
         }
       }
     }
     uses apply-advanced;
   }
   grouping sw-rule-set-object {
     leaf name {
       description "Define Rule Set name";
       type string {
         length "1 .. 63";
         junos:posix-pattern "^[[:alnum:]][[:alnum:]_-]*$";
         junos:pattern-message "Must be a string beginning with a number or letter and consisting of letters, numbers, dashes and underscores.";
       }
     }
     uses apply-advanced;
     list rule {
       key name;
       ordered-by user;
       description "Define a rule term";
       leaf name {
         description "Rule name";
         type string {
           length "1 .. 63";
           junos:posix-pattern "^[[:alnum:]][[:alnum:]_-]*$";
           junos:pattern-message "Must be a string beginning with a number or letter and consisting of letters, numbers, dashes and underscores.";
         }
       }
       uses apply-advanced;
       container then {
         description "Action to take if the condition is matched";
         uses apply-advanced;
         choice designation {
           case case_1 {
             leaf ds-lite {
               description "Apply DS-Lite softwire";
               junos:must "(\"services softwires softwire-types ds-lite $$\")";
               junos:must-message "referenced softwire concentrator must be
                                  defined under 'services softwires softwire-types ds-lite'";
               type string {
                 length "1 .. 63";
                 junos:posix-pattern "^[[:alnum:]][[:alnum:]_-]*$";
                 junos:pattern-message "Must be a string beginning with a number or letter and consisting of letters, numbers, dashes and underscores.";
               }
             }
           }
           case case_2 {
             leaf v6rd {
               description "Apply 6rd softwire";
               type string {
                 length "1 .. 63";
                 junos:posix-pattern "^[[:alnum:]][[:alnum:]_-]*$";
                 junos:pattern-message "Must be a string beginning with a number or letter and consisting of letters, numbers, dashes and underscores.";
               }
             }
           }
           case case_3 {
             leaf map-e {
               description "Apply MAP-E softwire";
               junos:must "(\"services softwires softwire-types map-e $$\")";
               junos:must-message "Undefined softwire concentrator for map-e";
               type string {
                 length "1 .. 63";
                 junos:posix-pattern "^[[:alnum:]][[:alnum:]_-]*$";
                 junos:pattern-message "Must be a string beginning with a number or letter and consisting of letters, numbers, dashes and underscores.";
               }
             }
           }
         }
       }
     }
     leaf match-direction {
       description "Match direction";
       type enumeration {
         enum "input" {
           description "Match on input to interface";
         }
         enum "output" {
           description "Match on output from interface";
         }
       }
     }
   }
   grouping system-id-ip-map {
     leaf name {
       type jt:mac-unicast;
     }
     uses apply-advanced;
     leaf ip-address {
       description "Peer ID (IP Address)";
       type jt:ipv4prefix;
     }
   }
   grouping te-class-object {
     leaf traffic-class {
       description "Traffic class";
       type enumeration {
         enum "ct0" {
           description "Traffic class 0";
         }
         enum "ct1" {
           description "Traffic class 1";
         }
         enum "ct2" {
           description "Traffic class 2";
         }
         enum "ct3" {
           description "Traffic class 3";
         }
       }
     }
     leaf priority {
       description "Preemption priority for this class";
       type union {
         type string {
           pattern "<.*>|$.*";
         }
         type uint32 {
           range "0 .. 7";
         }
       }
     }
   }
   grouping tenant-system-type {
     description "Tenant name";
     leaf name {
       description "Tenant name";
       junos:must "(\"tenants $$\")";
       junos:must-message "Tenants must be defined under [tenants] ";
       type string;
     }
     uses apply-advanced;
     leaf max-sessions {
       description "Max number of IDP sessions";
       type union {
         type uint32;
         type string {
           pattern "<.*>|$.*";
         }
       }
     }
   }
   grouping tenant_interfaces_type {
     description "Physical interface";
     leaf name {
       description "Interface name";
       type union {
         type jt:interface-unit;
         type string {
           pattern "<.*>|$.*";
         }
       }
     }
     uses apply-advanced;
     list unit {
       key name;
       description "Logical interface";
       leaf name {
         type string;
       }
       uses apply-advanced;
       container policer-overhead {
         description "Policer overhead adjustment for this unit";
         uses apply-advanced;
         leaf policer-overhead-value {
           description "Policer overhead bytes to be accounted in ingress and egress";
           units "bytes";
           junos:must "((!(\".. ingress\") && !(\".. egress\")))";
           junos:must-message "Do not use the options ingress or egress when adjust values are specified";
           type union {
             type string {
               pattern "<.*>|$.*";
             }
             type int32 {
               range "-64 .. 64";
             }
           }
         }
         leaf ingress {
           description "Ingress value in bytes";
           units "bytes";
           type union {
             type string {
               pattern "<.*>|$.*";
             }
             type int32 {
               range "-64 .. 64";
             }
           }
         }
         leaf egress {
           description "Egress value in bytes";
           units "bytes";
           type union {
             type string {
               pattern "<.*>|$.*";
             }
             type int32 {
               range "-64 .. 64";
             }
           }
         }
       }
       leaf alias {
         description "Interface alias";
         junos:must "(!(\"interfaces interface-range $$\"))";
         junos:must-message "Interface alias cannot be an existing interface range name";
         type string;
       }
       leaf enhanced-convergence {
         description "Optimize convergence time for L3";
         type empty;
       }
       leaf proxy-macip-advertisement {
         description "Proxy advertisement of type 2 MAC+IP route for EVPN";
         type empty;
       }
       leaf virtual-gateway-accept-data {
         description "Accept packets destined for virtual gateway address";
         type empty;
       }
       container peer-psd {
         presence "enable peer-psd";
         description "Peer psd";
         leaf psd-name {
           description "Peer psd name";
           junos:must "(\".. .. peer-interface\")";
           junos:must-message "peer-interface must be configured on this interface";
           type string;
         }
       }
       container peer-interface {
         presence "enable peer-interface";
         description "Peer interface";
         uses apply-advanced;
         leaf interface-name {
           description "Peer interface name";
           junos:must "((\".. .. peer-psd\" || \"interfaces $$-IFL peer-interface\"))";
           junos:must-message "Peer interface or peer psd must be configured";
           type union {
             type jt:interface-unit;
             type string {
               pattern "<.*>|$.*";
             }
           }
         }
       }
       container interface-shared-with {
         presence "enable interface-shared-with";
         junos:must "(\"chassis system-domains\")";
         junos:must-message "Chassis system-domains must be configured";
         description "Specify which PSD owns this logical interface";
         uses apply-advanced;
         leaf psd-name {
           description "Name of protected system domain (psd[1-31], ex. psd2)";
           type string {
             junos:posix-pattern "^psd([1-9]|[1-2][0-9]|[3][0-1])$";
             junos:pattern-message "Protected system domain name is a string consisting of 'psd' follows by the PSD ID (1-31), ex. psd2";
           }
         }
       }
       choice enable-disable {
         case case_1 {
           leaf disable {
             description "Disable this logical interface";
             type empty;
           }
         }
       }
       leaf passive-monitor-mode {
         description "Use interface to tap packets from another router";
         type empty;
       }
       leaf per-session-scheduler {
         description "Enable per-session queuing on an IQ2 interface";
         junos:must "(!((\"interfaces ${interface} per-unit-scheduler\" || \"interfaces ${interface} shared-scheduler\")))";
         junos:must-message "session queueing is not supported with unit queueing";
         type empty;
       }
       container account-layer2-overhead {
         presence "enable account-layer2-overhead";
         description "Account layer2 overhead in IFL byte statistics";
         uses apply-advanced;
         leaf overhead-value {
           description "Layer2 overhead bytes to be accounted in ingress and egress";
           units "bytes";
           junos:must "((!(\".. ingress\") && !(\".. egress\")))";
           junos:must-message "Do not use the options ingress or egress when adjust values are specified";
           type union {
             type string {
               pattern "<.*>|$.*";
             }
             type int8 {
               range "-128 .. 127";
             }
           }
         }
         leaf ingress {
           description "Layer2 overhead bytes to be accounted in ingress";
           units "bytes";
           type union {
             type string {
               pattern "<.*>|$.*";
             }
             type int8 {
               range "-128 .. 127";
             }
           }
         }
         leaf egress {
           description "Layer2 overhead bytes to be accounted in egress";
           units "bytes";
           type union {
             type string {
               pattern "<.*>|$.*";
             }
             type int8 {
               range "-128 .. 127";
             }
           }
         }
       }
       container forwarding-class-accounting {
         presence "enable forwarding-class-accounting";
         junos:must "((\".. forwarding-class-accounting enhanced\" || !(any \".. .. unit <*> forwarding-class-accounting enhanced\")))";
         junos:must-message "Cannot mix Forwarding-class accounting modes between IFLs of same IFD. Configured in 'enhanced' mode on atleast one of the IFL.";
         description "Configure Forwarding-class-accounting parameters for IFL ";
         uses apply-advanced;
         leaf direction {
           description "Direction of the traffic to be accounted for IFL";
           type enumeration {
             enum "ingress" {
               description "Enable forwarding-class-accounting for ingress traffic";
             }
             enum "egress" {
               description "Enable forwarding-class-accounting for egress traffic";
             }
             enum "both" {
               description "Enable forwarding-class-accounting for both directions";
             }
           }
         }
         container enhanced {
           presence "enable enhanced";
           junos:must "(!(\"forwarding-options hyper-mode\"))";
           junos:must-message "To configure enhanced, 'forwarding-options hyper-mode' should not be configured";
           junos:must "(!(\".. .. forwarding-class-accounting direction\"))";
           junos:must-message "Cannot set both 'enhanced' and 'direction' directly under forwarding-class-accounting.";
           junos:must "((!(\".. .. family\") || (\".. .. family inet\" || \".. .. family inet6\")))";
           junos:must-message "Forwarding-class accounting is supported only for inet/inet6 family";
           uses apply-advanced;
           leaf traffic-type {
             description "Traffic-type to be accounted for forwarding-class-accounting for IFL";
             type enumeration {
               enum "unicast-statistics" {
                 description "Count only unicast traffic for forwarding-class-accounting for IFL ";
               }
               enum "multicast-statistics" {
                 description "Count only multicast traffic for forwarding-class-accounting for IFL";
               }
             }
           }
           leaf family {
             description "Protocol traffic to be accounted for forwarding-class-accounting for IFL";
             type enumeration {
               enum "inet" {
                 description "Enable forwarding-class-accounting for IPv4 family only for IFL";
               }
               enum "inet6" {
                 description "Enable forwarding-class-accounting for IPv6 family only for IFL";
               }
               enum "both" {
                 description "Enable forwarding-class-accounting for both IPv4 and IPv6 family for IFL";
               }
             }
           }
           leaf direction {
             description "Direction of the traffic to be accounted for forwarding-class-accounting for IFL";
             type enumeration {
               enum "ingress" {
                 description "Enable forwarding-class-accounting for ingress traffic for IFL";
               }
               enum "egress" {
                 description "Enable forwarding-class-accounting for egress traffic for IFL";
               }
               enum "both" {
                 description "Enable forwarding-class-accounting for both ingress and egress traffic for IFL";
               }
             }
           }
           leaf overhead-bytes {
             description "Per octet overhead bytes to be accounted for forwarding-class-accounting for IFL ";
             default "0";
             type union {
               type string {
                 pattern "<.*>|$.*";
               }
               type uint32 {
                 range "0 .. 255";
               }
             }
           }
         }
       }
       leaf clear-dont-fragment-bit {
         description "Clear DF bit in packet (AS PIC and J-series only as well as MIF)";
         type empty;
       }
       leaf packet-inject-enable {
         description "Enable packet inject functionality on this IFL";
         type empty;
       }
       leaf reassemble-packets {
         description "Do reassembly of fragmented tunnel packets";
         type empty;
       }
       container services-options {
         description "Services interface-specific options";
         uses apply-advanced;
       }
       container rpm {
         junos:must "(!(\"interfaces ${interface} unit $$={0} rpm\"))";
         junos:must-message "RPM/TWAMP services cannot be enabled under unit 0";
         junos:must "(\"interfaces ${interface} unit $$={0} family inet\")";
         junos:must-message "unit 0 family inet must be configured on this interface";
         description "Enable RPM service on this interface";
         uses apply-advanced;
         choice rpm_or_twamp {
           case case_1 {
             choice rpm-type {
               case case_1 {
                 leaf client {
                   description "Client mode";
                   type empty;
                 }
               }
               case case_2 {
                 leaf server {
                   description "Server mode";
                   type empty;
                 }
               }
               case case_3 {
                 leaf client-delegate-probes {
                   description "Client delegate probe mode";
                   type empty;
                 }
               }
             }
           }
           case case_2 {
             leaf twamp-server {
               description "Set TWAMP server mode on this interface";
               junos:must "(unique \"interfaces ${interface} unit <*> rpm twamp-server\")";
               junos:must-message "TWAMP service can be enabled on 1 logical interface only";
               type empty;
             }
           }
           case case_3 {
             leaf twamp-client {
               description "Set TWAMP client mode on this interface";
               junos:must "(unique \"interfaces ${interface} unit <*> rpm twamp-client\")";
               junos:must-message "TWAMP service can be enabled on 1 logical interface only";
               type empty;
             }
           }
         }
       }
       leaf description {
         description "Text description of interface";
         type string;
       }
       leaf metadata {
         description "Text metadata attached to interface";
         type string;
       }
       container dial-options {
         junos:must "(!(\".. encapsulation multilink-ppp\"))";
         junos:must-message "MLPPP bundle cannot be configured with dial-options";
         junos:must "((\".. family inet\" || (\".. family inet6\" || \".. family mlppp\")))";
         junos:must-message "Family must be defined for a unit with dial-options";
         description "Dial options";
         uses apply-advanced;
         choice interface_id_choice {
           case case_1 {
             leaf l2tp-interface-id {
               description "Identifier for group of PPP sessions";
               junos:must "(!(\".. .. service-domain\"))";
               junos:must-message "L2TP dial-options and service-domain must not be defined on the same unit";
               type string {
                 length "1 .. 63";
                 junos:posix-pattern "^[A-Za-z0-9][_0-9A-Za-z-]{0,62}$";
                 junos:pattern-message "Must be a string beginning with a number or letter and consisting of no more than 63 total letters, numbers, dashes and underscores.";
               }
             }
           }
           case case_2 {
             leaf ipsec-interface-id {
               description "Identifier for group of dynamic peers";
               junos:must "(\".. ..  service-domain inside\")";
               junos:must-message "ipsec-interface-id must be defined only on the inside unit";
               type string {
                 length "1 .. 63";
                 junos:posix-pattern "^[A-Za-z0-9][_0-9A-Za-z-]{0,62}$";
                 junos:pattern-message "Must be a string beginning with a number or letter and consisting of no more than 63 total letters, numbers, dashes and underscores.";
               }
             }
           }
         }
         choice ifl_type {
           case case_1 {
             leaf dedicated {
               description "Use this unit for only one PPP/IPSec session";
               type empty;
             }
           }
           case case_2 {
             leaf shared {
               description "Share this unit for multiple PPP/IPSec sessions";
               type empty;
             }
           }
         }
       }
       container actual-transit-statistics {
         presence "enable actual-transit-statistics";
         description "Actual transit statistics";
       }
       list demux-source {
         key name;
         ordered-by user;
         description "Demux based on source address";
         junos:must "((!(\".. encapsulation\") && !(\".. demux-destination\")))";
         junos:must-message "demux-source cannot be used with demux-destination or another encapsulation";
         uses demux_options_table;
       }
       list demux-destination {
         key name;
         ordered-by user;
         description "Demux based on destination address";
         junos:must "((!(\".. encapsulation\") && !(\".. demux-source\")))";
         junos:must-message "demux-destination cannot be used with demux-source or another encapsulation";
         uses demux_options_table;
       }
       container demux {
         junos:must "((!(\".. demux-source\") && !(\".. demux-destination\")))";
         junos:must-message "demux-source or demux-destination cannot be used with demux configuration";
         description "Demux based on source or destination address";
         uses apply-advanced;
         container inet {
           presence "enable inet";
           description "Family inet";
           uses apply-advanced;
           leaf address {
             description "Address type";
             type enumeration {
               enum "source" {
                 description "Demux based on source address";
                 junos:must "(!(\".. .. inet6 address destination\"))";
                 junos:must-message "address source and address destination cannot be configured simultaneously";
               }
               enum "destination" {
                 description "Demux based on destination address";
                 junos:must "(!(\".. .. inet6 address source\"))";
                 junos:must-message "address source and address destination cannot be configured simultaneously";
               }
             }
           }
           container auto-configure {
             description "Auto configuration";
             junos:must "(!(\".. address destination\"))";
             junos:must-message "demux-destination cannot be used with dynamic IP configuration";
             uses dynamic_ipv4_type;
           }
         }
         container inet6 {
           presence "enable inet6";
           description "Family inet6";
           uses apply-advanced;
           leaf address {
             description "Address type";
             type enumeration {
               enum "source" {
                 description "Demux based on source address";
                 junos:must "(!(\".. .. inet address destination\"))";
                 junos:must-message "address source and address destination cannot be configured simultaneously";
               }
               enum "destination" {
                 description "Demux based on destination address";
                 junos:must "(!(\".. .. inet address source\"))";
                 junos:must-message "address source and address destination cannot be configured simultaneously";
               }
             }
           }
           container auto-configure {
             description "Auto configuration";
             junos:must "(!(\".. address destination\"))";
             junos:must-message "demux-destination cannot be used with dynamic IPv6 configuration";
             uses dynamic_ipv6_type;
           }
         }
       }
       leaf encapsulation {
         description "Logical link-layer encapsulation";
         type enumeration {
           enum "atm-nlpid" {
             description "ATM NLPID encapsulation";
           }
           enum "atm-cisco-nlpid" {
             description "Cisco-compatible ATM NLPID encapsulation";
           }
           enum "atm-snap" {
             description "ATM LLC/SNAP encapsulation";
           }
           enum "atm-vc-mux" {
             description "ATM VC multiplexing";
           }
           enum "atm-ccc-vc-mux" {
             description "ATM VC for CCC";
           }
           enum "atm-tcc-vc-mux" {
             description "ATM VC for translational cross-connect";
           }
           enum "atm-tcc-snap" {
             description "ATM LLC/SNAP for translational cross-connect";
           }
           enum "atm-ccc-cell-relay" {
             description "ATM cell relay for CCC";
           }
           enum "vlan-vci-ccc" {
             description "CCC for VLAN Q-in-Q and ATM VPI/VCI interworking";
           }
           enum "ether-over-atm-llc" {
             description "Ethernet over ATM (LLC/SNAP) encapsulation";
           }
           enum "ether-vpls-over-atm-llc" {
             description "Ethernet VPLS over ATM (bridging) encapsulation";
           }
           enum "ppp-over-ether-over-atm-llc" {
             description "PPPoE over ATM (LLC/SNAP) encapsulation";
           }
           enum "ppp-over-ether" {
             description "PPPoE encapsulation";
             junos:must "(!(\"forwarding-options hyper-mode\"))";
             junos:must-message "To configure encapsulation ppp-over-ether, 'forwarding-options hyper-mode' should not be configured";
             junos:must "(!(\".. family\"))";
             junos:must-message "Can't configure protocol family with encapsulation ppp-over-ether";
           }
           enum "atm-ppp-vc-mux" {
             description "ATM PPP over raw AAL5";
           }
           enum "atm-ppp-llc" {
             description "ATM PPP over AAL5/LLC";
           }
           enum "atm-mlppp-llc" {
             description "ATM MLPPP over AAL5/LLC";
           }
           enum "frame-relay-ppp" {
             description "PPP over Frame Relay";
             junos:must "(!(\".. family inet6\"))";
             junos:must-message "family inet6 is not supported on encapsulation frame-relay-ppp";
             junos:must "(!(\".. family inet\"))";
             junos:must-message "family inet is not supported on encapsulation frame-relay-ppp";
             junos:must "(\".. .. encapsulation frame-relay\")";
             junos:must-message "Physical link-layer encapsulation must be frame-relay";
           }
           enum "frame-relay-ccc" {
             description "Frame Relay DLCI for CCC";
           }
           enum "frame-relay" {
             description "Frame Relay DLCI";
           }
           enum "frame-relay-tcc" {
             description "Frame Relay DLCI for translational cross-connect";
           }
           enum "frame-relay-ether-type" {
             description "Cisco-compatible Frame Relay Encapsulation DLCI";
             junos:must "((\".. .. encapsulation flexible-frame-relay\" || (\".. .. encapsulation frame-relay-ether-type\" || \".. .. encapsulation frame-relay-ether-type-tcc\")))";
             junos:must-message "Interface encapsulation must be cisco-compatible or flexible frame relay";
           }
           enum "frame-relay-ether-type-tcc" {
             description "Cisco-compatible Frame Relay Encapsulation DLCI for TCC";
           }
           enum "ether-vpls-fr" {
             description "Ethernet VPLS over Frame Relay (bridging) encapsulation";
           }
           enum "vlan-ccc" {
             description "802.1q tagging for a cross-connect";
           }
           enum "ethernet-ccc" {
             description "Ethernet for a cross-connect";
           }
           enum "vlan-vpls" {
             description "VLAN virtual private LAN service";
           }
           enum "vlan-bridge" {
             description "VLAN layer-2 bridging";
           }
           enum "ethernet-tcc" {
             description "Ethernet translational cross-connect";
           }
           enum "dix" {
             description "Ethernet DIXv2 (RFC 894)";
           }
           enum "ethernet" {
             description "Ethernet II (RFC 894)";
           }
           enum "ethernet-vpls" {
             description "Ethernet II virtual private LAN service";
           }
           enum "ethernet-bridge" {
             description "Ethernet II bridging";
           }
           enum "vlan" {
             description "802.1q-tagged Ethernet";
           }
           enum "vlan-tcc" {
             description "802.1q tagging for a translational cross-connect";
           }
           enum "multilink-ppp" {
             description "Multilink PPP";
           }
           enum "multilink-frame-relay-end-to-end" {
             description "Multilink Frame Relay end-to-end (FRF.15)";
           }
           enum "ppp-ccc" {
             description "Serial PPP device for a cross-connect";
           }
         }
       }
       leaf gre {
         description "Allow GRE packets";
         type empty;
       }
       leaf mtu {
         description "Maximum transmission unit packet size";
         type union {
           type string {
             pattern "<.*>|$.*";
           }
           type uint32;
         }
       }
       choice pointedness {
         case case_1 {
           leaf point-to-point {
             description "Point-to-point connection";
             type empty;
           }
         }
         case case_2 {
           leaf multipoint {
             description "Multipoint connection";
             type empty;
           }
         }
       }
       leaf bandwidth {
         description "Logical unit bandwidth (informational only)";
         type string;
       }
       leaf global-layer2-domainid {
         description "Global Layer-2 Identifier for this interface";
         type union {
           type string {
             pattern "<.*>|$.*";
           }
           type uint32 {
             range "5 .. 4094";
           }
         }
       }
       container radio-router {
         description "Parameters for dynamic link cost management";
         presence "enable radio-router";
         uses dynamic_ifbw_parms_type;
       }
       choice traps-choice {
         leaf traps {
           description "Enable SNMP notifications on state changes";
           type empty;
         }
         leaf no-traps {
           description "Don't enable SNMP notifications on state changes";
           type empty;
         }
       }
       choice routing-services-choice {
         leaf routing-services {
           description "Enable routing services";
           status deprecated;
           type empty;
         }
         leaf no-routing-services {
           description "Don't enable routing services";
           status deprecated;
           type empty;
         }
       }
       container routing-service {
         description "Routing Services on this interface";
         uses apply-advanced;
         choice enable-disable {
           case case_1 {
             leaf enable {
               description "Enable Routing Service";
               type empty;
             }
           }
           case case_2 {
             leaf disable {
               description "Disable Routing Service";
               type empty;
             }
           }
         }
       }
       container arp-resp {
         presence "enable arp-resp";
         description "Knob to control ARP response on the interface, default is restricted";
         choice arp-response-options {
           case case_1 {
             leaf unrestricted {
               description "Enable unrestricted ARP respone on the interface";
               type empty;
             }
           }
           case case_2 {
             leaf restricted {
               description "Enable restricted proxy ARP response on the interface";
               type empty;
             }
           }
         }
       }
       container proxy-arp {
         presence "enable proxy-arp";
         junos:must "(!(\"switch-options no-arp-trap \"))";
         junos:must-message "Cannot enable proxy ARP with no-arp-trap";
         description "Enable proxy ARP on the interface, default is unrestricted";
         choice proxyarp-options {
           case case_1 {
             leaf unrestricted {
               description "Enable unrestricted proxy ARP on the interface";
               type empty;
             }
           }
           case case_2 {
             leaf restricted {
               description "Enable restricted proxy ARP on the interface";
               type empty;
             }
           }
         }
       }
       choice vlan_choice {
         case case_1 {
           leaf vlan-id {
             description "Virtual LAN identifier value for 802.1q VLAN tags";
             junos:must "(!(\"interfaces ${interface} stacked-vlan-tagging\"))";
             junos:must-message "vlan-id is not supported on stacked-vlan-tagging mode";
             type string;
           }
         }
         case case_2 {
           leaf vlan-id-range {
             description "Virtual LAN identifier range of form vid1-vid2";
             junos:must "((\"interfaces ${interface} vlan-tagging\" || \"interfaces ${interface} flexible-vlan-tagging\"))";
             junos:must-message "valid only with vlan-tagging or flexible-vlan-tagging mode";
             type jt:vlan-range;
           }
         }
         case case_3 {
           leaf-list inner-vlan-id-swap-ranges {
             description "Inner vlan-id swap range(s) of form vid1-vid2 for dynamic L2 VLANs";
             type jt:vlan-range;
           }
         }
         case case_4 {
           leaf-list vlan-id-list {
             description "List of VLAN identifiers";
             junos:must "((\" .. encapsulation vlan-ccc\" || (\"interfaces ${interface} encapsulation extended-vlan-ccc\" || (\" .. encapsulation vlan-vpls\" || (\"interfaces ${interface} encapsulation extended-vlan-vpls\" || (\" .. encapsulation vlan-bridge\" || \"interfaces ${interface} encapsulation extended-vlan-bridge\"))))))";
             junos:must-message "valid only with ccc/vpls/bridge encapsulation";
             junos:must "((\"interfaces ${interface} vlan-tagging\" || \"interfaces ${interface} flexible-vlan-tagging\"))";
             junos:must-message "valid only with vlan-tagging or flexible-vlan-tagging mode";
             type jt:vlan-range;
           }
         }
         case case_5 {
           leaf-list vlan-tag {
             ordered-by user;
             description "IEEE 802.1q tag list for VLAN tagged frames";
             status deprecated;
             type string;
           }
         }
         case case_6 {
           container vlan-tags {
             presence "enable vlan-tags";
             junos:must "((!(\"interfaces ${interface} vlan-tagging\") || !((\". inner\" || (\". inner-range\" || \". inner-list\")))))";
             junos:must-message "inner/inner-range/inner-list is valid only on stacked-vlan-tagging and flexible-vlan-tagging mode";
             junos:must "((!(\"interfaces ${interface} stacked-vlan-tagging\") || (\". inner\" || (\". inner-range\" || \". inner-list\"))))";
             junos:must-message "inner/inner-range/inner-list must be defined for stacked-vlan-tagging mode";
             junos:must "((\".. demux-options\" || (\"interfaces ${interface} vlan-tagging\" || (\"interfaces ${interface} stacked-vlan-tagging\" || \"interfaces ${interface} flexible-vlan-tagging\"))))";
             junos:must-message "valid only with vlan-tagging, stacked-vlan-tagging or flexible-vlan-tagging mode";
             description "IEEE 802.1q tags";
             leaf outer {
               description "[tpid.]vlan-id, tpid format is 0xNNNN and is optional";
               type string;
             }
             choice inner_choice {
               case case_1 {
                 leaf inner {
                   description "[tpid.]vlan-id, tpid format is 0xNNNN and is optional";
                   type string;
                 }
               }
               case case_2 {
                 leaf inner-range {
                   description "[tpid.]vid1-vid2, tpid format is 0xNNNN and is optional";
                   type string {
                     junos:posix-pattern "^((0[Xx][0-9A-Fa-f]{4}.){0,1}([1-9][0-9]{0,2}|[1-3][0-9]{3}|40[0-8][0-9]|409[0-4])-([1-9][0-9]{0,2}|[1-3][0-9]{3}|40[0-8][0-9]|409[0-4]))$";
                     junos:pattern-message "vid in vlan-tag ([0xNNNN.]vid1-vid2) must be 1 to 4094";
                   }
                 }
               }
               case case_3 {
                 leaf-list inner-list {
                   description "List of VLAN identifiers";
                   junos:must "((\" .. .. encapsulation vlan-ccc\" || (\"interfaces ${interface} encapsulation extended-vlan-ccc\" || (\" .. .. encapsulation vlan-vpls\" || (\"interfaces ${interface} encapsulation extended-vlan-vpls\" || (\" .. .. encapsulation vlan-bridge\" || \"interfaces ${interface} encapsulation extended-vlan-bridge\"))))))";
                   junos:must-message "valid only with ccc/vpls/bridge encapsulation";
                   type jt:vlan-range;
                 }
               }
             }
           }
         }
       }
       leaf deep-vlan-qualified-learning {
         description "Enable qualified MAC-address learning on the specified vlan tag";
         junos:must "((\".. vlan-tags outer\" && \".. vlan-tags inner\"))";
         junos:must-message "deep-vlan-qualified-learning can be specified only with one outer and one inner vlan tags";
         type union {
           type string {
             pattern "<.*>|$.*";
           }
           type uint32 {
             range 3;
           }
         }
       }
       leaf native-inner-vlan-id {
         description "Native virtual LAN identifier for singly tagged frames";
         junos:must "((\".. vlan-tags\" || \".. family bridge inner-vlan-id-list\"))";
         junos:must-message "native-inner-vlan-id can be specified only on a dual vlan tagged unit";
         junos:must "(\"interfaces ${interface} flexible-vlan-tagging\")";
         junos:must-message "native-inner-vlan-id can be specified only with flexible-vlan-tagging mode";
         type union {
           type string {
             pattern "<.*>|$.*";
           }
           type uint32 {
             range "0 .. 4094";
           }
         }
       }
       container inner-vlan-id-range {
         junos:must "(\"interfaces ${interface} encapsulation vlan-vci-ccc\")";
         junos:must-message "inner-vlan-id-range valid only for vlan-vci-ccc encapsulation";
         description "Inner vlan-id range start <start-vlan-id> end <end-vlan-id>";
         leaf start {
           description "Inner vlan-id range's start value";
           type union {
             type string {
               pattern "<.*>|$.*";
             }
             type uint32 {
               range "32 .. 4094";
             }
           }
         }
         leaf end {
           description "Inner vlan-id range's end value";
           type union {
             type string {
               pattern "<.*>|$.*";
             }
             type uint32 {
               range "32 .. 4094";
             }
           }
         }
       }
       container accept-source-mac {
         junos:must "(\".. family ethernet-switching\")";
         junos:must-message "source mac filters are allowed only on interfaces with family ethernet-switching";
         description "Remote media access control address to/from which to accept traffic";
         uses apply-advanced;
         list mac-address {
           key name;
           description "Remote MAC address";
           uses mac_list;
         }
       }
       container input-vlan-map {
         description "VLAN map operation on input";
         uses vlan_map;
       }
       container output-vlan-map {
         description "VLAN map operation on output";
         uses vlan_map;
       }
       leaf swap-by-poppush {
         description "Pop original vlan tag and then push a new vlan tag";
         type empty;
       }
       leaf receive-lsp {
         description "Name of incoming label-switched path";
         type string;
       }
       leaf transmit-lsp {
         description "Name of outgoing label-switched path";
         type string;
       }
       leaf dlci {
         description "Frame Relay data-link control identifier";
         type union {
           type string {
             pattern "<.*>|$.*";
           }
           type uint32 {
             range "1 .. 1022";
           }
         }
       }
       leaf multicast-dlci {
         description "Frame Relay data-link control identifier for multicast packets";
         type union {
           type string {
             pattern "<.*>|$.*";
           }
           type uint32 {
             range "1 .. 1022";
           }
         }
       }
       choice vci_type {
         case case_1 {
           leaf vci {
             description "ATM point-to-point virtual circuit identifier ([vpi.]vci)";
             junos:must "(!(\".. encapsulation vlan-vci-ccc\"))";
             junos:must-message "'vci-range' must be used with encapsulation vlan-vci-ccc";
             type jt:atm-vci;
           }
         }
         case case_2 {
           leaf allow-any-vci {
             description "Allow all VCIs to open in atm-ccc-cell-relay mode";
             type empty;
           }
         }
         case case_3 {
           leaf vpi {
             description "ATM point-to-point virtual path identifier (vpi)";
             type union {
               type string {
                 pattern "<.*>|$.*";
               }
               type uint32 {
                 range "0 .. 255";
               }
             }
           }
         }
         case case_4 {
           leaf trunk-id {
             description "ATM trunk identifier";
             type union {
               type string {
                 pattern "<.*>|$.*";
               }
               type uint32 {
                 range "0 .. 31";
               }
             }
           }
         }
       }
       leaf no-vpivci-swapping {
         description "Do not swap VPI/VCI for Cell Relay";
         junos:must "(\".. encapsulation atm-ccc-cell-relay\")";
         junos:must-message "encapsulation must be atm-ccc-cell-relay";
         type empty;
       }
       choice psn_vci_type {
         case case_1 {
           leaf psn-vci {
             description "PSN VCI";
             junos:must "(\".. encapsulation atm-ccc-cell-relay\")";
             junos:must-message "encapsulation must be atm-ccc-cell-relay";
             junos:must "(!(\".. no-vpivci-swapping\"))";
             junos:must-message "no-vpivci-swapping must not be configured";
             type jt:atm-vci;
           }
         }
         case case_2 {
           leaf psn-vpi {
             description "PSN VPI";
             junos:must "(\".. encapsulation atm-ccc-cell-relay\")";
             junos:must-message "encapsulation must be atm-ccc-cell-relay";
             junos:must "(!(\".. no-vpivci-swapping\"))";
             junos:must-message "no-vpivci-swapping must not be configured";
             type union {
               type string {
                 pattern "<.*>|$.*";
               }
               type uint32 {
                 range "0 .. 255";
               }
             }
           }
         }
       }
       container atm-l2circuit-mode {
         description "Select ATM Layer 2 circuit transport mode";
         choice mode_choice {
           case case_1 {
             leaf cell {
               description "ATM Layer 2 circuit cell mode";
               type empty;
             }
           }
           case case_2 {
             leaf aal5 {
               description "ATM Layer 2 circuit AAL5 mode";
               type empty;
             }
           }
         }
       }
       container vci-range {
         junos:must "(!(\".. vci\"))";
         junos:must-message "'vci-range' and 'vci' statements cannot co-exist";
         description "ATM VCI range start <start-vci> end <end-vci>";
         leaf start {
           description "ATM VCI range's start value";
           type union {
             type string {
               pattern "<.*>|$.*";
             }
             type uint16 {
               range "32 .. 4094";
             }
           }
         }
         leaf end {
           description "ATM VCI range's end value";
           type union {
             type string {
               pattern "<.*>|$.*";
             }
             type uint16 {
               range "32 .. 4094";
             }
           }
         }
       }
       leaf trunk-bandwidth {
         description "ATM trunk bandwidth";
         units "bits per second";
         type string;
       }
       leaf multicast-vci {
         description "ATM virtual circuit identifier for multicast packets";
         type jt:atm-vci;
       }
       container shaping {
         description "Virtual circuit traffic-shaping options";
         uses dcd_shaping_config;
       }
       container oam-period {
         description "OAM cell period";
         choice oam_period_choices {
           case case_1 {
             leaf oam-period {
               description "OAM cell period";
               units "seconds";
               type union {
                 type string {
                   pattern "<.*>|$.*";
                 }
                 type uint32 {
                   range "1 .. 900";
                 }
               }
             }
           }
           case case_2 {
             container disable {
               presence "enable disable";
               description "Disable F5 OAM loopback";
             }
           }
         }
       }
       container oam-liveness {
         description "OAM virtual circuit liveness parameters";
         uses apply-advanced;
         leaf up-count {
           description "Number of OAM cells to consider VC up";
           type union {
             type string {
               pattern "<.*>|$.*";
             }
             type uint32 {
               range "1 .. 255";
             }
           }
         }
         leaf down-count {
           description "Number of OAM cells to consider VC down";
           type union {
             type string {
               pattern "<.*>|$.*";
             }
             type uint32 {
               range "1 .. 255";
             }
           }
         }
       }
       container ppp-options {
         description "Point-to-Point Protocol interface-specific options";
         uses ppp_options_type;
       }
       container pppoe-options {
         description "PPP over Ethernet interface-specific options";
         uses pppoe_options_type;
       }
       container pppoe-underlying-options {
         description "PPP over Ethernet underlying interface-specific options";
         junos:must "(\".. encapsulation ppp-over-ether\")";
         junos:must-message "pppoe-underlying-options are only supported on encapsulation ppp-over-ether";
         uses pppoe_underlying_options_type;
       }
       container advisory-options {
         description "Interface-specific recommendations";
         uses advisory_options_type;
       }
       container auto-configure {
         description "Auto configuration";
         uses auto_configure_vlan_type;
       }
       container demux-options {
         description "IP demux interface-specific options";
         uses demux_options_type;
       }
       container targeted-distribution {
         presence "enable targeted-distribution";
         junos:must "(!(\"interfaces ${interface} aggregated-ether-options link-speed mixed\"))";
         junos:must-message "targetted-distribution is incompatible with link-speed mixed";
         description "Interface participates in targeted-distribution";
         uses apply-advanced;
         leaf primary-list {
           description "Primary targeted distribution list";
           type string {
             length "1 .. 20";
           }
         }
         leaf backup-list {
           description "Backup targeted distribution list";
           type string {
             length "1 .. 20";
           }
         }
         leaf standby-list {
           description "Standby targeted distribution list";
           type string {
             length "1 .. 20";
           }
         }
       }
       container targeted-options {
         presence "enable targeted-options";
         junos:must "(\".. targeted-distribution\")";
         junos:must-message "targeted-options is supported only when targeted-distribution is configured.";
         description "Targeting specific options";
         uses apply-advanced;
         leaf weight {
           description "Targeting weight for subscriber";
           type string;
         }
         leaf primary {
           description "Primary link for the subscriber";
           type union {
             type jt:interface-device;
             type string {
               pattern "<.*>|$.*";
             }
           }
         }
         leaf backup {
           description "Backup link for the subscriber";
           type union {
             type jt:interface-device;
             type string {
               pattern "<.*>|$.*";
             }
           }
         }
         leaf group {
           description "Group name to which the subscriber is associated";
           type string {
             junos:posix-pattern "!default";
             junos:pattern-message "default is a reserved group-name";
           }
         }
       }
       choice keepalive_choices {
         case case_1 {
           container keepalives {
             description "Send or demand keepalive messages";
             presence "enable keepalives";
             uses keepalives_type;
           }
         }
         case case_2 {
           leaf no-keepalives {
             description "Do not send or demand keepalive messages";
             type empty;
           }
         }
       }
       leaf inverse-arp {
         description "Enable inverse ARP";
         type empty;
       }
       leaf transmit-weight {
         description "ATM2 transmit weight for VC under VP tunnel";
         type union {
           type string {
             pattern "<.*>|$.*";
           }
           type uint16 {
             range "1 .. 32767";
           }
         }
       }
       container epd-threshold {
         description "Early packet discard threshold for ATM2";
         uses epd_threshold_config;
       }
       leaf cell-bundle-size {
         description "L2 circuit cell bundle size";
         units "cells";
         type union {
           type string {
             pattern "<.*>|$.*";
           }
           type uint32 {
             range "1 .. 176";
           }
         }
       }
       leaf cell-bundle-timeout {
         description "L2 circuit cell bundle timeout";
         units "microseconds";
         type union {
           type string {
             pattern "<.*>|$.*";
           }
           type uint32 {
             range "1 .. 512";
           }
         }
       }
       leaf plp-to-clp {
         description "Enable ATM2 PLP to CLP copy";
         type empty;
       }
       leaf atm-scheduler-map {
         description "Assign ATM2 CoS scheduling map";
         type union {
           type string {
             pattern "default";
           }
           type string;
         }
       }
       leaf mrru {
         description "Maximum received reconstructed unit";
         units "bytes";
         type union {
           type string {
             pattern "<.*>|$.*";
           }
           type uint16 {
             range "1500 .. 4500";
           }
         }
       }
       leaf short-sequence {
         description "Short sequence number header format (MLPPP only)";
         type empty;
       }
       leaf fragment-threshold {
         description "Fragmentation threshold";
         units "bytes";
         type union {
           type string {
             pattern "<.*>|$.*";
           }
           type uint32 {
             range "64 .. 4500";
           }
         }
       }
       leaf drop-timeout {
         description "Drop timeout";
         units "milliseconds";
         type union {
           type string {
             pattern "<.*>|$.*";
           }
           type uint16 {
             range "0 .. 2000";
           }
         }
       }
       leaf disable-mlppp-inner-ppp-pfc {
         description "Disable compression for inner PPP header in MLPPP payload";
         type empty;
       }
       leaf minimum-links {
         description "Minimum number of links to sustain the bundle";
         type union {
           type string {
             pattern "<.*>|$.*";
           }
           type uint16;
         }
       }
       leaf multilink-max-classes {
         description "Number of multilink classes";
         type union {
           type string {
             pattern "<.*>|$.*";
           }
           type uint16;
         }
       }
       container compression {
         presence "enable compression";
         junos:must "(!(\".. encapsulation multilink-frame-relay-end-to-end\"))";
         junos:must-message "CRTP is not supported for multilink-frame-relay-end-to-end encapsulation";
         description "Various packet header compressions";
         uses apply-advanced;
         container rtp {
           presence "enable rtp";
           description "Compress and decompress RTP";
           uses apply-advanced;
           leaf f-max-period {
             description "Maximum number of compressed packets between transmission of full headers";
             type union {
               type string {
                 pattern "<.*>|$.*";
               }
               type uint32 {
                 range "1 .. 65535";
               }
             }
           }
           leaf-list queues {
             ordered-by user;
             description "Queue holding RTP packets. Default is queue 1";
             type enumeration {
               enum "q0" {
                 description "RTP packets assigned to queue 0";
               }
               enum "q1" {
                 description "RTP packets assigned to queue 1";
               }
               enum "q2" {
                 description "RTP packets assigned to queue 2";
               }
               enum "q3" {
                 description "RTP packets assigned to queue 3";
               }
             }
           }
           container port {
             presence "enable port";
             description "UDP destination ports reserved for RTP packets";
             leaf minimum {
               type union {
                 type string {
                   pattern "<.*>|$.*";
                 }
                 type uint32 {
                   range "0 .. 65535";
                 }
               }
             }
             leaf maximum {
               type union {
                 type string {
                   pattern "<.*>|$.*";
                 }
                 type uint32 {
                   range "0 .. 65535";
                 }
               }
             }
           }
           container maximum-contexts {
             description "Maximum number of simultaneous RTP contexts";
             leaf number {
               description "Maximum number of simultaneous RTP contexts";
               type union {
                 type string {
                   pattern "<.*>|$.*";
                 }
                 type uint32 {
                   range "16 .. 2048";
                 }
               }
             }
           }
         }
       }
       leaf interleave-fragments {
         description "Interleave long packets with high priority ones";
         type empty;
       }
       leaf link-layer-overhead {
         description "Link layer bit stuffing overhead (0.0 .. 50.0 percent)";
         type jt:unsigned-float;
       }
       leaf accounting-profile {
         description "Accounting profile name";
         junos:must "((\"accounting-options interface-profile $$\" || \"accounting-options flat-file-profile $$\"))";
         junos:must-message "referenced accounting profile must be defined";
         type string;
       }
       leaf peer-unit {
         description "Peer unit number";
         type union {
           type string {
             pattern "<.*>|$.*";
           }
           type uint32 {
             range "0 .. 16385";
           }
         }
       }
       container tunnel {
         description "Tunnel parameters";
         uses apply-advanced;
         container encapsulation {
           presence "enable encapsulation";
           description "Encapsulation over tunnel";
           container vxlan-gpe {
             presence "enable vxlan-gpe";
             junos:must "((!(\".. udp\") && !(\".. ipip\")))";
             junos:must-message "Only one encapsulation can  be set per IFL";
             uses apply-advanced;
             container source {
               uses apply-advanced;
               leaf address {
                 description "Interface address prefix";
                 junos:must "(!(\".. interface\"))";
                 junos:must-message "To configure address interface must be not set";
                 type jt:ipv4addr;
               }
               leaf mac-address {
                 description "Interface source mac address";
                 junos:must "((\".. interface\" || \".. address\"))";
                 junos:must-message "Either address or interface must be set";
                 type jt:mac-addr;
               }
               leaf interface {
                 description "Name of the interface";
                 type union {
                   type jt:interface-name;
                   type string {
                     pattern "<.*>|$.*";
                   }
                 }
               }
             }
             container destination {
               uses apply-advanced;
               leaf address {
                 description "Interface address prefix";
                 type jt:ipv4addr;
               }
               leaf mac-address {
                 description "Interface destination mac address";
                 junos:must "(\".. address\")";
                 junos:must-message "destination address must be set";
                 type jt:mac-addr;
               }
             }
             leaf tunnel-endpoint {
               description "Tunnel end point type";
               type enumeration {
                 enum "vxlan" {
                   description "To configure vxlan tunnel-end-point";
                 }
               }
             }
             leaf destination-udp-port {
               description "Value to write to the destination-udp-port field";
               type union {
                 type string {
                   pattern "<.*>|$.*";
                 }
                 type uint32 {
                   range "1 .. 65535";
                 }
               }
             }
             leaf vni {
               description "Value to write to the vni field";
               type union {
                 type string {
                   pattern "<.*>|$.*";
                 }
                 type uint32 {
                   range "0 .. 16777214";
                 }
               }
             }
           }
           container udp {
             presence "enable udp";
             junos:must "((!(\".. .. .. family ccc\") && !(\".. .. .. family tcc\")))";
             junos:must-message "Only inet, inet6, mpls, iso families allowed for udp tunnel in encap mode";
             junos:must "((!(\".. vxlan-gpe\") && (!(\".. ipip\") && !(\"..gre\"))))";
             junos:must-message "Only one encapsulation can  be set per IFL";
             description "Family for tunnel encapsulation udp";
             uses apply-advanced;
             container source {
               uses apply-advanced;
               leaf address {
                 description "Interface address prefix";
                 junos:must "(!(\".. interface\"))";
                 junos:must-message "To configure address interface must be not set";
                 type jt:ipv4addr;
               }
               leaf interface {
                 description "Name of the interface";
                 type union {
                   type jt:interface-name;
                   type string {
                     pattern "<.*>|$.*";
                   }
                 }
               }
             }
             container destination {
               uses apply-advanced;
               leaf address {
                 description "Interface address prefix";
                 type jt:ipv4addr;
               }
             }
           }
           container ipip {
             presence "enable ipip";
             junos:must "((!(\".. .. .. family ccc\") && (!(\".. .. .. family tcc\") && !(\".. .. .. family iso\"))))";
             junos:must-message "Only inet, inet6, mpls families allowed for ipip tunnel in decap/encap mode";
             junos:must "((!(\".. udp\") && (!(\".. vxlan-gpe\") && !(\".. gre\"))))";
             junos:must-message "Only one encapsulation can  be set per IFL";
             description "Family for tunnel encapsulation ipip";
             uses apply-advanced;
             container source {
               uses apply-advanced;
               leaf address {
                 description "Interface address prefix";
                 junos:must "(!(\".. interface\"))";
                 junos:must-message "To configure address interface must be not set";
                 type jt:ipv4addr;
               }
               leaf interface {
                 description "Name of the interface";
                 type union {
                   type jt:interface-name;
                   type string {
                     pattern "<.*>|$.*";
                   }
                 }
               }
             }
             container destination {
               uses apply-advanced;
               leaf address {
                 description "Interface address prefix";
                 type jt:ipv4addr;
               }
             }
           }
         }
         leaf source {
           description "Tunnel source";
           type jt:ipaddr;
         }
         leaf destination {
           description "Tunnel destination";
           type jt:ipaddr;
         }
         leaf key {
           description "Tunnel key";
           type union {
             type string {
               pattern "<.*>|$.*";
             }
             type uint32 {
               range "0 .. 4294967295";
             }
           }
         }
         leaf backup-destination {
           description "Backup tunnel destination";
           junos:must "(!(\".. destination $$\"))";
           junos:must-message "Backup and primary tunnel destinations must be different";
           type jt:ipaddr;
         }
         choice fragmentation {
           case case_1 {
             leaf allow-fragmentation {
               description "Do not set DF bit on packets";
               type empty;
             }
           }
           case case_2 {
             leaf do-not-fragment {
               description "Set DF bit on packets";
               type empty;
             }
           }
         }
         leaf ttl {
           description "Time to live";
           type union {
             type string {
               pattern "<.*>|$.*";
             }
             type uint32 {
               range "1 .. 255";
             }
           }
         }
         leaf traffic-class {
           description "TOS/Traffic class field of IP-header";
           type union {
             type string {
               pattern "<.*>|$.*";
             }
             type uint32 {
               range "0 .. 255";
             }
           }
         }
         leaf flow-label {
           description "Flow label field of IP6-header";
           type union {
             type string {
               pattern "<.*>|$.*";
             }
             type uint32 {
               range "0 .. 1048575";
             }
           }
         }
         choice path-mtu-discovery-choice {
           leaf path-mtu-discovery {
             description "Enable path MTU discovery for tunnels";
             type empty;
           }
           leaf no-path-mtu-discovery {
             description "Don't enable path MTU discovery for tunnels";
             type empty;
           }
         }
         container routing-instance {
           description "Routing instance to which tunnel ends belong";
           uses apply-advanced;
           leaf destination {
             description "Routing instance of tunnel destination";
             junos:must "((\"routing-instances $$\" || any \"tenants <*> routing-instances $$\"))";
             junos:must-message "referenced routing-instance must be defined";
             type string {
               junos:posix-pattern "!^((__.*__)|(all)|(.*[ ].*)|(\"\")|(.{129,}))$";
               junos:pattern-message "Must be a non-reserved string of 128 characters or less with no spaces.";
             }
           }
         }
       }
       leaf compression-device {
         description "Logical interface used for compression";
         type union {
           type jt:interface-unit;
           type string {
             pattern "<.*>|$.*";
           }
         }
       }
       container atm-policer {
         junos:must "(\".. family\")";
         junos:must-message "Family must be defined for a unit with atm-policer";
         description "ATM policing for logical interface";
         uses apply-advanced;
         leaf input-atm-policer {
           description "Input atm policer";
           type string;
         }
       }
       container layer2-policer {
         junos:must "(\".. family\")";
         junos:must-message "Family must be defined for a unit with layer2-policer";
         description "Layer2 policing for logical interface";
         uses apply-advanced;
         choice layer2-input-policer-choice {
           case case_1 {
             leaf input-policer {
               description "Two-color policer for received packets";
               junos:must "(!(\"firewall policer $$ then forwarding-class\"))";
               junos:must-message "Forwarding class cannot be modified for Layer 2 policer";
               junos:must "(!(\"firewall policer $$ then loss-priority medium-low\"))";
               junos:must-message "Loss priority 'medium-low' is not valid for Layer 2 policer";
               junos:must "(!(\"firewall policer $$ then loss-priority low\"))";
               junos:must-message "Loss priority 'low' is not valid for Layer 2 policer";
               junos:must "(\"firewall policer $$ logical-interface-policer\")";
               junos:must-message "Layer 2 policer must be a logical interface policer";
               type string;
             }
           }
           case case_2 {
             leaf input-hierarchical-policer {
               description "Hierarchical policer for received packets";
               junos:must "((!(\".. .. family mlppp\") && (!(\".. .. family mlfr-end-to-end\") && !(\".. .. family mlfr-uni-nni\"))))";
               junos:must-message "no hierarchical polcier on ifls which are part of mlppp/mlfr bundle";
               junos:must "(!(\".. .. .. layer2-policer\"))";
               junos:must-message "no hierarchical policer on both ifd and its member ifls";
               type string;
             }
           }
           case case_3 {
             leaf input-three-color {
               description "Color-blind three-color policer for received packets";
               junos:must "((\"firewall three-color-policer $$ single-rate color-blind\" || (\"firewall three-color-policer $$ single-packet-rate color-blind\" || (\"firewall three-color-policer $$ two-rate color-blind\" || \"firewall three-color-policer $$ two-packet-rate color-blind\"))))";
               junos:must-message "Layer 2 input three-color policer must be color-blind";
               junos:must "(\"firewall three-color-policer $$ logical-interface-policer\")";
               junos:must-message "Layer 2 three-color policer must be a logical interface policer";
               type string;
             }
           }
         }
         choice layer2-output-policer-choice {
           case case_1 {
             leaf output-policer {
               description "Two-color policer for transmitted packets";
               junos:must "(!(\"firewall policer $$ then forwarding-class\"))";
               junos:must-message "Forwarding class cannot be modified for Layer 2 policer";
               junos:must "(!(\"firewall policer $$ then loss-priority medium-low\"))";
               junos:must-message "Loss priority 'medium-low' is not valid for Layer 2 policer";
               junos:must "(!(\"firewall policer $$ then loss-priority low\"))";
               junos:must-message "Loss priority 'low' is not valid for Layer 2 policer";
               junos:must "(\"firewall policer $$ logical-interface-policer\")";
               junos:must-message "Layer 2 policer must be a logical interface policer";
               type string;
             }
           }
           case case_2 {
             leaf output-three-color {
               description "Three-color policer for transmitted packets";
               junos:must "(\"firewall three-color-policer $$ logical-interface-policer\")";
               junos:must-message "Layer 2 three-color policer must be a logical interface policer";
               type string;
             }
           }
         }
       }
       container filter {
         description "Filters to apply to all families configured under this logical interface";
         uses apply-advanced;
         choice input_choice {
           case case_1 {
             container input {
               description "Name of filter to be applied to received packets";
               leaf filter-name {
                 description "Name of the filter";
                 type string;
               }
               leaf shared-name {
                 description "Filter shared-name of instances of interface-shared filter";
                 type string;
               }
               leaf precedence {
                 description "Precedence of the filter";
                 type union {
                   type string {
                     pattern "<.*>|$.*";
                   }
                   type uint32 {
                     range "0 .. 255";
                   }
                 }
               }
             }
           }
         }
         choice output_choice {
           case case_1 {
             container output {
               description "Name of filter to be applied to transmitted packets";
               leaf filter-name {
                 description "Name of the filter";
                 type string;
               }
               leaf shared-name {
                 description "Filter shared-name of instances of interface-shared filter";
                 type string;
               }
               leaf precedence {
                 description "Precedence of the filter";
                 type union {
                   type string {
                     pattern "<.*>|$.*";
                   }
                   type uint32 {
                     range "0 .. 255";
                   }
                 }
               }
             }
           }
         }
       }
       list multi-chassis-protection {
         key name;
         description "Inter-Chassis protection configuration";
         junos:must "(\"interfaces ${interface} aggregated-ether-options mc-ae mode active-active\")";
         junos:must-message "multi-chassis-protection is only supported for MC-AE active-active mode";
         uses multi-chassis-protection-group-ifl;
       }
       leaf statistics {
         description "Enable statistics collection in PFE";
         type empty;
       }
       container esi {
         presence "enable esi";
         description "ESI configuration of logical interface";
         uses apply-advanced;
         container auto-derive {
           junos:must "(!(\"interfaces ${interface} esi auto-derive\"))";
           junos:must-message "ESI identifier can not be configured when auto-derive is configured under IFD";
           description "Auto-derive ESI value for the interface";
           uses apply-advanced;
           choice esitype {
             case case_1 {
               leaf lacp {
                 description "Auto-derive ESI from lacp";
                 type empty;
               }
             }
           }
         }
         leaf identifier {
           description "ESI value for the interface";
           junos:must "(unique \"interfaces <*> unit <*> esi $$\")";
           junos:must-message "ESI value must be unique under all IFDs and IFLs";
           junos:must "(!(\"..  auto-derive\"))";
           junos:must-message "ESI identifier can not be configured when auto-derive is configured under the same IFL";
           junos:must "(!(\"interfaces ${interface} esi auto-derive\"))";
           junos:must-message "ESI identifier can not be configured when auto-derive is configured under IFD";
           type jt:esi;
         }
         choice mode {
           case case_1 {
             leaf single-active {
               description "Single-active mode";
               type empty;
             }
           }
           case case_2 {
             leaf all-active {
               description "All-active mode";
               type empty;
             }
           }
         }
         container df-election-granularity {
           presence "enable df-election-granularity";
           description "DF Election Granularity Selection ";
           uses apply-advanced;
           choice mode {
             case case_1 {
               container per-esi {
                 presence "enable per-esi";
                 description "DF Election Granularity Per Esi";
                 uses apply-advanced;
                 leaf lacp-oos-on-ndf {
                   description "Lacp Oos";
                   junos:must "(!(\"interfaces ${interface} esi all-active\"))";
                   junos:must-message "lacp-oos-on-ndf can be configured only with single-active";
                   junos:must "(\"interfaces ${interface} aggregated-ether-options lacp\")";
                   junos:must-message "LACP must be enbled for lacp-oos-on-ndf";
                   type empty;
                 }
               }
             }
             case case_2 {
               leaf per-esi-vlan {
                 description "Per Esi Vlan";
                 type empty;
               }
             }
           }
         }
         container df-election-type {
           presence "enable df-election-type";
           description "DF Election Type";
           uses apply-advanced;
           choice pref_choice {
             case case_1 {
               container preference {
                 presence "enable preference";
                 description "Preference based DF election";
                 uses apply-advanced;
                 leaf value {
                   description "Preference value for EVPN Multihoming DF election";
                   default "32767";
                   type union {
                     type string {
                       pattern "<.*>|$.*";
                     }
                     type uint32 {
                       range "0 .. 65535";
                     }
                   }
                 }
               }
             }
           }
           choice mod_choice {
             case case_1 {
               container mod {
                 presence "enable mod";
                 junos:must "(!(\".. preference\"))";
                 junos:must-message "preference must not be configured";
                 description "MOD based DF election";
               }
             }
           }
         }
         leaf source-bmac {
           description "Unicast Source B-MAC address per ESI for PBB-EVPN";
           junos:must "(unique \"interfaces <*> unit <*> esi source-bmac $$\")";
           junos:must-message "source-bmac value must be unique under all IFDs and IFLs";
           type jt:mac-unicast;
         }
       }
       choice virtual-gateway {
         case case_1 {
           leaf no-auto-virtual-gateway-esi {
             description "Disable auto ESI generation for virtual gateway address";
             junos:must "((any \".. family inet address <*> virtual-gateway-address\" || any \".. family inet6 address <*> virtual-gateway-address\"))";
             junos:must-message "Only when virtual gateway address is configured";
             type empty;
           }
         }
         case case_2 {
           container virtual-gateway-esi {
             description "ESI configuration of virtual gateway";
             uses apply-advanced;
             leaf identifier {
               description "ESI value for the interface";
               junos:must "(unique \"interfaces <*> unit <*> virtual-gateway-esi $$\")";
               junos:must-message "virtual-gateway-esi value must be unique under all IFDs and IFLs";
               junos:must "(unique \"interfaces <*> unit <*> esi $$\")";
               junos:must-message "ESI value must be unique under all IFDs and IFLs";
               type jt:esi;
             }
             choice mode {
               case case_1 {
                 leaf single-active {
                   description "Single-active mode";
                   type empty;
                 }
               }
               case case_2 {
                 leaf all-active {
                   description "All-active mode";
                   type empty;
                 }
               }
             }
           }
         }
       }
       container service {
         description "Service operations";
         uses apply-advanced;
         list pcef {
           key name;
           ordered-by user;
           description "PCEF configuration";
           leaf name {
             description "PCEF Profile name";
             junos:must "((\".. family inet service\" || \".. family inet6 service\"))";
             junos:must-message "Must be configured along with a family inet/inet6 service.";
             type string;
           }
           uses apply-advanced;
           leaf activate-all {
             description "Activate all rules and rulebases in the pcef profile";
             junos:must "(!(\"activate\"))";
             junos:must-message "Can't be configured with activate-rule or activate- rulebase.";
             type empty;
           }
           list activate {
             key name;
             ordered-by user;
             description "Name of pcef profile rule or rulebase to activate";
             leaf name {
               description "Name of pcef profile rule or rulebase to activate";
               type string;
             }
             uses apply-advanced;
           }
         }
       }
       choice generate-eui64-choice {
         leaf generate-eui64 {
           description "To generate Link Local EUI-64 addresses";
           junos:must "(\".. family inet6 unnumbered-address\")";
           junos:must-message "generate-eui64 attribute must be set when unnumbered-address is configured under family inet6";
           type empty;
         }
         leaf no-generate-eui64 {
           description "Don't to generate Link Local EUI-64 addresses";
           junos:must "(\".. family inet6 unnumbered-address\")";
           junos:must-message "generate-eui64 attribute must be set when unnumbered-address is configured under family inet6";
           type empty;
         }
       }
       container family {
         junos:must "(!(\".. encapsulation ppp-over-ether\"))";
         junos:must-message "Can't configure protocol family with encapsulation ppp-over-ether";
         description "Protocol family";
         container inet {
           presence "enable inet";
           junos:must "(!(\".. .. .. encapsulation vlan-vpls\"))";
           junos:must-message "Can't configure protocol family inet with encapsulation vpls";
           description "IPv4 parameters";
           uses apply-advanced;
           container dhcp {
             description "Dynamic Host Configuration Protocol client configuration";
             presence "enable dhcp";
             junos:must "(!(any \"forwarding-options dhcp-relay group <*> interface ${interface}.${unit}\"))";
             junos:must-message "Incompatible with the interface configured under 'forwarding-options dhcp-relay group'";
             junos:must "(!(\"system services dhcp\"))";
             junos:must-message "Incompatible with the dhcp server configured under 'system services dhcp'";
             junos:must "(!(\"system autoinstallation interfaces\"))";
             junos:must-message "Incompatible with 'system autoinstallation interfaces'";
             junos:must "(!(\".. address\"))";
             junos:must-message "Incompatible with interface assigned with address";
             uses dhcp-client-type;
           }
           container targeted-broadcast {
             presence "enable targeted-broadcast";
             junos:must "(!((\"interfaces $$={irb} unit ${unit} family $$={inet} targeted-broadcast\" && \"protocols l2-learning global-mode transparent-bridge\")))";
             junos:must-message "targeted-broadcast do not be supported on irb interface in transparent mode";
             description "Directed broadcast";
             uses apply-advanced;
             choice targeted-bcast-choice {
               case case_1 {
                 leaf forward-and-send-to-re {
                   description "Allow packets to be forwarded and sent to re";
                   type empty;
                 }
               }
               case case_2 {
                 leaf forward-only {
                   description "Allow packets only to be forwarded";
                   type empty;
                 }
               }
             }
           }
           leaf destination-class-usage {
             description "Enable destination class usage on this interface";
             status deprecated;
             type empty;
           }
           leaf transit-options-packets {
             description "Transit IP options packets (don't send to Routing Engine)";
             status deprecated;
             type empty;
           }
           leaf transit-ttl-exceeded {
             description "Transit IP TTL-exceeded packets (don't send to Routing Engine)";
             status deprecated;
             type empty;
           }
           leaf receive-options-packets {
             description "Receive IP options packets (don't send to Routing Engine)";
             type empty;
           }
           leaf receive-ttl-exceeded {
             description "Receive IP TTL-exceeded packets (don't send to Routing Engine)";
             type empty;
           }
           container accounting {
             description "Configure interface-based accounting options";
             uses apply-advanced;
             container source-class-usage {
               description "Enable source class usage on this interface";
               uses apply-advanced;
               leaf input {
                 description "Specify this interface for source-class-usage input";
                 type empty;
               }
               leaf output {
                 description "Specify this interface for source-class-usage output";
                 type empty;
               }
             }
             leaf destination-class-usage {
               description "Enable destination class usage on this interface";
               type empty;
             }
           }
           leaf mac-validate {
             description "Validate source MAC address";
             type enumeration {
               enum "strict" {
                 description "Strict mac-validation";
               }
               enum "loose" {
                 description "Loose mac-validation";
               }
             }
           }
           container rpf-check {
             presence "enable rpf-check";
             description "Enable reverse-path-forwarding checks on this interface";
             uses apply-advanced;
             leaf fail-filter {
               description "Name of filter applied to packets failing RPF check";
               type string;
             }
             container mode {
               description "Mode for reverse path forwarding";
               leaf loose {
                 description "Reverse-path-forwarding loose mode";
                 type empty;
               }
             }
           }
           leaf mtu {
             description "Protocol family maximum transmission unit";
             type union {
               type uint32;
               type string {
                 pattern "<.*>|$.*";
               }
             }
           }
           leaf arp-max-cache {
             description "Max interface ARP nexthop cache size";
             type union {
               type string {
                 pattern "<.*>|$.*";
               }
               type uint32 {
                 range "1 .. 2000000";
               }
             }
           }
           leaf arp-new-hold-limit {
             description "Max no. of new unresolved nexthops";
             junos:must "(\".. arp-max-cache\")";
             junos:must-message "Interface max ARP cache size must be configured";
             type union {
               type string {
                 pattern "<.*>|$.*";
               }
               type uint32 {
                 range "1 .. 2000000";
               }
             }
           }
           leaf tcp-mss {
             description "Protocol family tcp maximum segment size";
             type union {
               type string {
                 pattern "<.*>|$.*";
               }
               type uint32 {
                 range "1 .. 65535";
               }
             }
           }
           leaf no-redirects {
             description "Do not redirect traffic";
             type empty;
           }
           leaf no-neighbor-learn {
             description "Disable neighbor address learning on interface";
             type empty;
           }
           leaf unconditional-src-learn {
             description "Glean from arp packets even when source cannot be validated";
             type empty;
           }
           leaf multicast-only {
             description "Allow only multicast traffic (tunnels only)";
             type empty;
           }
           leaf primary {
             description "Candidate for primary interface in system";
             type empty;
           }
           leaf ipsec-sa {
             description "Name of security association";
             type string {
               length "1 .. 32";
             }
           }
           leaf allow-filter-on-re {
             description "Enable kernel filter on network ports";
             type empty;
           }
           list demux-source {
             key name;
             ordered-by user;
             description "Demux based on source prefix";
             junos:must "(!(\".. demux-destination\"))";
             junos:must-message "demux-source can not be configured with demux-destination";
             leaf name {
               type string;
             }
             uses apply-advanced;
           }
           list demux-destination {
             key name;
             ordered-by user;
             description "Demux based on destination prefix";
             junos:must "(!(\".. demux-source\"))";
             junos:must-message "demux-source can not be configured with demux-destination";
             leaf name {
               type string;
             }
             uses apply-advanced;
           }
           container filter {
             description "Packet filtering";
             uses apply-advanced;
             choice input_choice {
               case case_1 {
                 container input {
                   description "Filter to be applied to received packets";
                   leaf filter-name {
                     description "Name of the filter";
                     type string;
                   }
                   leaf shared-name {
                     description "Filter shared-name of instances of interface-shared filter";
                     type string;
                   }
                   leaf precedence {
                     description "Precedence of the filter";
                     type union {
                       type string {
                         pattern "<.*>|$.*";
                       }
                       type uint32 {
                         range "0 .. 255";
                       }
                     }
                   }
                 }
               }
               case case_2 {
                 leaf-list input-list {
                   ordered-by user;
                   description "List of filter modules applied to received packets ";
                   type string;
                 }
               }
             }
             leaf-list input-chain {
               ordered-by user;
               description "List of filter modules applied to received packets ";
               type string;
             }
             leaf-list output-chain {
               ordered-by user;
               description "List of filter modules applied to transmitted packets ";
               type string;
             }
             choice output_choice {
               case case_1 {
                 container output {
                   description "Filter to be applied to transmitted packets";
                   leaf filter-name {
                     description "Name of the filter";
                     type string;
                   }
                   leaf shared-name {
                     description "Filter shared-name of instances of interface-shared filter";
                     type string;
                   }
                   leaf precedence {
                     description "Precedence of the filter";
                     type union {
                       type string {
                         pattern "<.*>|$.*";
                       }
                       type uint32 {
                         range "0 .. 255";
                       }
                     }
                   }
                 }
               }
               case case_2 {
                 leaf-list output-list {
                   ordered-by user;
                   description "List of filter modules applied to transmitted packets ";
                   type string;
                 }
               }
             }
             container adf {
               description "Ascend Data Filter definition";
               uses apply-advanced;
               list rule {
                 key name;
                 ordered-by user;
                 description "Set of ADF rules";
                 leaf name {
                   description "Value for a single rule";
                   type string;
                 }
                 uses apply-advanced;
               }
               leaf counter {
                 description "Add a counter to each rule";
                 type empty;
               }
               leaf input-precedence {
                 description "Precedence of the input rules";
                 type union {
                   type string {
                     pattern "<.*>|$.*";
                   }
                   type uint32 {
                     range "0 .. 255";
                   }
                 }
               }
               leaf not-mandatory {
                 description "No errors will be reported if no rules are present";
                 type empty;
               }
               leaf output-precedence {
                 description "Precedence of the output rules";
                 type union {
                   type string {
                     pattern "<.*>|$.*";
                   }
                   type uint32 {
                     range "0 .. 255";
                   }
                 }
               }
             }
             leaf group {
               description "Group to which interface belongs";
               type union {
                 type string {
                   pattern "<.*>|$.*";
                 }
                 type uint32 {
                   range "1 .. 255";
                 }
               }
             }
             leaf dialer {
               description "Name of filter applied on dialer";
               junos:must "(\".. .. .. .. dialer-options dial-string\")";
               junos:must-message "Dial string is mandatory for dialer filter";
               junos:must "(!(\".. .. .. .. dialer-options watch-list\"))";
               junos:must-message "A dialer interface cannot have watch-list as well as dialer filter";
               type string;
             }
           }
           container ingress-queuing-filter {
             description "Protocol family ingress-queuing-filter";
             leaf filter-name {
               description "Name of the ingress-queuing-filter";
               type string;
             }
           }
           container iq-policing-filter {
             description "Protocol family ingress-queuing-policing-filter";
             leaf filter-name {
               description "Name of the ingress-queuing-policing-filter";
               type string;
             }
           }
           container simple-filter {
             description "Filter for doing multifield classification";
             uses apply-advanced;
             leaf input {
               description "Name of simple filter applied to received packets";
               type string;
             }
           }
           leaf input-hierarchical-policer {
             description "Hierarchical policer for received packets";
             type string;
           }
           container policer {
             description "Interface policing";
             uses apply-advanced;
             leaf arp {
               description "Name of policer applied to received ARP packets";
               junos:must "(!(\".. disable-arp-policer\"))";
               junos:must-message "Interface configuration can have either disable-arp-policer or arp policer configured";
               junos:must "((!(\".. .. .. .. peer-unit\") || (\".. .. .. .. encapsulation ethernet\" || \".. .. .. .. encapsulation vlan\")))";
               junos:must-message "Interface encapsulation must be ethernet or vlan";
               type string;
             }
             leaf input {
               description "Name of policer applied to received packets";
               junos:must "(!(\".. .. input-hierarchical-policer\"))";
               junos:must-message "Both input policer and input hierarchical policer can not be applied on the same family";
               type string;
             }
             leaf output {
               description "Name of policer applied to transmitted packets";
               type string;
             }
           }
           container sampling {
             junos:must "((\"forwarding-options sampling family inet\" || (\"forwarding-options packet-capture\" || any \"forwarding-options sampling instance <*> family inet\")))";
             junos:must-message "Requires forwarding-options sampling or packet-capture config";
             description "Interface sampling";
             uses apply-advanced;
             leaf input {
               description "Sample all packets input on this interface";
               type empty;
             }
             leaf output {
               description "Sample all packets output on this interface";
               type empty;
             }
           }
           container service {
             junos:must "((!(\".. rpf-check\") || \"chassis network-services enhanced-ip\"))";
             junos:must-message "rpf-check can not be enabled with interface services";
             description "Service operations";
             uses apply-advanced;
             container input {
               description "Service sets to consider for received packets";
               uses apply-advanced;
               list service-set {
                 key name;
                 ordered-by user;
                 description "Service set to consider for received packets";
                 leaf name {
                   description "Name of service set";
                   junos:must "((!(\".. .. .. .. .. .. demux-source\") && !(\".. .. .. .. .. .. demux-destination\")))";
                   junos:must-message "Service set cannot be configured on interfaces with demux-source or demux-destination";
                   junos:must "(\"services service-set $$ interface-service\")";
                   junos:must-message "this service set must be an interface service";
                   type string {
                     junos:posix-pattern "^[[:alnum:]][[:alnum:]/.:_-]*$";
                     junos:pattern-message "Must be a string beginning with a number or letter and consisting of letters, numbers, dashes, underscores, forward slashes, colons and dots.";
                   }
                 }
                 uses apply-advanced;
                 leaf service-filter {
                   description "Name of service filter";
                   type string;
                 }
               }
               leaf post-service-filter {
                 description "Post-service filter to apply to received packets";
                 type string;
               }
             }
             container output {
               description "Service sets to consider for transmitted packets";
               uses apply-advanced;
               list service-set {
                 key name;
                 ordered-by user;
                 description "Service set to consider for transmitted packets";
                 leaf name {
                   description "Name of service set";
                   type string {
                     junos:posix-pattern "^[[:alnum:]][[:alnum:]/.:_-]*$";
                     junos:pattern-message "Must be a string beginning with a number or letter and consisting of letters, numbers, dashes, underscores, forward slashes, colons and dots.";
                   }
                 }
                 uses apply-advanced;
                 leaf service-filter {
                   description "Name of service filter";
                   type string;
                 }
               }
             }
           }
           list next-hop-tunnel {
             key name;
             ordered-by user;
             description "One or more next-hop tunnel tables";
             leaf name {
               description "Next-hop tunnel gateway address";
               type string;
             }
             uses apply-advanced;
             leaf ipsec-vpn {
               description "Name of IPSec VPN";
               junos:must "(\"security ipsec vpn $$\")";
               junos:must-message "Referenced IPSec vpn must be defined under [edit security ipsec vpn] hierarchy level";
               junos:must "(unique \"interfaces st0 unit <*> family inet next-hop-tunnel <*> ipsec-vpn $$\")";
               junos:must-message "Referenced IPSec vpn must be unique";
               type string;
             }
           }
           container tunnel-termination {
             presence "enable tunnel-termination";
             description "Tunnel termination";
           }
           list address {
             key name;
             ordered-by user;
             description "Interface address/destination prefix";
             junos:must "((!(\".. unnumbered-address\") && !(\".. location-pool-address\")))";
             junos:must-message "address cannot be defined with unnumbered-address or location-pool-address simultaneously";
             leaf name {
               description "Interface address/destination prefix";
               type jt:ipv4prefix;
             }
             uses apply-advanced;
             leaf destination {
               description "Destination address";
               type jt:ipv4addr;
             }
             leaf destination-profile {
               description "Profile to use for destination address";
               junos:must "(\"access group-profile $$ ppp\")";
               junos:must-message "referenced group-profile must be defined and must contain ppp statement";
               type string;
             }
             leaf broadcast {
               description "Broadcast address";
               type jt:ipv4addr;
             }
             leaf primary {
               description "Candidate for primary address in system";
               type empty;
             }
             leaf preferred {
               description "Preferred address on interface";
               type empty;
             }
             leaf master-only {
               description "Master management IP address for router";
               type empty;
             }
             list multipoint-destination {
               key name;
               ordered-by user;
               description "Multipoint NBMA destination";
               leaf name {
                 description "Destination address";
                 type jt:ipv4addr;
               }
               uses apply-advanced;
               choice link-address {
                 case case_1 {
                   leaf dlci {
                     description "Frame Relay data-link control identifier";
                     type union {
                       type string {
                         pattern "<.*>|$.*";
                       }
                       type uint32 {
                         range "1 .. 1022";
                       }
                     }
                   }
                 }
                 case case_2 {
                   leaf vci {
                     description "ATM virtual circuit identifier ([vpi.]vci)";
                     type jt:atm-vci;
                   }
                 }
               }
               container shaping {
                 description "Virtual circuit traffic-shaping options";
                 uses dcd_shaping_config;
               }
               container oam-period {
                 description "OAM cell period";
                 choice oam_period_choices {
                   case case_1 {
                     leaf oam_period {
                       description "OAM cell period";
                       units "seconds";
                       type union {
                         type string {
                           pattern "<.*>|$.*";
                         }
                         type uint32 {
                           range "1 .. 900";
                         }
                       }
                     }
                   }
                   case case_2 {
                     container disable {
                       presence "enable disable";
                       description "Disable OAM loopback";
                     }
                   }
                 }
               }
               container oam-liveness {
                 description "OAM virtual circuit liveness parameters";
                 uses apply-advanced;
                 leaf up-count {
                   description "Number of OAM cells to consider VC up";
                   type union {
                     type string {
                       pattern "<.*>|$.*";
                     }
                     type uint32 {
                       range "1 .. 255";
                     }
                   }
                 }
                 leaf down-count {
                   description "Number of OAM cells to consider VC down";
                   type union {
                     type string {
                       pattern "<.*>|$.*";
                     }
                     type uint32 {
                       range "1 .. 255";
                     }
                   }
                 }
               }
               leaf inverse-arp {
                 description "Enable inverse ARP reply messages";
                 type empty;
               }
               leaf transmit-weight {
                 description "ATM2 transmit weight for VC under VP tunnel";
                 type union {
                   type string {
                     pattern "<.*>|$.*";
                   }
                   type uint16 {
                     range "1 .. 32767";
                   }
                 }
               }
               container epd-threshold {
                 description "Early packet discard threshold for ATM2";
                 uses epd_threshold_config;
               }
             }
             list arp {
               key name;
               ordered-by user;
               description "Static Address Resolution Protocol entries";
               leaf name {
                 description "Destination IP address";
                 type jt:ipv4addr;
               }
               leaf l2-interface {
                 description "Layer 2 interface name for ARP entry";
                 type union {
                   type jt:interface-name;
                   type string {
                     pattern "<.*>|$.*";
                   }
                 }
               }
               choice mac_address_type {
                 case case_1 {
                   leaf mac {
                     description "MAC address";
                     type jt:mac-unicast;
                   }
                 }
                 case case_2 {
                   leaf multicast-mac {
                     description "Multicast MAC address";
                     type jt:mac-multicast;
                   }
                 }
               }
               leaf publish {
                 description "Reply to ARP requests for this entry";
                 junos:must "((\".. mac\" || \".. multicast-mac\"))";
                 junos:must-message "mac or multicast-mac must be configured to publish";
                 type empty;
               }
             }
             list host-discovery {
               key name;
               ordered-by user;
               description "Discover servers IP based on subnet range";
               junos:must "(\"system arp proactive-arp-detection \")";
               junos:must-message "Proactive ARP Detection feature should be enabled";
               max-elements 8;
               leaf name {
                 description "IP address subnet range";
                 type jt:ipv4prefix;
               }
               leaf aging-timer {
                 description "ARP aging timer";
                 type union {
                   type string {
                     pattern "<.*>|$.*";
                   }
                   type uint32 {
                     range "10 .. 1200";
                   }
                 }
               }
               leaf discovery-interval {
                 description "ARP proactive discovery time";
                 type union {
                   type string {
                     pattern "<.*>|$.*";
                   }
                   type uint32 {
                     range "3 .. 300";
                   }
                 }
               }
             }
             container web-authentication {
               description "Parameters for web-based firewall-user authentication";
               uses apply-advanced;
               leaf http {
                 description "Enable authentication via HTTP";
                 type empty;
               }
               leaf https {
                 description "Enable authentication via HTTPS";
                 type empty;
               }
               leaf redirect-to-https {
                 description "Web authentication redirect to HTTPS";
                 junos:must "(\".. https\")";
                 junos:must-message "https must be enabled";
                 type empty;
               }
             }
             list vrrp-group {
               key name;
               ordered-by user;
               description "VRRP group";
               uses vrrp-group;
             }
             leaf virtual-gateway-address {
               description "Virtual Gateway IP address";
               junos:must "(!(\".. vrrp-group\"))";
               junos:must-message "vrrp configuration incompatible with virtual gateway address";
               type jt:ipv4addr;
             }
           }
           container unnumbered-address {
             description "Unnumbered interface address/destination prefix";
             leaf source {
               description "Interface from which to take local address";
               junos:must "(\"interfaces $$-IFL family inet address\")";
               junos:must-message "referred interface must have address configured under family inet";
               type union {
                 type jt:interface-unit;
                 type string {
                   pattern "<.*>|$.*";
                 }
               }
             }
             leaf preferred-source-address {
               description "Preferred address on the donor interface";
               type string;
             }
             leaf destination {
               description "Destination address";
               type jt:ipv4addr;
             }
             leaf destination-profile {
               description "Profile to use for destination address";
               junos:must "(\"access group-profile $$ ppp\")";
               junos:must-message "referenced group-profile must be defined and must contain ppp statement";
               type string;
             }
           }
           container location-pool-address {
             presence "enable location-pool-address";
             junos:must "((!(\".. address\") && !(\".. unnumbered-address\")))";
             junos:must-message "location-pool-address cannot be defined with address or unnumbered-address simultaneously";
             description "Location-based IP address pool";
             uses apply-advanced;
             leaf pool-name {
               description "Pool name";
               junos:must "(\"access address-assignment location-pool $$\")";
               junos:must-message "referenced IP address location pool must be defined";
               type string {
                 length "1 .. 64";
               }
             }
           }
           leaf negotiate-address {
             description "Negotiate address with remote";
             junos:must "(!(\".. .. .. .. encapsulation multilink-frame-relay-uni-nni\"))";
             junos:must-message "negotiate-address is not supported with family mlfr-uni-nni ";
             junos:must "(!(\".. .. .. encapsulation multilink-frame-relay-end-to-end\"))";
             junos:must-message "negotiate-address is not supported with family mlfr-end-to-end ";
             junos:must "(!(\".. location-pool-address\"))";
             junos:must-message "negotiate-address and location-pool-address must not be defined simultaneously";
             junos:must "(!(\".. unnumbered-address\"))";
             junos:must-message "negotiate-address and unnumbered-address must not be defined simultaneously";
             junos:must "(!(\".. address\"))";
             junos:must-message "negotiate-address and address must not be defined simultaneously";
             type empty;
           }
           leaf destination-udp-port {
             description "Choose destination UDP port number";
             junos:must "(\".. .. .. tunnel encapsulation udp\")";
             junos:must-message "destination-udp-port can be configured only for encapsulation udp on fti interface";
             type union {
               type string {
                 pattern "<.*>|$.*";
               }
               type uint32 {
                 range "10000 .. 10009";
               }
             }
           }
         }
         container iso {
           presence "enable iso";
           junos:must "(!(\".. .. encapsulation frame-relay-ppp\"))";
           junos:must-message "family iso is not supported on encapsulation frame-relay-ppp";
           description "OSI ISO protocol parameters";
           uses apply-advanced;
           list address {
             key name;
             ordered-by user;
             description "Interface address";
             leaf name {
               description "Interface address";
               type jt:isoaddr;
             }
             uses apply-advanced;
           }
           leaf mtu {
             description "Protocol family maximum transmission unit";
             type union {
               type uint32;
               type string {
                 pattern "<.*>|$.*";
               }
             }
           }
           leaf destination-udp-port {
             description "Choose destination UDP port number";
             junos:must "(\".. .. .. tunnel encapsulation udp\")";
             junos:must-message "destination-udp-port can be configured only for encapsulation udp on fti interface";
             type union {
               type string {
                 pattern "<.*>|$.*";
               }
               type uint32 {
                 range "10030 .. 10039";
               }
             }
           }
         }
         container inet6 {
           presence "enable inet6";
           description "IPv6 protocol parameters";
           uses apply-advanced;
           container dhcpv6-client {
             junos:must "(!(\"system services dhcp\"))";
             junos:must-message "Incompatible with the dhcp server configured under 'system services dhcp'";
             junos:must "(!(\"system autoinstallation\"))";
             junos:must-message "Incompatible with 'system autoinstallation'";
             junos:must "(!(\".. address\"))";
             junos:must-message "Incompatible with interface assigned with address";
             junos:must "(!(any \"forwarding-options dhcp-relay dhcpv6  group <*> interface ${interface}.${unit}\"))";
             junos:must-message "DHCPv6 client and relay cannot be configured on the same interface ";
             junos:must "(!(any \"system services dhcp-local-server dhcpv6 group <*> interface ${interface}.${unit}\"))";
             junos:must-message "DHCPv6 client and server cannot be configured on the same interface ";
             description "Dynamic Host Configuration Protocol DHCPv6 client configuration";
             uses apply-advanced;
             leaf client-type {
               description "DHCPv6 client type";
               type enumeration {
                 enum "stateful" {
                   description "Stateful client type for address assignment.";
                 }
                 enum "autoconfig" {
                   description "Autoconfig  client type for router-advertisement";
                   junos:must "(\"protocols router-advertisement interface ${interface}.${unit}\")";
                   junos:must-message "Interface for ra messages is must for auto mode";
                   junos:must "(!(\"interfaces ${interface} unit ${unit} family inet6 dhcpv6-client update-router-advertisement\"))";
                   junos:must-message "Incompatible with 'dhcpv6-client update-router-advertisement'";
                   junos:must "(!(\"interfaces ${interface} unit ${unit} family inet6 dhcpv6-client client-ia-type ia-pd\"))";
                   junos:must-message "Incompatible with 'client-ia-type ia-pd'";
                 }
               }
             }
             list client-ia-type {
               key name;
               ordered-by user;
               description "DHCPv6 client identity association type";
               leaf name {
                 type enumeration {
                   enum "ia-na" {
                     description "Identity Association-Non-temporary Address";
                   }
                   enum "ia-pd" {
                     description "Identity Association-Prefix Address";
                   }
                 }
               }
               uses apply-advanced;
             }
             container rapid-commit {
               presence "enable rapid-commit";
               description "Option is used to signal the use of the two message exchange for address assignment";
             }
             container prefix-delegating {
               junos:must "(\"interfaces ${interface} unit ${unit} family inet6 dhcpv6-client client-ia-type ia-pd\")";
               junos:must-message "Incompatible with out 'client-ia-type ia-pd'";
               description "Prefix delegating parameters";
               uses apply-advanced;
               leaf preferred-prefix-length {
                 description "Client preferred prefix length";
                 type union {
                   type string {
                     pattern "<.*>|$.*";
                   }
                   type uint32 {
                     range "0 .. 64";
                   }
                 }
               }
               leaf sub-prefix-length {
                 description "The sub prefix length for LAN interfaces";
                 type union {
                   type string {
                     pattern "<.*>|$.*";
                   }
                   type uint32 {
                     range "1 .. 127";
                   }
                 }
               }
             }
             container client-identifier {
               description "DHCP Server identifies a client by client-identifier value ";
               leaf duid-type {
                 description "DUID identifying a client";
                 type enumeration {
                   enum "duid-llt" {
                     description "Link-layer address plus time";
                   }
                   enum "vendor" {
                     description "Vendor-assigned unique ID based on Enterprise Number";
                   }
                   enum "duid-ll" {
                     description "Link-layer address";
                   }
                 }
               }
             }
             leaf vendor-id {
               description "Vendor class id for the dhcpv6 client";
               type string {
                 length "1 .. 60";
               }
             }
             list req-option {
               key name;
               ordered-by user;
               description "DHCPV6 client requested option configuration";
               leaf name {
                 type enumeration {
                   enum "dns-server" {
                     description "Dns-server option";
                   }
                   enum "domain" {
                     description "Dns-server option";
                   }
                   enum "ntp-server" {
                     description "Ntp-server option";
                   }
                   enum "time-zone" {
                     description "Time-zone option";
                   }
                   enum "sip-server" {
                     description "Sip-server option";
                   }
                   enum "sip-domain" {
                     description "Sip-domain option";
                   }
                   enum "nis-server" {
                     description "Nis-server option";
                   }
                   enum "nis-domain" {
                     description "Nis-domain option";
                   }
                   enum "fqdn" {
                     description "Fully-qualified-domain option";
                   }
                   enum "vendor-spec" {
                     description "Vendor-spec option";
                   }
                   enum "zero-touch-redirect" {
                     description "Zero-touch-redirect";
                   }
                   enum "bootfile-url" {
                     description "Bootfile url";
                   }
                   enum "bootfile-param" {
                     description "Bootfile param";
                   }
                 }
               }
               uses apply-advanced;
             }
             container options {
               description "DHCP options";
               uses apply-advanced;
               list number {
                 key name;
                 description "DHCP option code";
                 leaf name {
                   description "DHCP option identifier code";
                   type union {
                     type string {
                       pattern "<.*>|$.*";
                     }
                     type uint32 {
                       range "1 .. 254";
                     }
                   }
                 }
                 choice option-type-choice {
                   case case_1 {
                     leaf hex-string {
                       description "Hexadecimal string";
                       type string {
                         length "1 .. 510";
                         junos:posix-pattern "^[[:xdigit:]]+$";
                         junos:pattern-message "Must be hexadecimal digits (0-9, a-f, A-F)";
                       }
                     }
                   }
                 }
               }
             }
             leaf retransmission-attempt {
               description "Number of attempts to retransmit the DHCPV6 client protocol packet";
               default "9";
               type union {
                 type string {
                   pattern "<.*>|$.*";
                 }
                 type uint32 {
                   range "0 .. 50000";
                 }
               }
             }
             container no-dns-install {
               presence "enable no-dns-install";
               description "Not propagate DNS to kernel";
             }
             container update-router-advertisement {
               junos:must "(\"interfaces ${interface} unit ${unit} family inet6 dhcpv6-client client-ia-type $$={2}\")";
               junos:must-message "Incompatible without 'client-ia-type ia-pd'";
               description "Dhcpv6 client update rpd for prefix delegation";
               uses apply-advanced;
               list interface {
                 key name;
                 ordered-by user;
                 description "Interfaces on which to delegate prefix";
                 max-elements 3;
                 leaf name {
                   description "Interfaces-name on which to delegate prefix";
                   junos:must "(unique \"interfaces <*> unit 0 family inet6 dhcpv6-client update-router-advertisement interface $$\")";
                   junos:must-message "This interface is already updated by a dhcpv6-client";
                   junos:must "(!(\"protocols router-advertisement interface $$\"))";
                   junos:must-message "Incompatible with the interface configured under 'protocols router-advertisement interface'";
                   type union {
                     type jt:interface-name;
                     type string {
                       pattern "<.*>|$.*";
                     }
                   }
                 }
                 uses apply-advanced;
                 choice managed-configuration-choice {
                   leaf managed-configuration {
                     description "Set managed address configuration";
                     type empty;
                   }
                   leaf no-managed-configuration {
                     description "Don't set managed address configuration";
                     type empty;
                   }
                 }
                 choice other-stateful-configuration-choice {
                   leaf other-stateful-configuration {
                     description "Set other stateful configuration";
                     type empty;
                   }
                   leaf no-other-stateful-configuration {
                     description "Don't set other stateful configuration";
                     type empty;
                   }
                 }
                 leaf max-advertisement-interval {
                   description "Maximum advertisement interval";
                   units "seconds";
                   type union {
                     type string {
                       pattern "<.*>|$.*";
                     }
                     type uint32 {
                       range "4 .. 1800";
                     }
                   }
                 }
                 leaf min-advertisement-interval {
                   description "Minimum advertisement interval";
                   units "seconds";
                   type union {
                     type string {
                       pattern "<.*>|$.*";
                     }
                     type uint32 {
                       range "3 .. 1350";
                     }
                   }
                 }
                 choice enable-recursive-dns-server-option-choice {
                   leaf enable-recursive-dns-server-option {
                     description "Enables the recursive DNS server option";
                     type empty;
                   }
                   leaf no-enable-recursive-dns-server-option {
                     description "Don't enables the recursive DNS server option";
                     type empty;
                   }
                 }
               }
             }
             leaf update-server {
               description "Propagate TCP/IP settings to DHCP server";
               type empty;
             }
           }
           container rpf-check {
             presence "enable rpf-check";
             description "Enable reverse-path-forwarding checks on this interface";
             uses apply-advanced;
             leaf fail-filter {
               description "Name of filter applied to packets failing RPF check";
               type string;
             }
             container mode {
               description "Mode for reverse path forwarding";
               leaf loose {
                 description "Reverse-path-forwarding loose mode";
                 type empty;
               }
             }
           }
           container accounting {
             description "Interface-based accounting options";
             uses apply-advanced;
             container source-class-usage {
               uses apply-advanced;
               leaf input {
                 description "Interface for source-class-usage input";
                 type empty;
               }
               leaf output {
                 description "Interface for source-class-usage output";
                 type empty;
               }
             }
             leaf destination-class-usage {
               description "Enable destination class usage on this interface";
               type empty;
             }
           }
           leaf mtu {
             description "Protocol family maximum transmission unit";
             type union {
               type uint32;
               type string {
                 pattern "<.*>|$.*";
               }
             }
           }
           leaf tcp-mss {
             description "Protocol family tcp maximum segment size";
             type union {
               type string {
                 pattern "<.*>|$.*";
               }
               type uint32 {
                 range "1 .. 65535";
               }
             }
           }
           leaf nd6-stale-time {
             description "Stale time to reconfirm reachability with inet6 neighbour";
             units "seconds";
             type union {
               type string {
                 pattern "<.*>|$.*";
               }
               type uint32 {
                 range "1 .. 18000";
               }
             }
           }
           leaf no-neighbor-learn {
             description "Disable neighbor address learning on interface";
             type empty;
           }
           leaf slaac-enable {
             description "Enable slaac on management interface";
             type empty;
           }
           container ndp-proxy {
             description "Enable ndp proxy on interface";
             uses apply-advanced;
             leaf interface-restricted {
               description "Enable ndp interface proxy restricted to interface";
               type empty;
             }
           }
           container dad-proxy {
             junos:must "(\".. ndp-proxy\")";
             junos:must-message "ndp-proxy must be configured";
             description "DAD proxy on interface";
             uses apply-advanced;
             leaf interface-restricted {
               description "Enable DAD interface proxy restricted to interface";
               type empty;
             }
           }
           leaf nd6-max-cache {
             description "Max interface ND nexthop cache size";
             type union {
               type string {
                 pattern "<.*>|$.*";
               }
               type uint32 {
                 range "1 .. 2000000";
               }
             }
           }
           leaf nd6-new-hold-limit {
             description "Max no. of new unresolved nexthops";
             junos:must "(\".. nd6-max-cache\")";
             junos:must-message "Interface max ND cache size must be configured";
             type union {
               type string {
                 pattern "<.*>|$.*";
               }
               type uint32 {
                 range "1 .. 2000000";
               }
             }
           }
           leaf no-redirects {
             description "Do not redirect traffic";
             type empty;
           }
           leaf allow-filter-on-re {
             description "Enable kernel filter on network ports";
             type empty;
           }
           container filter {
             description "Packet filtering";
             uses apply-advanced;
             choice input_choice {
               case case_1 {
                 container input {
                   description "Filter to be applied to received packets";
                   leaf filter-name {
                     description "Name of the filter";
                     type string;
                   }
                   leaf shared-name {
                     description "Filter shared-name of instances of interface-shared filter";
                     type string;
                   }
                   leaf precedence {
                     description "Precedence of the filter";
                     type union {
                       type string {
                         pattern "<.*>|$.*";
                       }
                       type uint32 {
                         range "0 .. 255";
                       }
                     }
                   }
                 }
               }
               case case_2 {
                 leaf-list input-list {
                   ordered-by user;
                   description "List of filter modules applied to received packets ";
                   type string;
                 }
               }
             }
             choice output_choice {
               case case_1 {
                 container output {
                   description "Filter to be applied to transmitted packets";
                   leaf filter-name {
                     description "Name of the filter";
                     type string;
                   }
                   leaf shared-name {
                     description "Filter shared-name of instances of interface-shared filter";
                     type string;
                   }
                   leaf precedence {
                     description "Precedence of the filter";
                     type union {
                       type string {
                         pattern "<.*>|$.*";
                       }
                       type uint32 {
                         range "0 .. 255";
                       }
                     }
                   }
                 }
               }
               case case_2 {
                 leaf-list output-list {
                   ordered-by user;
                   description "List of filter modules applied to transmitted packets ";
                   type string;
                 }
               }
             }
             leaf-list input-chain {
               ordered-by user;
               description "List of filter modules applied to received packets ";
               type string;
             }
             leaf-list output-chain {
               ordered-by user;
               description "List of filter modules applied to transmitted packets ";
               type string;
             }
             container adf {
               description "Ascend Data Filter definition";
               uses apply-advanced;
               list rule {
                 key name;
                 ordered-by user;
                 description "Set of ADF rules";
                 leaf name {
                   description "Value for a single rule";
                   type string;
                 }
                 uses apply-advanced;
               }
               leaf counter {
                 description "Add a counter to each rule";
                 type empty;
               }
               leaf input-precedence {
                 description "Precedence of the input rules";
                 type union {
                   type string {
                     pattern "<.*>|$.*";
                   }
                   type uint32 {
                     range "0 .. 255";
                   }
                 }
               }
               leaf not-mandatory {
                 description "No errors will be reported if no rules are present";
                 type empty;
               }
               leaf output-precedence {
                 description "Precedence of the output rules";
                 type union {
                   type string {
                     pattern "<.*>|$.*";
                   }
                   type uint32 {
                     range "0 .. 255";
                   }
                 }
               }
             }
             leaf group {
               description "Group to which interface belongs";
               type union {
                 type string {
                   pattern "<.*>|$.*";
                 }
                 type uint32 {
                   range "1 .. 255";
                 }
               }
             }
             leaf dialer {
               description "Name of filter applied on dialer";
               junos:must "(\".. .. .. .. dialer-options dial-string\")";
               junos:must-message "Dial string is mandatory for dialer filter";
               junos:must "(!(\".. .. .. .. dialer-options watch-list\"))";
               junos:must-message "A dialer interface cannot have watch-list as well as dialer filter";
               type string;
             }
           }
           container ingress-queuing-filter {
             description "Protocol family ingress-queuing-filter";
             leaf filter-name {
               description "Name of the ingress-queuing-filter";
               type string;
             }
           }
           leaf input-hierarchical-policer {
             description "Hierarchical policer for received packets";
             type string;
           }
           container policer {
             description "Interface policing";
             uses apply-advanced;
             leaf input {
               description "Name of policer applied to received packets";
               type string;
             }
             leaf output {
               description "Name of policer applied to transmitted packets";
               type string;
             }
           }
           container sampling {
             junos:must "((\"forwarding-options sampling family inet6\" || (\"forwarding-options packet-capture\" || any \"forwarding-options sampling instance <*> family inet6\")))";
             junos:must-message "Requires forwarding-options sampling or packet-capture config";
             description "Interface sampling";
             uses apply-advanced;
             leaf input {
               description "Sample all packets input on this interface";
               type empty;
             }
             leaf output {
               description "Sample all packets output on this interface";
               type empty;
             }
           }
           container service {
             description "Service operations";
             uses apply-advanced;
             container input {
               description "Service sets to consider for received packets";
               uses apply-advanced;
               list service-set {
                 key name;
                 ordered-by user;
                 description "Service set to consider for received packets";
                 leaf name {
                   description "Name of service set";
                   junos:must "((!(\".. .. .. .. .. .. demux-source\") && !(\".. .. .. .. .. .. demux-destination\")))";
                   junos:must-message "Service set cannot be configured on interfaces with demux-source or demux-destination";
                   junos:must "(\"services service-set $$ interface-service\")";
                   junos:must-message "this service set must be an interface service";
                   type string {
                     junos:posix-pattern "^[[:alnum:]][[:alnum:]/.:_-]*$";
                     junos:pattern-message "Must be a string beginning with a number or letter and consisting of letters, numbers, dashes, underscores, forward slashes, colons and dots.";
                   }
                 }
                 uses apply-advanced;
                 leaf service-filter {
                   description "Name of service filter";
                   type string;
                 }
               }
               leaf post-service-filter {
                 description "Post-service filter to apply to received packets";
                 type string;
               }
             }
             container output {
               description "Service sets to consider for transmitted packets";
               uses apply-advanced;
               list service-set {
                 key name;
                 ordered-by user;
                 description "Service set to consider for transmitted packets";
                 leaf name {
                   description "Name of service set";
                   type string {
                     junos:posix-pattern "^[[:alnum:]][[:alnum:]/.:_-]*$";
                     junos:pattern-message "Must be a string beginning with a number or letter and consisting of letters, numbers, dashes, underscores, forward slashes, colons and dots.";
                   }
                 }
                 uses apply-advanced;
                 leaf service-filter {
                   description "Name of service filter";
                   type string;
                 }
               }
             }
           }
           container tunnel-termination {
             presence "enable tunnel-termination";
             description "Tunnel termination";
           }
           list address {
             key name;
             ordered-by user;
             description "Interface address or destination prefix";
             junos:must "(!(\".. unnumbered-address\"))";
             junos:must-message "ipv6 unnumbered-address and ipv6 address must not be defined simultaneously";
             leaf name {
               description "Interface address or destination prefix";
               type jt:ipv6prefix;
             }
             uses apply-advanced;
             leaf destination {
               description "Destination address";
               type jt:ipv6addr;
             }
             leaf eui-64 {
               description "Generate EUI-64 interface ID";
               type empty;
             }
             leaf primary {
               description "Candidate for primary address in system";
               type empty;
             }
             leaf preferred {
               description "Preferred address on interface";
               type empty;
             }
             leaf master-only {
               description "Master management IP address for router";
               type empty;
             }
             list ndp {
               key name;
               ordered-by user;
               description "Static Neighbor Discovery Protocol  entries";
               leaf name {
                 description "Destination IP address";
                 type jt:ipv6addr;
               }
               leaf l2-interface {
                 description "Layer 2 interface name for NDP entry";
                 type union {
                   type jt:interface-name;
                   type string {
                     pattern "<.*>|$.*";
                   }
                 }
               }
               choice mac_address_type {
                 case case_1 {
                   leaf mac {
                     description "MAC address";
                     type jt:mac-unicast;
                   }
                 }
                 case case_2 {
                   leaf multicast-mac {
                     description "Multicast MAC address";
                     type jt:mac-multicast;
                   }
                 }
               }
               leaf publish {
                 description "Reply to NDP requests for this entry";
                 junos:must "((\".. mac\" || \".. multicast-mac\"))";
                 junos:must-message "either 'mac' or 'multicast-mac' must be configured along with 'publish' statment";
                 type empty;
               }
             }
             list vrrp-inet6-group {
               key name;
               ordered-by user;
               description "VRRP group";
               junos:must "(!(\".. eui-64\"))";
               junos:must-message "'vrrp-inet6-group' is not supported when 'eui-64' is configured";
               uses vrrp-group;
             }
             container web-authentication {
               description "Parameters for web-based firewall-user authentication";
               uses apply-advanced;
               leaf http {
                 description "Enable authentication via HTTP";
                 type empty;
               }
               leaf https {
                 description "Enable authentication via HTTPS";
                 type empty;
               }
               leaf redirect-to-https {
                 description "Web authentication redirect to HTTPS";
                 junos:must "(\".. https\")";
                 junos:must-message "https must be enabled";
                 type empty;
               }
             }
             leaf virtual-gateway-address {
               description "Virtual Gateway IP address";
               junos:must "(!(\".. vrrp-inet6-group\"))";
               junos:must-message "vrrp configuration incompatible with virtual gateway address";
               type jt:ipv6addr;
             }
             leaf subnet-router-anycast {
               description "Create a subnet roter anycast address for this address.";
               type empty;
             }
           }
           list demux-source {
             key name;
             ordered-by user;
             description "Demux based on source prefix";
             junos:must "(!(\".. demux-destination\"))";
             junos:must-message "demux-source can not be configured with demux-destination";
             leaf name {
               type string;
             }
             uses apply-advanced;
           }
           list demux-destination {
             key name;
             ordered-by user;
             description "Demux based on destination prefix";
             junos:must "(!(\".. demux-source\"))";
             junos:must-message "demux-source can not be configured with demux-destination";
             leaf name {
               type string;
             }
             uses apply-advanced;
           }
           container unnumbered-address {
             description "Unnumbered interface address/destination prefix";
             leaf source {
               description "Interface from which to take local address";
               junos:must "(\"interfaces $$-IFL family inet6 address\")";
               junos:must-message "referred interface must have address configured under family inet6";
               type union {
                 type jt:interface-unit;
                 type string {
                   pattern "<.*>|$.*";
                 }
               }
             }
             leaf preferred-source-address {
               description "Preferred address on the donor interface";
               type string;
             }
           }
           choice dad-disable-choice {
             leaf dad-disable {
               description "Disable duplicate-address-detection";
               type empty;
             }
             leaf no-dad-disable {
               description "Don't disable duplicate-address-detection";
               type empty;
             }
           }
           leaf destination-udp-port {
             description "Choose destination UDP port number";
             junos:must "(\".. .. .. tunnel encapsulation udp\")";
             junos:must-message "destination-udp-port can be configured only for encapsulation udp on fti interface";
             type union {
               type string {
                 pattern "<.*>|$.*";
               }
               type uint32 {
                 range "10010 .. 10019";
               }
             }
           }
           leaf negotiate-address {
             description "Negotiate address with remote";
             junos:must "(!(\".. unnumbered-address\"))";
             junos:must-message "negotiate-address and unnumbered-address must not be defined simultaneously";
             junos:must "(!(\".. address\"))";
             junos:must-message "negotiate-address and address must not be defined simultaneously";
             type empty;
           }
         }
         container mpls {
           presence "enable mpls";
           junos:must "(!(\".. .. encapsulation frame-relay-ppp\"))";
           junos:must-message "family mpls is not supported on encapsulation frame-relay-ppp";
           description "MPLS protocol parameters";
           uses apply-advanced;
           leaf mtu {
             description "Protocol family maximum transmission unit";
             type union {
               type uint32;
               type string {
                 pattern "<.*>|$.*";
               }
             }
           }
           leaf maximum-labels {
             description "Protocol family maximum number of labels";
             type union {
               type string {
                 pattern "<.*>|$.*";
               }
               type uint32;
             }
           }
           container filter {
             description "Packet filtering";
             uses apply-advanced;
             choice input_choice {
               case case_1 {
                 leaf input {
                   description "Name of filter applied to received packets";
                   type string;
                 }
               }
               case case_2 {
                 leaf-list input-list {
                   ordered-by user;
                   description "List of filter modules applied to received packets ";
                   type string;
                 }
               }
             }
             leaf-list input-chain {
               ordered-by user;
               description "List of filter modules applied to received packets ";
               type string;
             }
             choice output_choice {
               case case_1 {
                 leaf output {
                   description "Name of filter applied to transmitted packets";
                   type string;
                 }
               }
               case case_2 {
                 leaf-list output-list {
                   ordered-by user;
                   description "List of filter modules applied to transmitted packets ";
                   type string;
                 }
               }
             }
             leaf-list output-chain {
               ordered-by user;
               description "List of filter modules applied to transmitted packets ";
               type string;
             }
             leaf group {
               description "Interface group to which interface belongs";
               type union {
                 type string {
                   pattern "<.*>|$.*";
                 }
                 type uint32 {
                   range "1 .. 255";
                 }
               }
             }
             leaf dialer {
               description "Name of filter applied on dialer";
               junos:must "(\".. .. .. .. dialer-options dial-string\")";
               junos:must-message "Dial string is mandatory for dialer filter";
               junos:must "(!(\".. .. .. .. dialer-options watch-list\"))";
               junos:must-message "A dialer interface cannot have watch-list as well as dialer filter";
               type string;
             }
           }
           container ingress-queuing-filter {
             description "Protocol family ingress-queuing-filter";
             leaf filter-name {
               description "Name of the ingress-queuing-filter";
               type string;
             }
           }
           leaf input-hierarchical-policer {
             description "Hierarchical policer for received packets";
             type string;
           }
           container policer {
             description "Interface policing";
             uses apply-advanced;
             leaf input {
               description "Name of policer applied to received packets";
               type string;
             }
             leaf output {
               description "Name of policer applied to transmitted packets";
               type string;
             }
           }
           leaf destination-udp-port {
             description "Choose destination UDP port number";
             junos:must "(\".. .. .. tunnel encapsulation udp\")";
             junos:must-message "destination-udp-port can be configured only for encapsulation udp on fti interface";
             type union {
               type string {
                 pattern "<.*>|$.*";
               }
               type uint32 {
                 range "10020 .. 10029";
               }
             }
           }
         }
         container mlppp {
           junos:must "(!(\"interfaces ${interface} container-options\"))";
           junos:must-message "mlppp is not supported for container interfaces";
           description "Multilink PPP protocol parameters";
           uses apply-advanced;
           leaf bundle {
             description "Logical interface name this link will join";
             junos:must "((!(\".. .. .. dial-options\") || \"interfaces $$-IFL encapsulation multilink-ppp\"))";
             junos:must-message "Bundle interface must be configured";
             junos:must "((!(\".. .. .. pppoe-options\") || \"interfaces $$-IFL encapsulation multilink-ppp\"))";
             junos:must-message "Bundle interface must be configured";
             type string;
           }
           choice anchor-points {
             case case_1 {
               leaf service-interface {
                 description "Services interface to use";
                 junos:must "(\"interfaces $$\")";
                 junos:must-message "Interface must be defined in the interfaces hierarchy";
                 type union {
                   type jt:interface-device;
                   type string {
                     pattern "<.*>|$.*";
                   }
                 }
               }
             }
             case case_2 {
               leaf service-device-pool {
                 description "Service interface pool name to use";
                 junos:must "(\"services service-device-pools pool $$\")";
                 junos:must-message "referenced service device pool must be defined";
                 type string {
                   length "1 .. 63";
                 }
               }
             }
           }
           leaf dynamic-profile {
             description " dynamic profile for interface to use";
             junos:must "(\"dynamic-profiles $$\")";
             junos:must-message "referenced dynamic-profile must be defined";
             type string {
               length "1 .. 80";
             }
           }
         }
         container mlfr-end-to-end {
           presence "enable mlfr-end-to-end";
           junos:must "(!(\".. .. encapsulation frame-relay-ppp\"))";
           junos:must-message "family mlfr-end-to-end is not supported on encapsulation frame-relay-ppp";
           description "Multilink Frame Relay end-to-end protocol parameters";
           uses apply-advanced;
           leaf bundle {
             description "Logical interface name this link will join";
             type union {
               type jt:interface-unit;
               type string {
                 pattern "<.*>|$.*";
               }
             }
           }
         }
         container mlfr-uni-nni {
           presence "enable mlfr-uni-nni";
           junos:must "(!(\".. .. encapsulation frame-relay-ppp\"))";
           junos:must-message "family mlfr-uni-uni is not supported on encapsulation frame-relay-ppp";
           description "Multilink Frame Relay UNI NNI protocol parameters";
           uses apply-advanced;
           leaf bundle {
             description "Logical interface name this link will join";
             type union {
               type jt:interface-unit;
               type string {
                 pattern "<.*>|$.*";
               }
             }
           }
         }
         container ccc {
           presence "enable ccc";
           junos:must "(!(\".. .. encapsulation frame-relay-ppp\"))";
           junos:must-message "family ccc is not supported on encapsulation frame-relay-ppp";
           description "Circuit cross-connect parameters";
           uses apply-advanced;
           leaf mtu {
             description "Protocol family maximum transmission unit";
             type union {
               type uint32;
               type string {
                 pattern "<.*>|$.*";
               }
             }
           }
           container filter {
             description "Packet filtering";
             uses apply-advanced;
             choice input_choice {
               case case_1 {
                 leaf input {
                   description "Name of filter applied to received packets";
                   type string;
                 }
               }
               case case_2 {
                 leaf-list input-list {
                   ordered-by user;
                   description "List of filter modules applied to received packets ";
                   type string;
                 }
               }
             }
             leaf-list input-chain {
               ordered-by user;
               description "List of filter modules applied to received packets ";
               type string;
             }
             choice output_choice {
               case case_1 {
                 leaf output {
                   description "Name of filter applied to transmitted packets";
                   type string;
                 }
               }
               case case_2 {
                 leaf-list output-list {
                   ordered-by user;
                   description "List of filter modules applied to transmitted packets ";
                   type string;
                 }
               }
             }
             leaf-list output-chain {
               ordered-by user;
               description "List of filter modules applied to transmitted packets ";
               type string;
             }
             leaf group {
               description "Interface group to which interface belongs";
               type union {
                 type string {
                   pattern "<.*>|$.*";
                 }
                 type uint32 {
                   range "1 .. 255";
                 }
               }
             }
           }
           container ingress-queuing-filter {
             description "Protocol family ingress-queuing-filter";
             leaf filter-name {
               description "Name of the ingress-queuing-filter";
               type string;
             }
           }
           container policer {
             description "Interface policing";
             uses apply-advanced;
             leaf input {
               description "Name of policer applied to received packets";
               type string;
             }
             leaf output {
               description "Name of policer applied to transmitted packets";
               type string;
             }
           }
           leaf translate-fecn-and-becn {
             description "Translate FECN and BECN bits";
             type empty;
           }
           choice de-or-plp {
             case case_1 {
               leaf translate-discard-eligible {
                 description "Translate DE bit";
                 type empty;
               }
             }
             case case_2 {
               leaf translate-plp-control-word-de {
                 description "Translate PLP to/from Martini Control DE bit";
                 type empty;
               }
             }
           }
           leaf keep-address-and-control {
             description "Don't strip PPP address and control bytes";
             type empty;
           }
         }
         container tcc {
           presence "enable tcc";
           junos:must "(!(\".. .. encapsulation frame-relay-ppp\"))";
           junos:must-message "family tcc is not supported on encapsulation frame-relay-ppp";
           description "Translational cross-connect parameters";
           uses apply-advanced;
           container policer {
             description "Interface policing";
             uses apply-advanced;
             leaf input {
               description "Name of policer applied to received packets";
               type string;
             }
             leaf output {
               description "Name of policer applied to transmitted packets";
               type string;
             }
           }
           container proxy {
             presence "enable proxy";
             uses apply-advanced;
             leaf inet-address {
               description "Remote host address on non-Ethernet side of Ethernet TCC";
               type jt:ipv4addr;
             }
           }
           container remote {
             presence "enable remote";
             uses apply-advanced;
             leaf inet-address {
               description "Remote host address on Ethernet side of Ethernet TCC";
               type jt:ipv4addr;
             }
             leaf mac-address {
               description "Remote host MAC address on Ethernet side of Ethernet TCC";
               type jt:mac-addr;
             }
           }
           leaf-list protocols {
             ordered-by user;
             description "Protocols supported on TCC interface";
             type enumeration {
               enum "mpls" {
                 description "Multiprotocol Label Switching";
               }
               enum "inet" {
                 description "IP version 4";
               }
               enum "iso" {
                 description "International Organization for Standardization";
               }
               enum "inet6" {
                 description "IP version 6";
               }
             }
           }
         }
         container vpls {
           presence "enable vpls";
           description "Virtual private LAN service parameters";
           uses apply-advanced;
           leaf core-facing {
             description "Interface is core facing";
             type empty;
           }
           container filter {
             description "Packet filtering";
             uses apply-advanced;
             choice input_choice {
               case case_1 {
                 container input {
                   description "Filter to be applied to received packets";
                   leaf filter-name {
                     description "Name of the filter";
                     type string;
                   }
                   leaf shared-name {
                     description "Filter shared-name of instances of interface-shared filter";
                     type string;
                   }
                   leaf precedence {
                     description "Precedence of the filter";
                     type union {
                       type string {
                         pattern "<.*>|$.*";
                       }
                       type uint32 {
                         range "0 .. 255";
                       }
                     }
                   }
                 }
               }
               case case_2 {
                 leaf-list input-list {
                   ordered-by user;
                   description "List of filter modules applied to received packets ";
                   type string;
                 }
               }
             }
             leaf-list input-chain {
               ordered-by user;
               description "List of filter modules applied to received packets ";
               type string;
             }
             leaf-list output-chain {
               ordered-by user;
               description "List of filter modules applied to transmitted packets ";
               type string;
             }
             choice output_choice {
               case case_1 {
                 container output {
                   description "Filter to be applied to transmitted packets";
                   leaf filter-name {
                     description "Name of the filter";
                     type string;
                   }
                   leaf shared-name {
                     description "Filter shared-name of instances of interface-shared filter";
                     type string;
                   }
                   leaf precedence {
                     description "Precedence of the filter";
                     type union {
                       type string {
                         pattern "<.*>|$.*";
                       }
                       type uint32 {
                         range "0 .. 255";
                       }
                     }
                   }
                 }
               }
               case case_2 {
                 leaf-list output-list {
                   ordered-by user;
                   description "List of filter modules applied to transmitted packets ";
                   type string;
                 }
               }
             }
             container adf {
               description "Ascend Data Filter definition";
               uses apply-advanced;
               list rule {
                 key name;
                 ordered-by user;
                 description "Set of ADF rules";
                 leaf name {
                   description "Value for a single rule";
                   type string;
                 }
                 uses apply-advanced;
               }
               leaf counter {
                 description "Add a counter to each rule";
                 type empty;
               }
               leaf input-precedence {
                 description "Precedence of the input rules";
                 type union {
                   type string {
                     pattern "<.*>|$.*";
                   }
                   type uint32 {
                     range "0 .. 255";
                   }
                 }
               }
               leaf not-mandatory {
                 description "No errors will be reported if no rules are present";
                 type empty;
               }
               leaf output-precedence {
                 description "Precedence of the output rules";
                 type union {
                   type string {
                     pattern "<.*>|$.*";
                   }
                   type uint32 {
                     range "0 .. 255";
                   }
                 }
               }
             }
             leaf group {
               description "Group to which interface belongs";
               type union {
                 type string {
                   pattern "<.*>|$.*";
                 }
                 type uint32 {
                   range "1 .. 255";
                 }
               }
             }
           }
           container ingress-queuing-filter {
             description "Protocol family ingress-queuing-filter";
             leaf filter-name {
               description "Name of the ingress-queuing-filter";
               type string;
             }
           }
           container iq-policing-filter {
             description "Protocol family ingress-queuing-policing-filter";
             leaf filter-name {
               description "Name of the ingress-queuing-policing-filter";
               type string;
             }
           }
           container policer {
             description "Interface policing";
             uses apply-advanced;
             leaf input {
               description "Name of policer applied to received packets";
               type string;
             }
             leaf output {
               description "Name of policer applied to transmitted packets";
               type string;
             }
           }
           container sampling {
             junos:must "((any \"forwarding-options sampling instance <*> family vpls\" || any \"forwarding-options sampling instance <*> family bridge\"))";
             junos:must-message "Configure family either vpls or bridge under forwarding-options sampling";
             description "Interface sampling";
             uses apply-advanced;
             leaf input {
               description "Sample all packets input on this interface";
               type empty;
             }
             leaf output {
               description "Sample all packets output on this interface";
               type empty;
             }
           }
         }
         container bridge {
           presence "enable bridge";
           junos:must "((!(\".. vpls\") && (!(\".. inet\") && (!(\".. inet6\") && (!(\".. ccc\") && (!(\".. ethernet-switching\") && (!(\".. iso\") && (!(\".. llc2\") && (!(\".. mpls\") && (!(\".. tcc\") && (!(\".. pppoe\") && !(\".. gre\"))))))))))))";
           junos:must-message "family bridge and rest of the families are mutually exclusive";
           description "Layer-2 bridging parameters";
           uses apply-advanced;
           leaf core-facing {
             description "Interface is core facing";
             type empty;
           }
           container filter {
             description "Packet filtering";
             uses apply-advanced;
             choice input_choice {
               case case_1 {
                 container input {
                   description "Filter to be applied to received packets";
                   leaf filter-name {
                     description "Name of the filter";
                     type string;
                   }
                   leaf shared-name {
                     description "Filter shared-name of instances of interface-shared filter";
                     type string;
                   }
                   leaf precedence {
                     description "Precedence of the filter";
                     type union {
                       type string {
                         pattern "<.*>|$.*";
                       }
                       type uint32 {
                         range "0 .. 255";
                       }
                     }
                   }
                 }
               }
               case case_2 {
                 leaf-list input-list {
                   ordered-by user;
                   description "List of filter modules applied to received packets ";
                   type string;
                 }
               }
             }
             leaf-list input-chain {
               ordered-by user;
               description "List of filter modules applied to received packets ";
               type string;
             }
             leaf-list output-chain {
               ordered-by user;
               description "List of filter modules applied to transmitted packets ";
               type string;
             }
             choice output_choice {
               case case_1 {
                 container output {
                   description "Filter to be applied to transmitted packets";
                   leaf filter-name {
                     description "Name of the filter";
                     type string;
                   }
                   leaf shared-name {
                     description "Filter shared-name of instances of interface-shared filter";
                     type string;
                   }
                   leaf precedence {
                     description "Precedence of the filter";
                     type union {
                       type string {
                         pattern "<.*>|$.*";
                       }
                       type uint32 {
                         range "0 .. 255";
                       }
                     }
                   }
                 }
               }
               case case_2 {
                 leaf-list output-list {
                   ordered-by user;
                   description "List of filter modules applied to transmitted packets ";
                   type string;
                 }
               }
             }
             container adf {
               description "Ascend Data Filter definition";
               uses apply-advanced;
               list rule {
                 key name;
                 ordered-by user;
                 description "Set of ADF rules";
                 leaf name {
                   description "Value for a single rule";
                   type string;
                 }
                 uses apply-advanced;
               }
               leaf counter {
                 description "Add a counter to each rule";
                 type empty;
               }
               leaf input-precedence {
                 description "Precedence of the input rules";
                 type union {
                   type string {
                     pattern "<.*>|$.*";
                   }
                   type uint32 {
                     range "0 .. 255";
                   }
                 }
               }
               leaf not-mandatory {
                 description "No errors will be reported if no rules are present";
                 type empty;
               }
               leaf output-precedence {
                 description "Precedence of the output rules";
                 type union {
                   type string {
                     pattern "<.*>|$.*";
                   }
                   type uint32 {
                     range "0 .. 255";
                   }
                 }
               }
             }
             leaf group {
               description "Group to which interface belongs";
               type union {
                 type string {
                   pattern "<.*>|$.*";
                 }
                 type uint32 {
                   range "1 .. 255";
                 }
               }
             }
           }
           container ingress-queuing-filter {
             description "Protocol family ingress-queuing-filter";
             leaf filter-name {
               description "Name of the ingress-queuing-filter";
               type string;
             }
           }
           container iq-policing-filter {
             description "Protocol family ingress-queuing-policing-filter";
             leaf filter-name {
               description "Name of the ingress-queuing-policing-filter";
               type string;
             }
           }
           container policer {
             description "Interface policing";
             uses apply-advanced;
             leaf input {
               description "Name of policer applied to received packets";
               type string;
             }
             leaf output {
               description "Name of policer applied to transmitted packets";
               type string;
             }
           }
           leaf interface-mode {
             description "Interface mode (access or trunk)";
             type enumeration {
               enum "access" {
                 description "Interface mode is access";
                 junos:must "((!(\"interfaces ${interface} vlan-tagging\") && (!(\"interfaces ${interface} flexible-vlan-tagging\") && !(\"interfaces ${interface} stacked-vlan-tagging\"))))";
                 junos:must-message "interface-mode access is allowed only for untagged interfaces";
               }
               enum "trunk" {
                 description "Interface mode is trunk";
                 junos:must "(!(\"interfaces ${interface} no-native-vlan-insert\"))";
                 junos:must-message "'interface-mode trunk' must not be configured with 'no-native-vlan-insert'";
                 junos:must "(((\"protocols mvrp interface ${interface}\" || any \"routing-instances <*> protocols mvrp interface ${interface}\") || (\".. vlan-id-list\" || (\".. isid-list\" || (\".. inner-vlan-id-list\" || (\".. vlan members\" || (\"..inner-vlan members\" || (\".. vlan-id\" || \".. vlan-auto-sense\"))))))))";
                 junos:must-message "'interface-mode trunk' must be defined with either 'vlan-id-list','isid-list', 'inner-vlan-id-list' or the interface must be configured for 'protocols mvrp' or 'vlan-auto-sense'";
               }
             }
           }
           leaf vlan-auto-sense {
             description "Enable VLAN auto sense on this interface";
             junos:must "(\".. interface-mode trunk\")";
             junos:must-message "vlan-auto-sense can be enabled only on trunk interfaces";
             type empty;
           }
           leaf bridge-domain-type {
             description "Bridge domain type (svlan or bvlan)";
             type enumeration {
               enum "svlan" {
                 description "Bridge domain type svlan";
                 junos:must "(\".. isid-list all-service-groups\")";
                 junos:must-message "bridge-domain-type svlan is allowed only for isid tagged interfaces";
                 junos:must "(\".. interface-mode trunk\")";
                 junos:must-message "bridge-domain-type svlan is allowed only for trunk interfaces";
               }
               enum "bvlan" {
                 description "Bridge domain type bvlan";
                 junos:must "(\".. isid-list all\")";
                 junos:must-message "bridge-domain-type bvlan is allowed only for isid tagged interfaces";
                 junos:must "(\".. interface-mode trunk\")";
                 junos:must-message "bridge-domain-type bvlan is allowed only for trunk interfaces";
               }
             }
           }
           leaf inter-switch-link {
             description "PVLAN inter switch link";
             junos:must "(\".. interface-mode trunk\")";
             junos:must-message "'Inter switch link' is supported only under trunk interface mode";
             type empty;
           }
           choice vlan_list {
             case case_1 {
               leaf vlan-id {
                 description "Access mode and trunk mode VLAN membership";
                 type union {
                   type string {
                     pattern "<.*>|$.*";
                   }
                   type uint32 {
                     range "1 .. 4094";
                   }
                 }
               }
             }
             case case_2 {
               leaf-list vlan-id-list {
                 description "Trunk mode VLAN membership for this interface";
                 junos:must "((!(\".. .. .. vlan-id\") && !(\".. .. .. vlan-tags\")))";
                 junos:must-message "'vlan-id-list' cannot be used on interface with vlan-id/vlan-tags";
                 junos:must "(!(\"interfaces ${interface} stacked-vlan-tagging\"))";
                 junos:must-message "'vlan-id-list' is not supported on stacked-vlan-tagging mode";
                 junos:must "(\".. interface-mode trunk\")";
                 junos:must-message "'vlan-id-list' statement supported only under trunk interface mode";
                 type jt:vlan-range;
               }
             }
             case case_3 {
               leaf-list inner-vlan-id-list {
                 description "Trunk mode VLAN membership for this interface based on inner VLAN tag";
                 junos:must "((!(\".. .. .. vlan-tags inner\") && !(\".. .. .. vlan-tags inner-range\")))";
                 junos:must-message "'inner-vlan-id-list' cannot be used on interface with vlan-tags inner/inner-range";
                 junos:must "((\".. .. .. vlan-id\" || \".. .. .. vlan-tags\"))";
                 junos:must-message "'inner-vlan-id-list' can be used only on interface with vlan-id/vlan-tags";
                 junos:must "(\"interfaces ${interface} flexible-vlan-tagging\")";
                 junos:must-message "'inner-vlan-id-list' is supported only on flexible-vlan-tagging mode";
                 junos:must "(\".. interface-mode trunk\")";
                 junos:must-message "'inner-vlan-id-list' statement supported only under trunk interface mode";
                 type jt:vlan-range;
               }
             }
           }
           container vlan-rewrite {
             junos:must "((\".. inner-vlan-id-list\" || \".. vlan-id-list\"))";
             junos:must-message "'vlan-rewrite' statement can be used only with 'vlan-id-list' or inner-vlan-id-list configured";
             junos:must "(\".. interface-mode trunk\")";
             junos:must-message "'vlan-rewrite' statement supported only under trunk interface mode";
             description "Specify vlan translation";
             uses apply-advanced;
             list translate {
               key name;
               ordered-by user;
               description "Translate incoming VLAN tag";
               leaf name {
                 description "Specify the incoming VLAN tag";
                 type union {
                   type string {
                     pattern "<.*>|$.*";
                   }
                   type uint32 {
                     range "1 .. 4094";
                   }
                 }
               }
               leaf to-vlan-id {
                 description "Specify the bridge-domain VLAN-ID";
                 type union {
                   type string {
                     pattern "<.*>|$.*";
                   }
                   type uint32 {
                     range "1 .. 4094";
                   }
                 }
               }
             }
           }
           choice isid_list {
             case case_1 {
               leaf isid-list {
                 description "Specify the ISID list";
                 type enumeration {
                   enum "all-service-groups" {
                     description "Map all ISIDs specified under the service-groups";
                     junos:must "(\".. interface-mode trunk\")";
                     junos:must-message "'all-service-groups' statement supported only under trunk interface mode";
                   }
                   enum "all" {
                     description "Map all ISIDs";
                     junos:must "(\".. interface-mode trunk\")";
                     junos:must-message "'all' statement supported only under trunk interface mode";
                   }
                 }
               }
             }
           }
           container storm-control {
             junos:must "((\".. interface-mode trunk\" || (\".. interface-mode access\" || (\"interfaces ${interface} unit ${unit} encapsulation vlan-bridge\" || (\"interfaces ${interface} unit ${unit} encapsulation vlan-vpls\" || (\"interfaces ${interface} unit ${unit} encapsulation ethernet-bridge\" || \"interfaces ${interface} unit ${unit} encapsulation ethernet-vpls\"))))))";
             junos:must-message "Storm control supported with trunk or access interfaces and limited encapsulations";
             description "Storm control profile name to bind";
             uses apply-advanced;
             leaf profile-name {
               description "Profile name";
               junos:must "((\"forwarding-options storm-control-profiles\" || \".. .. .. .. forwarding-options storm-control-profiles $$\"))";
               junos:must-message "Storm profile name must be defined in the [edit forwarding-options storm-control-profiles] hierarchy";
               type string;
             }
           }
           container recovery-timeout {
             junos:must "(\".. storm-control\")";
             junos:must-message "Recovery timeout should be configured only with storm-control";
             description "Recovery timeout for this interface";
             leaf time-in-seconds {
               units "seconds";
               type union {
                 type string {
                   pattern "<.*>|$.*";
                 }
                 type uint32 {
                   range "10 .. 3600";
                 }
               }
             }
           }
           container sampling {
             junos:must "(any \"forwarding-options sampling instance <*> family bridge\")";
             junos:must-message "Configure family bridge under forwarding-options sampling";
             description "Interface sampling";
             uses apply-advanced;
             leaf input {
               description "Sample all packets input on this interface";
               type empty;
             }
             leaf output {
               description "Sample all packets output on this interface";
               type empty;
             }
           }
         }
         container ethernet-switching {
           description "Ethernet switching parameters";
           presence "enable ethernet-switching";
           junos:must "((!(\".. vpls\") && (!(\".. inet\") && (!(\".. inet6\") && (!(\".. bridge\") && (!(\".. ccc\") && (!(\".. iso\") && (!(\".. llc2\") && (!(\".. mpls\") && (!(\".. tcc\") && (!(\".. pppoe\") && !(\".. gre\"))))))))))))";
           junos:must-message "Family ethernet-switching and rest of the families are mutually exclusive";
           junos:must "(!((\"protocols l2-learning global-mode switching\" && any \"security zones security-zone <*> interfaces ${interface}\")))";
           junos:must-message "In switching mode, ethernet-switching interface must not be in security zone.";
           junos:must "(!((\"interfaces ${interface} vlan-tagging\" && \"protocols l2-learning global-mode switching\")))";
           junos:must-message "An interface cannot have both family ethernet-switching and vlan-tagging configured";
           uses ethernet-switching-type;
         }
         container fibre-channel {
           description "Fibre channel switching parameters";
           presence "enable fibre-channel";
           uses fibre-channel-type;
         }
         container pppoe {
           description "PPP over Ethernet underlying interface-specific options";
           presence "enable pppoe";
           junos:must "(!(\"forwarding-options hyper-mode\"))";
           junos:must-message "To configure family pppoe, 'forwarding-options hyper-mode' should not be configured";
           junos:must "((!(\".. vpls\") && (!(\".. ccc\") && (!(\".. ethernet-switching\") && (!(\".. iso\") && (!(\".. llc2\") && (!(\".. mpls\") && (!(\".. tcc\") && (!(\".. bridge\") && !(\".. gre\"))))))))))";
           junos:must-message "Invalid family type configured with family pppoe";
           junos:must "(!(\".. .. pppoe-underlying-options\"))";
           junos:must-message "family pppoe is mutually exclusive with pppoe-underlying-options";
           uses pppoe_underlying_options_type;
         }
         container any {
           presence "enable any";
           description "Parameters for 'any' family";
           uses apply-advanced;
           container filter {
             description "Layer 2 packet filtering";
             uses apply-advanced;
             leaf input {
               description "Name of filter applied to received packets";
               junos:must "((\"firewall family any filter $$\" || (!(\"firewall\") && \".. .. .. .. .. .. firewall family any filter $$\")))";
               junos:must-message "referenced filter must be defined under firewall family any";
               type string {
                 junos:posix-pattern "!^((__.*)|(.{65,}))$";
                 junos:pattern-message "Must be a non-reserved string of 64 characters or less";
               }
             }
             leaf group {
               description "Group to which interface belongs";
               type union {
                 type string {
                   pattern "<.*>|$.*";
                 }
                 type uint32 {
                   range "1 .. 255";
                 }
               }
             }
           }
         }
         uses apply-advanced;
       }
       leaf service-domain {
         description "Service domain to which interface belongs";
         type enumeration {
           enum "inside" {
             description "Inside network";
           }
           enum "outside" {
             description "Outside network";
           }
         }
       }
       leaf copy-tos-to-outer-ip-header {
         description "Copy IP payload header's ToS field to GRE delivery header";
         type empty;
       }
       leaf copy-tos-to-outer-ip-header-transit {
         description "Copy IP ToS field to GRE header for transit packets";
         type empty;
       }
       leaf force-control-packets-on-transit-path {
         description "Force control packets to follow transit path";
         type empty;
       }
       container load-balancing-options {
         junos:must "(!(\".. .. load-balancing-options high-availability-options one-to-one\"))";
         junos:must-message "load-balancing-options are used when number of active members is more than one";
         description "AMS subunit load balancing options";
         uses apply-advanced;
         leaf preferred-active {
           description "Preferred active Interface name";
           junos:must "((\".. .. .. load-balancing-options member-interface $$\" && !(\".. .. .. load-balancing-options high-availability-options many-to-one preferred-backup $$\")))";
           junos:must-message "Active should be one of member-interfaces excluding preferred-backup";
           type union {
             type jt:interface-device;
             type string {
               pattern "<.*>|$.*";
             }
           }
         }
         leaf disable-hash {
           description "Hash based distribution is not needed for this subunit";
           junos:must "(\".. .. service-domain\")";
           junos:must-message "service-domain must be configured if disable-hash is enabled";
           junos:must "(!(\".. hash-keys\"))";
           junos:must-message "hash-keys must not be configured if disable-hash is enabled";
           type empty;
         }
         container hash-keys {
           uses apply-advanced;
           leaf-list ingress-key {
             ordered-by user;
             description "Hash Key for the ingress direction";
             type enumeration {
               enum "source-ip" {
                 description "Source Ip Address";
               }
               enum "destination-ip" {
                 description "Destination Ip Address";
               }
               enum "protocol" {
                 description "Protocol";
               }
               enum "iif" {
                 description "Incoming Interface";
               }
             }
           }
           leaf-list egress-key {
             ordered-by user;
             description "Hash Key for the egress direction";
             status deprecated;
             type enumeration {
               enum "source-ip" {
                 description "Source Ip Address";
                 status deprecated;
               }
               enum "destination-ip" {
                 description "Destination Ip Address";
                 status deprecated;
               }
               enum "protocol" {
                 description "Protocol";
                 status deprecated;
               }
               enum "oif" {
                 description "Outgoing Interface";
                 status deprecated;
               }
             }
           }
           leaf ipv6-source-prefix-length {
             description "IPv6 source prefix length for hash computation";
             type enumeration {
               enum "56" {
                 description "56 bit IPv6 address prefix";
               }
               enum "64" {
                 description "64 bit IPv6 address prefix";
               }
               enum "96" {
                 description "96 bit IPv6 address prefix";
               }
               enum "128" {
                 description "Complete 128 bit IPv6 address";
               }
             }
           }
         }
       }
       container interface-state {
         description "IRB interface state computation";
         uses apply-advanced;
         choice state {
           case case_1 {
             leaf local {
               description "IRB State computation based on local interface state";
               type empty;
             }
           }
           case case_2 {
             leaf remote {
               description "IRB State computation based on remote reachability";
               type empty;
             }
           }
           case case_3 {
             leaf local-remote {
               description "IRB State computation based on local or remote reachability";
               type empty;
             }
           }
           case case_4 {
             leaf local-interface {
               description "IRB State computation based on loopback AE port state";
               type union {
                 type jt:interface-name;
                 type string {
                   pattern "<.*>|$.*";
                 }
               }
             }
           }
         }
         leaf local-count {
           description "Minimum number of local layer2 link in up state to consider IRB up";
           junos:must "(!(\".. remote\"))";
           junos:must-message "Must configure local, local-remote or keep default";
           type union {
             type uint16;
             type string {
               pattern "<.*>|$.*";
             }
           }
         }
         leaf vtep-count {
           description "Minimum number of VTEP link in up state to consider IRB up";
           junos:must "(!(\".. local\"))";
           junos:must-message "Must configure remote,local-remote or keep default";
           type union {
             type uint16;
             type string {
               pattern "<.*>|$.*";
             }
           }
         }
         container hold-time {
           description "Delay before marking interface up or down for defect";
           uses apply-advanced;
           leaf up {
             description "Delay in seconds before marking IRB interface up";
             units "seconds";
             type union {
               type uint32;
               type string {
                 pattern "<.*>|$.*";
               }
             }
           }
           leaf down {
             description "Delay in seconds before marking IRB interface down";
             units "seconds";
             type union {
               type uint32;
               type string {
                 pattern "<.*>|$.*";
               }
             }
           }
         }
       }
       leaf mac {
         description "Configure logical interface MAC address";
         type jt:mac-unicast;
       }
       leaf virtual-gateway-v4-mac {
         description "Configure virtual gateway IPV4 virtual MAC address";
         type jt:mac-unicast;
       }
       leaf virtual-gateway-v6-mac {
         description "Configure virtual gateway IPV6 virtual MAC address";
         type jt:mac-unicast;
       }
       container forwarding-options {
         description "Aggregated Ethernet interface forwarding-options";
         uses apply-advanced;
         container load-balance-stateful {
           description "Stateful load balancing";
           uses apply-advanced;
           leaf per-flow {
             description "Enable feature";
             type empty;
           }
           leaf rebalance {
             description "Rebalancing interval";
             units "per minute";
             type union {
               type string {
                 pattern "<.*>|$.*";
               }
               type uint32 {
                 range "1 .. 1000";
               }
             }
           }
           leaf load-type {
             description "Load - defines the flows";
             type enumeration {
               enum "high" {
                 description "If the no of flows on this aggregate is large(1000-10000 flows) ";
               }
               enum "medium" {
                 description "If the no of flows on this aggregate is moderate(100-1000 flows)";
               }
               enum "low" {
                 description "If the no of flows on this aggregate is less(1-100)";
               }
             }
           }
         }
       }
       leaf etree-ac-role {
         description "ETREE attachment circuit role";
         type enumeration {
           enum "root" {
             description "ETREE root interface";
           }
           enum "leaf" {
             description "ETREE leaf interface";
           }
         }
       }
       container load-balance {
         description "Load-balance weight per subscriber interface";
         uses apply-advanced;
         leaf weight {
           description "Load-balance weight";
           type union {
             type string {
               pattern "<.*>|$.*";
             }
             type uint32 {
               range "1 .. 1000";
             }
           }
         }
       }
       container dialer-options {
         presence "enable dialer-options";
         description "Dialer options";
         uses apply-advanced;
         leaf pool {
           description "Dialer pool";
           junos:must "(unique \"interfaces <dl*>\")";
           junos:must-message "Only one dl interface can be configured";
           junos:must "((!(\"interfaces umd0 dialer-options pool $$\") || !(\".. callback\")))";
           junos:must-message "callback is not supported if the subordinate interface is umd0";
           junos:must "(any \"interfaces <*> dialer-options pool $$\")";
           junos:must-message "Pool not configured in any subordinate interface";
           type string {
             length "1 .. 64";
           }
         }
         leaf-list route {
           ordered-by user;
           description "Route on dialer";
           type jt:ipprefix;
         }
         leaf always-on {
           description "Always keep on-line";
           junos:must "(unique \"interfaces <dl*> unit <*> dialer-options always-on\")";
           junos:must-message "Only one dl logical interface can have always-on configured";
           junos:must "(!((\".. .. family inet  filter dialer\" || (\".. .. family inet6 filter dialer\" || \".. .. family mpls  filter dialer\"))))";
           junos:must-message "A dialer interface cannot have always-on enabled and filter at the same time";
           type empty;
         }
         leaf-list dial-string {
           ordered-by user;
           description "String to dial out";
           type string {
             length "1 .. 63";
           }
           max-elements 15;
         }
         container incoming-map {
           description "Map incoming call to dialer";
           uses apply-advanced;
           choice caller-type {
             case case_1 {
               list caller {
                 key name;
                 ordered-by user;
                 description "Caller Id to be screened";
                 max-elements 300;
                 leaf name {
                   description "Caller ID (upto 15 digits)";
                   type string {
                     junos:posix-pattern "^([0-9]{1,15})$";
                     junos:pattern-message "Can contain up to 15 digits";
                   }
                 }
               }
             }
             case case_2 {
               leaf accept-all {
                 description "Accept all incoming calls";
                 type empty;
               }
             }
           }
         }
         leaf callback {
           description "Call back on any incoming call to the dialer";
           junos:must "(!(\".. watch-list \"))";
           junos:must-message "A dialer interface cannot have callback enabled and watch-list at the same time";
           junos:must "(\".. dial-string\")";
           junos:must-message "Dial string is mandatory for callback";
           junos:must "(\".. incoming-map\")";
           junos:must-message "incoming-map is mandatory for callback";
           type empty;
         }
         leaf callback-wait-period {
           description "Time to wait before calling back";
           units "seconds";
           junos:must "(\".. callback\")";
           junos:must-message "Callback needs to be configured";
           type union {
             type string {
               pattern "<.*>|$.*";
             }
             type uint32 {
               range "2 .. 255";
             }
           }
         }
         leaf redial-delay {
           description "Time to wait before redialing";
           units "seconds";
           type union {
             type string {
               pattern "<.*>|$.*";
             }
             type uint32 {
               range "2 .. 255";
             }
           }
         }
         leaf self-recover-time {
           description "Sub-interface self-recover time";
           units "seconds";
           type union {
             type string {
               pattern "<.*>|$.*";
             }
             type uint32 {
               range "2 .. 120";
             }
           }
         }
         leaf idle-timeout {
           description "Delay before taking down the interface";
           default "120";
           units "seconds";
           junos:must "((\".. .. family inet  filter dialer\" || (\".. .. family inet6 filter dialer\" || \".. .. family mpls  filter dialer\")))";
           junos:must-message "Dialer filter must be configured";
           type union {
             type string {
               pattern "<.*>|$.*";
             }
             type uint32 {
               range "0 .. 4294967295";
             }
           }
         }
         list watch-list {
           key name;
           description "Dialer watch list";
           junos:must "(\".. dial-string\")";
           junos:must-message "dial-string is mandatory for watch-list";
           leaf name {
             description "Address prefix";
             type jt:ipprefix-only;
           }
           uses apply-advanced;
         }
         leaf load-threshold {
           description "Load threshold for adding interfaces";
           junos:must "(\".. .. .. encapsulation multilink-ppp\")";
           junos:must-message "Encapsulation must be multilink-ppp";
           type union {
             type string {
               pattern "<.*>|$.*";
             }
             type uint32 {
               range "0 .. 100";
             }
           }
         }
         leaf load-interval {
           description "Interval used to calculate average load";
           units "seconds";
           junos:must "(\".. .. .. encapsulation multilink-ppp\")";
           junos:must-message "Encapsulation must be multilink-ppp";
           type union {
             type string {
               pattern "<.*>|$.*";
             }
             type uint32 {
               range "20 .. 180";
             }
           }
         }
         leaf activation-delay {
           description "Activation delay";
           units "seconds";
           junos:must "(!((\".. .. family inet  filter dialer\" || (\".. .. family inet6 filter dialer\" || \".. .. family mpls  filter dialer\"))))";
           junos:must-message "Activation delay cannot be configured for dialer filter";
           type union {
             type string {
               pattern "<.*>|$.*";
             }
             type uint32 {
               range "1 .. 4294967295";
             }
           }
         }
         leaf deactivation-delay {
           description "Deactivation delay";
           units "seconds";
           junos:must "(!((\".. .. family inet  filter dialer\" || (\".. .. family inet6 filter dialer\" || \".. .. family mpls  filter dialer\"))))";
           junos:must-message "Deactivation delay cannot be configured for dialer filter";
           type union {
             type string {
               pattern "<.*>|$.*";
             }
             type uint32 {
               range "1 .. 4294967295";
             }
           }
         }
         leaf initial-route-check {
           description "Delay to check primary after the router is up";
           default "120";
           units "seconds";
           junos:must "(\".. watch-list\")";
           junos:must-message "No watch list specified under dialer options";
           type union {
             type string {
               pattern "<.*>|$.*";
             }
             type uint16 {
               range "1 .. 300";
             }
           }
         }
       }
       container backup-options {
         description "Backup interface configuration options";
         uses apply-advanced;
         leaf interface {
           description "Backup interface";
           junos:must "(!(\"interfaces $$-IFL dialer-options always-on\"))";
           junos:must-message "A dialer interface cannot be backup as well as always-on";
           junos:must "(\"interfaces $$-IFL dialer-options dial-string\")";
           junos:must-message "No dial-string configured in backup dialer interface";
           junos:must "(!(\"interfaces $$-IFL dialer-options callback \"))";
           junos:must-message "A dialer interface cannot be backup as well as have callback";
           junos:must "(!((\"interfaces $$-IFL family inet  filter dialer\" || (\"interfaces $$-IFL family inet6 filter dialer\" || \"interfaces $$-IFL family mpls  filter dialer\"))))";
           junos:must-message "A dialer interface cannot be backup as well as have dialer filter";
           junos:must "(!(\"interfaces $$-IFL dialer-options watch-list \"))";
           junos:must-message "A dialer interface cannot be backup as well as have watch list";
           junos:must "(\"interfaces $$-IFL dialer-options\")";
           junos:must-message "No dialer options configured in backup dialer interface";
           type union {
             type jt:interface-name;
             type string {
               pattern "<.*>|$.*";
             }
           }
         }
       }
     }
   }
   grouping advisory_options_type {
     uses apply-advanced;
     leaf upstream-rate {
       description "Recommended upstream shaping rate";
       units "bits per second";
       type string;
     }
     leaf downstream-rate {
       description "Recommended downstream shaping rate";
       units "bits per second";
       type string;
     }
   }
   grouping auto_configure_vlan_type {
     uses apply-advanced;
     container stacked-vlan-ranges {
       presence "enable stacked-vlan-ranges";
       junos:must "((\".. .. stacked-vlan-tagging\" || (\".. .. flexible-vlan-tagging\" || \"system services subscriber-management mode control-plane\")))";
       junos:must-message "Stacked or Flexible VLAN tagging must be configured for interface";
       description "Stacked Vlan Range configuration";
       uses apply-advanced;
       list dynamic-profile {
         key name;
         ordered-by user;
         description "Attach dynamic-profile to ranges";
         max-elements 16;
         leaf name {
           description "Profile name";
           junos:must "((\"dynamic-profiles $$\" || \"system services subscriber-management mode user-plane\"))";
           junos:must-message "Dynamic-profile must be defined in the [edit dynamic-profiles] hierarchy";
           type string;
         }
         uses apply-advanced;
         list accept {
           key name;
           ordered-by user;
           description "Configure accepted packet types";
           uses auto_configure_packet_types;
         }
         list ranges {
           key name;
           ordered-by user;
           description "Configure interface based on stacked-vlan range";
           leaf name {
             description "Stacked-vlan range: [any | <low-tag>-<high-tag>],[any | <low-tag>-<high-tag>]";
             type string {
               junos:posix-pattern "((any|^(([1-9][0-9]{0,2}|[1-3][0-9]{3}|40[0-8][0-9]|409[0-4])-([1-9][0-9]{0,2}|[1-3][0-9]{3}|40[0-8][0-9]|409[0-4]))),(any|(([1-9][0-9]{0,2}|[1-3][0-9]{3}|40[0-8][0-9]|409[0-4])-([1-9][0-9]{0,2}|[1-3][0-9]{3}|40[0-8][0-9]|409[0-4]))))$";
               junos:pattern-message "invalid vlan tag";
             }
           }
           uses apply-advanced;
         }
         container access-profile {
           description "Auto-configure VLAN access profile for these ranges";
           leaf ap-name {
             description "Access profile name";
             junos:must "(\"access profile $$\")";
             junos:must-message "Access-profile must be defined in the [edit access profile] hierarchy";
             type string {
               length "1 .. 64";
             }
           }
         }
       }
       container override {
         presence "enable override";
         description "SVLAN profile override specification ";
         uses apply-advanced;
         list outer-tag {
           key name;
           ordered-by user;
           description "Specify pair of SVLAN tags for profile override";
           max-elements 8;
           leaf name {
             description "Stacked-vlan outer tag range to be overridden";
             type union {
               type string {
                 pattern "<.*>|$.*";
               }
               type uint32 {
                 range "1 .. 4094";
               }
             }
           }
           uses apply-advanced;
           leaf inner-tag {
             description "Stacked-vlan inner tag to be overridden";
             type union {
               type string {
                 pattern "<.*>|$.*";
               }
               type uint32 {
                 range "1 .. 4094";
               }
             }
           }
           leaf dynamic-profile {
             description "Dynamic profile to override with";
             junos:must "((\"dynamic-profiles $$\" || \"system services subscriber-management mode user-plane\"))";
             junos:must-message "Dynamic-profile must be defined in the [edit dynamic-profiles] hierarchy";
             type string;
           }
         }
       }
       container authentication {
         description "Auto-configure stacked VLAN authentication";
         uses auto_configure_authentication_type;
       }
       container access-profile {
         description "Auto-configure stacked VLAN access profile";
         leaf access-profile-name {
           description "Access profile name";
           junos:must "(\"access profile $$\")";
           junos:must-message "Access-profile must be defined in the [edit access profile] hierarchy";
           type string {
             length "1 .. 64";
           }
         }
       }
     }
     container vlan-ranges {
       junos:must "((\".. .. vlan-tagging\" || (\".. .. flexible-vlan-tagging\" || \"system services subscriber-management mode control-plane\")))";
       junos:must-message "Vlan or Flexible VLAN tagging must be configured for interface";
       description "Vlan Range configuration";
       uses apply-advanced;
       list dynamic-profile {
         key name;
         ordered-by user;
         description "Attach dynamic-profile to ranges";
         max-elements 16;
         leaf name {
           description "Profile name";
           junos:must "((\"dynamic-profiles $$\" || \"system services subscriber-management mode user-plane\"))";
           junos:must-message "Dynamic-profile must be defined in the [edit dynamic-profiles] hierarchy";
           type string;
         }
         uses apply-advanced;
         choice accept_type {
           case case_1 {
             list accept {
               key name;
               ordered-by user;
               description "Configure accepted packet types";
               uses auto_configure_packet_types;
             }
           }
           case case_2 {
             list accept-out-of-band {
               key name;
               ordered-by user;
               description "Configure accepted out-of-band packet types";
               uses auto_configure_oob_packet_types;
             }
           }
         }
         list ranges {
           key name;
           ordered-by user;
           description "Configure interface based on vlan range";
           leaf name {
             description "Vlan range: [any | <low-tag>-<high-tag>]";
             type string {
               junos:posix-pattern "any|^(([1-9][0-9]{0,2}|[1-3][0-9]{3}|40[0-8][0-9]|409[0-4])-([1-9][0-9]{0,2}|[1-3][0-9]{3}|40[0-8][0-9]|409[0-4]))$";
               junos:pattern-message "invalid vlan tag";
             }
           }
           uses apply-advanced;
         }
         container access-profile {
           description "Auto-configure VLAN access profile for these ranges";
           leaf ap-name {
             description "Access profile name";
             junos:must "(\"access profile $$\")";
             junos:must-message "Access-profile must be defined in the [edit access profile] hierarchy";
             type string {
               length "1 .. 64";
             }
           }
         }
       }
       container override {
         presence "enable override";
         description "VLAN profile override specification";
         uses apply-advanced;
         list tag {
           key name;
           ordered-by user;
           description "Specify VLAN tag for profile override";
           max-elements 8;
           leaf name {
             description "Vlan tag to be overridden";
             type union {
               type string {
                 pattern "<.*>|$.*";
               }
               type uint32 {
                 range "1 .. 4094";
               }
             }
           }
           uses apply-advanced;
           leaf dynamic-profile {
             description "Dynamic profile to override with";
             junos:must "((\"dynamic-profiles $$\" || \"system services subscriber-management mode user-plane\"))";
             junos:must-message "Dynamic-profile must be defined in the [edit dynamic-profiles] hierarchy";
             type string;
           }
         }
       }
       container authentication {
         description "Auto-configure VLAN authentication";
         uses auto_configure_authentication_type;
       }
       container access-profile {
         description "Auto-configure VLAN access profile";
         leaf access-profile-name {
           description "Access profile name";
           junos:must "(\"access profile $$\")";
           junos:must-message "Access-profile must be defined in the [edit access profile] hierarchy";
           type string {
             length "1 .. 64";
           }
         }
       }
     }
     container agent-circuit-identifier {
       description "ACI configuration";
       uses apply-advanced;
       leaf dynamic-profile {
         description "Dynamic profile name";
         junos:must "((\"dynamic-profiles $$\" || \"system services subscriber-management mode user-plane\"))";
         junos:must-message "referenced dynamic-profile must be defined";
         type string {
           length "1 .. 64";
         }
       }
     }
     container line-identity {
       description "Line-identity configuration";
       uses apply-advanced;
       container includes {
         presence "enable includes";
         description "Agent options configuration";
         uses apply-advanced;
         leaf circuit-id {
           description "Agent Circit id";
           type empty;
         }
         leaf remote-id {
           description "Agent Remote id";
           type empty;
         }
         container accept-no-ids {
           presence "enable accept-no-ids";
           description "Accept packet with no agent options";
           uses apply-advanced;
         }
       }
       leaf dynamic-profile {
         description "Dynamic profile name";
         junos:must "(\".. includes\")";
         junos:must-message "includes must be configured";
         junos:must "((\"dynamic-profiles $$\" || \"system services subscriber-management mode user-plane\"))";
         junos:must-message "referenced dynamic-profile must be defined";
         type string {
           length "1 .. 64";
         }
       }
     }
     leaf remove-when-no-subscribers {
       description "Requests auto-deletion of interface when not in use by subscribers";
       type empty;
     }
   }
   grouping auto_configure_authentication_type {
     description "Autoconf VLAN authentication";
     uses apply-advanced;
     list packet-types {
       key name;
       ordered-by user;
       description "Configure accepted packet types for authentication";
       uses auto_configure_packet_types;
     }
     leaf password {
       description "Username password";
       type string {
         length "1 .. 64";
       }
     }
     container username-include {
       description "Username options";
       uses apply-advanced;
       leaf delimiter {
         description "Delimiter/separator character";
         type string {
           length 1;
         }
       }
       leaf domain-name {
         description "Domain name";
         type string {
           length "1 .. 64";
         }
       }
       leaf user-prefix {
         description "User defined prefix";
         type string {
           length "1 .. 64";
         }
       }
       leaf mac-address {
         description "Include MAC address";
         junos:must "(any \".. .. .. dynamic-profile <*> accept $$={dhcp-v4}\")";
         junos:must-message "The dynamic-profile must be configured to accept dhcp-v4 only";
         type empty;
       }
       container option-82 {
         presence "enable option-82";
         description "Include option 82";
         leaf circuit-id {
           description "Include option 82 circuit-id (sub option 1)";
           type empty;
         }
         leaf remote-id {
           description "Include option 82 remote-id (sub option 2)";
           type empty;
         }
       }
       leaf option-18 {
         description "Include option 18 for dhcp-v6";
         type empty;
       }
       leaf option-37 {
         description "Include option 37 for dhcp-v6";
         type empty;
       }
       leaf circuit-type {
         description "Include circuit type";
         type empty;
       }
       leaf radius-realm {
         description "Include Radius realm name";
         type string {
           length "1 .. 64";
         }
       }
       leaf interface-name {
         description "Include interface name";
         type empty;
       }
       leaf vlan-tags {
         description "Include vlan tag(s)";
         type empty;
       }
     }
   }
   grouping auto_configure_oob_packet_types {
     leaf name {
       type enumeration {
         enum "ancp" {
           description "ANCP";
         }
       }
     }
   }
   grouping auto_configure_packet_types {
     leaf name {
       type enumeration {
         enum "inet" {
           description "Family inet";
         }
         enum "inet6" {
           description "Family inet6";
         }
         enum "pppoe" {
           description "PPPoE PADI only";
         }
         enum "dhcp-v4" {
           description "DHCP v4 Discover only";
         }
         enum "dhcp-v6" {
           description "DHCP v6 Solicit only";
         }
         enum "any" {
           description "Any in-band packet type";
         }
       }
     }
   }
   grouping dcd_shaping_config {
     description "Traffic-shaping profile";
     uses apply-advanced;
     choice useless_shaping_choice {
       case case_1 {
         container cbr {
           presence "enable cbr";
           description "Constant bandwidth utilization";
           leaf cbr-value {
             description "Constant bandwidth utilization";
             type string;
           }
           leaf cdvt {
             description "Cell Delay Variation Tolerance";
             units "microseconds";
             type union {
               type string {
                 pattern "<.*>|$.*";
               }
               type uint32 {
                 range "1 .. 9999";
               }
             }
           }
         }
       }
       case case_2 {
         container vbr {
           description "Variable bandwidth utilization";
           leaf peak {
             description "Peak rate";
             type string;
           }
           leaf sustained {
             description "Sustained rate";
             type string;
           }
           leaf burst {
             description "Burst size";
             type string;
           }
           leaf cdvt {
             description "Cell Delay Variation Tolerance";
             units "microseconds";
             type union {
               type string {
                 pattern "<.*>|$.*";
               }
               type uint32 {
                 range "1 .. 9999";
               }
             }
           }
         }
       }
       case case_3 {
         container rtvbr {
           description "ATM2 real-time variable bandwidth utilization";
           leaf peak {
             description "Peak rate";
             type string;
           }
           leaf sustained {
             description "Sustained rate";
             type string;
           }
           leaf burst {
             description "Burst size";
             type string;
           }
           leaf cdvt {
             description "Cell Delay Variation Tolerance";
             units "microseconds";
             type union {
               type string {
                 pattern "<.*>|$.*";
               }
               type uint32 {
                 range "1 .. 9999";
               }
             }
           }
         }
       }
     }
     leaf queue-length {
       description "Queue length";
       type union {
         type string {
           pattern "<.*>|$.*";
         }
         type uint32 {
           range "1 .. 16383";
         }
       }
     }
   }
   grouping demux_options_table {
     leaf name {
       type enumeration {
         enum "inet" {
           description "Family inet";
         }
         enum "inet6" {
           description "Family inet6";
         }
       }
     }
   }
   grouping demux_options_type {
     uses apply-advanced;
     leaf underlying-interface {
       description "Underlying interface name";
       type string;
     }
   }
   grouping dhcp-client-type {
     description "Dynamic Host Configuration Protocol client configuration";
     uses apply-advanced;
     container client-identifier {
       description "DHCP server identifies a client by client-identifier value ";
       uses apply-advanced;
       choice client-identifier-choice {
         case case_1 {
           leaf ascii {
             description "Client identifier as an ASCII string";
             type string;
           }
         }
         case case_2 {
           leaf hexadecimal {
             description "Client identifier as a hexadecimal string";
             type string {
               junos:posix-pattern "^[[:xdigit:]]+$";
               junos:pattern-message "Must be hexadecimal digits (0-9, a-f, A-F)";
             }
           }
         }
       }
       container user-id {
         description "Add user id to client-id option ";
         choice user-id-choice {
           case case_1 {
             leaf ascii {
               description "Client identifier as an ASCII string";
               type string;
             }
           }
           case case_2 {
             leaf hexadecimal {
               description "Client identifier as a hexadecimal string";
               type string {
                 junos:posix-pattern "^[[:xdigit:]]+$";
                 junos:pattern-message "Must be hexadecimal digits (0-9, a-f, A-F)";
               }
             }
           }
         }
       }
       container prefix {
         description "Add prefix to client-id option";
         uses apply-advanced;
         leaf host-name {
           description "Add router host name to client-id option";
           type empty;
         }
         leaf logical-system-name {
           description "Add logical system name to client-id option";
           type empty;
         }
         leaf routing-instance-name {
           description "Add routing instance name to client-id option";
           type empty;
         }
       }
       leaf use-interface-description {
         description "Use the interface description";
         type enumeration {
           enum "logical" {
             description "Use the logical interface description";
           }
           enum "device" {
             description "Use the device interface description";
           }
         }
       }
       leaf hardware-type {
         description "Hardware type";
         default "0";
         type union {
           type string {
             pattern "<.*>|$.*";
           }
           type uint8 {
             range "0 .. 255";
           }
         }
       }
     }
     container no-dns-install {
       presence "enable no-dns-install";
       description "Do not install DNS information learned from DHCP server";
     }
     leaf lease-time {
       description "Lease time in seconds requested in DHCP client protocol packet";
       units "seconds";
       type string;
     }
     leaf retransmission-attempt {
       description "Number of attempts to retransmit the DHCP client protocol packet";
       default "4";
       type union {
         type string {
           pattern "<.*>|$.*";
         }
         type uint32 {
           range "0 .. 50000";
         }
       }
     }
     leaf retransmission-interval {
       description "Number of seconds between successive retransmission";
       default "4";
       units "seconds";
       type union {
         type string {
           pattern "<.*>|$.*";
         }
         type uint32 {
           range "4 .. 64";
         }
       }
     }
     leaf metric {
       description "Client initiated default-route metric";
       default "0";
       type union {
         type string {
           pattern "<.*>|$.*";
         }
         type uint32 {
           range "0 .. 255";
         }
       }
     }
     leaf server-address {
       description "DHCP Server-address";
       type jt:ipv4addr;
     }
     leaf update-server {
       description "Propagate TCP/IP settings to DHCP server";
       type empty;
     }
     leaf vendor-id {
       description "Vendor class id for the DHCP Client";
       type string {
         length "1 .. 60";
       }
     }
     leaf force-discover {
       description "Send DHCPDISCOVER after DHCPREQUEST retransmission failure";
       type empty;
     }
     container options {
       description "DHCP options";
       uses apply-advanced;
       list number {
         key name;
         description "DHCP option code";
         leaf name {
           description "DHCP option identifier code";
           type union {
             type string {
               pattern "<.*>|$.*";
             }
             type uint32 {
               range "1 .. 254";
             }
           }
         }
         choice option-type-choice {
           case case_1 {
             leaf hex-string {
               description "Hexadecimal string";
               type string {
                 length "1 .. 510";
                 junos:posix-pattern "^[[:xdigit:]]+$";
                 junos:pattern-message "Must be hexadecimal digits (0-9, a-f, A-F)";
               }
             }
           }
         }
       }
       leaf no-hostname {
         description "Do not carry hostname (RFC option code is 12) in packet";
         type empty;
       }
     }
     list requested-options {
       key name;
       description "DHCP options";
       leaf name {
         description "DHCP option identifier code";
         type union {
           type string {
             pattern "<.*>|$.*";
           }
           type uint32 {
             range "1 .. 254";
           }
         }
       }
     }
   }
   grouping dynamic_ifbw_parms_type {
     uses apply-advanced;
     leaf capacity {
       description "Weight of current (vs. maximum) data rate";
       status deprecated;
       units "percent";
       type union {
         type string {
           pattern "<.*>|$.*";
         }
         type uint32 {
           range "0 .. 100";
         }
       }
     }
     leaf margin {
       description "Maximum reduction in bandwidth due to low link quality";
       status deprecated;
       units "percent";
       type union {
         type string {
           pattern "<.*>|$.*";
         }
         type uint32 {
           range "0 .. 100";
         }
       }
     }
     leaf delay {
       description "Bandwidth reduction when delay is announced as 1 second";
       status deprecated;
       units "bits per second";
       type string;
     }
     leaf bandwidth {
       description "Weight of current (vs. maximum) data rate";
       type union {
         type string {
           pattern "<.*>|$.*";
         }
         type uint32 {
           range "0 .. 100";
         }
       }
     }
     leaf resource {
       description "Resource weight";
       type union {
         type string {
           pattern "<.*>|$.*";
         }
         type uint32 {
           range "0 .. 100";
         }
       }
     }
     leaf latency {
       description "Latency weight";
       type union {
         type string {
           pattern "<.*>|$.*";
         }
         type uint32 {
           range "0 .. 100";
         }
       }
     }
     leaf quality {
       description "Relative Link Quality weight";
       type union {
         type string {
           pattern "<.*>|$.*";
         }
         type uint32 {
           range "0 .. 100";
         }
       }
     }
     leaf data-rate {
       description "Data rate weight";
       type union {
         type string {
           pattern "<.*>|$.*";
         }
         type uint32 {
           range "0 .. 100";
         }
       }
     }
     leaf threshold {
       description "Percentage bandwidth change required for routing updates";
       units "percent";
       type union {
         type string {
           pattern "<.*>|$.*";
         }
         type uint32 {
           range "0 .. 100";
         }
       }
     }
     container credit {
       presence "enable credit";
       description "Credit-based scheduling parameters";
       uses apply-advanced;
       leaf interval {
         description "Grant rate interval in 100mS steps";
         type union {
           type string {
             pattern "<.*>|$.*";
           }
           type uint16 {
             range "1 .. 60";
           }
         }
       }
     }
   }
   grouping dynamic_ipv4_type {
     description "Packet triggered subscribers";
     uses apply-advanced;
     container address-ranges {
       description "Packet triggered subscribers configuration";
       uses apply-advanced;
       list dynamic-profile {
         key name;
         ordered-by user;
         description "Attach dynamic-profile to packet triggered subscriber ranges";
         max-elements 16;
         leaf name {
           description "Profile name";
           junos:must "(\"dynamic-profiles $$\")";
           junos:must-message "Dynamic-profile must be defined in the [edit dynamic-profiles] hierarchy";
           type string;
         }
         uses apply-advanced;
         list network {
           key name;
           ordered-by user;
           description "IPv4 Network address";
           max-elements 16;
           leaf name {
             description "Specify the network address";
             type jt:ipv4prefix;
           }
           uses apply-advanced;
           list range {
             key name;
             ordered-by user;
             description "Configure demux interface based on source IP address range";
             max-elements 16;
             leaf name {
               description "Name of range";
               type string;
             }
             uses apply-advanced;
             leaf low {
               description "Lower limit of address range";
               type jt:ipv4prefix;
             }
             leaf high {
               description "Upper limit of address range";
               type jt:ipv4prefix;
             }
           }
         }
       }
       container authentication {
         description "Auto-configure packet triggered subscriber authentication";
         uses dynamic_ip_authentication_type;
       }
     }
   }
   grouping dynamic_ip_authentication_type {
     description "Autoconf packet trigger subscriber authentication";
     uses apply-advanced;
     leaf password {
       description "Username password";
       type string {
         length "1 .. 64";
       }
     }
     container username-include {
       description "Username options";
       uses apply-advanced;
       leaf delimiter {
         description "Delimiter/separator character";
         type string {
           length 1;
         }
       }
       leaf domain-name {
         description "Domain name";
         type string {
           length "1 .. 64";
         }
       }
       leaf user-prefix {
         description "User defined prefix";
         type string {
           length "1 .. 64";
         }
       }
       leaf auth-server-realm {
         description "Authentication server realm name";
         type string {
           length "1 .. 64";
         }
       }
       leaf interface-name {
         description "Interface name";
         type empty;
       }
       leaf source-address {
         description "Source address";
         type empty;
       }
     }
   }
   grouping dynamic_ipv6_type {
     description "Packet triggered subscribers";
     uses apply-advanced;
     container prefix-ranges {
       description "Packet triggered subscribers configuration";
       uses apply-advanced;
       list dynamic-profile {
         key name;
         ordered-by user;
         description "Attach dynamic-profile to packet triggered subscriber ranges";
         max-elements 16;
         leaf name {
           description "Profile name";
           junos:must "(\"dynamic-profiles $$\")";
           junos:must-message "Dynamic-profile must be defined in the [edit dynamic-profiles] hierarchy";
           type string;
         }
         uses apply-advanced;
         list prefix {
           key name;
           ordered-by user;
           description "IPv6 Network prefix ";
           max-elements 16;
           leaf name {
             description "Specify the network prefix";
             type jt:ipv6prefix;
           }
           uses apply-advanced;
           list range {
             key name;
             ordered-by user;
             description "Configure demux interface based on source IP address range";
             max-elements 16;
             leaf name {
               description "Name of range";
               type string;
             }
             uses apply-advanced;
             leaf low {
               description "Lower limit of prefix range";
               type jt:ipv6prefix;
             }
             leaf high {
               description "Upper limit of prefix range";
               type jt:ipv6prefix;
             }
           }
         }
       }
       container authentication {
         description "Auto-configure packet triggered subscriber authentication";
         uses dynamic_ip_authentication_type;
       }
     }
   }
   grouping epd_threshold_config {
     uses apply-advanced;
     leaf epd-threshold-plp0 {
       description "Early packet discard threshold value";
       units "cells";
       type string;
     }
     leaf plp1 {
       description "Early packet drop threshold value for PLP 1";
       units "cells";
       type string;
     }
   }
   grouping ethernet-switching-type {
     description "Ethernet switching family";
     uses apply-advanced;
     leaf port-mode {
       description "Type of port mode";
       type enumeration {
         enum "access" {
           description "Interface mode is access";
         }
         enum "tagged-access" {
           description "Interface mode is tagged-access";
         }
         enum "trunk" {
           description "Interface mode is trunk";
         }
       }
     }
     leaf interface-mode {
       description "Type of interface mode";
       default "access";
       type enumeration {
         enum "access" {
           description "Interface mode is access";
           junos:must "((!(\"interfaces ${interface} vlan-tagging\") && (!(\"interfaces ${interface} flexible-vlan-tagging\") && (!(\"interfaces ${interface} stacked-vlan-tagging\") && !(\"interfaces ${interface} encapsulation extended-vlan-bridge\")))))";
           junos:must-message "interface-mode access is allowed only for untagged interfaces, also not allowed with flexible-vlan-tagging and extended-vlan-bridge";
         }
         enum "trunk" {
           description "Interface mode is trunk";
           junos:must "((!((\"protocols dot1x authenticator interface ${interface}.${unit}\" || \"protocols dot1x supplicant interface ${interface}.${unit}\")) || (\"interfaces ${interface} native-vlan-id\" && !(\"interfaces ${interface} flexible-vlan-tagging\"))))";
           junos:must-message "Must configure native-vlan-id but no flexible-vlan-tagging for dot1x enabled port";
           junos:must "(!(\"interfaces ${interface} encapsulation extended-vlan-bridge\"))";
           junos:must-message "interface-mode is not allowed for extended-vlan-bridge";
         }
       }
     }
     leaf inter-switch-link {
       description "PVLAN inter switch link";
       junos:must "(\".. interface-mode trunk\")";
       junos:must-message "'Inter switch link' is supported only under trunk interface mode";
       type empty;
     }
     leaf reflective-relay {
       description "Reflective-relay mode for this interface";
       junos:must "(\".. port-mode tagged-access\")";
       junos:must-message "Reflective relay is supported only on tagged-access port";
       type empty;
     }
     choice vlan_choice_list {
       case case_1 {
         container vlan {
           description "Virtual LAN parameters";
           uses apply-advanced;
           leaf-list members {
             ordered-by user;
             description "Membership for this interface (name or id)";
             type string;
           }
         }
       }
       case case_2 {
         container inner-vlan {
           description "Trunk mode vlan membership for this interface";
           uses apply-advanced;
           leaf-list members {
             ordered-by user;
             description "Membership for this interface (name or id)";
             type string;
           }
         }
       }
       case case_3 {
         leaf-list inner-vlan-id-list {
           description "Trunk mode VLAN membership for this interface based on inner VLAN tag";
           junos:must "((!(\".. .. .. vlan-tags inner\") && !(\".. .. .. vlan-tags inner-range\")))";
           junos:must-message "'inner-vlan-id-list' cannot be used on interface with vlan-tags inner or inner-range configured";
           junos:must "((\".. .. .. vlan-id\" || \".. .. .. vlan-tags\"))";
           junos:must-message "'inner-vlan-id-list' can be used only on interface with vlan-id/vlan-tags";
           junos:must "(\"interfaces ${interface} flexible-vlan-tagging\")";
           junos:must-message "'inner-vlan-id-list' is supported only on flexible-vlan-tagging mode";
           junos:must "(\".. interface-mode trunk\")";
           junos:must-message "'inner-vlan-id-list' statement supported only under trunk interface mode";
           type jt:vlan-range;
         }
       }
     }
     leaf vlan-auto-sense {
       description "Enable VLAN auto sense on this interface";
       junos:must "(\".. interface-mode trunk\")";
       junos:must-message "vlan-auto-sense can be enabled only on trunk ports";
       type empty;
     }
     leaf bridge-domain-type {
       description "Bridge domain type";
       type enumeration {
         enum "svlan" {
           description "Bridge domain type SVLAN";
           junos:must "(\".. isid-list all-service-groups\")";
           junos:must-message "bridge-domain-type SVLAN is allowed only for ISID tagged interfaces";
           junos:must "(\".. interface-mode trunk\")";
           junos:must-message "bridge-domain-type SVLAN is allowed only for trunk interfaces";
         }
         enum "bvlan" {
           description "Bridge domain type BVLAN";
           junos:must "(\".. isid-list all\")";
           junos:must-message "bridge-domain-type BVLAN is allowed only for ISID tagged interfaces";
           junos:must "(\".. interface-mode trunk\")";
           junos:must-message "bridge-domain-type BVLAN is allowed only for trunk interfaces";
         }
       }
     }
     container vlan-rewrite {
       junos:must "((\".. inner-vlan-id-list\" || \".. vlan members\"))";
       junos:must-message "'vlan-rewrite' statement can be used only with 'vlan members' or inner-vlan-id-list configured";
       junos:must "(\".. interface-mode trunk\")";
       junos:must-message "'vlan-rewrite' statement supported only under trunk interface mode";
       description "Specify VLAN translation";
       uses apply-advanced;
       list translate {
         key name;
         ordered-by user;
         description "Translate incoming VLAN tag";
         leaf name {
           description "Specify the incoming VLAN tag";
           type union {
             type string {
               pattern "<.*>|$.*";
             }
             type uint32 {
               range "1 .. 4094";
             }
           }
         }
         leaf to-vlan-id {
           description "Specify the bridge-domain VLAN-ID";
           type union {
             type string {
               pattern "<.*>|$.*";
             }
             type uint32 {
               range "1 .. 4094";
             }
           }
         }
       }
     }
     leaf native-vlan-id {
       description "Untagged packets on a trunk/tagged-access interface belong to this vlan";
       type string {
       }
     }
     choice isid_list {
       case case_1 {
         leaf isid-list {
           description "Specify the ISID list";
           type enumeration {
             enum "all-service-groups" {
               description "Map all ISIDs specified under the service-groups";
               junos:must "(\".. interface-mode trunk\")";
               junos:must-message "'all-service-groups' statement supported only under trunk interface mode";
             }
             enum "all" {
               description "Map all ISIDs";
               junos:must "(\".. interface-mode trunk\")";
               junos:must-message "'all' statement supported only under trunk interface mode";
             }
           }
         }
       }
     }
     leaf core-facing {
       description "Interface is core facing";
       type empty;
     }
     container filter {
       description "Packet filtering";
       uses apply-advanced;
       leaf input {
         description "Name of filter applied to received packets";
         type string;
       }
       leaf input-precedence {
         description "Precedence of the filter";
         type union {
           type string {
             pattern "<.*>|$.*";
           }
           type uint32 {
             range "0 .. 255";
           }
         }
       }
       leaf-list input-list {
         ordered-by user;
         description "List of filter modules applied to received packets ";
         type string;
       }
       leaf output {
         description "Name of filter applied to transmitted packets";
         type string;
       }
       leaf output-precedence {
         description "Precedence of the filter";
         type union {
           type string {
             pattern "<.*>|$.*";
           }
           type uint32 {
             range "0 .. 255";
           }
         }
       }
       leaf-list output-list {
         ordered-by user;
         description "List of filter modules applied to transmitted packets ";
         type string;
       }
       leaf-list input-chain {
         ordered-by user;
         description "List of filter modules applied to received packets ";
         type string;
       }
       leaf-list output-chain {
         ordered-by user;
         description "List of filter modules applied to transmitted packets ";
         type string;
       }
       container adf {
         description "Ascend Data Filter definition";
         uses apply-advanced;
         list rule {
           key name;
           ordered-by user;
           description "Set of ADF rules";
           leaf name {
             description "Value for a single rule";
             type string;
           }
           uses apply-advanced;
         }
         leaf counter {
           description "Add a counter to each rule";
           type empty;
         }
         leaf input-precedence {
           description "Precedence of the input rules";
           type union {
             type string {
               pattern "<.*>|$.*";
             }
             type uint32 {
               range "0 .. 255";
             }
           }
         }
         leaf not-mandatory {
           description "No errors will be reported if no rules are present";
           type empty;
         }
         leaf output-precedence {
           description "Precedence of the output rules";
           type union {
             type string {
               pattern "<.*>|$.*";
             }
             type uint32 {
               range "0 .. 255";
             }
           }
         }
       }
       leaf group {
         description "Group to which interface belongs";
         type union {
           type string {
             pattern "<.*>|$.*";
           }
           type uint32 {
             range "1 .. 255";
           }
         }
       }
     }
     container policer {
       description "Interface policing";
       uses apply-advanced;
       leaf input {
         description "Name of policer applied to received packets";
         type string;
       }
       leaf output {
         description "Name of policer applied to transmitted packets";
         type string;
       }
     }
     container storm-control {
       description "Storm control profile name to bind";
       uses apply-advanced;
       leaf profile-name {
         description "Profile name";
         junos:must "(\"forwarding-options storm-control-profiles $$\")";
         junos:must-message "Storm profile name must be defined in the [edit forwarding-options storm-control-profiles] hierarchy";
         type string;
       }
     }
     container recovery-timeout {
       description "Recovery timeout for this interface";
       leaf time-in-seconds {
         units "seconds";
         type union {
           type string {
             pattern "<.*>|$.*";
           }
           type uint32 {
             range "10 .. 3600";
           }
         }
       }
     }
   }
   grouping fibre-channel-type {
     description "Fibre Channel switching family";
     uses apply-advanced;
     leaf port-mode {
       description "Port mode";
       type enumeration {
         enum "f-port" {
           description "Fabric port";
         }
         enum "e-port" {
           description "Inter-switch port";
         }
         enum "np-port" {
           description "Proxy node port";
         }
         enum "auto" {
           description "Interface mode (F/E) is determined at runtime";
         }
       }
     }
     leaf no-npiv {
       description "Disable NPIV";
       junos:must "((\".. port-mode f-port\" || (\".. port-mode auto\" || !(\".. port-mode\"))))";
       junos:must-message "Interface must be f-port or auto to disable NPIV";
       type empty;
     }
     container fc-fabric {
       description "Virtual fabric parameters";
       uses apply-advanced;
       leaf-list members {
         ordered-by user;
         description "Virtual Fabric Membership for this interface (name or id)";
         type string;
       }
     }
     leaf native-fabric {
       description "FC frames with no virtual fabric header on a interface belong to this fabric";
       type string {
         junos:posix-pattern "^([[:alpha:]][[:alnum:]_.-]+)|^([1-9][0-9]{0,2}|[1-3][0-9]{3}|40[0-8][0-9]|409[0-4])$";
         junos:pattern-message "Must be a valid FC fabric name or ID";
       }
     }
   }
   grouping keepalives_type {
     uses apply-advanced;
     leaf interval {
       description "Keepalive period";
       units "seconds";
       type union {
         type string {
           pattern "<.*>|$.*";
         }
         type uint16 {
           range "1 .. 32767";
         }
       }
     }
     leaf up-count {
       description "Keepalive received to bring link up";
       type union {
         type string {
           pattern "<.*>|$.*";
         }
         type uint16 {
           range "1 .. 255";
         }
       }
     }
     leaf down-count {
       description "Keepalive missed to bring link down";
       type union {
         type string {
           pattern "<.*>|$.*";
         }
         type uint16 {
           range "1 .. 255";
         }
       }
     }
   }
   grouping mac_list {
     description "MAC address";
     leaf name {
       type jt:mac-addr;
     }
     uses apply-advanced;
     container policer {
       description "MAC policing";
       uses apply-advanced;
       leaf input {
         description "Name of policer applied to received packets";
         type string;
       }
       leaf output {
         description "Name of policer applied to transmitted packets";
         type string;
       }
     }
   }
   grouping multi-chassis-protection-group-ifl {
     leaf name {
       description "IP address for this peer";
       junos:must "((\"protocols iccp peer $$\" || any \"logical-systems <*> protocols iccp peer $$\"))";
       junos:must-message "The peer ip must match with ones defined at <protocols iccp peer>";
       junos:must "(\".. .. .. .. .. protocols iccp peer $$\")";
       junos:must-message "iccp peer ip address does not match with the one configured under protocols iccp";
       type jt:ipv4addr;
     }
     uses apply-advanced;
     leaf interface {
       description "Inter-Chassis protection link";
       junos:must "(((((!(any \"logical-systems <*> routing-instances <*> protocols rstp interface $$\") && !(any \"logical-systems <*> routing-instances <*> protocols rstp interface all\")) || any \"logical-systems <*> routing-instances <*> protocols rstp interface $$ disable\") && ((((!(any \"logical-systems <*> routing-instances <*> protocols vstp interface $$\") && !(any \"logical-systems <*> routing-instances <*> protocols vstp interface all\")) && (!(any \"logical-systems <*> routing-instances <*> protocols vstp vlan all interface all\") && (!(any \"logical-systems <*> routing-instances <*> protocols vstp vlan <*> interface $$\") && !(any \"logical-systems <*> routing-instances <*> protocols vstp vlan <*> interface all\")))) || any \"logical-systems <*> routing-instances <*> protocols vstp interface $$ disable\") && ((!(any \"logical-systems <*> routing-instances <*> protocols mstp interface $$\") && !(any \"logical-systems <*> routing-instances <*> protocols mstp interface all\")) || any \"logical-systems <*> routing-instances <*> protocols mstp interface $$ disable\"))) && (((!(any \"logical-systems <*> protocols rstp interface $$\") && !(any \"logical-systems <*> protocols rstp interface all\")) || any \"logical-systems <*> protocols rstp interface $$ disable\") && ((((!(any \"logical-systems <*> protocols vstp interface $$\") && !(any \"logical-systems <*> protocols vstp interface all\")) && (!(any \"logical-systems <*> protocols vstp vlan all interface all\") && (!(any \"logical-systems <*> protocols vstp vlan <*> interface $$\") && !(any \"logical-systems <*> protocols vstp vlan <*> interface all\")))) || any \"logical-systems <*> protocols vstp interface $$ disable\") && ((!(any \"logical-systems <*> protocols mstp interface $$\") && !(any \"logical-systems <*> protocols mstp interface all\")) || any \"logical-systems <*> protocols mstp interface $$ disable\")))))";
       junos:must-message "Inter-Chasis link interface cannot be an STP interface. Please disable xstp on this interface";
       junos:must "(((((!(any \"routing-instances <*> protocols rstp interface $$\") && !(any \"routing-instances <*> protocols rstp interface all\")) || any \"routing-instances <*> protocols rstp interface $$ disable\") && ((((!(any \"routing-instances <*> protocols vstp interface $$\") && !(any \"routing-instances <*> protocols vstp interface all\")) && (!(any \"routing-instances <*> protocols vstp vlan all interface all\") && (!(any \"routing-instances <*> protocols vstp vlan <*> interface $$\") && !(any \"routing-instances <*> protocols vstp vlan <*> interface all\")))) || any \"routing-instances <*> protocols vstp interface $$ disable\") && ((!(any \"routing-instances <*> protocols mstp interface $$\") && !(any \"routing-instances <*> protocols mstp interface all\")) || any \"routing-instances <*> protocols mstp interface $$ disable\"))) && (((!(\"protocols rstp interface $$\") && !(\"protocols rstp interface all\")) || \"protocols rstp interface $$ disable\") && ((((!(\"protocols vstp interface $$\") && !(\"protocols vstp interface all\")) && (!(\"protocols vstp vlan all interface all\") && (!(any \"protocols vstp vlan <*> interface $$\") && !(any \"protocols vstp vlan <*> interface all\")))) || \"protocols vstp interface $$ disable\") && ((!(\"protocols mstp interface $$\") && !(\"protocols mstp interface all\")) || \"protocols mstp interface $$ disable\")))))";
       junos:must-message "Inter-Chasis link interface cannot be an STP interface. Please disable xstp on this interface";
       type string {
         length "1 .. 40";
         junos:posix-pattern "^((ge-)|(mge-)|(xe-)|(ae)|(xle-)|(et-)|(sxe-))";
         junos:pattern-message "Only ae, ge, mge, xe, xle, sxe and et inteface is supported";
       }
     }
     leaf icl-down-delay {
       description "Time in seconds between ICL down and MCAEs moving to standby";
       default "1";
       units "seconds";
       type union {
         type string {
           pattern "<.*>|$.*";
         }
         type int32 {
           range "1 .. 6000";
         }
       }
     }
   }
   grouping ppp_options_type {
     uses apply-advanced;
     leaf dynamic-profile {
       description "Dynamic profile name";
       junos:must "(\"dynamic-profiles $$\")";
       junos:must-message "referenced dynamic-profile must be defined";
       junos:must "(any \".. .. .. unit <*>\")";
       junos:must-message "dynamic-profile statement can be configured only on logical interfaces";
       type string;
     }
     container chap {
       presence "enable chap";
       description "Challenge Handshake Authentication Protocol options";
       uses apply-advanced;
       choice access-data {
         case case_1 {
           leaf access-profile {
             description "Profile containing client list and access parameters";
             junos:must "(\"access profile $$\")";
             junos:must-message "referenced access profile must be defined";
             type string {
               length "1 .. 63";
             }
           }
         }
         case case_2 {
           leaf default-chap-secret {
             description "Default CHAP secret to be used when no matching access profile exists";
             type jt:unreadable;
           }
         }
       }
       leaf local-name {
         description "Name sent in CHAP-Challenge and CHAP-Response";
         type string;
       }
       leaf no-rfc2486 {
         description "RFC2486 compliance is not enforced";
         type empty;
       }
       leaf passive {
         description "Handle incoming CHAP requests only";
         type empty;
       }
       container challenge-length {
         description "CHAP challenge length";
         leaf minimum {
           description "Minimum CHAP challenge length";
           default "16";
           units "bytes";
           type union {
             type string {
               pattern "<.*>|$.*";
             }
             type uint8 {
               range "8 .. 63";
             }
           }
         }
         leaf maximum {
           description "Maximum CHAP challenge length";
           default "32";
           units "bytes";
           type union {
             type string {
               pattern "<.*>|$.*";
             }
             type uint8 {
               range "8 .. 63";
             }
           }
         }
       }
     }
     container pap {
       presence "enable pap";
       description "Password Authentication Protocol options";
       uses apply-advanced;
       choice access-data {
         case case_1 {
           leaf access-profile {
             description "Profile containing client list and access parameters";
             junos:must "(\"access profile $$\")";
             junos:must-message "referenced access profile must be defined";
             type string {
               length "1 .. 63";
             }
           }
         }
         case case_2 {
           leaf default-password {
             description "Default PAP password used in the absence of matching profile";
             type jt:unreadable;
           }
         }
       }
       leaf local-name {
         description "Name sent in PAP request packet";
         type string;
       }
       leaf no-rfc2486 {
         description "RFC2486 compliance is not enforced";
         type empty;
       }
       leaf local-password {
         description "Password sent in PAP request packet";
         type jt:unreadable;
       }
       leaf passive {
         description "Do not handle PAP authentication requests";
         junos:must "(\".. local-password\")";
         junos:must-message "local-password MUST be set if passive is used with PAP";
         type empty;
       }
     }
     leaf-list authentication {
       ordered-by user;
       description "Order in which PPP authentication protocols are negotiated";
       junos:must "(any \".. .. .. unit <*>\")";
       junos:must-message "authentication statement can be configured only on logical interfaces";
       type enumeration {
         enum "pap" {
           description "Password Authentication Protocol";
         }
         enum "chap" {
           description "Challenge Handshake Authentication Protocol";
         }
       }
     }
     container compression {
       description "Set compression options";
       leaf acfc {
         description "Negotiate Address/Control field compression";
         junos:must "(!(\".. .. .. encapsulation frame-relay-ppp\"))";
         junos:must-message "compression acfc is not supported on encapsulation frame-relay-ppp";
         type empty;
       }
       leaf pfc {
         description "Negotiate Protocol field compression";
         type empty;
       }
     }
     leaf lcp-restart-timer {
       description "LCP restart timer";
       units "milliseconds";
       junos:must "(any \".. .. .. unit <*>\")";
       junos:must-message "lcp-restart-timer statement can be configured only on logical interfaces";
       type union {
         type string {
           pattern "<.*>|$.*";
         }
         type uint16 {
           range "20 .. 10000";
         }
       }
     }
     leaf ncp-restart-timer {
       description "NCP restart timer";
       units "milliseconds";
       junos:must "(any \".. .. .. unit <*>\")";
       junos:must-message "ncp-restart-timer statement can be configured only on logical interfaces";
       type union {
         type string {
           pattern "<.*>|$.*";
         }
         type uint16 {
           range "500 .. 10000";
         }
       }
     }
     leaf no-termination-request {
       description "Don't send PPP termination requests";
       type empty;
     }
     leaf loopback-clear-timer {
       description "Loopback clear timer";
       units "seconds";
       junos:must "(any \".. .. .. unit <*>\")";
       junos:must-message "loopback-clear-timer statement can be configured only on logical interfaces";
       type union {
         type string {
           pattern "<.*>|$.*";
         }
         type uint8 {
           range "1 .. 60";
         }
       }
     }
     leaf lcp-max-conf-req {
       description "Maximum LCP Conf-Req to be sent, 0 means infinite";
       junos:must "(any \".. .. .. unit <*>\")";
       junos:must-message "lcp-max-conf-req statement can be configured only on logical interfaces";
       type union {
         type string {
           pattern "<.*>|$.*";
         }
         type uint32 {
           range "0 .. 65535";
         }
       }
     }
     leaf ncp-max-conf-req {
       description "Maximum NCP Conf-Req to be sent, 0 means infinite";
       junos:must "(any \".. .. .. unit <*>\")";
       junos:must-message "ncp-max-conf-req statement can be configured only on logical interfaces";
       type union {
         type string {
           pattern "<.*>|$.*";
         }
         type uint32 {
           range "0 .. 65535";
         }
       }
     }
     leaf on-demand-ip-address {
       description "Enable On-Demand IPv4 address allocation and de-allocation";
       junos:must "(any \".. .. .. unit <*>\")";
       junos:must-message "on-demand-ip-address statement can be configured only on logical interfaces";
       type empty;
     }
     leaf aaa-options {
       description "Attach AAA options name to dynamic-profile";
       junos:must "(\"access aaa-options $$\")";
       junos:must-message "referenced aaa-options name must be defined";
       type string {
         length "1 .. 63";
       }
     }
     container initiate-ncp {
       junos:must "(any \".. .. .. unit <*>\")";
       junos:must-message "initiate-ncp statement can be configured only on logical interfaces";
       description "Enable server initiated NCP";
       uses apply-advanced;
       leaf ip {
         description "Enable server initiated IPNCP";
         type empty;
       }
       leaf ipv6 {
         description "Enable server initiated IPv6NCP";
         type empty;
       }
       leaf dual-stack-passive {
         description "Disable server initiated IPNCP/IPv6NCP for dual-stack client";
         type empty;
       }
     }
     leaf mru {
       description "The Maximum Receive Unit size in bytes";
       junos:must "(any \".. .. .. unit <*>\")";
       junos:must-message "mru statement can be configured only on logical interfaces";
       type union {
         type string {
           pattern "<.*>|$.*";
         }
         type uint32 {
           range "64 .. 9192";
         }
       }
     }
     leaf mtu {
       description "The Maximum Transfer Unit size in bytes";
       junos:must "(any \".. .. .. unit <*>\")";
       junos:must-message "mtu statement can be configured only on logical interfaces";
       type string;
     }
     leaf peer-ip-address-optional {
       description "Set Peer IP Address Optional in IP NCP Negotiations";
       type empty;
     }
     leaf ipcp-suggest-dns-option {
       description "Suggest peer to negotiate with DNS Addresses options";
       type empty;
     }
     leaf ignore-magic-number-mismatch {
       description "Ignore magic-number validation failure in LCP keepalive";
       type empty;
     }
     container local-authentication {
       description "Local Authentication Protocol options";
       uses local_auth_type;
     }
     leaf lcp-connection-update {
       description "Enable LCP connection update request to peer";
       type empty;
     }
   }
   grouping local_auth_type {
     description "Local authentication";
     uses apply-advanced;
     leaf password {
       description "Username password";
       type string {
         length "1 .. 64";
       }
     }
     container username-include {
       description "Add username options";
       uses apply-advanced;
       leaf mac-address {
         description "Include MAC address";
         type empty;
       }
       leaf circuit-id {
         description "Include circuit-id ";
         type empty;
       }
       leaf remote-id {
         description "Include remote-id ";
         type empty;
       }
       leaf domain-name {
         description "Domain name";
         type string {
           length "1 .. 64";
         }
       }
       leaf delimiter {
         description "Delimiter/separator character";
         type string {
           length 1;
         }
       }
     }
   }
   grouping pppoe_options_type {
     uses apply-advanced;
     leaf underlying-interface {
       description "Underlying interface name";
       junos:must "((!(\"interfaces $$-IFL pppoe-underlying-options dynamic-profile\") && !(\"interfaces $$-IFL family pppoe dynamic-profile\")))";
       junos:must-message "Underlying interface cannot be used for both static and dynamic PPPoE interfaces";
       junos:must "((\"interfaces $$-IFL encapsulation ppp-over-ether\" || (\"interfaces $$-IFL encapsulation ppp-over-ether-over-atm-llc\" || \"interfaces $$-IFL family pppoe\")))";
       junos:must-message "Underlying interface must be configured";
       type string;
     }
     leaf idle-timeout {
       description "Time for which session can be idle (0 = forever)";
       units "seconds";
       type union {
         type string {
           pattern "<.*>|$.*";
         }
         type uint32 {
           range "0 .. 4294967295";
         }
       }
     }
     leaf access-concentrator {
       description "Name of the access concentrator (PPPoE server)";
       type string;
     }
     leaf service-name {
       description "Service to be requested (from PPPoE server)";
       type string;
     }
     leaf auto-reconnect {
       description "Time to reconnect after session terminates (0 = never)";
       units "seconds";
       type union {
         type string {
           pattern "<.*>|$.*";
         }
         type uint32 {
           range "0 .. 4294967295";
         }
       }
     }
     choice pppoe-mode {
       case case_1 {
         leaf server {
           description "PPPoE operates in server mode";
           type empty;
         }
       }
       case case_2 {
         leaf client {
           description "PPPoE operates in client mode";
           type empty;
         }
       }
     }
     leaf ppp-max-payload {
       description "Specify the value of ppp-max-payload tag";
       type union {
         type string {
           pattern "<.*>|$.*";
         }
         type uint32 {
           range "1492 .. 9192";
         }
       }
     }
   }
   grouping pppoe_underlying_options_type {
     uses apply-advanced;
     leaf access-concentrator {
       description "Name of the access concentrator (PPPoE server)";
       type string {
         length "1 .. 64";
       }
     }
     leaf direct-connect {
       description "Ignore received VS tags for PPPoE sessions";
       type empty;
     }
     leaf duplicate-protection {
       description "Disallow multiple PPPoE sessions to a single client";
       type empty;
     }
     leaf dynamic-profile {
       description "Attach dynamic-profile to interface";
       junos:must "((\"dynamic-profiles $$\" || \"system services subscriber-management mode user-plane\"))";
       junos:must-message "referenced dynamic-profile must be defined";
       type string {
         length "1 .. 64";
       }
     }
     leaf max-sessions {
       description "Maximum number of PPPoE sessions allowed on underlying interface";
       type union {
         type string {
           pattern "<.*>|$.*";
         }
         type uint32;
       }
     }
     leaf max-sessions-vsa-ignore {
       description "Ignore the max-sessions VSA";
       type empty;
     }
     leaf service-name-table {
       description "Attach Service Name Table to interface";
       junos:must "(\"protocols pppoe service-name-tables $$\")";
       junos:must-message "referenced service name table must be defined";
       type string {
         length "1 .. 32";
       }
     }
     container short-cycle-protection {
       presence "enable short-cycle-protection";
       description "Enable short cycle protection on underlying interface";
       uses apply-advanced;
       leaf lockout-time-min {
         description "Minimum lockout time";
         units "seconds";
         type union {
           type string {
             pattern "<.*>|$.*";
           }
           type uint32 {
             range "1 .. 86400";
           }
         }
       }
       leaf lockout-time-max {
         description "Maximum lockout time";
         units "seconds";
         type union {
           type string {
             pattern "<.*>|$.*";
           }
           type uint32 {
             range "1 .. 86400";
           }
         }
       }
       leaf filter {
         description "Granularity of blocking filter";
         type enumeration {
           enum "aci" {
             description "Block by Agent Circuit ID";
           }
         }
       }
     }
   }
   grouping term_object {
     leaf name {
       description "Term name";
       type string {
         length "1 .. 63";
         junos:posix-pattern "^[[:alnum:]][[:alnum:]_-]*$";
         junos:pattern-message "Must be a string beginning with a number or letter and consisting of letters, numbers, dashes and underscores.";
       }
     }
     leaf alg {
       description "Application Layer Gateway";
       type enumeration {
         enum "bootp" {
           description "Bootstrap protocol";
         }
         enum "dce-rpc" {
           description "DCE RPC";
         }
         enum "dce-rpc-portmap" {
           description "DCE RPC portmap";
         }
         enum "dns" {
           description "Domain Name Service";
         }
         enum "exec" {
           description "Remote Execution Protocol";
         }
         enum "ftp" {
           description "File Transfer Protocol";
         }
         enum "ftp-data" {
           description "File Transfer Protocol Data Session";
         }
         enum "gprs-gtp-c" {
           description "GPRS Tunneling Control Plane";
         }
         enum "gprs-gtp-u" {
           description "GPRS Tunneling User Plane";
         }
         enum "gprs-gtp-v0" {
           description "GPRS Tunneling Version 0";
         }
         enum "gprs-sctp" {
           description "GPRS Stream Control Protocol";
         }
         enum "h323" {
           description "H.323";
         }
         enum "icmp" {
           description "ICMP";
         }
         enum "icmpv6" {
           description "ICMPv6";
         }
         enum "ignore" {
           description "Ignore application type";
         }
         enum "iiop" {
           description "Internet Inter-ORB Protocol";
         }
         enum "ike-esp-nat" {
           description "IKE/ESP with NAT";
         }
         enum "ip" {
           description "IP";
         }
         enum "login" {
           description "Login";
         }
         enum "mgcp-ca" {
           description "MGCP-CA";
         }
         enum "mgcp-ua" {
           description "MGCP-UA";
         }
         enum "ms-rpc" {
           description "Microsoft RPC";
         }
         enum "netbios" {
           description "NetBIOS";
         }
         enum "netshow" {
           description "NetShow";
         }
         enum "none" {
           description "None";
         }
         enum "pptp" {
           description "Point-to-Point Tunneling Protocol";
         }
         enum "q931" {
           description "Q.931";
         }
         enum "ras" {
           description "RAS";
         }
         enum "realaudio" {
           description "RealAudio";
         }
         enum "rpc" {
           description "RPC";
         }
         enum "rpc-portmap" {
           description "RPC portmap";
         }
         enum "rsh" {
           description "Remote Shell";
         }
         enum "rtsp" {
           description "Real Time Streaming Protocol";
         }
         enum "sccp" {
           description "Skinny Client Control Protocol";
         }
         enum "sip" {
           description "Session Initiation Protocol";
         }
         enum "shell" {
           description "Shell";
         }
         enum "snmp" {
           description "SNMP";
         }
         enum "sqlnet" {
           description "SQLNet";
         }
         enum "sqlnet-v2" {
           description "Oracle SQL*Net Version 2";
         }
         enum "sun-rpc" {
           description "Sun Microsystems RPC";
         }
         enum "talk" {
           description "Talk Program";
         }
         enum "tftp" {
           description "Trivial File Transfer Protocol";
         }
         enum "traceroute" {
           description "Traceroute";
         }
         enum "http" {
           description "Hypertext Transfer Protocol";
         }
         enum "winframe" {
           description "WinFrame";
         }
         enum "https" {
           description "Hypertext Transfer Protocol";
         }
         enum "imap" {
           description "Internet Mail Access Protocol";
         }
         enum "smtp" {
           description "Simple Mail Transfer Protocol";
         }
         enum "ssh" {
           description "Secure Shell Protocol";
         }
         enum "telnet" {
           description "Telnet Protocol";
         }
         enum "twamp" {
           description "Two Way Active Meaurement Protocol";
         }
         enum "pop3" {
           description "Post Office Protocol 3 Protocol";
         }
         enum "smtps" {
           description "Simple Mail Transfer Protocol Over TLS";
         }
         enum "imaps" {
           description "Internet Mail Access Protocol Over TLS";
         }
         enum "pop3s" {
           description "Post Office Protocol 3 Protocol Over TLS";
         }
       }
     }
     leaf protocol {
       description "Match IP protocol type";
       type string;
     }
     leaf source-port {
       description "Match TCP/UDP source port";
       type string;
     }
     leaf destination-port {
       description "Match TCP/UDP destination port";
       type string;
     }
     leaf icmp-type {
       description "Match ICMP message type";
       type string;
     }
     leaf icmp-code {
       description "Match ICMP message code";
       type string;
     }
     leaf icmp6-type {
       description "Match ICMP6 message type";
       type string;
     }
     leaf icmp6-code {
       description "Match ICMP6 message code";
       type string;
     }
     leaf rpc-program-number {
       description "Match range of RPC program numbers";
       type string {
         junos:posix-pattern "^(0|[1-9][0-9]{0,9})(-(0|[1-9][0-9]{0,9}))?$";
         junos:pattern-message "Value must be an integer or a range of integers";
       }
     }
     leaf uuid {
       description "Match universal unique identifier for DCE RPC objects";
       type string {
         junos:posix-pattern "^[[:xdigit:]]{8}-[[:xdigit:]]{4}-[[:xdigit:]]{4}-[[:xdigit:]]{4}-[[:xdigit:]]{12}$";
         junos:pattern-message "Value must be of the form xxxxxxxx-xxxx-xxxx-xxxx-xxxxxxxxxxxx";
       }
     }
     leaf inactivity-timeout {
       description "Application-specific inactivity timeout";
       units "seconds";
       type string;
     }
   }
   grouping time-format-object {
     uses apply-advanced;
     leaf year {
       description "Year in time format for syslog";
       type empty;
     }
     leaf millisecond {
       description "Millisecond in time format for syslog";
       type empty;
     }
   }
   grouping traffic-selector-term-object {
     description "Traffic Selector term details";
     leaf name {
       description "Rule name";
       type string {
         length "1 .. 63";
         junos:posix-pattern "^[[:alnum:]][[:alnum:]_-]*$";
         junos:pattern-message "Must be a string beginning with a number or letter and consisting of letters, numbers, dashes and underscores.";
       }
     }
     uses apply-advanced;
     leaf local-ip {
       description "IP address of local traffic-selector";
       type jt:ipprefix-mandatory;
     }
     leaf remote-ip {
       description "IP address of remote traffic-selector";
       type jt:ipprefix-mandatory;
     }
     leaf protocol {
       description "Define protocol";
       junos:must "((\" .. local-ip\" || \" .. remote-ip\"))";
       junos:must-message "Either local-ip or remote-ip must be defined for protocol";
       type string;
     }
     leaf source-port {
       description "Hyphenated source port range";
       junos:must "((\" .. local-ip\" && \" .. protocol\"))";
       junos:must-message "local-ip and protocol must be defined for source-port";
       type string;
     }
     leaf destination-port {
       description "Hyphenated destination port range";
       junos:must "((\" .. remote-ip\" && \" .. protocol\"))";
       junos:must-message "remote-ip and protocol must be defined for destination-port";
       type string;
     }
   }
   grouping tunable-object {
     leaf name {
       type string;
     }
     uses apply-advanced;
     leaf tunable-value {
       description "Protocol tunable value";
       type union {
         type uint32;
         type string {
           pattern "<.*>|$.*";
         }
       }
     }
   }
   grouping tunnel-inspection-profile-type {
     description "Configure tunnel-inspection profile";
     leaf name {
       description "Tunnel-inspection profile name";
       type string {
         length "1 .. 63";
       }
     }
     uses apply-advanced;
     choice inspection-type {
       case case_1 {
         list vxlan {
           key name;
           ordered-by user;
           description "Define a vxlan tunnel";
           uses vxlan-tunnel-type;
         }
       }
     }
   }
   grouping tunnel-inspection-vni-type {
     description "VNI config";
     leaf name {
       description "VNI name";
       type string {
         length "1 .. 64";
       }
     }
     uses apply-advanced;
     choice vni-type {
       case case_1 {
         list vni-range {
           key name;
           ordered-by user;
           description "VNI range";
           uses vni-range-type;
         }
       }
       case case_2 {
         leaf-list vni-id {
           ordered-by user;
           description "VNI ID";
           type union {
             type uint32;
             type string {
               pattern "<.*>|$.*";
             }
           }
         }
       }
     }
   }
   grouping tunnel_type {
     description "Tunnel packets";
     uses apply-advanced;
     choice ipsec-vpn-choice {
       case case_1 {
         leaf ipsec-vpn {
           description "Enable VPN with name";
           junos:must "(!(\"security ipsec vpn $$ bind-interface\"))";
           junos:must-message "Route based ipsec-vpn cannot be referenced for policy";
           junos:must "(\"security ipsec vpn $$\")";
           junos:must-message "Security VPN must be defined";
           type string {
             length "1 .. 63";
           }
         }
       }
       case case_2 {
         leaf ipsec-group-vpn {
           description "Enable dynamic IPSEC group with name";
           status deprecated;
           junos:must "(\"security group-vpn member ipsec vpn $$\")";
           junos:must-message "Security group VPN must be defined";
           type string {
             length "1 .. 63";
           }
         }
       }
     }
     leaf pair-policy {
       description "Policy in the reverse direction, to form a pair";
       type string {
         length "1 .. 63";
         junos:posix-pattern "^[[:alnum:]][[:alnum:]_-]*$";
         junos:pattern-message "Must be a string beginning with a number or letter and consisting of letters, numbers, dashes and underscores.";
       }
     }
   }
   grouping url-list-type {
     description "Configure url-list object";
     leaf name {
       description "Configure name of url-list object";
       type string {
         length "1 .. 29";
         junos:posix-pattern "^[a-zA-Z_]+[a-zA-Z_0-9-]*$";
         junos:pattern-message "Must be a string beginning with a letter or underscore and consisting of letters, numbers, dashes and underscores.";
       }
     }
     uses apply-advanced;
     leaf-list value {
       ordered-by user;
       description "Configure value of url-list object";
       type string {
         length "1 .. 249";
       }
     }
   }
   grouping user-group-mapping-type {
     uses apply-advanced;
     container ldap {
       description "LDAP";
       uses apply-advanced;
       leaf authentication-algorithm {
         description "Authentication-algorithm";
         type enumeration {
           enum "simple" {
             description "Simple authentication";
           }
         }
       }
       leaf ssl {
         description "SSL";
         type empty;
       }
       leaf base {
         description "Base distinguished name";
         type string {
           length "1 .. 128";
         }
       }
       container user {
         description "User name";
         uses apply-advanced;
         leaf user-name {
           description "User name";
           type string {
             length "1 .. 64";
             junos:posix-pattern "^[[:alnum:]._-]+$|^\\\\*$";
             junos:pattern-message "Must be a string consisting of letters, numbers, dashes, underscores and dots";
           }
         }
         leaf password {
           description "Password string";
           type string {
             length "1 .. 128";
           }
         }
       }
       list address {
         key name;
         ordered-by user;
         description "Address of LDAP server";
         leaf name {
           description "Address";
           type jt:ipaddr;
         }
         uses apply-advanced;
         leaf port {
           description "LDAP port";
           type union {
             type string {
               pattern "<.*>|$.*";
             }
             type uint16 {
               range "1 .. 65535";
             }
           }
         }
       }
     }
   }
   grouping usf-range-address-type {
     description "Range address";
     leaf name {
       description "Lower limit of address range";
       type jt:ipprefix;
     }
     uses apply-advanced;
     container to {
       description "Port range upper limit";
       uses apply-advanced;
       leaf range-high {
         description "Upper limit of address range";
         type jt:ipprefix;
       }
     }
   }
   grouping utm-apppxy-traceoptions {
     description "Traceoptions for utm application proxy process";
     uses apply-advanced;
     list flag {
       key name;
       ordered-by user;
       description "Tracing parameters for utm application proxy";
       leaf name {
         description "Tracing parameters for utm application proxy flag name";
         type enumeration {
           enum "abort" {
             description "Trace application-proxy session abort";
           }
           enum "application-objects" {
             description "Trace application-proxy objects information";
           }
           enum "utm-realtime" {
             description "Trace application-proxy realtime-thread information";
           }
           enum "anti-virus" {
             description "Trace anti-virus information";
           }
           enum "basic" {
             description "Trace application-proxy basic information";
           }
           enum "buffer" {
             description "Trace application-proxy data buffer information";
           }
           enum "detail" {
             description "Trace application-proxy detailed information";
           }
           enum "ftp-data" {
             description "Trace FTP data connection information";
           }
           enum "ftp-control" {
             description "Trace FTP control connection information";
           }
           enum "http" {
             description "Trace HTTP protocol information";
           }
           enum "imap" {
             description "Trace IMAP protocol information";
           }
           enum "memory" {
             description "Trace memory usage";
           }
           enum "parser" {
             description "Trace protocol parser";
           }
           enum "pfe" {
             description "Trace communication with PFE";
           }
           enum "pop3" {
             description "Trace POP3 protocol information";
           }
           enum "queue" {
             description "Trace queue information";
           }
           enum "smtp" {
             description "Trace SMTP protocol information";
           }
           enum "tcp" {
             description "Trace TCP level information";
           }
           enum "timer" {
             description "Trace timer processing";
           }
           enum "connection-rating" {
             description "Trace connection rating information";
           }
           enum "mime" {
             description "Trace MIME parser information";
           }
           enum "regex-engine" {
             description "Trace Pattern Match Engine (PME) information";
           }
           enum "sophos-anti-virus" {
             description "Trace anti-virus sophos engine information";
           }
           enum "all" {
             description "Enable all application-proxy trace options";
           }
         }
       }
     }
   }
   grouping utm-ipc-traceoptions {
     description "Traceoptions for utm IPC";
     uses apply-advanced;
     list flag {
       key name;
       ordered-by user;
       description "Traceoptions for utm IPC flag";
       leaf name {
         description "Trace options for utm IPC flag name";
         type enumeration {
           enum "basic" {
             description "Trace basic IPC related information";
           }
           enum "detail" {
             description "Trace detail IPC related information";
           }
           enum "connection-manager" {
             description "Trace IPC connection manager";
           }
           enum "connection-status" {
             description "Trace IPC connection status";
           }
           enum "pfe" {
             description "Trace communication with pfe";
           }
           enum "utm-realtime" {
             description "Trace IPC realtime-thread information";
           }
           enum "all" {
             description "Enable all IPC trace options";
           }
         }
       }
     }
   }
   grouping utm-traceoptions {
     description "Trace options for utm process";
     uses apply-advanced;
     list flag {
       key name;
       ordered-by user;
       description "Tracing UTM information";
       leaf name {
         description "Flag name";
         type enumeration {
           enum "cli" {
             description "Trace CLI";
           }
           enum "daemon" {
             description "Trace daemon information";
           }
           enum "ipc" {
             description "Trace IPC information";
           }
           enum "pfe" {
             description "Trace pfe information";
           }
           enum "all" {
             description "Enable all utm trace options";
           }
         }
       }
     }
   }
   grouping v6-relay-option-interface-id-type {
     description "Interface ID processing";
     uses apply-advanced;
     container prefix {
       description "Add prefix to circuit/interface-id or remote-id";
       uses apply-advanced;
       leaf host-name {
         description "Add router host name to circuit / interface-id or remote-id";
         type empty;
       }
       leaf logical-system-name {
         description "Add logical system name to circuit / interface-id or remote-id";
         type empty;
       }
       leaf routing-instance-name {
         description "Add routing instance name to circuit / interface-id or remote-id";
         type empty;
       }
     }
     leaf use-interface-description {
       description "Use interface description instead of circuit identifier";
       junos:must "(!(\".. require-interface-description\"))";
       junos:must-message "use-interface-description may not be set with require-interface-desciption";
       type enumeration {
         enum "logical" {
           description "Use the logical interface description";
         }
         enum "device" {
           description "Use the device interface description";
         }
       }
     }
     leaf use-vlan-id {
       description "Use VLAN id instead of name";
       junos:must "((!(\".. no-vlan-interface-name\") && (!(\".. use-interface-description\") && !(\".. require-interface-description\"))))";
       junos:must-message "Vlan-tag cannot be added as no-vlan-interface-name or interface-description is configured";
       type empty;
     }
     leaf no-vlan-interface-name {
       description "Not include vlan or interface name";
       type empty;
     }
     leaf include-irb-and-l2 {
       description "Include IRB and L2 interface name";
       type empty;
     }
     container use-option-82 {
       description "Use option-82 circuit-id for interface-id";
       presence "enable use-option-82";
       uses v6-relay-option-cid-rid-action;
     }
     container keep-incoming-interface-id {
       description "Keep incoming interface identifier";
       presence "enable keep-incoming-interface-id";
       uses v6-relay-option-cid-rid-action;
     }
   }
   grouping v6-relay-option-cid-rid-action {
     uses apply-advanced;
     leaf strict {
       description "Drop packet if id not present";
       type empty;
     }
   }
   grouping v6-relay-option-remote-id-type {
     description "Remote ID processing";
     uses apply-advanced;
     container prefix {
       description "Add prefix to circuit/interface-id or remote-id";
       uses apply-advanced;
       leaf host-name {
         description "Add router host name to circuit / interface-id or remote-id";
         type empty;
       }
       leaf logical-system-name {
         description "Add logical system name to circuit / interface-id or remote-id";
         type empty;
       }
       leaf routing-instance-name {
         description "Add routing instance name to circuit / interface-id or remote-id";
         type empty;
       }
     }
     leaf use-interface-description {
       description "Use interface description instead of circuit identifier";
       junos:must "(!(\".. require-interface-description\"))";
       junos:must-message "use-interface-description may not be set with require-interface-desciption";
       type enumeration {
         enum "logical" {
           description "Use the logical interface description";
         }
         enum "device" {
           description "Use the device interface description";
         }
       }
     }
     leaf use-vlan-id {
       description "Use VLAN id instead of name";
       junos:must "((!(\".. no-vlan-interface-name\") && (!(\".. use-interface-description\") && !(\".. require-interface-description\"))))";
       junos:must-message "Vlan-tag cannot be added as no-vlan-interface-name or interface-description is configured";
       type empty;
     }
     leaf no-vlan-interface-name {
       description "Not include vlan or interface name";
       type empty;
     }
     leaf include-irb-and-l2 {
       description "Include IRB and L2 interface name";
       type empty;
     }
     container use-option-82 {
       description "Use option-82 remote-id for v6 remote-id";
       presence "enable use-option-82";
       uses v6-relay-option-cid-rid-action;
     }
     leaf keep-incoming-remote-id {
       description "Keep incoming remote identifier";
       type empty;
     }
   }
   grouping v6-server-group-type {
     uses apply-advanced;
     list server-group {
       key name;
       ordered-by user;
       description "One or more server groups";
       leaf name {
         description "DHCPv6 Server group name";
         type string {
           length "1 .. 64";
           junos:posix-pattern "^[A-Za-z0-9][_0-9A-Za-z-]*$";
           junos:pattern-message "Must be a non-reserved string of 64 characters or less";
         }
       }
       uses apply-advanced;
       list address {
         key name;
         ordered-by user;
         description "IP Address of one or more DHCP servers";
         max-elements 32;
         leaf name {
           description "IP Address of DHCP server";
           type jt:ipaddr;
         }
         uses apply-advanced;
       }
     }
   }
   grouping vector-routing-traceoptions {
     description "Vector routing traceoptions";
     uses apply-advanced;
     leaf no-remote-trace {
       description "Disable remote tracing";
       junos:must "(\"system tracing\")";
       junos:must-message "'no-remote-trace' is valid only when [system tracing] is configured";
       type empty;
     }
     container file {
       description "Trace file information";
       leaf filename {
         description "Name of file in which to write trace information";
         type string {
           length "1 .. 1024";
           junos:posix-pattern "![/ %]";
           junos:pattern-message "Must not contain '/', % or a space";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     list flag {
       key name;
       ordered-by user;
       description "Trace flags";
       leaf name {
         type enumeration {
           enum "all" {
             description "Trace everything";
           }
           enum "vector-routing-re" {
             description "Trace events on RE side";
           }
           enum "vector-routing-control" {
             description "Trace events on PFE-ukernel side";
           }
           enum "vector-routiing-rt" {
             description "Trace events on pfe-rt side";
           }
         }
       }
     }
   }
   grouping vendor-object {
     leaf name {
       description "Values for vendor field";
       type string;
     }
     uses apply-advanced;
     leaf product-name {
       description "Values for product field";
       type string;
     }
   }
   grouping vlan-policy {
     description "Virtual LAN";
     leaf name {
       description "VLAN id";
       type string;
     }
     uses apply-advanced;
     container policy {
       description "Attach policy";
       uses apply-advanced;
       leaf policy-name {
         description "Router Advertisement Guard policy name";
         type string;
       }
       choice policy-type {
         case case_1 {
           leaf stateful {
             description "Stateful router advertisement guard";
             type empty;
           }
         }
         case case_2 {
           leaf stateless {
             description "Stateless router advertisement guard";
             type empty;
           }
         }
       }
     }
   }
   grouping vlan-slaacd {
     description "Virtual LAN";
     leaf name {
       description "VLAN id";
       type string;
     }
     uses apply-advanced;
   }
   grouping vlan-types {
     description "Virtual LAN";
     leaf name {
       description "VLAN name";
       junos:must "((\".. vlan-id\" || \".. vlan-id-list\"))";
       junos:must-message "vlan-id/vlan-id-list must be configure";
       junos:must "(((!(\"vlans ${vlan} isolated-vlan\") && (!(\"vlans ${vlan} community-vlans\") && !(\"vlans ${vlan} private-vlan\"))) || !(\"vlans ${vlan} forwarding-options filter output\")))";
       junos:must-message "Configuring Egress VACL is not supported on PVLAN";
       type string {
         length "2 .. 64";
       }
     }
     uses apply-advanced;
     leaf vlan-id {
       description "IEEE 802.1q VLAN identifier for VLAN";
       type string;
     }
     leaf-list vlan-id-list {
       description "Create VLAN for each of the vlan-id specified in the vlan-id-list";
       junos:must "(!(\".. vlan-id\"))";
       junos:must-message "vlan-id and vlan-id-list cannot be configured together";
       junos:must "(!((\"routing-instances ${instance} instance-type mac-vrf\" && \" .. vxlan\")))";
       junos:must-message "vxlan can not be specified under vlan-id-list for mac-vrf instance";
       junos:must "((!(\".. isolated-vlan\") && !(\".. community-vlans\")))";
       junos:must-message "PVLAN related configuration cannot be specified with vlan-id-list";
       junos:must "(!(\" .. multicast-snooping-options\"))";
       junos:must-message "multicast-snooping-options can not be specified under vlan-id-list";
       junos:must "(!(\" .. domain-type\"))";
       junos:must-message "domain-type can not be specified  under vlan-id-list";
       junos:must "(!(\".. interface\"))";
       junos:must-message "interface can not be specified under vlan-id-list";
       junos:must "(!(any \".. switch-options interface <*> static-mac\"))";
       junos:must-message "static mac can not be specified under vlan-id-list";
       type jt:vlan-range;
     }
     leaf l3-interface {
       description "L3 interface name for this vlans";
       junos:must "(\".. vlan-id none\")";
       junos:must-message "l3-interface can be configured only under vlans with 'vlan-id none'";
       junos:must "(unique \"vmhost vlans <*> l3-interface $$\")";
       junos:must-message "Same l3-interface cannot be attached to more than one vlan";
       junos:must "(!((\".. .. .. protocols evpn mclag\" && !(\".. no-arp-suppression\"))))";
       junos:must-message "no-arp-suppression needs to be configured, when evpn is configured with mclag.";
       junos:must "(!((\".. mcae-mac-synchronize\" && \"interfaces $$-IFL mac\")))";
       junos:must-message "irb-ifl mac and vlan mcae-mac-synchronize cannot coexist";
       junos:must "((!(\"interfaces $$-IFL family mpls\") || !((\"routing-instances ${instance} instance-type virtual-switch\" && (\"routing-instances ${instance} protocols vpls\" && \"routing-instances ${instance} route-distinguisher\")))))";
       junos:must-message "routing-interface with family MPLS cannot be added to virtual-switch with protocol VPLS";
       junos:must "((!(\".. vlan-tags\") || !(\"interfaces $$-IFL family mpls\")))";
       junos:must-message "routing-interface with family MPLS cannot be added to bridge-domain with 'vlan-tags'";
       junos:must "(!(\"routing-instances ${instance} service-type vlan-bundle\"))";
       junos:must-message "routing-interface not valid for vlan-bundle service type";
       junos:must "((!(\".. vlan-id all\") && !(\".. vlan-id inner-all\")))";
       junos:must-message "l3-interface cannot be configured under vlans with 'vlan-id all' or 'vlan-id inner-all'";
       junos:must "((\".. vlan-id\" || \".. vlan-tags\"))";
       junos:must-message "l3-interface can be configured only under vlans with 'vlan-id'/'vlan-tags'";
       junos:must "(\"interfaces $$-IFL\")";
       junos:must-message "Interface must already be defined under [edit interfaces]";
       type union {
         type jt:interface-unit;
         type string {
           pattern "<.*>|$.*";
         }
       }
     }
     leaf description {
       description "Text description of VLANs";
       type string {
         junos:posix-pattern "^.{1,255}$";
         junos:pattern-message "Must be a string of 255 characters or less";
       }
     }
     choice vlan-identifier-choice {
       case case_1 {
         container vlan-tags {
           presence "enable vlan-tags";
           description "IEEE 802.1q VLAN tags for VLANs";
           leaf outer {
             description "[tpid.]vlan-id, tpid format is 0xNNNN and is optional";
             type string {
               junos:posix-pattern "^(0[Xx][0-9A-Fa-f]{4}.([0-9]{1,3}|1[0-9]{3}|2[0-9]{3}|3[0-9]{3}|40[0-8][0-9]|409[0-4]))$|^([0-9]{1,3}|1[0-9]{3}|2[0-9]{3}|3[0-9]{3}|40[0-8][0-9]|409[0-4])$";
               junos:pattern-message "vlan-id in vlan-tag (0xNNNN.vlan-id) must be 0 to 4094";
             }
           }
           leaf inner {
             description "[tpid.]vlan-id, tpid format is 0xNNNN and is optional";
             type string {
               junos:posix-pattern "^(0[Xx][0-9A-Fa-f]{4}.([0-9]{1,3}|1[0-9]{3}|2[0-9]{3}|3[0-9]{3}|40[0-8][0-9]|409[0-4]))$|^([0-9]{1,3}|1[0-9]{3}|2[0-9]{3}|3[0-9]{3}|40[0-8][0-9]|409[0-4])$";
               junos:pattern-message "vlan-id in vlan-tag (0xNNNN.vlan-id) must be 0 to 4094";
             }
           }
         }
       }
     }
     list interface {
       key name;
       ordered-by user;
       description "Interface name for this VLAN";
       leaf name {
         junos:must "(!(\"interfaces $$-IFL encapsulation ethernet\"))";
         junos:must-message "encapsulation ethernet is not allowed on l2 interface";
         junos:must "(!(((\"interfaces $$-IFL vlan-id-list\" || \"interfaces $$-IFL vlan-id-range\") && (\".. .. .. .. instance-type mac-vrf\" && (\".. .. .. .. service-type vlan-aware\" || \".. .. .. .. service-type vlan-based\")))))";
         junos:must-message "Interface with vlan-id-list/vlan-id-range cannot be added to vlan under mac-vrf routing-instance with vlan-based/vlan-aware service-type";
         junos:must "((!(\"interfaces $$-IFL family\") || \"interfaces $$-IFL family ethernet-switching\"))";
         junos:must-message "only family ethernet-switching can be configured on this interface";
         junos:must "((!((\"interfaces $$ vlan-id-list\" || \"interfaces $$ vlan-tags inner-list\")) || (!((\".. .. vlan-id\" || \".. .. vlan-tags\")) || (\".. .. no-normalization\" || \".. .. switch-options no-normalization\"))))";
         junos:must-message "interface with vlan-id-list/inner-list cannot be added to a vlan with a vlan-id/vlan-tags configured";
         junos:must "(!((\"interfaces $$-IFL family ethernet-switching interface-mode\" || \"interfaces $$-IFL family ethernet-switching vlan members\")))";
         junos:must-message "Interface with 'interface-mode' config is not allowed under vlans";
         junos:must "(!(\".. .. .. interfaces $$\"))";
         junos:must-message "This interface is already defined at the routing-instance level";
         junos:must "((\"interfaces $$-IFL\" || !(\".. .. .. .. protocols evpn encapsulation\")))";
         junos:must-message "Interface not defined; Interface must be defined for configuring under VLAN for protocols evpn";
         junos:must "(((\".. .. vlan-id all\" && \"interfaces $$-IFL input-vlan-map pop\") || ((\".. .. vlan-id inner-all\" && \"interfaces $$-IFL input-vlan-map\") || (!((\".. .. vlan-id\" || \".. .. vlan-tags\")) || (!((\"interfaces $$-IFL input-vlan-map\" || \"interfaces $$-IFL output-vlan-map\")) || (\".. .. no-normalization\" || \".. .. switch-options no-normalization\"))))))";
         junos:must-message "interface with input/output vlan-maps cannot be added to a routing-instance with a vlan-id/vlan-tags configured";
         junos:must "((!(\"interfaces $$-IFL vlan-tags inner-range\") || ((\".. .. vlan-id all\" || \".. .. vlan-id inner-all\") || (\".. .. no-normalization\" || \".. .. switch-options no-normalization\"))))";
         junos:must-message "vlan-tags inner-range is specified for this logical interface; 'vlan-id all' or 'vlan-id inner-all' should also be enabled";
         junos:must "(((!(\"interfaces $$-IFL vlan-id-range\") || \".. .. vlan-id all\") || (\".. .. no-normalization\" || \".. .. switch-options no-normalization\")))";
         junos:must-message "vlan-id-range is specified for this logical interface; 'vlan-id all' should also be enabled";
         junos:must "(!(\".. .. switch-options interface $$ interface-mac-limit\"))";
         junos:must-message "Interface mac limit should not be configured at VLAN level for sub interfaces";
         junos:must "((!(\"interfaces $$-IFL vlan-id-list\") || !((\"interfaces $$-IFL input-vlan-map swap\" || \"interfaces $$-IFL input-vlan-map pop\"))))";
         junos:must-message "interface with vlan-id-list and input-vlan-map swap/pop is not supported";
         junos:must "((!(\"interfaces $$-IFL vlan-id\") || !((\".. .. vlan-tags\" || \".. .. vlan-id-list\"))))";
         junos:must-message "interface with vlan-id cannot be added to vlan with vlan-tags/vlan-id-list configured";
         junos:must "((!(\"interfaces $$-IFL vlan-id-list\") || !((\".. .. vlan-id\" || (\".. .. vlan-tags\" || \".. .. vlan-id-list\")))))";
         junos:must-message "interface with vlan-id-list cannot be added to a vlan with a vlan-id/vlan-tags/vlan-id-list configured";
         type string;
       }
       uses apply-advanced;
     }
     leaf no-local-switching {
       description "Disable local switching within CE-facing interfaces";
       type empty;
     }
     container forwarding-options {
       description "Forwarding options configuration";
       uses juniper-ethernet-switching-forwarding-options;
     }
     container multicast-snooping-options {
       description "Multicast snooping option configuration";
       junos:must "(\".. .. .. protocols igmp-snooping vlan ${vlan}\")";
       junos:must-message "multicast-snooping-options can be configured only if snooping is enabled on the vlan";
       uses juniper-multicast-snooping-options;
     }
     container switch-options {
       description "VLANs switch-options configuration";
       uses juniper-protocols-vlan;
     }
     leaf domain-type {
       description "Type of VLANs SVLAN/DVLAN";
       type enumeration {
         enum "bridge" {
           description "Forwarding instance";
         }
       }
     }
     leaf no-irb-layer-2-copy {
       description "Disable transmission of layer-2 copy of packets of IRB routing-interface";
       junos:must "(\".. l3-interface\")";
       junos:must-message "l3-interface must be configured to configure this feature";
       type empty;
     }
     leaf service-id {
       description "Service id required if VLAN is of type MC-AE, and vlan-id all or vlan-id none or vlan-tags is configured";
       type union {
         type string {
           pattern "<.*>|$.*";
         }
         type uint32 {
           range "1 .. 65535";
         }
       }
     }
     leaf domain-id {
       description "Domain-id for auto derived Route Target";
       junos:must "(\".. .. .. protocols evpn encapsulation vxlan\")";
       junos:must-message "domain-id is allowed for EVPN instances only";
       type union {
         type string {
           pattern "<.*>|$.*";
         }
         type uint32 {
           range "1 .. 15";
         }
       }
     }
     leaf mcae-mac-synchronize {
       description "Enable IRB MAC synchronization in this VLAN";
       junos:must "(\".. l3-interface\")";
       junos:must-message "Layer 3 interface for this VLAN is not configured";
       type empty;
     }
     container proxy-mac {
       junos:must "(\".. .. .. instance-type virtual-switch\")";
       junos:must-message "Applicable to instance-type evpn only";
       description "Proxy MAC settings";
       uses apply-advanced;
       leaf irb {
         description "Reply with virtual-gateway MAC or IRB MAC";
         junos:must "(!(\".. .. no-arp-suppression\"))";
         junos:must-message "Proxy MAC is not supported with no-arp-supression";
         junos:must "((\".. .. l3-interface\" && !(\".. proxy-mac-address\")))";
         junos:must-message "Proxy MAC in IRB mode should have routing-interface configured";
         type empty;
       }
       leaf proxy-mac-address {
         description "Reply with configured MAC for all requests";
         junos:must "(!(\".. .. no-arp-suppression\"))";
         junos:must-message "Proxy MAC is not supported with no-arp-supression";
         junos:must "((!(\".. .. l3-interface\") && !(\".. irb\")))";
         junos:must-message "Proxy MAC with specified MAC should not have routing-interface configured";
         type jt:mac-unicast;
       }
     }
     leaf mcae-mac-flush {
       description "Enable IRB MAC flush in a/s mode for this VLAN on MCAE link up";
       type empty;
     }
     leaf private-vlan {
       description "Type of secondary vlan for private vlan";
       junos:must "(!((\".. isolated-vlan\" || \".. community-vlans\")))";
       junos:must-message "This vlan is already configured as primary vlan";
       junos:must "(!(\".. l3-interface\"))";
       junos:must-message "l3-interface cannot be configured on a secondary vlan";
       type enumeration {
         enum "isolated" {
           description "Isolated vlan";
         }
         enum "community" {
           description "Community vlan";
         }
       }
     }
     leaf isolated-vlan {
       description "VLAN id or name";
       junos:must "(!(\".. private-vlan\"))";
       junos:must-message "This vlan is already configured as secondary vlan";
       type string {
       }
     }
     leaf-list community-vlans {
       ordered-by user;
       description "List of VLAN id or name";
       junos:must "(!(\".. private-vlan\"))";
       junos:must-message "This vlan is already configured as secondary vlan";
       type string;
     }
     container vxlan {
       junos:must "((\". riot-loopback\" || (!(\". riot-loopback\") && (((\". ovsdb-managed\" || \".. .. .. switch-options ovsdb-managed\") && (!((\". ingress-node-replication\" || \".. .. .. protocols evpn encapsulation vxlan\")) && !(\". multicast-group\"))) || ((!((\". ovsdb-managed\" || \".. .. .. switch-options ovsdb-managed\")) && ((\". ingress-node-replication\" || \".. .. .. protocols evpn encapsulation vxlan\") && !(\". multicast-group\"))) || (!((\". ovsdb-managed\" || \".. .. .. switch-options ovsdb-managed\")) && (!((\". ingress-node-replication\" || \".. .. .. protocols evpn encapsulation vxlan\")) && \". multicast-group\")))))))";
       junos:must-message "ovsdb, multicast-group, ingress-node-replication cannot be configured together. ingress-node-replication must be configured when remote-vtep-list is configured";
       junos:must "((\". ovsdb-managed\" || (\".. .. .. switch-options ovsdb-managed\" || (\". multicast-group\" || (\"routing-instances ${instance} remote-vtep-list\" || (\".. .. .. switch-options remote-vtep-list\" || (\". ingress-node-replication\" || (\".. .. .. protocols evpn encapsulation vxlan\" || \". riot-loopback\"))))))))";
       junos:must-message "One of multicast-group or ovsdb-managed or ingress-node-replication or protocols evpn encapsulation vxlan or remote-vtep-list or riot-loopback should be enabled";
       junos:must "((!(\".. vlan-id all\") && !(\".. vlan-id all\")))";
       junos:must-message "vxlan does not support bridge domain with 'vlan-id all' or 'vlan-id inner-all'";
       junos:must "((\". riot-loopback\" || (!(\". riot-loopback\") && (\"routing-instances ${instance} vtep-source-interface\" || \".. .. .. switch-options vtep-source-interface\"))))";
       junos:must-message "vtep-source-interface is required for VXLAN configuration";
       uses apply-advanced;
       leaf ovsdb-managed {
         description "Bridge-domain is managed remotely via VXLAN OVSDB Controller";
         junos:must "(!((\"routing-instances ${instance} remote-vtep-list\" || (\".. .. .. .. switch-options remote-vtep-list\" || (\".. multicast-group\" || \".. .. .. .. protocols evpn encapsulation vxlan\")))))";
         junos:must-message "ovsdb-managed not valid with remote-vtep-list or multicast-group or protocol evpn encapsulation vxlan";
         type empty;
       }
       leaf vni {
         description "VXLAN identifier";
         type union {
           type string {
             pattern "<.*>|$.*";
           }
           type uint32 {
             range "0 .. 16777214";
           }
         }
       }
       leaf translation-vni {
         description "Translated VXLAN identifier";
         type union {
           type string {
             pattern "<.*>|$.*";
           }
           type uint32 {
             range "1 .. 16777214";
           }
         }
       }
       leaf multicast-group {
         description "Multicast group registered for VXLAN segment";
         junos:must "(!((\"routing-instances ${instance} remote-vtep-list\" || (\".. .. .. switch-options remote-vtep-list\" || (\".. ovsdb-managed\" || (\"routing-instances ${instance} switch-options ovsdb-managed\" || \".. .. .. .. protocols evpn encapsulation vxlan\"))))))";
         junos:must-message "multicast-group not valid with remote-vtep-list or ovsdb-managed or evpn configuration";
         type jt:ipv4addr;
       }
       leaf encapsulate-inner-vlan {
         description "Retain inner VLAN in the packet";
         type empty;
       }
       leaf decapsulate-accept-inner-vlan {
         description "Accept VXLAN packets with inner VLAN";
         type empty;
       }
       leaf unreachable-vtep-aging-timer {
         description "Unreachable VXLAN tunnel endpoint removal timer";
         units "seconds";
         type union {
           type string {
             pattern "<.*>|$.*";
           }
           type uint16 {
             range "300 .. 1800";
           }
         }
       }
       leaf ingress-node-replication {
         description "Enable ingress node replication";
         junos:must "(!(\".. .. .. .. protocols evpn assisted-replication\"))";
         junos:must-message "ingress-node-replication cannot be configured with assisted-replication";
         junos:must "((\".. ovsdb-managed\" || (\".. .. .. .. switch-options ovsdb-managed\" || (\"routing-instances ${instance} remote-vtep-list\" || (\".. .. .. .. switch-options remote-vtep-list\" || \".. .. .. .. protocols evpn encapsulation vxlan\")))))";
         junos:must-message "Valid for ovsdb-managed instance or with remote-vtep-list or with protocols evpn encapsulation vxlan";
         type empty;
       }
       leaf-list static-remote-vtep-list {
         description "Configure vlan specific static remote VXLAN tunnel endpoints";
         type jt:ipaddr;
         max-elements 1024;
       }
       leaf riot-loopback {
         description "Enable loopback on RIOT platform";
         type empty;
       }
     }
   }
   grouping juniper-ethernet-switching-forwarding-options {
     uses apply-advanced;
     container filter {
       description "Filtering for ethernet switching forwarding table";
       uses apply-advanced;
       leaf input {
         description "Name of input filter to apply for forwarded packets";
         type string;
       }
       leaf output {
         description "Name of output filter to apply for forwarded packets";
         junos:must "(!(any \"firewall family ethernet-switching filter $$ term <*> from traffic-type-except\"))";
         junos:must-message "Vacl with term as 'from traffic-type-except' not supported on the egress side";
         junos:must "(!(any \"firewall family ethernet-switching filter $$ term <*> from traffic-type\"))";
         junos:must-message "Vacl with term as 'from traffic-type' not supported on the egress side";
         type string;
       }
     }
     container flood {
       description "Filtering for ethernet switching flood table";
       uses apply-advanced;
       leaf input {
         description "Name of input filter to apply for ethernet switching flood packets";
         type string;
       }
     }
     container dhcp-relay {
       description "Dynamic Host Configuration Protocol relay configuration";
       status deprecated;
       junos:must "(!(\"forwarding-options helpers bootp\"))";
       junos:must-message "'dhcp-relay' statement cannot be included along with 'forwarding-options helpers bootp' statement";
       uses jdhcp-relay-type;
     }
     container dhcp-security {
       description "DHCP access security configuration";
       presence "enable dhcp-security";
       uses jdhcp-security-type;
     }
     container fip-security {
       description "FCoE Initiation Protocol security configuration";
       presence "enable fip-security";
       uses fip-security-type;
     }
   }
   grouping fip-security-type {
     uses apply-advanced;
     list interface {
       key name;
       description "Configure access port security for this interface";
       leaf name {
         junos:must "(!(any \"vlans <*> interface $$ egress\"))";
         junos:must-message "Fip security options cannot be configured on egress members of a vlan";
         type union {
           type jt:interface-name;
           type string {
             pattern "<.*>|$.*";
           }
         }
       }
       uses apply-advanced;
       choice fcoe-trusted-choice {
         leaf fcoe-trusted {
           description "Make this interface trusted for FCoE";
           type empty;
         }
         leaf no-fcoe-trusted {
           description "Don't make this interface trusted for FCoE";
           type empty;
         }
       }
     }
     leaf fc-map {
       description "FCoE MAC address prefix";
       type string {
         junos:posix-pattern "^0x0EF[CD][abcdefABCDEF0123456789]{2}$";
         junos:pattern-message "Must be hexadecimal bit pattern of 0x0EFCHH or 0x0EFDHH";
       }
     }
     container examine-vn2vf {
       presence "enable examine-vn2vf";
       junos:must "(!(\".. examine-vn2vn\"))";
       junos:must-message "examine-vn2vf cannot be used with examine-vn2vn";
       description "Enable FIP snooping on this VLAN";
       uses apply-advanced;
       leaf satellite {
         description "FIP snooping enabled for extended port";
         type empty;
       }
     }
     container examine-vn2vn {
       presence "enable examine-vn2vn";
       junos:must "(!(\".. examine-vn2vf\"))";
       junos:must-message "examine-vn2vn cannot be used with examine-vn2vf";
       description "Enable VN2VN FIP snooping on this VLAN";
       uses apply-advanced;
       leaf beacon-period {
         description "FCoE VN2VN beacon period";
         default "8000";
         units "milliseconds";
         type union {
           type string {
             pattern "<.*>|$.*";
           }
           type uint32 {
             range "250 .. 90000";
           }
         }
       }
     }
   }
   grouping juniper-protocols-vlan {
     description "VLANs switch-options configuration";
     uses apply-advanced;
     container mac-table-size {
       junos:must "(!((\".. .. .. protocols vpls\" && \".. .. ..  instance-type virtual-switch\")))";
       junos:must-message "mac-table-size needs to be specified under switch-options for a virtual-switch instance";
       junos:must "(!(\".. .. .. .. vlans ${vlan} private-vlan\"))";
       junos:must-message "Switch-options configuration is not allowed on secondary VLANs";
       description "Size of MAC address forwarding table";
       uses apply-advanced;
       leaf limit {
         description "Maximum number of MAC addresses";
         type union {
           type string {
             pattern "<.*>|$.*";
           }
           type uint32;
         }
       }
       leaf packet-action {
         description "Action when MAC limit is reached";
         type enumeration {
           enum "none" {
             description "Forward the packet";
           }
           enum "drop" {
             description "Drop packets and do not learn. Default is forward";
           }
         }
       }
     }
     container mac-ip-table-size {
       junos:must "(!(((\".. .. .. protocols vpls\" || \".. .. .. protocols evpn\") && \".. .. ..  instance-type virtual-switch\")))";
       junos:must-message "mac-ip-table-size needs to be specified under switch-options for a virtual-switch instance";
       description "Size of MAC+IP bindings table";
       uses apply-advanced;
       leaf limit {
         description "Maximum number of MAC+IP bindings";
         type union {
           type string {
             pattern "<.*>|$.*";
           }
           type uint32;
         }
       }
     }
     container interface-mac-limit {
       junos:must "(!((\".. .. .. protocols vpls\" && \".. .. ..  instance-type virtual-switch\")))";
       junos:must-message "interface-mac-limit needs to be specified under switch-options for a virtual-switch instance";
       junos:must "(!(\".. .. .. .. vlans ${vlan} private-vlan\"))";
       junos:must-message "Switch-options configuration is not allowed on secondary VLANs";
       description "Maximum MAC address learned per interface";
       uses apply-advanced;
       leaf limit {
         description "Maximum number of MAC addresses per interface";
         type union {
           type string {
             pattern "<.*>|$.*";
           }
           type uint32;
         }
       }
       leaf packet-action {
         description "Action when MAC limit is reached";
         type enumeration {
           enum "none" {
             description "Forward the packet";
           }
           enum "drop" {
             description "Drop packets and do not learn. Default is forward";
           }
           enum "log" {
             description "Do not drop the packet but generate an alarm, an SNMP trap or a system log entry";
           }
           enum "shutdown" {
             description "Disable the interface and generate an alarm, an SNMP trap or a system log entry";
           }
           enum "drop-and-log" {
             description "Drop the packet and generate an alarm, an SNMP trap or a system log entry";
           }
         }
       }
     }
     container interface-mac-ip-limit {
       description "Maximum number of MAC+IP bindings learned on the interface";
       uses apply-advanced;
       leaf limit {
         description "Maximum number of MAC+IP bindings per interface";
         type union {
           type string {
             pattern "<.*>|$.*";
           }
           type uint32;
         }
       }
     }
     container mac-move-limit {
       presence "enable mac-move-limit";
       junos:must "(!(\".. .. .. .. vlans ${vlan} private-vlan\"))";
       junos:must-message "Switch-options configuration is not allowed on secondary VLANs";
       description "Number of MAC movements allowed on this VLAN";
       uses apply-advanced;
       leaf limit {
         description "Number of MAC movements allowed on this VLAN";
         type union {
           type string {
             pattern "<.*>|$.*";
           }
           type uint32 {
             range "1 .. 4294967295";
           }
         }
       }
       leaf packet-action {
         description "Action to be taken in case the MAC movement limit is exceeded";
         default "drop";
         type enumeration {
           enum "none" {
             description "Take no action";
           }
           enum "drop" {
             description "Drop the packet and do not generate an alarm";
           }
           enum "log" {
             description "Do not drop the packet but generate an alarm, an SNMP trap, or a system log entry.";
           }
           enum "shutdown" {
             description "Disable the interface and generate an alarm, an SNMP trap, or a system log entry.";
           }
           enum "drop-and-log" {
             description "Drop the packet and generate an alarm, an SNMP trap, or a system log entry.";
           }
           enum "vlan-member-shutdown" {
             description "Disable the interface of this VLAN";
           }
         }
       }
       list interface {
         key name;
         ordered-by user;
         description "Interface that connect this site to the VPN";
         leaf name {
           description "Interface name";
           type union {
             type jt:interface-name;
             type string {
               pattern "<.*>|$.*";
             }
           }
         }
         uses apply-advanced;
         leaf action-priority {
           description "Blocking priority of this interface on mac move detection";
           junos:must "(!(\".. .. .. .. .. vlans ${vlan} private-vlan\"))";
           junos:must-message "Switch-options configuration is not allowed on interfaces which are part of secondary VLANs";
           type union {
             type string {
               pattern "<.*>|$.*";
             }
             type uint32 {
               range "0 .. 7";
             }
           }
         }
       }
     }
     leaf mac-table-aging-time {
       description "Delay for discarding MAC address if no updates are received";
       units "seconds";
       type union {
         type string {
           pattern "<.*>|$.*";
         }
         type uint32;
       }
     }
     leaf no-mac-learning {
       description "Disable dynamic MAC address learning";
       junos:must "(!((\".. .. .. protocols vpls\" && \".. .. ..  instance-type virtual-switch\")))";
       junos:must-message "no-mac-learning needs to be specified under switch-options for a virtual-switch instance";
       junos:must "(!(\".. .. .. .. vlans ${vlan} private-vlan\"))";
       junos:must-message "Switch-options configuration is not allowed on secondary VLANs";
       type empty;
     }
     leaf no-normalization {
       description "Disable vlan id normalization for interfaces";
       type empty;
     }
     leaf mac-statistics {
       description "Enable MAC address statistics";
       junos:must "(!((\".. .. .. protocols vpls\" && \".. .. ..  instance-type virtual-switch\")))";
       junos:must-message "mac-statistics needs to be specified under switch-options for a virtual-switch instance";
       junos:must "(!(\".. .. .. .. vlans ${vlan} private-vlan\"))";
       junos:must-message "Switch-options configuration is not allowed on secondary VLANs";
       type empty;
     }
     container static-rvtep-mac {
       description "Configure Static MAC and remote VxLAN tunnel endpoint entries";
       uses apply-advanced;
       list mac {
         key "mac_addr remote-vtep";
         description "Unicast MAC address";
         leaf mac_addr {
           type jt:mac-unicast;
         }
         leaf remote-vtep {
           description "Configure static remote VXLAN tunnel endpoints";
           type jt:ipaddr;
         }
       }
     }
     list interface {
       key name;
       ordered-by user;
       description "Interface that connect this site to the VPN";
       junos:must "(!((\".. .. .. protocols vpls\" && \".. .. ..  instance-type virtual-switch\")))";
       junos:must-message "interface needs to be specified under switch-options for a virtual-switch instance";
       leaf name {
         description "Interface name";
         junos:must "(((\".. .. .. interface $$\" || (\".. .. .. .. .. interface $$\" || \"interfaces $$-IFL family ethernet-switching vlan\")) || \"interfaces $$-IFL family ethernet-switching\"))";
         junos:must-message "Interface must be part of this routing instance";
         junos:must "((\".. .. .. interface $$\" || (\".. .. .. .. .. interface $$\" || (\".. .. .. .. interface $$\" || \"interfaces $$-IFL family ethernet-switching\"))))";
         junos:must-message "Interface must be part of this routing instance";
         type union {
           type jt:interface-name;
           type string {
             pattern "<.*>|$.*";
           }
         }
       }
       uses apply-advanced;
       container interface-mac-limit {
         junos:must "(!(\".. .. .. .. .. vlans ${vlan} private-vlan\"))";
         junos:must-message "Switch-options configuration is not allowed on interfaces which are part of secondary VLANs";
         description "Maximum number of MAC addresses learned on the interface";
         uses apply-advanced;
         leaf limit {
           description "Maximum number of MAC addresses per interface";
           type union {
             type string {
               pattern "<.*>|$.*";
             }
             type uint32;
           }
         }
         leaf disable {
           description "Disable interface for interface-mac-limit";
           type empty;
         }
         leaf packet-action {
           description "Action when MAC limit is reached";
           type enumeration {
             enum "none" {
               description "Forward the packet";
             }
             enum "drop" {
               description "Drop packets and do not learn. Default is forward";
             }
             enum "log" {
               description "Do not drop the packet but generate an alarm, an SNMP trap or a system log entry";
             }
             enum "shutdown" {
               description "Disable the interface and generate an alarm, an SNMP trap or a system log entry";
             }
             enum "drop-and-log" {
               description "Drop the packet and generate an alarm, an SNMP trap or a system log entry";
             }
           }
         }
       }
       leaf action-priority {
         description "Blocking priority of this interface on mac move detection";
         junos:must "(!(\".. .. .. .. .. vlans ${vlan} private-vlan\"))";
         junos:must-message "Switch-options configuration is not allowed on interfaces which are part of secondary VLANs";
         type union {
           type string {
             pattern "<.*>|$.*";
           }
           type uint32 {
             range "0 .. 8";
           }
         }
       }
       list static-mac {
         key name;
         ordered-by user;
         description "Static MAC addresses assigned to this interface";
         junos:must "(!(\".. .. .. .. .. vlans ${vlan} private-vlan\"))";
         junos:must-message "Switch-options configuration is not allowed on interfaces which are part of secondary VLANs";
         leaf name {
           description "MAC address";
           junos:must "((!(\".. .. .. .. vlan-id all\") || all \".. vlan-id <*>\"))";
           junos:must-message " Specify vlan-id for qualified learning ";
           type jt:mac-addr;
         }
         uses apply-advanced;
         list vlan-id {
           key name;
           ordered-by user;
           description "VLAN ID of learning VLAN";
           junos:must "(\".. .. .. .. vlan-id all\")";
           junos:must-message "'vlan-id all' has to be configured for the bridging domain";
           leaf name {
             description "Learning VLAN";
             type union {
               type string {
                 pattern "<.*>|$.*";
               }
               type uint32 {
                 range "0 .. 4094";
               }
             }
           }
           uses apply-advanced;
         }
       }
       container interface-mac-ip-limit {
         description "Maximum number of MAC+IP bindings learned on the interface";
         uses apply-advanced;
         leaf limit {
           description "Maximum number of MAC+IP bindings per interface";
           type union {
             type string {
               pattern "<.*>|$.*";
             }
             type uint32;
           }
         }
       }
       leaf no-mac-learning {
         description "Disable dynamic MAC address learning";
         junos:must "(!(\".. .. .. .. .. vlans ${vlan} private-vlan\"))";
         junos:must-message "Switch-options configuration is not allowed on interfaces which are part of secondary VLANs";
         type empty;
       }
       leaf mac-pinning {
         description "Enable MAC pinning";
         type empty;
       }
       leaf persistent-learning {
         description "Enable persistent MAC learning on this interface";
         junos:must "(!(\"switch-options mac-table-aging-time \"))";
         junos:must-message "Persistent learning can not co-exist with mac-table-aging-time";
         type empty;
       }
     }
     container traceoptions {
       description "Trace options for this bridge domain";
       uses apply-advanced;
       leaf no-remote-trace {
         description "Disable remote tracing";
         junos:must "(\"system tracing\")";
         junos:must-message "'no-remote-trace' is valid only when [system tracing] is configured";
         type empty;
       }
       container file {
         description "Trace file information";
         leaf filename {
           description "Name of file in which to write trace information";
           type string {
             length "1 .. 1024";
             junos:posix-pattern "![/ %]";
             junos:pattern-message "Must not contain '/', % or a space";
           }
         }
         leaf size {
           description "Maximum trace file size";
           type string;
         }
         leaf files {
           description "Maximum number of trace files";
           default "3";
           type union {
             type string {
               pattern "<.*>|$.*";
             }
             type uint32 {
               range "2 .. 1000";
             }
           }
         }
         choice world-readable-choice {
           leaf world-readable {
             description "Allow any user to read the log file";
             type empty;
           }
           leaf no-world-readable {
             description "Don't allow any user to read the log file";
             type empty;
           }
         }
         leaf match {
           description "Regular expression for lines to be logged";
           type jt:regular-expression;
         }
       }
       leaf level {
         description "Level of debugging output";
         default "error";
         type enumeration {
           enum "error" {
             description "Match error conditions";
           }
           enum "warning" {
             description "Match warning messages";
           }
           enum "notice" {
             description "Match conditions that should be handled specially";
           }
           enum "info" {
             description "Match informational messages";
           }
           enum "verbose" {
             description "Match verbose messages";
           }
           enum "all" {
             description "Match all levels";
           }
         }
       }
       list flag {
         key name;
         ordered-by user;
         description "Type of operation or event to include in trace";
         leaf name {
           type enumeration {
             enum "configuration" {
               description "Configuration operations";
             }
             enum "routing-socket" {
               description "Routing socket operations";
             }
             enum "interface-device" {
               description "Interface device operations";
             }
             enum "interface-logical" {
               description "Logical interface operations";
             }
             enum "interface-family" {
               description "Interface family operations";
             }
             enum "learning-domain" {
               description "Learning domain operations";
             }
             enum "ipc" {
               description "Inter-process communications operations";
             }
             enum "mac-learning" {
               description "MAC address learning operations";
             }
             enum "initialization" {
               description "Initialization operations";
             }
             enum "flood-next-hop" {
               description "Flood next hop operations";
             }
             enum "storm-control" {
               description "Storm-control";
             }
             enum "unknown-unicast-forwarding" {
               description "Trace unknown unicast forwarding events";
             }
             enum "all" {
               description "All operations";
             }
           }
         }
       }
     }
   }
   grouping vlan_map {
     description "IEEE 802.1q Virtual LAN (VLAN) Tag mapping";
     uses apply-advanced;
     choice operation_choices {
       case case_1 {
         leaf push {
           description "Push a VLAN tag";
           type empty;
         }
       }
       case case_2 {
         leaf swap {
           description "Swap a VLAN tag";
           type empty;
         }
       }
       case case_3 {
         leaf pop {
           description "Pop a VLAN tag";
           type empty;
         }
       }
       case case_4 {
         leaf push-push {
           description "Push two VLAN tags";
           type empty;
         }
       }
       case case_5 {
         leaf swap-push {
           description "Swap VLAN tag and push a new VLAN tag";
           type empty;
         }
       }
       case case_6 {
         leaf swap-swap {
           description "Swap both outer and inner VLAN tags";
           type empty;
         }
       }
       case case_7 {
         leaf pop-swap {
           description "Pop outer VLAN tag and swap inner VLAN tag";
           type empty;
         }
       }
       case case_8 {
         leaf pop-pop {
           description "Pop both outer and inner VLAN tags";
           type empty;
         }
       }
     }
     leaf tag-protocol-id {
       description "IEEE 802.1q Tag Protocol Identifier to rewrite";
       type string {
         junos:posix-pattern "^0x[abcdefABCDEF0123456789]{4}$";
         junos:pattern-message "Must be hexadecimal bit pattern of form 0xNNNN";
       }
     }
     leaf inner-tag-protocol-id {
       description "IEEE 802.1q Tag Protocol ID to rewrite for inner tag";
       type string;
     }
     leaf vlan-id {
       description "VLAN ID to rewrite";
       type string;
     }
     leaf inner-vlan-id {
       description "VLAN ID to rewrite for inner tag";
       type string;
     }
   }
   grouping vni-range-type {
     leaf name {
       description "VNI range Lower limit";
       type union {
         type string {
           pattern "<.*>|$.*";
         }
         type uint32 {
           range "0 .. 16777215";
         }
       }
     }
     uses apply-advanced;
     container to {
       description "VNI range upper limit";
       uses apply-advanced;
       leaf range-high {
         description "Upper limit of vni range";
         type union {
           type string {
             pattern "<.*>|$.*";
           }
           type uint32 {
             range "0 .. 16777215";
           }
         }
       }
     }
   }
   grouping vrf-group-type {
     description "Configure vrf group object";
     leaf name {
       description "Vrf group name";
       type string {
         length "1 .. 64";
       }
     }
     uses apply-advanced;
     leaf-list vrf {
       ordered-by user;
       description "L3vpn vrf name";
       junos:must "(\"routing-instances $$ vrf-table-label\")";
       junos:must-message "referenced routing-instance must configured with vrf-table-label";
       junos:must "(\"routing-instances $$ instance-type vrf\")";
       junos:must-message "referenced routing-instance must be vrf type";
       type string;
     }
   }
   grouping vrrp-group {
     description "Virtual Router Redundancy Protocol group";
     leaf name {
       description "Identifier for VRRP group";
       type union {
         type string {
           pattern "<.*>|$.*";
         }
         type uint32 {
           range "0 .. 255";
         }
       }
     }
     uses apply-advanced;
     choice address {
       case case_1 {
         leaf-list virtual-address {
           ordered-by user;
           description "One or more virtual IPv4 addresses";
           type jt:ipv4addr;
         }
       }
       case case_2 {
         leaf-list virtual-inet6-address {
           ordered-by user;
           description "One or more virtual inet6 addresses";
           type jt:ipv6addr;
         }
       }
     }
     leaf virtual-link-local-address {
       description "Virtual link-local addresses";
       junos:must "(\".. .. vrrp-inet6-group\")";
       junos:must-message "'virtual-link-local-address' statement can be included only for interfaces of type 'family inet6'";
       type jt:ipv6addr;
     }
     leaf priority {
       description "Virtual router election priority";
       type union {
         type string {
           pattern "<.*>|$.*";
         }
         type uint32 {
           range "0 .. 255";
         }
       }
     }
     leaf preferred {
       description "Preferred group on subnet";
       type empty;
     }
     choice advertisement_type {
       case case_1 {
         leaf advertise-interval {
           description "Advertisement interval";
           units "seconds";
           type union {
             type string {
               pattern "<.*>|$.*";
             }
             type uint32 {
               range "1 .. 255";
             }
           }
         }
       }
       case case_2 {
         leaf fast-interval {
           description "Fast advertisement interval";
           units "milliseconds";
           type union {
             type string {
               pattern "<.*>|$.*";
             }
             type uint32 {
               range "10 .. 40950";
             }
           }
         }
       }
       case case_3 {
         leaf inet6-advertise-interval {
           description "Inet6 advertisement interval";
           units "milliseconds";
           type union {
             type string {
               pattern "<.*>|$.*";
             }
             type uint32 {
               range "100 .. 40000";
             }
           }
         }
       }
     }
     choice preempt_type {
       case case_1 {
         container preempt {
           presence "enable preempt";
           description "Allow preemption";
           uses apply-advanced;
           leaf hold-time {
             description "Preemption hold time";
             units "seconds";
             type union {
               type string {
                 pattern "<.*>|$.*";
               }
               type uint32 {
                 range "0 .. 3600";
               }
             }
           }
         }
       }
       case case_2 {
         leaf no-preempt {
           description "Don't allow preemption";
           type empty;
         }
       }
     }
     choice accept_type {
       case case_1 {
         leaf accept-data {
           description "Accept packets destined for virtual IP address";
           type empty;
         }
       }
       case case_2 {
         leaf no-accept-data {
           description "Don't accept packets destined for virtual IP address";
           type empty;
         }
       }
     }
     leaf authentication-type {
       description "Authentication type";
       junos:must "(\".. .. vrrp-group\")";
       junos:must-message "'authentication-type' statement can be included only for interfaces of type 'family inet'";
       type enumeration {
         enum "md5" {
           description "HMAC-MD5-96";
         }
         enum "simple" {
           description "Simple password";
         }
       }
     }
     leaf authentication-key {
       description "Authentication key";
       junos:must "(\".. .. vrrp-group\")";
       junos:must-message "'authentication-key' statement can be included only for interfaces of type 'family inet'";
       type jt:unreadable;
     }
     container track {
       description "Interfaces to track for VRRP group";
       uses apply-advanced;
       leaf priority-hold-time {
         description "Priority hold time";
         units "seconds";
         type union {
           type string {
             pattern "<.*>|$.*";
           }
           type uint32 {
             range "0 .. 3600";
           }
         }
       }
       list interface {
         key name;
         ordered-by user;
         description "Interface to track in VRRP group";
         leaf name {
           description "Name of interface";
           type union {
             type jt:interface-unit;
             type string {
               pattern "<.*>|$.*";
             }
           }
         }
         uses apply-advanced;
         list bandwidth-threshold {
           key name;
           description "Track bandwidth of interface";
           leaf name {
             description "Interface speed below which priority cost is incurred";
             units "bits per second";
             type string;
           }
           leaf priority-cost {
             description "Value subtracted from priority when bandwidth is below threshold";
             type union {
               type string {
                 pattern "<.*>|$.*";
               }
               type uint32 {
                 range "1 .. 254";
               }
             }
           }
         }
         leaf priority-cost {
           description "Value to subtract from priority when interface is down";
           type union {
             type string {
               pattern "<.*>|$.*";
             }
             type uint32 {
               range "1 .. 254";
             }
           }
         }
       }
       list route {
         key "route_address routing-instance";
         ordered-by user;
         description "Route to track in VRRP group";
         leaf route_address {
           description "Route address";
           type jt:ipprefix-mandatory;
         }
         leaf routing-instance {
           description "Routing instance to which route belongs, or 'default'";
           type string {
             junos:posix-pattern "!^((__.*__)|(all)|(.*[ ].*)|(\"\")|(.{129,}))$";
             junos:pattern-message "Must be a non-reserved string of 128 characters or less with no spaces.";
           }
         }
         leaf priority-cost {
           description "Value to subtract from priority when route is down";
           type union {
             type string {
               pattern "<.*>|$.*";
             }
             type uint32 {
               range "1 .. 254";
             }
           }
         }
       }
     }
     container vrrp-inherit-from {
       description "VRRP group to follow for this VRRP group";
       uses apply-advanced;
       leaf active-interface {
         description "Interface name of VRRP active group";
         type union {
           type jt:interface-unit;
           type string {
             pattern "<.*>|$.*";
           }
         }
       }
       leaf active-group {
         description "Identifier for VRRP active group";
         type union {
           type string {
             pattern "<.*>|$.*";
           }
           type uint32 {
             range "0 .. 255";
           }
         }
       }
     }
     leaf advertisements-threshold {
       description "Number of vrrp advertisements missed before declaring master down";
       type union {
         type string {
           pattern "<.*>|$.*";
         }
         type uint32 {
           range "1 .. 15";
         }
       }
     }
   }
   grouping vxlan-tunnel-type {
     description "Configure vxlan tunnel";
     leaf name {
       description "Vxlan tunnel name";
       type string {
         length "1 .. 63";
       }
     }
     uses apply-advanced;
     leaf policy-set {
       description "Define a security policy set";
       junos:must "((\".. .. .. .. security policies policy-set $$\" || \".. .. .. .. .. security policies policy-set $$\"))";
       junos:must-message "Security policy policy-set must be defined";
       type string {
         length "1 .. 63";
       }
     }
     list vni {
       key name;
       ordered-by user;
       description "Define VNI";
       max-elements 4096;
       uses vni-list-type;
     }
   }
   grouping vni-list-type {
     leaf name {
       description "VNI name";
       type string;
     }
   }
   grouping web-filtering-fallback-setting {
     description "Web-filtering fallback settings";
     uses apply-advanced;
     leaf default {
       description "Fallback default settings";
       type enumeration {
         enum "log-and-permit" {
         }
         enum "block" {
         }
       }
     }
     leaf server-connectivity {
       description "Fallback action when device cannot connect to server";
       type enumeration {
         enum "log-and-permit" {
         }
         enum "block" {
         }
       }
     }
     leaf timeout {
       description "Fallback action when connection to server timeout";
       type enumeration {
         enum "log-and-permit" {
         }
         enum "block" {
         }
       }
     }
     leaf too-many-requests {
       description "Fallback action when requests exceed the limit of engine";
       type enumeration {
         enum "log-and-permit" {
         }
         enum "block" {
         }
       }
     }
   }
   grouping web-filtering-traceoptions {
     description "Trace options for web-filtering feature";
     uses apply-advanced;
     list flag {
       key name;
       ordered-by user;
       description "Trace options for web-filtering feature trace flag";
       leaf name {
         description "Trace options for web-filtering feature trace flag name";
         type enumeration {
           enum "basic" {
             description "Trace web-filtering module generic basic information";
           }
           enum "session-manager" {
             description "Trace session management information";
           }
           enum "heartbeat" {
             description "Trace connectivity information with web-filter server";
           }
           enum "packet" {
             description "Trace packet information from session management";
           }
           enum "profile" {
             description "Trace profile config information";
           }
           enum "requests" {
             description "Trace requests sent to web-filter server";
           }
           enum "response" {
             description "Trace response received from web-filter server";
           }
           enum "socket" {
             description "Trace communication socket with web-filter server";
           }
           enum "timer" {
             description "Trace aging information for requests sent to server";
           }
           enum "ipc" {
             description "Trace communication events with PFE";
           }
           enum "cache" {
             description "Trace category cache operations";
           }
           enum "enhanced" {
             description "Trace Juniper enhanced web-filtering operations";
           }
           enum "all" {
             description "Enable trace all anti-virus trace options";
           }
         }
       }
     }
   }
   grouping webfilter-feature {
     description "Web-filtering feature settings";
     uses apply-advanced;
     container surf-control-integrated {
       description "Configure web-filtering surf-control integrated engine";
       status deprecated;
       uses surf-control-integrated-type;
     }
     container websense-redirect {
       description "Configure web-filtering websense redirect engine";
       uses websense-type;
     }
     container juniper-local {
       description "Configure web-filtering juniper local engine";
       uses juniper-local-type;
     }
     container juniper-enhanced {
       description "Configure web-filtering juniper enhanced engine";
       uses juniper-enhanced-type;
     }
   }
   grouping juniper-enhanced-type {
     description "Juniper Enhanced";
     uses apply-advanced;
     list profile {
       key name;
       ordered-by user;
       description "Juniper enhanced profile";
       leaf name {
         description "Juniper enhanced profile name";
         type string {
           length "1 .. 29";
         }
       }
       uses apply-advanced;
       leaf base-filter {
         description "Juniper base filter";
         type string;
       }
       list category {
         key name;
         ordered-by user;
         description "Juniper enhanced category";
         uses juniper-enhanced-category-type;
       }
       container site-reputation-action {
         description "Juniper enhanced site reputation action";
         presence "enable site-reputation-action";
         uses juniper-enhanced-site-reputation-setting;
       }
       leaf default {
         description "Juniper enhanced profile default";
         type enumeration {
           enum "permit" {
             description "Permit action";
           }
           enum "block" {
             description "Block action";
           }
           enum "log-and-permit" {
             description "Log and permit action";
           }
           enum "quarantine" {
             description "Quarantine action";
           }
         }
       }
       leaf custom-message {
         description "Custom message";
         junos:must "(\"security utm custom-objects custom-message $$\")";
         junos:must-message "custom-message must be defined";
         type string;
       }
       container fallback-settings {
         description "Juniper enhanced fallback settings";
         presence "enable fallback-settings";
         uses web-filtering-fallback-setting;
       }
       leaf timeout {
         description "Juniper enhanced timeout";
         units "seconds";
         type union {
           type string {
             pattern "<.*>|$.*";
           }
           type uint32;
         }
       }
       leaf no-safe-search {
         description "Do not perform safe-search for Juniper enhanced protocol";
         type empty;
       }
     }
   }
   grouping juniper-local-type {
     description "Juniper local";
     uses apply-advanced;
     list profile {
       key name;
       ordered-by user;
       description "Juniper local profile";
       leaf name {
         description "Juniper local profile name";
         type string {
           length "1 .. 29";
         }
       }
       uses apply-advanced;
       leaf default {
         description "Juniper local profile default";
         type enumeration {
           enum "permit" {
             description "Permit action";
           }
           enum "block" {
             description "Block action";
           }
           enum "log-and-permit" {
             description "Log and permit action";
           }
         }
       }
       list category {
         key name;
         ordered-by user;
         description "Custom category";
         uses custom-category-type;
       }
       leaf custom-message {
         description "Custom message";
         junos:must "(\"security utm custom-objects custom-message $$\")";
         junos:must-message "custom-message must be defined";
         type string;
       }
       leaf no-safe-search {
         description "Do not perform safe-search for Juniper local protocol";
         type empty;
       }
       container fallback-settings {
         description "Juniper local fallback settings";
         presence "enable fallback-settings";
         uses web-filtering-fallback-setting;
       }
       leaf timeout {
         description "Juniper local timeout";
         units "seconds";
         type union {
           type string {
             pattern "<.*>|$.*";
           }
           type uint32 {
             range "1 .. 1800";
           }
         }
       }
     }
   }
   grouping surf-control-integrated-type {
     description "Surf control integrated";
     uses apply-advanced;
     container cache {
       presence "enable cache";
       uses apply-advanced;
       leaf timeout {
         description "Surf control integrated cache timeout";
         default "1440";
         units "minutes";
         type union {
           type string {
             pattern "<.*>|$.*";
           }
           type uint32 {
             range "1 .. 1800";
           }
         }
       }
       leaf size {
         description "Surf control integrated cache size";
         default "1024";
         units "kilobytes";
         type string;
       }
     }
     container server {
       description "Surf control server";
       presence "enable server";
       uses server;
     }
     list profile {
       key name;
       ordered-by user;
       description "Surf control integrated profile";
       leaf name {
         description "Surf control integrated profile name";
         type string {
           length "1 .. 29";
         }
       }
       uses apply-advanced;
       list category {
         key name;
         ordered-by user;
         description "Surf control integrated category";
         uses surf-control-integrated-category-type;
       }
       leaf default {
         description "Surf control integrated profile default";
         type enumeration {
           enum "permit" {
             description "Permit action";
           }
           enum "block" {
             description "Block action";
           }
           enum "log-and-permit" {
             description "Log and permit action";
           }
         }
       }
       leaf custom-block-message {
         description "Surf control integrated custom block message";
         type string {
           length "1 .. 512";
         }
       }
       container fallback-settings {
         description "Surf control integrated fallback settings";
         presence "enable fallback-settings";
         uses web-filtering-fallback-setting;
       }
       leaf timeout {
         description "Surf control integrated timeout";
         default "15";
         units "seconds";
         type union {
           type string {
             pattern "<.*>|$.*";
           }
           type uint32 {
             range "1 .. 1800";
           }
         }
       }
     }
   }
   grouping surf-control-integrated-category-type {
     description "Surf control integrated category type";
     leaf name {
       description "Surf control integrated category type name";
       type string {
         length "1 .. 59";
       }
     }
     uses apply-advanced;
     leaf action {
       description "Surf control integrated category type action";
       type enumeration {
         enum "permit" {
           description "Permit action";
         }
         enum "block" {
           description "Block action";
         }
         enum "log-and-permit" {
           description "Log and permit action";
         }
       }
     }
   }
   grouping websense-type {
     description "Websense redirect";
     uses apply-advanced;
     list profile {
       key name;
       ordered-by user;
       description "Websense redirect profile";
       leaf name {
         description "Websense redirect profile name";
         type string {
           length "1 .. 29";
         }
       }
       uses apply-advanced;
       container server {
         description "Websense redirect server";
         presence "enable server";
         uses server;
       }
       list category {
         key name;
         ordered-by user;
         description "Custom category";
         uses custom-category-type;
       }
       leaf custom-message {
         description "Custom message";
         junos:must "(\"security utm custom-objects custom-message $$\")";
         junos:must-message "custom-message must be defined";
         type string;
       }
       leaf no-safe-search {
         description "Do not perform safe-search for websense redirect protocol";
         type empty;
       }
       container fallback-settings {
         description "Websense redirect fallback settings";
         presence "enable fallback-settings";
         uses web-filtering-fallback-setting;
       }
       leaf timeout {
         description "Websense redirect timeout";
         units "seconds";
         type union {
           type string {
             pattern "<.*>|$.*";
           }
           type uint32 {
             range "1 .. 1800";
           }
         }
       }
       leaf sockets {
         description "Websense redirect sockets number";
         type union {
           type string {
             pattern "<.*>|$.*";
           }
           type uint32 {
             range "1 .. 32";
           }
         }
       }
       leaf account {
         description "Websense redirect account";
         type string {
           length "1 .. 28";
         }
       }
     }
   }
   grouping wildcard-address-type {
     description "Wildcard address and mask";
     leaf name {
       description "Numeric IPv4 wildcard address with in the form of a.d.d.r/netmask";
       type string {
         length "1 .. 63";
       }
     }
     uses apply-advanced;
   }
   grouping write-option-82-type {
     uses apply-advanced;
   }
   grouping zone-interface-list-type {
     description "Logical interfaces in this zone";
     leaf name {
       description "Logical interface";
       junos:must "(!((\"protocols l2-learning global-mode switching\" && \"interfaces $$ family ethernet-switching\")))";
       junos:must-message "Referenced interface must not be ethernet-switching interface of switching mode";
       type union {
         type jt:interface-name;
         type string {
           pattern "<.*>|$.*";
         }
       }
     }
     uses apply-advanced;
     container host-inbound-traffic {
       uses interface_host_inbound_traffic_t;
     }
   }
   grouping interface_host_inbound_traffic_t {
     uses apply-advanced;
     list system-services {
       key name;
       ordered-by user;
       description "Type of incoming system-service traffic to accept";
       uses interface-system-services-object-type;
     }
     list protocols {
       key name;
       ordered-by user;
       description "Protocol type of incoming traffic to accept";
       uses host-inbound-protocols-object-type;
     }
   }
   grouping host-inbound-protocols-object-type {
     description "Protocol type of incoming traffic to accept";
     leaf name {
       description "Protocol name";
       type enumeration {
         enum "all" {
           description "All protocols";
         }
         enum "bfd" {
           description "Bidirectional Forwarding Detection";
         }
         enum "bgp" {
           description "Border Gateway Protocol";
         }
         enum "dvmrp" {
           description "Distance Vector Multicast Routing Protocol";
         }
         enum "igmp" {
           description "Internet Group Management Protocol";
         }
         enum "ldp" {
           description "Label Distribution Protocol";
         }
         enum "msdp" {
           description "Multicast Source Discovery Protocol";
         }
         enum "ndp" {
           description "IPv6 Neighbor Discovery Protocol";
         }
         enum "nhrp" {
           description "Next Hop Resolution Protocol";
         }
         enum "ospf" {
           description "Open Shortest Path First";
         }
         enum "ospf3" {
           description "Open Shortest Path First version 3";
         }
         enum "pgm" {
           description "Pragmatic General Multicast";
         }
         enum "pim" {
           description "Protocol Independent Multicast";
         }
         enum "rip" {
           description "Routing Information Protocol";
         }
         enum "ripng" {
           description "Routing Information Protocol next generation";
         }
         enum "router-discovery" {
           description "Router Discovery";
         }
         enum "rsvp" {
           description "Resource Reservation Protocol";
         }
         enum "sap" {
           description "Session Announcement Protocol";
         }
         enum "vrrp" {
           description "Virtual Router Redundancy Protocol";
         }
       }
     }
     uses apply-advanced;
     leaf except {
       description "Protocol type of incoming traffic to disallow";
       junos:must "(\".. .. protocols all\")";
       junos:must-message "'except'' statement can be included only along with 'protocols all' statement";
       type empty;
     }
   }
   grouping interface-system-services-object-type {
     description "Type of incoming system-service traffic to accept";
     leaf name {
       type enumeration {
         enum "all" {
           description "All system services";
           junos:must "(!(\".. .. system-services $$={any-service}\"))";
           junos:must-message "If `any` is set other services are disallowed";
         }
         enum "bootp" {
           description "Bootp and dhcp relay-agent service";
           junos:must "(!(\".. .. system-services $$={any-service}\"))";
           junos:must-message "If `any` is set other services are disallowed";
         }
         enum "dhcp" {
           description "Dynamic Host Configuration Protocol";
           junos:must "(!(\".. .. system-services $$={any-service}\"))";
           junos:must-message "If `any` is set other services are disallowed";
         }
         enum "dhcpv6" {
           description "Enable Dynamic Host Configuration Protocol for IPv6";
           junos:must "(!(\".. .. system-services $$={any-service}\"))";
           junos:must-message "If `any` is set other services are disallowed";
         }
         enum "dns" {
           description "DNS service";
           junos:must "(!(\".. .. system-services $$={any-service}\"))";
           junos:must-message "If `any` is set other services are disallowed";
         }
         enum "finger" {
           description "Finger service";
           junos:must "(!(\".. .. system-services $$={any-service}\"))";
           junos:must-message "If `any` is set other services are disallowed";
         }
         enum "ftp" {
           description "FTP";
           junos:must "(!(\".. .. system-services $$={any-service}\"))";
           junos:must-message "If `any` is set other services are disallowed";
         }
         enum "ident-reset" {
           description "Send back TCP RST to IDENT request for port 113";
           junos:must "(!(\".. .. system-services $$={any-service}\"))";
           junos:must-message "If `any` is set other services are disallowed";
         }
         enum "http" {
           description "Web management service using HTTP";
           junos:must "(!(\".. .. system-services $$={any-service}\"))";
           junos:must-message "If `any` is set other services are disallowed";
         }
         enum "https" {
           description "Web management service using HTTP secured by SSL";
           junos:must "(!(\".. .. system-services $$={any-service}\"))";
           junos:must-message "If `any` is set other services are disallowed";
         }
         enum "ike" {
           description "Internet Key Exchange";
           junos:must "(!(\".. .. system-services $$={any-service}\"))";
           junos:must-message "If `any` is set other services are disallowed";
         }
         enum "netconf" {
           description "NETCONF service";
           junos:must "(!(\".. .. system-services $$={any-service}\"))";
           junos:must-message "If `any` is set other services are disallowed";
         }
         enum "ping" {
           description "Internet Control Message Protocol echo requests";
           junos:must "(!(\".. .. system-services $$={any-service}\"))";
           junos:must-message "If `any` is set other services are disallowed";
         }
         enum "rlogin" {
           description "Rlogin service";
           junos:must "(!(\".. .. system-services $$={any-service}\"))";
           junos:must-message "If `any` is set other services are disallowed";
         }
         enum "reverse-telnet" {
           description "Reverse telnet service";
           junos:must "(!(\".. .. system-services $$={any-service}\"))";
           junos:must-message "If `any` is set other services are disallowed";
         }
         enum "reverse-ssh" {
           description "Reverse SSH service";
           junos:must "(!(\".. .. system-services $$={any-service}\"))";
           junos:must-message "If `any` is set other services are disallowed";
         }
         enum "rpm" {
           description "Real-time performance monitoring";
           junos:must "(!(\".. .. system-services $$={any-service}\"))";
           junos:must-message "If `any` is set other services are disallowed";
         }
         enum "rsh" {
           description "Rsh service";
           junos:must "(!(\".. .. system-services $$={any-service}\"))";
           junos:must-message "If `any` is set other services are disallowed";
         }
         enum "snmp" {
           description "Simple Network Management Protocol service";
           junos:must "(!(\".. .. system-services $$={any-service}\"))";
           junos:must-message "If `any` is set other services are disallowed";
         }
         enum "snmp-trap" {
           description "Simple Network Management Protocol traps";
           junos:must "(!(\".. .. system-services $$={any-service}\"))";
           junos:must-message "If `any` is set other services are disallowed";
         }
         enum "ssh" {
           description "SSH service";
           junos:must "(!(\".. .. system-services $$={any-service}\"))";
           junos:must-message "If `any` is set other services are disallowed";
         }
         enum "telnet" {
           description "Telnet service";
           junos:must "(!(\".. .. system-services $$={any-service}\"))";
           junos:must-message "If `any` is set other services are disallowed";
         }
         enum "traceroute" {
           description "Traceroute service";
           junos:must "(!(\".. .. system-services $$={any-service}\"))";
           junos:must-message "If `any` is set other services are disallowed";
         }
         enum "xnm-ssl" {
           description "JUNOScript API service over SSL";
           junos:must "(!(\".. .. system-services $$={any-service}\"))";
           junos:must-message "If `any` is set other services are disallowed";
         }
         enum "xnm-clear-text" {
           description "JUNOScript API for unencrypted traffic over TCP";
           junos:must "(!(\".. .. system-services $$={any-service}\"))";
           junos:must-message "If `any` is set other services are disallowed";
         }
         enum "tftp" {
           description "TFTP";
           junos:must "(!(\".. .. system-services $$={any-service}\"))";
           junos:must-message "If `any` is set other services are disallowed";
         }
         enum "lsping" {
           description "Label Switched Path ping service";
           junos:must "(!(\".. .. system-services $$={any-service}\"))";
           junos:must-message "If `any` is set other services are disallowed";
         }
         enum "ntp" {
           description "Network Time Protocol service";
           junos:must "(!(\".. .. system-services $$={any-service}\"))";
           junos:must-message "If `any` is set other services are disallowed";
         }
         enum "sip" {
           description "Enable Session Initiation Protocol service";
           junos:must "(!(\".. .. system-services $$={any-service}\"))";
           junos:must-message "If `any` is set other services are disallowed";
         }
         enum "r2cp" {
           description "Enable Radio-Router Control Protocol service";
           junos:must "(!(\".. .. system-services $$={any-service}\"))";
           junos:must-message "If `any` is set other services are disallowed";
         }
         enum "webapi-clear-text" {
           description "Webapi service using http";
           junos:must "(!(\".. .. system-services $$={any-service}\"))";
           junos:must-message "If `any` is set other services are disallowed";
         }
         enum "webapi-ssl" {
           description "Webapi service using HTTP secured by SSL";
           junos:must "(!(\".. .. system-services $$={any-service}\"))";
           junos:must-message "If `any` is set other services are disallowed";
         }
         enum "tcp-encap" {
           description "Tcp encapsulation service";
           junos:must "(!(\".. .. system-services $$={any-service}\"))";
           junos:must-message "If `any` is set other services are disallowed";
         }
         enum "appqoe" {
           description "APPQOE active probe service";
           junos:must "(!(\".. .. system-services $$={any-service}\"))";
           junos:must-message "If `any` is set other services are disallowed";
         }
         enum "high-availability" {
           description "High Availability service";
           junos:must "(!(\".. .. system-services $$={any-service}\"))";
           junos:must-message "If `any` is set other services are disallowed";
         }
         enum "any-service" {
           description "Enable services on entire port range";
         }
       }
     }
     uses apply-advanced;
     leaf except {
       description "Type of incoming system-service traffic to disallow";
       junos:must "(\".. .. system-services all\")";
       junos:must-message "'except'' statement can be included only along with 'system-services all' statement";
       type empty;
     }
   }
   grouping zone_host_inbound_traffic_t {
     uses apply-advanced;
     list system-services {
       key name;
       ordered-by user;
       description "Type of incoming system-service traffic to accept";
       uses zone-system-services-object-type;
     }
     list protocols {
       key name;
       ordered-by user;
       description "Protocol type of incoming traffic to accept";
       uses host-inbound-protocols-object-type;
     }
   }
   grouping zone-system-services-object-type {
     description "Type of incoming system-service traffic to accept";
     leaf name {
       type enumeration {
         enum "all" {
           description "All system services";
           junos:must "(!(\".. .. system-services $$={any-service}\"))";
           junos:must-message "If `any` is set other services are disallowed";
         }
         enum "bootp" {
           description "Bootp and dhcp relay-agent service";
           junos:must "(!(\".. .. system-services $$={any-service}\"))";
           junos:must-message "If `any` is set other services are disallowed";
         }
         enum "dhcp" {
           description "Dynamic Host Configuration Protocol";
           junos:must "(!(\".. .. system-services $$={any-service}\"))";
           junos:must-message "If `any` is set other services are disallowed";
         }
         enum "dhcpv6" {
           description "Enable Dynamic Host Configuration Protocol for IPv6";
           junos:must "(!(\".. .. system-services $$={any-service}\"))";
           junos:must-message "If `any` is set other services are disallowed";
         }
         enum "dns" {
           description "DNS service";
           junos:must "(!(\".. .. system-services $$={any-service}\"))";
           junos:must-message "If `any` is set other services are disallowed";
         }
         enum "finger" {
           description "Finger service";
           junos:must "(!(\".. .. system-services $$={any-service}\"))";
           junos:must-message "If `any` is set other services are disallowed";
         }
         enum "ftp" {
           description "FTP";
           junos:must "(!(\".. .. system-services $$={any-service}\"))";
           junos:must-message "If `any` is set other services are disallowed";
         }
         enum "ident-reset" {
           description "Send back TCP RST to IDENT request for port 113";
           junos:must "(!(\".. .. system-services $$={any-service}\"))";
           junos:must-message "If `any` is set other services are disallowed";
         }
         enum "http" {
           description "Web management service using HTTP";
           junos:must "(!(\".. .. system-services $$={any-service}\"))";
           junos:must-message "If `any` is set other services are disallowed";
         }
         enum "https" {
           description "Web management service using HTTP secured by SSL";
           junos:must "(!(\".. .. system-services $$={any-service}\"))";
           junos:must-message "If `any` is set other services are disallowed";
         }
         enum "ike" {
           description "Internet Key Exchange";
           junos:must "(!(\".. .. system-services $$={any-service}\"))";
           junos:must-message "If `any` is set other services are disallowed";
         }
         enum "netconf" {
           description "NETCONF service";
           junos:must "(!(\".. .. system-services $$={any-service}\"))";
           junos:must-message "If `any` is set other services are disallowed";
         }
         enum "ping" {
           description "Internet Control Message Protocol echo requests";
           junos:must "(!(\".. .. system-services $$={any-service}\"))";
           junos:must-message "If `any` is set other services are disallowed";
         }
         enum "rlogin" {
           description "Rlogin service";
           junos:must "(!(\".. .. system-services $$={any-service}\"))";
           junos:must-message "If `any` is set other services are disallowed";
         }
         enum "reverse-telnet" {
           description "Reverse telnet service";
           junos:must "(!(\".. .. system-services $$={any-service}\"))";
           junos:must-message "If `any` is set other services are disallowed";
         }
         enum "reverse-ssh" {
           description "Reverse SSH service";
           junos:must "(!(\".. .. system-services $$={any-service}\"))";
           junos:must-message "If `any` is set other services are disallowed";
         }
         enum "rpm" {
           description "Real-time performance monitoring";
           junos:must "(!(\".. .. system-services $$={any-service}\"))";
           junos:must-message "If `any` is set other services are disallowed";
         }
         enum "rsh" {
           description "Rsh service";
           junos:must "(!(\".. .. system-services $$={any-service}\"))";
           junos:must-message "If `any` is set other services are disallowed";
         }
         enum "snmp" {
           description "Simple Network Management Protocol service";
           junos:must "(!(\".. .. system-services $$={any-service}\"))";
           junos:must-message "If `any` is set other services are disallowed";
         }
         enum "snmp-trap" {
           description "Simple Network Management Protocol traps";
           junos:must "(!(\".. .. system-services $$={any-service}\"))";
           junos:must-message "If `any` is set other services are disallowed";
         }
         enum "ssh" {
           description "SSH service";
           junos:must "(!(\".. .. system-services $$={any-service}\"))";
           junos:must-message "If `any` is set other services are disallowed";
         }
         enum "telnet" {
           description "Telnet service";
           junos:must "(!(\".. .. system-services $$={any-service}\"))";
           junos:must-message "If `any` is set other services are disallowed";
         }
         enum "traceroute" {
           description "Traceroute service";
           junos:must "(!(\".. .. system-services $$={any-service}\"))";
           junos:must-message "If `any` is set other services are disallowed";
         }
         enum "xnm-ssl" {
           description "JUNOScript API service over SSL";
           junos:must "(!(\".. .. system-services $$={any-service}\"))";
           junos:must-message "If `any` is set other services are disallowed";
         }
         enum "xnm-clear-text" {
           description "JUNOScript API for unencrypted traffic over TCP";
           junos:must "(!(\".. .. system-services $$={any-service}\"))";
           junos:must-message "If `any` is set other services are disallowed";
         }
         enum "tftp" {
           description "TFTP";
           junos:must "(!(\".. .. system-services $$={any-service}\"))";
           junos:must-message "If `any` is set other services are disallowed";
         }
         enum "lsping" {
           description "Label Switched Path ping service";
           junos:must "(!(\".. .. system-services $$={any-service}\"))";
           junos:must-message "If `any` is set other services are disallowed";
         }
         enum "ntp" {
           description "Network Time Protocol service";
           junos:must "(!(\".. .. system-services $$={any-service}\"))";
           junos:must-message "If `any` is set other services are disallowed";
         }
         enum "sip" {
           description "Enable Session Initiation Protocol service";
           junos:must "(!(\".. .. system-services $$={any-service}\"))";
           junos:must-message "If `any` is set other services are disallowed";
         }
         enum "r2cp" {
           description "Enable Radio-Router Control Protocol service";
           junos:must "(!(\".. .. system-services $$={any-service}\"))";
           junos:must-message "If `any` is set other services are disallowed";
         }
         enum "webapi-clear-text" {
           description "Webapi service using http";
           junos:must "(!(\".. .. system-services $$={any-service}\"))";
           junos:must-message "If `any` is set other services are disallowed";
         }
         enum "webapi-ssl" {
           description "Webapi service using HTTP secured by SSL";
           junos:must "(!(\".. .. system-services $$={any-service}\"))";
           junos:must-message "If `any` is set other services are disallowed";
         }
         enum "tcp-encap" {
           description "Tcp encapsulation service";
           junos:must "(!(\".. .. system-services $$={any-service}\"))";
           junos:must-message "If `any` is set other services are disallowed";
         }
         enum "appqoe" {
           description "APPQOE active probe service";
           junos:must "(!(\".. .. system-services $$={any-service}\"))";
           junos:must-message "If `any` is set other services are disallowed";
         }
         enum "high-availability" {
           description "High Availability service";
           junos:must "(!(\".. .. system-services $$={any-service}\"))";
           junos:must-message "If `any` is set other services are disallowed";
         }
         enum "any-service" {
           description "Enable services on entire port range";
         }
       }
     }
     uses apply-advanced;
     leaf except {
       description "Type of incoming system-service traffic to disallow";
       junos:must "(\".. .. system-services all\")";
       junos:must-message "'except'' statement can be included only along with 'system-services all' statement";
       type empty;
     }
   }
 }
