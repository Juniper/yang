/*
 * Copyright (c) 2021 Juniper Networks, Inc.
 * All rights reserved.
 */
 module junos-ex-conf-class-of-service {
   namespace "http://yang.juniper.net/junos-ex/conf/class-of-service";

   prefix jc-class-of-service;

   import junos-common-ddl-extensions {
     prefix junos;
     revision-date 2019-01-01;
   }

   import junos-common-types {
     prefix jt;
     revision-date 2019-01-01;
   }

   import junos-ex-conf-root {
     prefix jc;
     revision-date 2019-01-01;
   }

   organization "Juniper Networks, Inc.";

   contact "yang-support@juniper.net";

   description "Junos class-of-service configuration module";

   revision 2019-01-01 {
     description "Junos: 21.4R1.12";
   }

   augment /jc:configuration {
     uses class-of-service-group;
   }
   augment /jc:configuration/jc:groups {
     uses class-of-service-group;
   }
   grouping class-of-service-group {
     container class-of-service {
       description "Class-of-service configuration";
       uses juniper-class-of-service-options;
     }
   }
   grouping juniper-class-of-service-options {
     uses apply-advanced;
     container classifiers {
       description "Classify incoming packets based on code point value";
       uses apply-advanced;
       list dscp {
         key name;
         ordered-by user;
         description "Differentiated Services code point classifier";
         leaf name {
           description "Classifier name";
           junos:must "((\".. forwarding-class\" || \".. import\"))";
           junos:must-message "'At least one 'forwarding class' or 'import' classifier definition is required for classifier configuration";
           type string {
             length "1 .. 64";
           }
         }
         uses apply-advanced;
         leaf import {
           description "Include this classifier in this definition";
           type union {
             type string {
               pattern "default";
             }
             type string {
               length "1 .. 64";
             }
           }
         }
         list forwarding-class {
           key name;
           description "Define a classification of code point aliases";
           leaf name {
             description "Forwarding class name";
             type string {
               length "1 .. 64";
             }
           }
           uses apply-advanced;
           list loss-priority {
             key name;
             description "Classify code points to a loss priority";
             leaf name {
               type enumeration {
                 enum "low" {
                   description "Code points to classify to loss priority low";
                 }
                 enum "high" {
                   description "Code points to classify to loss priority high";
                 }
                 enum "medium-low" {
                   description "Code points to classify to loss priority medium-low";
                 }
                 enum "medium-high" {
                   description "Code points to classify to loss priority medium-high";
                 }
               }
             }
             leaf-list code-points {
               ordered-by user;
               description "List of code point aliases and/or bit strings";
               type string;
             }
           }
         }
       }
       list dscp-ipv6 {
         key name;
         ordered-by user;
         description "Differentiated Services code point classifier IPv6";
         leaf name {
           description "Classifier name";
           junos:must "((\".. forwarding-class\" || \".. import\"))";
           junos:must-message "'At least one 'forwarding class' or 'import' classifier definition is required for classifier configuration";
           type string {
             length "1 .. 64";
           }
         }
         uses apply-advanced;
         leaf import {
           description "Include this classifier in this definition";
           type union {
             type string {
               pattern "default";
             }
             type string {
               length "1 .. 64";
             }
           }
         }
         list forwarding-class {
           key name;
           description "Define a classification of code point aliases";
           leaf name {
             description "Forwarding class name";
             type string {
               length "1 .. 64";
             }
           }
           uses apply-advanced;
           list loss-priority {
             key name;
             description "Classify code points to a loss priority";
             leaf name {
               type enumeration {
                 enum "low" {
                   description "Code points to classify to loss priority low";
                 }
                 enum "high" {
                   description "Code points to classify to loss priority high";
                 }
                 enum "medium-low" {
                   description "Code points to classify to loss priority medium-low";
                 }
                 enum "medium-high" {
                   description "Code points to classify to loss priority medium-high";
                 }
               }
             }
             leaf-list code-points {
               ordered-by user;
               description "List of code point aliases and/or bit strings";
               type string;
             }
           }
         }
       }
       list exp {
         key name;
         ordered-by user;
         description "MPLS EXP classifier";
         leaf name {
           description "Classifier name";
           junos:must "((\".. forwarding-class\" || \".. import\"))";
           junos:must-message "'At least one 'forwarding class' or 'import' classifier definition is required for classifier configuration";
           type string {
             length "1 .. 64";
           }
         }
         uses apply-advanced;
         leaf import {
           description "Include this classifier in this definition";
           type union {
             type string {
               pattern "default";
             }
             type string {
               length "1 .. 64";
             }
           }
         }
         list forwarding-class {
           key name;
           description "Define a classification of code point aliases";
           leaf name {
             description "Forwarding class name";
             type string {
               length "1 .. 64";
             }
           }
           uses apply-advanced;
           list loss-priority {
             key name;
             description "Classify code points to a loss priority";
             leaf name {
               type enumeration {
                 enum "low" {
                   description "Code points to classify to loss priority low";
                 }
                 enum "high" {
                   description "Code points to classify to loss priority high";
                 }
                 enum "medium-low" {
                   description "Code points to classify to loss priority medium-low";
                 }
                 enum "medium-high" {
                   description "Code points to classify to loss priority medium-high";
                 }
               }
             }
             leaf-list code-points {
               ordered-by user;
               description "List of code point aliases and/or bit strings";
               type string;
             }
           }
         }
       }
       list ieee-802.1 {
         key name;
         ordered-by user;
         description "IEEE-802.1 classifier";
         leaf name {
           description "Classifier name";
           junos:must "((\".. forwarding-class\" || \".. import\"))";
           junos:must-message "'At least one 'forwarding class' or 'import' classifier definition is required for classifier configuration";
           type string {
             length "1 .. 64";
           }
         }
         uses apply-advanced;
         leaf import {
           description "Include this classifier in this definition";
           type union {
             type string {
               pattern "default";
             }
             type string {
               length "1 .. 64";
             }
           }
         }
         list forwarding-class {
           key name;
           description "Define a classification of code point aliases";
           leaf name {
             description "Forwarding class name";
             type string {
               length "1 .. 64";
             }
           }
           uses apply-advanced;
           list loss-priority {
             key name;
             description "Classify code points to a loss priority";
             leaf name {
               type enumeration {
                 enum "low" {
                   description "Code points to classify to loss priority low";
                 }
                 enum "high" {
                   description "Code points to classify to loss priority high";
                 }
                 enum "medium-low" {
                   description "Code points to classify to loss priority medium-low";
                 }
                 enum "medium-high" {
                   description "Code points to classify to loss priority medium-high";
                 }
               }
             }
             leaf-list code-points {
               ordered-by user;
               description "List of code point aliases and/or bit strings";
               type string;
             }
           }
         }
       }
       list inet-precedence {
         key name;
         ordered-by user;
         description "IPv4 precedence classifier";
         leaf name {
           description "Classifier name";
           junos:must "((\".. forwarding-class\" || \".. import\"))";
           junos:must-message "'At least one 'forwarding class' or 'import' classifier definition is required for classifier configuration";
           type string {
             length "1 .. 64";
           }
         }
         uses apply-advanced;
         leaf import {
           description "Include this classifier in this definition";
           type union {
             type string {
               pattern "default";
             }
             type string {
               length "1 .. 64";
             }
           }
         }
         list forwarding-class {
           key name;
           description "Define a classification of code point aliases";
           leaf name {
             description "Forwarding class name";
             type string {
               length "1 .. 64";
             }
           }
           uses apply-advanced;
           list loss-priority {
             key name;
             description "Classify code points to a loss priority";
             leaf name {
               type enumeration {
                 enum "low" {
                   description "Code points to classify to loss priority low";
                 }
                 enum "high" {
                   description "Code points to classify to loss priority high";
                 }
                 enum "medium-low" {
                   description "Code points to classify to loss priority medium-low";
                 }
                 enum "medium-high" {
                   description "Code points to classify to loss priority medium-high";
                 }
               }
             }
             leaf-list code-points {
               ordered-by user;
               description "List of code point aliases and/or bit strings";
               type string;
             }
           }
         }
       }
       list ieee-802.1ad {
         key name;
         ordered-by user;
         description "IEEE-802.1ad (DEI) classifier";
         leaf name {
           description "Classifier name";
           junos:must "((\".. forwarding-class\" || \".. import\"))";
           junos:must-message "'At least one 'forwarding class' or 'import' classifier definition is required for classifier configuration";
           type string {
             length "1 .. 64";
           }
         }
         uses apply-advanced;
         leaf import {
           description "Include this classifier in this definition";
           type union {
             type string {
               pattern "default";
             }
             type string {
               length "1 .. 64";
             }
           }
         }
         list forwarding-class {
           key name;
           description "Define a classification of code point aliases";
           leaf name {
             description "Forwarding class name";
             type string {
               length "1 .. 64";
             }
           }
           uses apply-advanced;
           list loss-priority {
             key name;
             description "Classify code points to a loss priority";
             leaf name {
               type enumeration {
                 enum "low" {
                   description "Code points to classify to loss priority low";
                 }
                 enum "high" {
                   description "Code points to classify to loss priority high";
                 }
                 enum "medium-low" {
                   description "Code points to classify to loss priority medium-low";
                 }
                 enum "medium-high" {
                   description "Code points to classify to loss priority medium-high";
                 }
               }
             }
             leaf-list code-points {
               ordered-by user;
               description "List of code point aliases and/or bit strings";
               type string;
             }
           }
         }
       }
     }
     container traffic-class-map {
       description "Packet input priority map based on incoming packets code point";
       uses apply-advanced;
     }
     list policy-map {
       key name;
       description "Policy-map describing the packet marking rule";
       max-elements 65535;
       leaf name {
         description "Policy-map name";
         type string {
           length "1 .. 64";
         }
       }
       uses apply-advanced;
     }
     container loss-priority-maps {
       description "Map loss priority of incoming packets based on code point value";
       uses apply-advanced;
     }
     container loss-priority-rewrites {
       description "Rewrite code point of outgoing packet based on loss priority";
       uses apply-advanced;
     }
     container code-point-aliases {
       description "Mapping of code point aliases to bit strings";
       uses apply-advanced;
       list dscp {
         key name;
         description "Differentiated Services code point aliases";
         leaf name {
           description "DSCP alias name";
           type string {
             junos:posix-pattern "^([a-zA-Z].{0,63})$";
             junos:pattern-message "Must be string of 64 characters or less beginning with letter";
           }
         }
         leaf bits {
           description "DSCP 6-bit pattern";
           type string {
             junos:posix-pattern "^([01]{6})$";
             junos:pattern-message "Must be of form xxxxxx, where x is 1 or 0";
           }
         }
       }
       list dscp-ipv6 {
         key name;
         description "Differentiated Services code point aliases IPv6";
         leaf name {
           description "DSCP IPv6 alias name";
           type string {
             junos:posix-pattern "^([a-zA-Z].{0,63})$";
             junos:pattern-message "Must be string of 64 characters or less beginning with letter";
           }
         }
         leaf bits {
           description "DSCP 6-bit pattern";
           type string {
             junos:posix-pattern "^([01]{6})$";
             junos:pattern-message "Must be of form xxxxxx, where x is 1 or 0";
           }
         }
       }
       list exp {
         key name;
         description "MPLS EXP code point aliases";
         leaf name {
           description "EXP alias name";
           type string {
             junos:posix-pattern "^([a-zA-Z].{0,63})$";
             junos:pattern-message "Must be string of 64 characters or less beginning with letter";
           }
         }
         leaf bits {
           description "EXP 3-bit pattern";
           type string {
             junos:posix-pattern "^([01]{3})$";
             junos:pattern-message "Must be of form xxx, where x is 0 or 1";
           }
         }
       }
       list ieee-802.1 {
         key name;
         description "IEEE-802.1 code point aliases";
         leaf name {
           description "IEEE-802.1 alias name";
           type string {
             junos:posix-pattern "^([a-zA-Z].{0,63})$";
             junos:pattern-message "Must be string of 64 characters or less beginning with letter";
           }
         }
         leaf bits {
           description "IEEE-802.1 3-bit pattern";
           type string {
             junos:posix-pattern "^([01]{3})$";
             junos:pattern-message "Must be of form xxx, where x is 0 or 1";
           }
         }
       }
       list inet-precedence {
         key name;
         description "IPv4 precedence code point aliases";
         leaf name {
           description "IPv4 precedence alias name";
           type string {
             junos:posix-pattern "^([a-zA-Z].{0,63})$";
             junos:pattern-message "Must be string of 64 characters or less beginning with letter";
           }
         }
         leaf bits {
           description "IPv4 precedence 3-bit pattern";
           type string {
             junos:posix-pattern "^([01]{3})$";
             junos:pattern-message "Must be of form xxx, where x is 0 or 1";
           }
         }
       }
       list ieee-802.1ad {
         key name;
         description "IEEE-802.1ad (DEI) code point aliases";
         leaf name {
           description "IEEE-802.1ad (DEI) alias name";
           type string {
             junos:posix-pattern "^([a-zA-Z].{0,63})$";
             junos:pattern-message "Must be string of 64 characters or less beginning with letter";
           }
         }
         leaf bits {
           description "IEEE-802.1ad (DEI) 4-bit pattern";
           type string {
             junos:posix-pattern "^([01]{4})$";
             junos:pattern-message "Must be of form xxxx, where x is 0 or 1";
           }
         }
       }
     }
     container translation-table {
       description "Translation table";
       uses apply-advanced;
     }
     container host-outbound-traffic {
       description "Classify and mark host traffic to forwarding engine";
       uses apply-advanced;
       leaf forwarding-class {
         description "Classification of host traffic to forwarding engine";
         type string {
           length "1 .. 64";
         }
       }
       leaf dscp-code-point {
         description "Static DSCP code point of egress host traffic";
         type string {
           junos:posix-pattern "^(([01]{6})|([a-zA-Z].{0,63}))$";
           junos:pattern-message "Not 6-bit pattern or code point alias";
         }
       }
       leaf override-firewall {
         description "Override firewall filter actions for RE generated traffic";
         type empty;
       }
       container tcp {
         presence "enable tcp";
         description "Settings for host outbound TCP packets";
         uses apply-advanced;
         leaf raise-internet-control-priority {
           description "Place packets with IP Precedence set to Internet control into Q3 (network-control)";
           type empty;
         }
       }
       container protocol {
         description "Settings for specific host outbound protocol packets";
         uses apply-advanced;
         container isis-over-gre {
           description "Settings for ISIS over GRE packets";
           uses apply-advanced;
           leaf dscp-code-point {
             description "Static DSCP code point of egress host traffic";
             type string {
               junos:posix-pattern "^(([01]{6})|([a-zA-Z].{0,63}))$";
               junos:pattern-message "Not 6-bit pattern or code point alias";
             }
           }
         }
       }
     }
     list drop-profiles {
       key name;
       description "Random Early Drop (RED) data point map";
       leaf name {
         description "Drop profile name";
         type string {
           length "1 .. 64";
         }
       }
       uses apply-advanced;
       list fill-level {
         key name;
         description "Fill-level value of data point";
         leaf name {
           description "Percentage the queue is full";
           type union {
             type string {
               pattern "<.*>|$.*";
             }
             type uint32 {
               range "0 .. 100";
             }
           }
         }
         leaf drop-probability {
           description "Probability packet will be dropped";
           type union {
             type string {
               pattern "<.*>|$.*";
             }
             type uint32 {
               range "0 .. 100";
             }
           }
         }
       }
       container interpolate {
         description "Data points interpolated";
         uses apply-advanced;
         leaf-list fill-level {
           ordered-by user;
           description "Data points for queue full percentage";
           type union {
             type string {
               pattern "<.*>|$.*";
             }
             type uint32 {
               range "0 .. 100";
             }
           }
         }
         leaf-list drop-probability {
           ordered-by user;
           description "Data points for packet drop probability";
           type union {
             type string {
               pattern "<.*>|$.*";
             }
             type uint32 {
               range "0 .. 100";
             }
           }
         }
       }
     }
     leaf tri-color {
       description "Enable tricolor marking";
       type empty;
     }
     container shared-buffer {
       description "Shared buffer configuration";
       uses apply-advanced;
       leaf percent {
         description "Percentage of shared buffer to be used";
         type union {
           type string {
             pattern "<.*>|$.*";
           }
           type uint32 {
             range "5 .. 100";
           }
         }
       }
     }
     container forwarding-classes {
       description "One or more mappings of forwarding class to queue number";
       uses apply-advanced;
       list class {
         key name;
         description "Forwarding class to map to queue number";
         junos:must "(!(\".. queue\"))";
         junos:must-message "'queue' and 'class' cannot coexist";
         max-elements 16;
         leaf name {
           description "Name of forwarding class";
           type string {
             length "1 .. 64";
           }
         }
         leaf queue-num {
           description "Queue number";
           type union {
             type string {
               pattern "<.*>|$.*";
             }
             type uint32;
           }
         }
         leaf priority {
           description "Fabric priority";
           type enumeration {
             enum "low" {
               description "Low fabric priority";
             }
             enum "high" {
               description "High fabric priority";
             }
           }
         }
       }
       list queue {
         key name;
         description "Queue number to map to forwarding class";
         leaf name {
           description "Queue number";
           type union {
             type string {
               pattern "<.*>|$.*";
             }
             type uint32;
           }
         }
         leaf class-name {
           description "Forwarding class name";
           type string {
             length "1 .. 64";
           }
         }
         leaf priority {
           description "Fabric priority";
           type enumeration {
             enum "low" {
               description "Fabric priority low";
             }
             enum "high" {
               description "Fabric priority high";
             }
           }
         }
       }
     }
     container restricted-queues {
       description "Map forwarding classes to restricted queues";
       uses apply-advanced;
       list forwarding-class {
         key name;
         description "Forwarding class to map to a restricted queue";
         leaf name {
           description "Forwarding class name";
           type string {
             length "1 .. 64";
           }
         }
         leaf rqueue-num {
           description "Restricted queue number";
           type union {
             type string {
               pattern "<.*>|$.*";
             }
             type uint32 {
               range "0 .. 3";
             }
           }
         }
       }
     }
     list traffic-control-profiles {
       key name;
       description "Traffic shaping and scheduling profiles";
       leaf name {
         description "Traffic control profile name";
         type string {
           length "1 .. 64";
         }
       }
       uses apply-advanced;
       leaf scheduler-map {
         description "Mapping of forwarding classes to packet schedulers";
         type string {
           length "1 .. 64";
         }
       }
       leaf atm-service {
         description "ATM service category";
         type enumeration {
           enum "cbr" {
             description "Constant bit rate";
           }
           enum "rtvbr" {
             description "Real-time variable bit rate";
           }
           enum "nrtvbr" {
             description "Non-real-time variable bit rate";
           }
         }
       }
       leaf peak-rate {
         description "ATM Peak Cell Rate (PCR)";
         units "cps";
         type string;
       }
       leaf sustained-rate {
         description "ATM Sustained Cell Rate (SCR)";
         units "cps";
         type string;
       }
       leaf max-burst-size {
         description "ATM Maximum Burst Size (MBS)";
         units "cells";
         type union {
           type string {
             pattern "<.*>|$.*";
           }
           type uint64 {
             range "1 .. 4000";
           }
         }
       }
       container shaping-rate {
         description "Shaping rate";
         choice shaping_rate_choice {
           case case_1 {
             leaf rate {
               description "Shaping rate as an absolute rate";
               units "bits per second";
               junos:must "(!(\"interfaces ${interface} aggregated-ether-options link-speed mixed\"))";
               junos:must-message "Scheduler shaping-rate in bits per second is incompatible with link-speed mixed";
               type string;
             }
           }
           case case_2 {
             leaf percent {
               description "Shaping rate as a percentage";
               type union {
                 type string {
                   pattern "<.*>|$.*";
                 }
                 type uint32 {
                   range "1 .. 100";
                 }
               }
             }
           }
         }
         leaf burst-size {
           description "Shaping rate burst size";
           units "bytes";
           type string;
         }
       }
       container overhead-accounting {
         description "Overhead accounting";
         leaf mode {
           type string {
             length "1 .. 64";
           }
         }
         leaf bytes {
           description "Byte adjust value";
           type union {
             type string {
               pattern "<.*>|$.*";
             }
             type int32 {
               range "-120 .. 124";
             }
           }
         }
         leaf frame-mode-bytes {
           description "Overhead bytes when in frame-mode";
           junos:must "(!(\".. bytes\"))";
           junos:must-message "cannot specify both bytes and frame-mode-bytes";
           type union {
             type string {
               pattern "<.*>|$.*";
             }
             type int32 {
               range "-120 .. 124";
             }
           }
         }
         leaf cell-mode-bytes {
           description "Overhead bytes when in cell-mode";
           junos:must "(!(\".. bytes\"))";
           junos:must-message "cannot specify both bytes and cell-mode-bytes";
           type union {
             type string {
               pattern "<.*>|$.*";
             }
             type int32 {
               range "-120 .. 124";
             }
           }
         }
       }
       container shaping-rate-priority-strict-high {
         description "Shaping rate for strict high priority traffic";
         choice shaping_rate_choice {
           case case_1 {
             leaf rate {
               description "Shaping rate in bits per second";
               units "bits per second";
               type string;
             }
           }
           case case_2 {
             leaf percent {
               description "Shaping rate as a percentage";
               type union {
                 type string {
                   pattern "<.*>|$.*";
                 }
                 type uint32 {
                   range "1 .. 100";
                 }
               }
             }
           }
         }
         leaf burst-size {
           description "Shaping rate burst size";
           units "bytes";
           type string;
         }
       }
       container shaping-rate-priority-high {
         description "Shaping rate for high priority traffic";
         choice shaping_rate_choice {
           case case_1 {
             leaf rate {
               description "Shaping rate in bits per second";
               units "bits per second";
               type string;
             }
           }
           case case_2 {
             leaf percent {
               description "Shaping rate as a percentage";
               type union {
                 type string {
                   pattern "<.*>|$.*";
                 }
                 type uint32 {
                   range "1 .. 100";
                 }
               }
             }
           }
         }
         leaf burst-size {
           description "Shaping rate burst size";
           units "bytes";
           type string;
         }
       }
       container shaping-rate-priority-medium {
         description "Shaping rate for medium priority traffic";
         choice shaping_rate_choice {
           case case_1 {
             leaf rate {
               description "Shaping rate in bits per second";
               units "bits per second";
               type string;
             }
           }
           case case_2 {
             leaf percent {
               description "Shaping rate as a percentage";
               type union {
                 type string {
                   pattern "<.*>|$.*";
                 }
                 type uint32 {
                   range "1 .. 100";
                 }
               }
             }
           }
         }
         leaf burst-size {
           description "Shaping rate burst size";
           units "bytes";
           type string;
         }
       }
       container shaping-rate-priority-medium-low {
         description "Shaping rate for medium low priority traffic";
         choice shaping_rate_choice {
           case case_1 {
             leaf rate {
               description "Shaping rate in bits per second";
               units "bits per second";
               type string;
             }
           }
           case case_2 {
             leaf percent {
               description "Shaping rate as a percentage";
               type union {
                 type string {
                   pattern "<.*>|$.*";
                 }
                 type uint32 {
                   range "1 .. 100";
                 }
               }
             }
           }
         }
         leaf burst-size {
           description "Shaping rate burst size";
           units "bytes";
           type string;
         }
       }
       container shaping-rate-priority-low {
         description "Shaping rate for low priority traffic";
         choice shaping_rate_choice {
           case case_1 {
             leaf rate {
               description "Shaping rate in bits per second";
               units "bits per second";
               type string;
             }
           }
           case case_2 {
             leaf percent {
               description "Shaping rate as a percentage";
               type union {
                 type string {
                   pattern "<.*>|$.*";
                 }
                 type uint32 {
                   range "1 .. 100";
                 }
               }
             }
           }
         }
         leaf burst-size {
           description "Shaping rate burst size";
           units "bytes";
           type string;
         }
       }
       container shaping-rate-excess-high {
         description "Shaping rate for excess high traffic";
         choice shaping_rate_choice {
           case case_1 {
             leaf rate {
               description "Shaping rate in bits per second";
               units "bits per second";
               type string;
             }
           }
           case case_2 {
             leaf percent {
               description "Shaping rate as a percentage";
               type union {
                 type string {
                   pattern "<.*>|$.*";
                 }
                 type uint32 {
                   range "1 .. 100";
                 }
               }
             }
           }
         }
         leaf burst-size {
           description "Shaping rate burst size";
           units "bytes";
           type string;
         }
       }
       container shaping-rate-excess-low {
         description "Shaping rate for excess low traffic";
         choice shaping_rate_choice {
           case case_1 {
             leaf rate {
               description "Shaping rate in bits per second";
               units "bits per second";
               type string;
             }
           }
           case case_2 {
             leaf percent {
               description "Shaping rate as a percentage";
               type union {
                 type string {
                   pattern "<.*>|$.*";
                 }
                 type uint32 {
                   range "1 .. 100";
                 }
               }
             }
           }
         }
         leaf burst-size {
           description "Shaping rate burst size";
           units "bytes";
           type string;
         }
       }
       container shaping-rate-excess-medium-high {
         description "Shaping rate for excess medium-high traffic";
         choice shaping_rate_choice {
           case case_1 {
             leaf rate {
               description "Shaping rate in bits per second";
               units "bits per second";
               type string;
             }
           }
           case case_2 {
             leaf percent {
               description "Shaping rate as a percentage";
               type union {
                 type string {
                   pattern "<.*>|$.*";
                 }
                 type uint32 {
                   range "1 .. 100";
                 }
               }
             }
           }
         }
         leaf burst-size {
           description "Shaping rate burst size";
           units "bytes";
           type string;
         }
       }
       container shaping-rate-excess-medium-low {
         description "Shaping rate for excess medium-low traffic";
         choice shaping_rate_choice {
           case case_1 {
             leaf rate {
               description "Shaping rate in bits per second";
               units "bits per second";
               type string;
             }
           }
           case case_2 {
             leaf percent {
               description "Shaping rate as a percentage";
               type union {
                 type string {
                   pattern "<.*>|$.*";
                 }
                 type uint32 {
                   range "1 .. 100";
                 }
               }
             }
           }
         }
         leaf burst-size {
           description "Shaping rate burst size";
           units "bytes";
           type string;
         }
       }
       container guaranteed-rate {
         description "Guaranteed rate";
         choice guaranteed_rate_choice {
           case case_1 {
             leaf rate {
               description "Guaranteed rate as an absolute rate";
               units "bits per second";
               type string;
             }
           }
           case case_2 {
             leaf percent {
               description "Guaranteed rate as a percentage";
               type union {
                 type string {
                   pattern "<.*>|$.*";
                 }
                 type uint32 {
                   range "1 .. 100";
                 }
               }
             }
           }
         }
         leaf burst-size {
           description "Guaranteed rate burst size";
           units "bytes";
           type string;
         }
       }
       container excess-rate {
         junos:must "(!((\".. excess-rate-high\" || (\".. excess-rate-low\" || (\".. excess-rate-medium-high\" || \".. excess-rate-medium-low\")))))";
         junos:must-message "cannot specify both excess-rate and excess-rate-high or excess-rate-low or excess-rate-medium-high or excess-rate-medium-low";
         description "Excess bandwidth sharing proportion";
         choice excess_rate_choice {
           case case_1 {
             leaf proportion {
               description "Excess rate as a proportion";
               type union {
                 type string {
                   pattern "<.*>|$.*";
                 }
                 type uint32 {
                   range "0 .. 1000";
                 }
               }
             }
           }
           case case_2 {
             leaf percent {
               description "Excess rate as a percentage";
               type union {
                 type string {
                   pattern "<.*>|$.*";
                 }
                 type uint32 {
                   range "1 .. 100";
                 }
               }
             }
           }
         }
       }
       container excess-rate-high {
         junos:must "(!(\".. excess-rate\"))";
         junos:must-message "cannot specify both excess-rate and excess-rate-high";
         description "Excess bandwidth sharing for excess-high priority";
         choice excess_rate_choice {
           case case_1 {
             leaf proportion {
               description "Excess rate as a proportion";
               type union {
                 type string {
                   pattern "<.*>|$.*";
                 }
                 type uint32 {
                   range "0 .. 1000";
                 }
               }
             }
           }
           case case_2 {
             leaf percent {
               description "Excess rate as a percentage";
               type union {
                 type string {
                   pattern "<.*>|$.*";
                 }
                 type uint32 {
                   range "1 .. 100";
                 }
               }
             }
           }
         }
       }
       container excess-rate-medium-high {
         junos:must "(!(\".. excess-rate\"))";
         junos:must-message "cannot specify both excess-rate and excess-rate-medium-high";
         description "Excess bandwidth sharing for excess-medium-high priority";
         choice excess_rate_choice {
           case case_1 {
             leaf proportion {
               description "Excess rate as a proportion";
               type union {
                 type string {
                   pattern "<.*>|$.*";
                 }
                 type uint32 {
                   range "0 .. 1000";
                 }
               }
             }
           }
           case case_2 {
             leaf percent {
               description "Excess rate as a percentage";
               type union {
                 type string {
                   pattern "<.*>|$.*";
                 }
                 type uint32 {
                   range "1 .. 100";
                 }
               }
             }
           }
         }
       }
       container excess-rate-low {
         junos:must "(!(\".. excess-rate\"))";
         junos:must-message "cannot specify both excess-rate and excess-rate-low";
         description "Excess bandwidth sharing for excess-low priority";
         choice excess_rate_choice {
           case case_1 {
             leaf proportion {
               description "Excess rate as a proportion";
               type union {
                 type string {
                   pattern "<.*>|$.*";
                 }
                 type uint32 {
                   range "0 .. 1000";
                 }
               }
             }
           }
           case case_2 {
             leaf percent {
               description "Excess rate as a percentage";
               type union {
                 type string {
                   pattern "<.*>|$.*";
                 }
                 type uint32 {
                   range "1 .. 100";
                 }
               }
             }
           }
         }
       }
       container excess-rate-medium-low {
         junos:must "(!(\".. excess-rate\"))";
         junos:must-message "cannot specify both excess-rate and excess-rate-medium-low";
         description "Excess bandwidth sharing for excess-medium-low priority";
         choice excess_rate_choice {
           case case_1 {
             leaf proportion {
               description "Excess rate as a proportion";
               type union {
                 type string {
                   pattern "<.*>|$.*";
                 }
                 type uint32 {
                   range "0 .. 1000";
                 }
               }
             }
           }
           case case_2 {
             leaf percent {
               description "Excess rate as a percentage";
               type union {
                 type string {
                   pattern "<.*>|$.*";
                 }
                 type uint32 {
                   range "1 .. 100";
                 }
               }
             }
           }
         }
       }
       choice delay_buffer_sizing {
         case case_1 {
           container delay-buffer-rate {
             description "Delay buffer rate";
             choice delay_buffer_rate_choice {
               case case_1 {
                 leaf rate {
                   description "Delay buffer rate as an absolute rate";
                   units "bits per second";
                   type string;
                 }
               }
               case case_2 {
                 leaf percent {
                   description "Delay buffer rate as a percentage";
                   type union {
                     type string {
                       pattern "<.*>|$.*";
                     }
                     type uint32 {
                       range "1 .. 100";
                     }
                   }
                 }
               }
               case case_3 {
                 leaf cps {
                   description "Delay buffer rate as an absolute cells per second rate";
                   units "cells per second";
                   type string;
                 }
               }
             }
           }
         }
       }
       container adjust-minimum {
         description "Minimum shaping-rate when adjusted";
         leaf rate {
           description "Minimum shaping rate in bits per second";
           units "bits per second";
           type string;
         }
       }
     }
     list forwarding-class-sets {
       key name;
       description "Forwarding class sets";
       leaf name {
         description "Forwarding class set";
         type string {
           length "1 .. 64";
         }
       }
       uses apply-advanced;
       list class {
         key name;
         description "Forwarding class";
         leaf name {
           description "Class name";
           type string {
             length "1 .. 64";
           }
         }
         uses apply-advanced;
       }
     }
     list congestion-notification-profile {
       key name;
       description "Congestion notification profile";
       leaf name {
         description "Congestion notification name";
         type string {
           length "1 .. 64";
         }
       }
       uses apply-advanced;
       container input {
         description "Input congestion notification components";
         uses apply-advanced;
         container ieee-802.1 {
           description "IEEE 802.1 code point";
           uses apply-advanced;
           list code-point {
             key name;
             description "IEEE 802.1 code point";
             max-elements 8;
             leaf name {
               description "IEEE 802.1 code point";
               type string {
                 junos:posix-pattern "^([01]{3})$";
                 junos:pattern-message "Must be of form xxx, where x is 0 or 1";
               }
             }
             uses apply-advanced;
             leaf pfc {
               description "PFC";
               type empty;
             }
             choice qfc-control {
               case case_1 {
               }
               case case_2 {
                 container qcn {
                   presence "enable qcn";
                   description "QCN";
                   uses apply-advanced;
                   container defense-mode-edge {
                     description "Choose the defense mode edge";
                     uses apply-advanced;
                     container alternate-priority {
                       description "Choose the alternate priority for defense mode edge";
                       uses apply-advanced;
                       leaf bits {
                         description "IEEE 802.1 code point";
                         type string {
                           junos:posix-pattern "^([01]{3})$";
                           junos:pattern-message "Must be of form xxx, where x is 0 or 1";
                         }
                       }
                     }
                   }
                 }
               }
             }
           }
         }
       }
       container output {
         description "Output congestion notification components";
         uses apply-advanced;
         list class {
           key name;
           description "Forwarding class";
           max-elements 16;
           leaf name {
             description "Class name";
             type string {
               length "1 .. 64";
             }
           }
           uses apply-advanced;
           leaf remove-cntag {
             description "Remove cntag for this forwarding class";
             type empty;
           }
         }
       }
     }
     container system-defaults {
       description "System defaults";
       uses apply-advanced;
       container traffic-control-profiles {
         description "Default traffic control profiles";
         uses apply-advanced;
         container interface-set-input {
           description "Default input traffic control profile for dynamic interface-set";
           leaf profile-name {
             description "Name of traffic control profile";
             type string {
               length "1 .. 64";
             }
           }
         }
         container interface-set-output {
           description "Default output traffic control profile for dynamic interface-set";
           leaf profile-name {
             description "Name of traffic control profile";
             type string {
               length "1 .. 64";
             }
           }
         }
       }
     }
     container interfaces {
       description "Apply class-of-service options to interfaces";
       uses apply-advanced;
       list interface {
         key name;
         uses cos_interfaces_type;
       }
     }
     list routing-instances {
       key name;
       description "Apply CoS options to routing instances with VRF table label";
       leaf name {
         description "Routing instance name (or wildcard)";
         junos:must "((!(\".. classifiers\") || (!(\"routing-instances $$\") || (\"routing-instances $$ vrf-table-label\" || (\"routing-instances $$ protocols vpls no-tunnel-services\" || \"routing-instances $$ routing-options localize\")))))";
         junos:must-message "'vrf-table-label' or 'no-tunnel-services' or 'routing-options localize' for this routing instance is required for classifier configuration";
         type string {
           junos:posix-pattern "!^(([*]{1,})|(__.*__)|(.{129,}))$";
           junos:pattern-message "Must be a non-reserved string of 128 characters or less";
         }
       }
       uses apply-advanced;
       container classifiers {
         description "Classifiers applied to incoming packets";
         uses apply-advanced;
         leaf no-default {
           description "Do not apply default classifiers to this interface";
           type empty;
         }
         container exp {
           description "EXP classifier";
           leaf classifier-name {
             description "Name of classifier to be applied";
             type union {
               type string {
                 pattern "default";
               }
               type string {
                 length "1 .. 64";
               }
             }
           }
         }
         container ieee-802.1 {
           description "IEEE-802.1 classifier";
           leaf classifier-name {
             description "Name of classifier to be applied";
             type union {
               type string {
                 pattern "default";
               }
               type string {
                 length "1 .. 64";
               }
             }
           }
           leaf encapsulated {
             description "Inner or outer ethernet header";
             junos:must "(\".. vlan-tag\")";
             junos:must-message "vlan-tag must be specified";
             type empty;
           }
           leaf vlan-tag {
             description "VLAN tag used for classification";
             type enumeration {
               enum "outer" {
                 description "Classification based on outer VLAN tag";
               }
               enum "inner" {
                 description "Classification based on inner VLAN tag";
               }
             }
           }
         }
         container dscp {
           description "Differentiated Services code point classifier";
           leaf classifier-name {
             description "Name of classifier to be applied";
             type union {
               type string {
                 pattern "default";
               }
               type string {
                 length "1 .. 64";
               }
             }
           }
         }
         container dscp-ipv6 {
           description "Differentiated Services code point classifier IPv6";
           leaf classifier-name {
             description "Name of classifier to be applied";
             type union {
               type string {
                 pattern "default";
               }
               type string {
                 length "1 .. 64";
               }
             }
           }
         }
       }
       container rewrite-rules {
         description "Rewrite rules applied to outgoing packets";
         uses apply-advanced;
         choice _802_rewrites {
           case case_1 {
             container ieee-802.1 {
               description "IEEE-802.1 rewrite rule";
               leaf rewrite-rule-name {
                 description "Name of rewrite rule to be applied";
                 type union {
                   type string {
                     pattern "default";
                   }
                   type string {
                     length "1 .. 64";
                   }
                 }
               }
               leaf encapsulated {
                 description "Inner ethernet header";
                 junos:must "(\".. vlan-tag\")";
                 junos:must-message "vlan-tag must be specified";
                 type empty;
               }
               leaf vlan-tag {
                 description "One or more VLAN tags to which rewrite rule applies";
                 type enumeration {
                   enum "outer" {
                     description "Rewrite rule applies to outer VLAN tag";
                   }
                   enum "outer-and-inner" {
                     description "Rewrite rule applies to outer and inner VLAN tag";
                   }
                 }
               }
             }
           }
           case case_2 {
             container ieee-802.1ad {
               description "IEEE-802.1ad (DEI) rewrite rule";
               leaf rewrite-rule-name {
                 description "Name of rewrite rule to be applied";
                 type union {
                   type string {
                     pattern "default";
                   }
                   type string {
                     length "1 .. 64";
                   }
                 }
               }
               leaf encapsulated {
                 description "Inner ethernet header";
                 junos:must "(\".. vlan-tag\")";
                 junos:must-message "vlan-tag must be specified";
                 type empty;
               }
               leaf vlan-tag {
                 description "One or more VLAN tags to which rewrite rule applies";
                 type enumeration {
                   enum "outer" {
                     description "Rewrite rule applies to outer VLAN tag";
                   }
                   enum "outer-and-inner" {
                     description "Rewrite rule applies to outer and inner VLAN tag";
                   }
                 }
               }
             }
           }
         }
       }
     }
     container rewrite-rules {
       description "Write code point value of outgoing packets";
       uses apply-advanced;
       list dscp {
         key name;
         ordered-by user;
         description "Differentiated Services code point rewrite rule";
         leaf name {
           description "Rewrite rule name";
           junos:must "((\".. forwarding-class\" || \".. import\"))";
           junos:must-message "'At least one 'forwarding class' or 'import' rewrite definition is required for rewrite configuration";
           type string {
             length "1 .. 64";
           }
         }
         uses apply-advanced;
         leaf import {
           description "Include this rewrite rule in this definition";
           type union {
             type string {
               pattern "default";
             }
             type string {
               length "1 .. 64";
             }
           }
         }
         list forwarding-class {
           key name;
           description "Markings for named forwarding class";
           leaf name {
             description "Forwarding class name";
             type string {
               length "1 .. 64";
             }
           }
           uses apply-advanced;
           list loss-priority {
             key name;
             description "Code point marking based on loss priority";
             leaf name {
               type enumeration {
                 enum "low" {
                   description "Marking when loss priority is low";
                 }
                 enum "high" {
                   description "Marking when loss priority is high";
                 }
                 enum "medium-low" {
                   description "Marking when loss priority is medium-low";
                 }
                 enum "medium-high" {
                   description "Marking when loss priority is medium-high";
                 }
               }
             }
             leaf code-point {
               description "Code point aliases or bit string";
               type string {
                 junos:posix-pattern "^(([01]{6})|([a-zA-Z].{0,63}))$";
                 junos:pattern-message "Not 6-bit pattern or code point alias";
               }
             }
           }
         }
       }
       list dscp-ipv6 {
         key name;
         ordered-by user;
         description "Differentiated Services code point rewrite rule IPv6";
         leaf name {
           description "Rewrite rule name";
           junos:must "((\".. forwarding-class\" || \".. import\"))";
           junos:must-message "'At least one 'forwarding class' or 'import' rewrite definition is required for rewrite configuration";
           type string {
             length "1 .. 64";
           }
         }
         uses apply-advanced;
         leaf import {
           description "Include this rewrite rule in this definition";
           type union {
             type string {
               pattern "default";
             }
             type string {
               length "1 .. 64";
             }
           }
         }
         list forwarding-class {
           key name;
           description "Markings for named forwarding class";
           leaf name {
             description "Forwarding class name";
             type string {
               length "1 .. 64";
             }
           }
           uses apply-advanced;
           list loss-priority {
             key name;
             description "Code point marking based on loss priority";
             leaf name {
               type enumeration {
                 enum "low" {
                   description "Marking when loss priority is low";
                 }
                 enum "high" {
                   description "Marking when loss priority is high";
                 }
                 enum "medium-low" {
                   description "Marking when loss priority is medium-low";
                 }
                 enum "medium-high" {
                   description "Marking when loss priority is medium-high";
                 }
               }
             }
             leaf code-point {
               description "Code point aliases or bit string";
               type string {
                 junos:posix-pattern "^(([01]{6})|([a-zA-Z].{0,63}))$";
                 junos:pattern-message "Not 6-bit pattern or code point alias";
               }
             }
           }
         }
       }
       list exp {
         key name;
         ordered-by user;
         description "MPLS EXP rewrite rule";
         leaf name {
           description "Rewrite rule name";
           junos:must "((\".. forwarding-class\" || \".. import\"))";
           junos:must-message "'At least one 'forwarding class' or 'import' rewrite definition is required for rewrite configuration";
           type string {
             length "1 .. 64";
           }
         }
         uses apply-advanced;
         leaf import {
           description "Include this rewrite rule in this definition";
           type union {
             type string {
               pattern "default";
             }
             type string {
               length "1 .. 64";
             }
           }
         }
         list forwarding-class {
           key name;
           description "Markings for named forwarding class";
           leaf name {
             description "Forwarding class name";
             type string {
               length "1 .. 64";
             }
           }
           uses apply-advanced;
           list loss-priority {
             key name;
             description "Code point marking based on loss priority";
             leaf name {
               type enumeration {
                 enum "low" {
                   description "Marking when loss priority is low";
                 }
                 enum "high" {
                   description "Marking when loss priority is high";
                 }
                 enum "medium-low" {
                   description "Marking when loss priority is medium-low";
                 }
                 enum "medium-high" {
                   description "Marking when loss priority is medium-high";
                 }
               }
             }
             leaf code-point {
               description "Code point aliases or bit string";
               type string {
                 junos:posix-pattern "^(([01]{3})|([a-zA-Z].{0,63}))$";
                 junos:pattern-message "Not 3-bit pattern or code point alias";
               }
             }
           }
         }
       }
       list ieee-802.1 {
         key name;
         ordered-by user;
         description "IEEE-802.1 rewrite rule";
         leaf name {
           description "Rewrite rule name";
           junos:must "((\".. forwarding-class\" || \".. import\"))";
           junos:must-message "'At least one 'forwarding class' or 'import' rewrite definition is required for rewrite configuration";
           type string {
             length "1 .. 64";
           }
         }
         uses apply-advanced;
         leaf import {
           description "Include this rewrite rule in this definition";
           type union {
             type string {
               pattern "default";
             }
             type string {
               length "1 .. 64";
             }
           }
         }
         list forwarding-class {
           key name;
           description "Markings for named forwarding class";
           leaf name {
             description "Forwarding class name";
             type string {
               length "1 .. 64";
             }
           }
           uses apply-advanced;
           list loss-priority {
             key name;
             description "Code point marking based on loss priority";
             leaf name {
               type enumeration {
                 enum "low" {
                   description "Marking when loss priority is low";
                 }
                 enum "high" {
                   description "Marking when loss priority is high";
                 }
                 enum "medium-low" {
                   description "Marking when loss priority is medium-low";
                 }
                 enum "medium-high" {
                   description "Marking when loss priority is medium-high";
                 }
               }
             }
             leaf code-point {
               description "Code point aliases or bit string";
               type string {
                 junos:posix-pattern "^(([01]{3})|([a-zA-Z].{0,63}))$";
                 junos:pattern-message "Not 3-bit pattern or code point alias";
               }
             }
           }
         }
       }
       list inet-precedence {
         key name;
         ordered-by user;
         description "IPv4 precedence rewrite rule";
         leaf name {
           description "Rewrite rule name";
           junos:must "((\".. forwarding-class\" || \".. import\"))";
           junos:must-message "'At least one 'forwarding class' or 'import' rewrite definition is required for rewrite configuration";
           type string {
             length "1 .. 64";
           }
         }
         uses apply-advanced;
         leaf import {
           description "Include this rewrite rule in this definition";
           type union {
             type string {
               pattern "default";
             }
             type string {
               length "1 .. 64";
             }
           }
         }
         list forwarding-class {
           key name;
           description "Markings for named forwarding class";
           leaf name {
             description "Forwarding class name";
             type string {
               length "1 .. 64";
             }
           }
           uses apply-advanced;
           list loss-priority {
             key name;
             description "Code point marking based on loss priority";
             leaf name {
               type enumeration {
                 enum "low" {
                   description "Marking when loss priority is low";
                 }
                 enum "high" {
                   description "Marking when loss priority is high";
                 }
                 enum "medium-low" {
                   description "Marking when loss priority is medium-low";
                 }
                 enum "medium-high" {
                   description "Marking when loss priority is medium-high";
                 }
               }
             }
             leaf code-point {
               description "Code point aliases or bit string";
               type string {
                 junos:posix-pattern "^(([01]{3})|([a-zA-Z].{0,63}))$";
                 junos:pattern-message "Not 3-bit pattern or code point alias";
               }
             }
           }
         }
       }
       list ieee-802.1ad {
         key name;
         ordered-by user;
         description "IEEE-802.1ad (DEI) rewrite rule";
         leaf name {
           description "Rewrite rule name";
           junos:must "((\".. forwarding-class\" || \".. import\"))";
           junos:must-message "'At least one 'forwarding class' or 'import' rewrite definition is required for rewrite configuration";
           type string {
             length "1 .. 64";
           }
         }
         uses apply-advanced;
         leaf import {
           description "Include this rewrite rule in this definition";
           type union {
             type string {
               pattern "default";
             }
             type string {
               length "1 .. 64";
             }
           }
         }
         list forwarding-class {
           key name;
           description "Markings for named forwarding class";
           leaf name {
             description "Forwarding class name";
             type string {
               length "1 .. 64";
             }
           }
           uses apply-advanced;
           list loss-priority {
             key name;
             description "Code point marking based on loss priority";
             leaf name {
               type enumeration {
                 enum "low" {
                   description "Marking when loss priority is low";
                 }
                 enum "high" {
                   description "Marking when loss priority is high";
                 }
                 enum "medium-low" {
                   description "Marking when loss priority is medium-low";
                 }
                 enum "medium-high" {
                   description "Marking when loss priority is medium-high";
                 }
               }
             }
             leaf code-point {
               description "Code point aliases or bit string";
               type string {
                 junos:posix-pattern "^(([01]{4})|([a-zA-Z].{0,63}))$";
                 junos:pattern-message "Not 4-bit pattern or code point alias";
               }
             }
           }
         }
       }
     }
     container fabric {
       description "Define CoS parameters of switch fabric";
       uses apply-advanced;
       container scheduler-map {
         description "Mapping of fabric traffic to packet schedulers";
         uses apply-advanced;
         list priority {
           key name;
           description "Fabric traffic priority";
           leaf name {
             type enumeration {
               enum "low" {
                 description "Low priority fabric traffic";
               }
               enum "high" {
                 description "High priority fabric traffic";
               }
             }
           }
           leaf scheduler {
             description "Scheduler name";
             type string {
               length "1 .. 64";
             }
           }
         }
       }
     }
     list scheduler-maps {
       key name;
       description "Mapping of forwarding classes to packet schedulers";
       leaf name {
         description "Scheduler map name";
         type string {
           length "1 .. 64";
         }
       }
       uses apply-advanced;
       list forwarding-class {
         key name;
         description "Forwarding class name to map to scheduler";
         leaf name {
           description "Forwarding class name";
           type string {
             length "1 .. 64";
           }
         }
         leaf scheduler {
           description "Scheduler name";
           type string {
             length "1 .. 64";
           }
         }
       }
     }
     list fragmentation-maps {
       key name;
       description "Mapping of forwarding class to fragmentation options";
       leaf name {
         description "Fragmentation map name";
         type string {
           length "1 .. 64";
         }
       }
       uses apply-advanced;
       list forwarding-class {
         key name;
         description "Forwarding class name to map to fragmentation options";
         leaf name {
           description "Forwarding class name";
           type string {
             length "1 .. 64";
           }
         }
         uses apply-advanced;
         choice fragmentation-control {
           case case_1 {
             leaf fragment-threshold {
               description "Fragmentation threshold";
               units "bytes";
               type union {
                 type string {
                   pattern "<.*>|$.*";
                 }
                 type uint16 {
                   range "64 .. 9192";
                 }
               }
             }
           }
           case case_2 {
             leaf no-fragmentation {
               description "Don't allow fragmentation";
               type empty;
             }
           }
         }
         leaf multilink-class {
           description "Multilink-Class assigned to the forwarding class";
           type union {
             type string {
               pattern "<.*>|$.*";
             }
             type uint16 {
               range "0 .. 7";
             }
           }
         }
         leaf drop-timeout {
           description "Drop timeout";
           units "milliseconds";
           type union {
             type string {
               pattern "<.*>|$.*";
             }
             type uint16 {
               range "0 .. 2000";
             }
           }
         }
       }
     }
     list schedulers {
       key name;
       description "Packet schedulers";
       leaf name {
         description "Scheduler name";
         type string {
           length "1 .. 64";
         }
       }
       uses apply-advanced;
       container transmit-rate {
         description "Transmit rate";
         uses apply-advanced;
         choice transmit_rate_choice {
           case case_1 {
             leaf rate {
               description "Transmit rate as rate";
               units "bits per second";
               junos:must "(!(\"interfaces ${interface} aggregated-ether-options link-speed mixed\"))";
               junos:must-message "Scheduler transmit-rate in bits per second is incompatible with link-speed mixed";
               type string;
             }
           }
           case case_2 {
             leaf percent {
               description "Transmit rate as percentage";
               type union {
                 type string {
                   pattern "<.*>|$.*";
                 }
                 type uint32 {
                   range "0 .. 100";
                 }
               }
             }
           }
           case case_3 {
             container remainder {
               presence "enable remainder";
               description "Remainder available";
               uses apply-advanced;
               leaf percent {
                 default "0";
                 type union {
                   type string {
                     pattern "<.*>|$.*";
                   }
                   type uint32 {
                     range "0 .. 100";
                   }
                 }
               }
             }
           }
         }
         choice rate_limit_choice {
           case case_1 {
             leaf exact {
               description "Enforce exact transmit rate";
               type empty;
             }
           }
           case case_2 {
             leaf rate-limit {
               description "Enforce rate limit that uses policer";
               type empty;
             }
           }
         }
       }
       container excess-rate {
         junos:must "((!((\".. transmit-rate exact\" && \".. excess-rate\")) && (!((\".. transmit-rate rate-limit\" && \".. excess-rate\")) && !((\".. priority $$={strict-high}\" && \".. excess-rate\")))))";
         junos:must-message "Cannot specify excess-rate with transmit-rate exact/rate-limit or strict-high priority";
         description "Excess bandwidth sharing proportion";
         choice excess_rate_choice {
           case case_1 {
             leaf proportion {
               description "Excess rate as a proportion";
               type union {
                 type string {
                   pattern "<.*>|$.*";
                 }
                 type uint32 {
                   range "0 .. 1000";
                 }
               }
             }
           }
           case case_2 {
             leaf percent {
               description "Excess rate as a percentage";
               type union {
                 type string {
                   pattern "<.*>|$.*";
                 }
                 type uint32 {
                   range "1 .. 100";
                 }
               }
             }
           }
         }
       }
       container shaping-rate {
         junos:must "(!((\".. transmit-rate rate-limit\" && \".. shaping-rate\")))";
         junos:must-message "only one option (shaping-rate or transmit-rate rate-limit) can be configured at a time";
         junos:must "(!((\".. transmit-rate exact\" && \".. shaping-rate\")))";
         junos:must-message "only one option (shaping-rate or transmit-rate exact) can be configured at a time";
         description "Shaping rate";
         choice shaping_rate_choice {
           case case_1 {
             leaf rate {
               description "Shaping rate as an absolute rate";
               units "bits per second";
               junos:must "(!(\"interfaces ${interface} aggregated-ether-options link-speed mixed\"))";
               junos:must-message "Scheduler shaping-rate in bits per second is incompatible with link-speed mixed";
               type string;
             }
           }
           case case_2 {
             leaf percent {
               description "Shaping rate as a percentage";
               type union {
                 type string {
                   pattern "<.*>|$.*";
                 }
                 type uint32 {
                   range "1 .. 100";
                 }
               }
             }
           }
         }
         leaf burst-size {
           description "Shaping rate burst size";
           units "bytes";
           type string;
         }
       }
       container buffer-size {
         description "Queue transmission buffer size";
         uses apply-advanced;
         choice buffer_size_choice {
           case case_1 {
             leaf percent {
               description "Buffer size as a percentage";
               type union {
                 type string {
                   pattern "<.*>|$.*";
                 }
                 type uint32 {
                   range "0 .. 100";
                 }
               }
             }
           }
           case case_2 {
             container remainder {
               presence "enable remainder";
               description "Remainder of buffer size available";
               uses apply-advanced;
               leaf percent {
                 default "0";
                 type union {
                   type string {
                     pattern "<.*>|$.*";
                   }
                   type uint32 {
                     range "0 .. 100";
                   }
                 }
               }
             }
           }
           case case_3 {
           }
           case case_4 {
             leaf temporal {
               description "Buffer size as temporal value";
               units "microseconds";
               type string;
             }
           }
         }
         choice buffer_limit {
           case case_1 {
             leaf exact {
               description "Enforce exact buffer size";
               type empty;
             }
           }
         }
         container buffer-partition {
           presence "enable buffer-partition";
           description "Partition buffer size among multicast and unicast";
           uses apply-advanced;
           container multicast {
             presence "enable multicast";
             description "Specify multicast fraction of reserved buffer";
             uses apply-advanced;
             leaf percent {
               default "50";
               type union {
                 type string {
                   pattern "<.*>|$.*";
                 }
                 type uint32 {
                   range "0 .. 100";
                 }
               }
             }
           }
         }
       }
       container shared-buffer {
         description "Queue transmission shared-buffer";
         uses apply-advanced;
         container maximum {
           presence "enable maximum";
           description "Control the amount of shared buffer a given queue can consume";
           uses apply-advanced;
           leaf percent {
             description "Maximum shared buffer size as a percentage";
             default "0";
             type union {
               type string {
                 pattern "<.*>|$.*";
               }
               type uint32 {
                 range "0 .. 100";
               }
             }
           }
           container multicast {
             presence "enable multicast";
             description "Control the amount of shared buffer mcast pkts consume";
             uses apply-advanced;
             leaf percent {
               description "Maximum shared buffer size as a percentage";
               default "0";
               type union {
                 type string {
                   pattern "<.*>|$.*";
                 }
                 type uint32 {
                   range "0 .. 100";
                 }
               }
             }
           }
         }
       }
       leaf priority {
         description "Scheduling priority";
         type string {
           length "1 .. 64";
         }
       }
       leaf excess-priority {
         description "Priority in the excess region";
         junos:must "((!((\".. transmit-rate exact\" && (\".. excess-priority $$={high}\" || (\".. excess-priority $$={low}\" || (\".. excess-priority $$={medium-high}\" || \".. excess-priority $$={medium-low}\"))))) && (!((\".. transmit-rate rate-limit\" && (\".. excess-priority $$={high}\" || (\".. excess-priority $$={low}\" || (\".. excess-priority $$={medium-high}\" || \".. excess-priority $$={medium-low}\"))))) && !((\".. priority $$={strict-high}\" && (\".. excess-priority $$={high}\" || (\".. excess-priority $$={low}\" || (\".. excess-priority $$={medium-high}\" || \".. excess-priority $$={medium-low}\"))))))))";
         junos:must-message "Cannot specify excess-priority with transmit-rate exact/rate-limit or strict-high priority";
         type string {
           length "1 .. 64";
         }
       }
       list drop-profile-map {
         key "loss-priority protocol";
         description "Assign drop profile to a loss priority and protocol";
         leaf loss-priority {
           description "Loss priority value";
           type enumeration {
             enum "low" {
               description "Loss priority low";
             }
             enum "high" {
               description "Loss priority high";
             }
             enum "medium-low" {
               description "Loss priority medium-low";
             }
             enum "medium-high" {
               description "Loss priority medium-high";
             }
             enum "any" {
               description "Ignore loss priority when assigning drop profile";
             }
           }
         }
         leaf protocol {
           description "Protocol type";
           type enumeration {
             enum "tcp" {
               description "TCP protocol only";
             }
             enum "non-tcp" {
               description "Non-TCP protocols only";
             }
             enum "any" {
               description "Ignore protocol type when assigning drop profile";
             }
           }
         }
         leaf drop-profile {
           description "Name of drop profile to apply";
           type string {
             length "1 .. 64";
           }
         }
       }
       leaf adjust-percent {
         description "Percent of a bandwidth adjustment applied to a queue";
         units "percent";
         type union {
           type string {
             pattern "<.*>|$.*";
           }
           type uint32 {
             range "0 .. 100";
           }
         }
       }
       leaf adjust-minimum {
         description "Minimum shaping-rate when adjusted";
         units "bits per second";
         type string;
       }
     }
     container traceoptions {
       description "Trace options for class-of-service process";
       uses apply-advanced;
       leaf no-remote-trace {
         description "Disable remote tracing";
         junos:must "(\"system tracing\")";
         junos:must-message "'no-remote-trace' is valid only when [system tracing] is configured";
         type empty;
       }
       container file {
         description "Trace file information";
         leaf filename {
           description "Name of file in which to write trace information";
           type string {
             length "1 .. 1024";
             junos:posix-pattern "![/ %]";
             junos:pattern-message "Must not contain '/', % or a space";
           }
         }
         leaf size {
           description "Maximum trace file size";
           type string;
         }
         leaf files {
           description "Maximum number of trace files";
           default "3";
           type union {
             type string {
               pattern "<.*>|$.*";
             }
             type uint32 {
               range "2 .. 1000";
             }
           }
         }
         choice world-readable-choice {
           leaf world-readable {
             description "Allow any user to read the log file";
             type empty;
           }
           leaf no-world-readable {
             description "Don't allow any user to read the log file";
             type empty;
           }
         }
         leaf match {
           description "Regular expression for lines to be logged";
           type jt:regular-expression;
         }
       }
       list flag {
         key name;
         description "Tracing parameters";
         leaf name {
           type enumeration {
             enum "init" {
               description "Trace initialization events";
             }
             enum "show" {
               description "Trace show command servicing";
             }
             enum "route-socket" {
               description "Trace route-socket events";
             }
             enum "parse" {
               description "Trace parser processing";
             }
             enum "process" {
               description "Trace configuration processing";
             }
             enum "util" {
               description "Trace utilities";
             }
             enum "restart" {
               description "Trace restart processing";
             }
             enum "snmp" {
               description "Trace SNMP-related processing";
             }
             enum "hardware-database" {
               description "Trace chassis hardware database related processing";
             }
             enum "asynch" {
               description "Trace asynchronous configuration processing";
             }
             enum "dynamic" {
               description "Trace dynamic CoS functions";
             }
             enum "cos-adjustment" {
               description "Trace CoS rate adjustments";
             }
             enum "performance-monitor" {
               description "Trace performance monitor counters";
             }
             enum "chassis-scheduler" {
               description "Trace chassis stream scheduler processing";
             }
             enum "cn-util" {
               description "Trace utilities for congestion-notification";
             }
             enum "snmp-timeouts" {
               description "Trace SNMP COSD kernel timeouts";
             }
             enum "all" {
               description "Trace everything";
             }
             enum "feature-capability" {
               description "Trace feature capability";
             }
             enum "application" {
               description "Trace Junos application programming";
             }
             enum "jvision" {
               description "Cos Junos Jvision traces";
             }
           }
         }
       }
     }
     container multi-destination {
       description "Multicast class of service";
       uses apply-advanced;
       leaf scheduler-map {
         description "Scheduler map for multi destination";
         type string {
           length "1 .. 64";
         }
       }
       container family {
         description "Family Inet/Inet6/Ethernet";
         uses apply-advanced;
         container ethernet {
           description "Ethernet switching options";
           uses apply-advanced;
           leaf broadcast {
             description "Forwarding class to be applied to broadcast";
             type string {
               length "1 .. 64";
             }
           }
         }
         container inet {
           description "IP Multicast";
           uses apply-advanced;
           container classifier {
             description "Classifier applied to ip-multicast";
             uses apply-advanced;
             container dscp {
               description "Differentiated Services code point classifier";
               leaf classifier-name {
                 description "Name of classifier to be applied";
                 type string {
                   length "1 .. 64";
                 }
               }
             }
             container inet-precedence {
               description "IPv4 precedence classifier";
               leaf classifier-name {
                 description "Name of classifier to be applied";
                 type string {
                   length "1 .. 64";
                 }
               }
             }
           }
         }
         container inet6 {
           description "IPv6 Multicast";
           uses apply-advanced;
           container classifier {
             description "Classifier applied to ipv6-multicast";
             uses apply-advanced;
             container dscp-ipv6 {
               description "Differentiated Services code point classifier";
               leaf classifier-name {
                 description "Name of classifier to be applied";
                 type string {
                   length "1 .. 64";
                 }
               }
             }
           }
         }
       }
       container classifiers {
         junos:must "(!(\".. forwarding-class\"))";
         junos:must-message "Either Forwarding-class or Classifiers can be configured";
         description "Classifier applied to multicast traffic";
         uses apply-advanced;
         container ieee-802.1 {
           description "IEEE-802.1 classifier";
           leaf classifier-name {
             description "Name of classifier to be applied";
             type string {
               length "1 .. 64";
             }
           }
         }
         container dscp {
           junos:must "(!(\".. inet-precedence\"))";
           junos:must-message "Either DSCP or Inet-Precedence can be configured";
           description "Differentiated services code point classifier";
           leaf classifier-name {
             description "Name of classifier to be applied";
             type string {
               length "1 .. 64";
             }
           }
         }
       }
     }
     container forwarding-policy {
       description "Class-of-service forwarding policy";
       uses apply-advanced;
       list next-hop-map {
         key name;
         ordered-by user;
         description "Class-of-service next-hop map";
         leaf name {
           description "Name to identify next-hop map";
           type string {
             junos:posix-pattern "^.{1,64}$";
             junos:pattern-message "Must be string of 64 characters or less";
           }
         }
         uses apply-advanced;
         list forwarding-class {
           key name;
           ordered-by user;
           description "Forwarding class from which to map";
           leaf name {
             description "Forwarding class";
             type string {
               junos:posix-pattern "^.{1,64}$";
               junos:pattern-message "Must be string of 64 characters or less";
             }
           }
           uses apply-advanced;
           leaf-list next-hop {
             ordered-by user;
             description "Next-hop identifier to which to map";
             type union {
               type jt:ipaddr-or-interface;
               type string {
                 pattern "<.*>|$.*";
               }
             }
           }
           leaf-list lsp-next-hop {
             ordered-by user;
             description "Regular expression for LSP next hop";
             type string;
           }
           leaf non-lsp-next-hop {
             description "Any non-RSVP LSP next hop";
             type empty;
           }
           leaf non-labelled-next-hop {
             description "Any non-labelled next hop";
             type empty;
           }
           leaf discard {
             description "Discard next hop";
             type empty;
           }
         }
         container forwarding-class-default {
           description "Next Hop For traffic which does not meet any FC in the next-hop-map";
           uses apply-advanced;
           leaf-list next-hop {
             ordered-by user;
             description "Next-hop identifier to which to map";
             type union {
               type jt:ipaddr-or-interface;
               type string {
                 pattern "<.*>|$.*";
               }
             }
           }
           leaf-list lsp-next-hop {
             ordered-by user;
             description "Regular expression for LSP next hop";
             type string;
           }
           leaf non-lsp-next-hop {
             description "Any non-RSVP LSP next hop";
             type empty;
           }
           leaf non-labelled-next-hop {
             description "Any non-labelled next hop";
             type empty;
           }
           leaf discard {
             description "Discard next hop";
             type empty;
           }
         }
       }
       list class {
         key name;
         ordered-by user;
         description "Class-of-service description";
         leaf name {
           description "Name to identify class of service";
           type string {
             junos:posix-pattern "^.{1,64}$";
             junos:pattern-message "Must be string of 64 characters or less";
           }
         }
         uses apply-advanced;
         container classification-override {
           description "Define classification overrides";
           uses apply-advanced;
           leaf forwarding-class {
             description "Forwarding class name";
             type string {
               junos:posix-pattern "^.{1,64}$";
               junos:pattern-message "Must be string of 64 characters or less";
             }
           }
         }
       }
     }
   }
   grouping apply-advanced {
     description "Apply advanced configuration logic";
     leaf-list apply-groups {
       ordered-by user;
       description "Groups from which to inherit configuration data";
       type string;
     }
     leaf-list apply-groups-except {
       ordered-by user;
       description "Don't inherit configuration data from these groups";
       type string;
     }
     list apply-macro {
       key name;
       ordered-by user;
       description "Macro and parameters for commit script expansion";
       uses apply-macro-type;
     }
   }
   grouping apply-macro-type {
     description "Macro data for commit-script expansion";
     leaf name {
       description "Name of the macro to be expanded";
       type string;
     }
     list data {
       key name;
       uses macro-data-type;
     }
   }
   grouping cos_interfaces_type {
     description "Physical interface";
     leaf name {
       description "Interface name (or wildcard)";
       junos:must "((!(\".. classifiers\") || !(\".. forwarding-class\")))";
       junos:must-message "Forwarding-class and BA Classifiers not allowed on the same physical interface together";
       junos:must "((!((any \".. unit <*> rewrite-rules dscp-ipv6\" || any \".. unit <*> rewrite-rules inet6-precedence <*> protocol $$={mpls}\")) || !(\".. output-forwarding-class-map\")))";
       junos:must-message "DSCP-IPv6 rewrite or IPv6 Precedence for MPLS traffic and forwarding class map not allowed on same interface";
       junos:must "((!((any \".. unit <*> rewrite-rules dscp\" || any \".. unit <*> rewrite-rules inet-precedence <*> protocol $$={mpls}\")) || !(\".. output-forwarding-class-map\")))";
       junos:must-message "DSCP rewrite or IP Precedence rewrite for MPLS traffic and forwarding class map not allowed on same interface";
       junos:must "((!(any \".. unit <*> output-forwarding-class-map\") || !(\".. output-forwarding-class-map\")))";
       junos:must-message "Cannot configure forwarding-class-map statement on both physical and logical interface";
       junos:must "((!((any \".. unit <*> scheduler-map\" || (any \".. unit <*> input-scheduler-map\" || (any \".. unit <*> output-traffic-control-profile\" || any \".. unit <*> input-traffic-control-profile\")))) || !((\".. scheduler-map\" || \".. input-scheduler-map\"))))";
       junos:must-message "Cannot configure scheduler-map or traffic-control-profile statement on both physical and logical interface";
       junos:must "((!((\".. scheduler-map\" || \".. input-scheduler-map\")) || (!(\"interfaces $$\") || !((\"interfaces $$ per-unit-scheduler\" || (\"interfaces $$ shared-scheduler\" || \"interfaces $$ hierarchical-scheduler\"))))))";
       junos:must-message "'per-unit-scheduler', 'hierarchical-scheduler', or 'shared scheduler' is not compatible with scheduler map/input scheduler map on an interface";
       junos:must "((!(any \".. unit <*> input-traffic-control-profile\") || (!(\"interfaces $$\") || (\"interfaces $$ per-unit-scheduler\" || (\"interfaces $$ shared-scheduler\" || (\"interfaces $$ hierarchical-scheduler\" || any \"interfaces $$ unit <*> pppoe-options\"))))))";
       junos:must-message "'per-unit-scheduler', 'hierarchical-scheduler',or 'shared scheduler' for this interface is required for input-traffic-control-profile configuration on interface unit";
       junos:must "((!(any \".. unit <*> output-traffic-control-profile\") || (!(\"interfaces $$\") || (\"interfaces $$ per-unit-scheduler\" || (\"interfaces $$ shared-scheduler\" || (\"interfaces $$ hierarchical-scheduler\" || (\"interfaces $$ cascade-port\" || (any \"interfaces $$ unit <*> pppoe-options\" || (any \"interfaces <ps*>\" || any \"interfaces $$ unit <*> demux-options\")))))))))";
       junos:must-message "'per-unit-scheduler', 'hierarchical-scheduler', or 'shared scheduler' for this interface is required for output-traffic-control-profile configuration on interface unit";
       junos:must "((!(any \".. unit <*> shaping-rate\") || (!(\"interfaces $$\") || (\"interfaces $$ per-unit-scheduler\" || (\"interfaces $$ shared-scheduler\" || (\"interfaces $$ hierarchical-scheduler\" || (any \"interfaces $$ unit <*> pppoe-options\" || any \"interfaces $$ unit <*> demux-options\")))))))";
       junos:must-message "'per-unit-scheduler', 'hierarchical-scheduler', or 'shared scheduler' for this interface is required for bandwidth configuration on interface unit";
       junos:must "((!(any \".. unit <*> virtual-channel-group\") || (!(\"interfaces $$\") || \"interfaces $$ per-unit-scheduler\")))";
       junos:must-message "'per-unit-scheduler' for this interface is required for virtual-channel-group on interface unit";
       junos:must "((!((any \".. unit <*> scheduler-map\" || any \".. unit <*> input-scheduler-map\")) || (!(\"interfaces $$\") || (\"interfaces $$ per-unit-scheduler\" || (\"interfaces $$ shared-scheduler\" || (\"interfaces $$ hierarchical-scheduler\" || (\"interfaces $$ cascade-port\" || (any \"interfaces $$ unit <*> pppoe-options\" || any \"interfaces $$ unit <*> demux-options\"))))))))";
       junos:must-message "'per-unit-scheduler', 'hierarchical-scheduler', or 'shared-scheduler' for this interface is required for scheduler map on interface unit";
       type union {
         type jt:interface-device-wildcard;
         type string {
           pattern "<.*>|$.*";
         }
       }
     }
     uses apply-advanced;
     leaf congestion-notification-profile {
       description "Congestion notification profile for the interface";
       type string {
         length "1 .. 64";
       }
     }
     leaf scheduler-map {
       description "Output scheduler map";
       type string {
         length "1 .. 64";
       }
     }
     leaf input-scheduler-map {
       description "Input scheduler map";
       type string {
         length "1 .. 64";
       }
     }
     leaf scheduler-map-chassis {
       description "Scheduler map applied to chassis queues (not PIC queues)";
       type union {
         type string {
           pattern "derived";
         }
         type string {
           length "1 .. 64";
         }
       }
     }
     container shaping-rate {
       junos:must "(!(\"interfaces ${interface} aggregated-ether-options link-speed mixed\"))";
       junos:must-message "CoS features are incompatible with link-speed mixed";
       description "Output shaping rate";
       leaf rate {
         description "Shaping rate as an absolute rate";
         units "bits per second";
         type string;
       }
     }
     container input-shaping-rate {
       junos:must "(!(\"interfaces ${interface} aggregated-ether-options link-speed mixed\"))";
       junos:must-message "CoS features are incompatible with link-speed mixed";
       description "Input shaping rate";
       leaf rate {
         description "Input shaping rate as an absolute rate";
         units "bits per second";
         type string;
       }
     }
     container input-traffic-control-profile {
       junos:must "(!((\"..  input-scheduler-map\" || \".. input-shaping-rate\")))";
       junos:must-message "input-traffic-control-profile cannot be configured if any of the following are configured: input-scheduler-map, input-shaping-rate";
       description "Input traffic control profile";
       leaf profile-name {
         description "Name of the traffic control profile";
         type string {
           length "1 .. 64";
         }
       }
     }
     container input-traffic-control-profile-remaining {
       junos:must "(!((\"..  scheduler-map\" || \".. shaping-rate\")))";
       junos:must-message "input-traffic-control-profile cannot be configured if any of the following are configured: scheduler-map, shaping-rate";
       description "Input traffic control profile for remaining traffic on the ifd";
       leaf profile-name {
         description "Name of the traffic control profile";
         type string {
           length "1 .. 64";
         }
       }
     }
     container output-traffic-control-profile-remaining {
       junos:must "(!((\"..  scheduler-map\" || \".. shaping-rate\")))";
       junos:must-message "output-traffic-control-profile cannot be configured if any of the following are configured: scheduler-map, shaping-rate";
       description "Output traffic control profile for remaining traffic on the ifd";
       leaf profile-name {
         description "Name of the traffic control profile";
         type string {
           length "1 .. 64";
         }
       }
     }
     container member-link-scheduler {
       junos:must "(!(\"interfaces ${interface} aggregated-ether-options link-speed mixed\"))";
       junos:must-message "CoS features are incompatible with link-speed mixed";
       description "Scheduler parameter model for member link";
       choice model {
         case case_1 {
           leaf scale {
             description "Scale scheduler parameters on aggregate interface";
             type empty;
           }
         }
         case case_2 {
           leaf replicate {
             description "Copy scheduler parameters from aggregate interface";
             type empty;
           }
         }
       }
     }
     container exclude-queue-overhead-bytes {
       presence "enable exclude-queue-overhead-bytes";
       description "Exclude the overhead bytes from the queue statistics";
       uses apply-advanced;
       leaf include-hierarchy {
         description "Perform overhead adjustment on IFD and all children";
         type empty;
       }
     }
     container logical-interface-aggregate-statistics {
       presence "enable logical-interface-aggregate-statistics";
       description "Logical interface aggregate queue statistics";
     }
     list unit {
       key name;
       description "Logical interface unit (or wildcard)";
       leaf name {
         description "Logical unit number";
         type union {
           type string {
             pattern "\*";
           }
           type union {
             type string {
               pattern "<.*>|$.*";
             }
             type uint32 {
               range "0 .. 1073741823";
             }
           }
         }
       }
       uses apply-advanced;
       leaf forwarding-class {
         description "Forwarding class assigned to incoming packets";
         type string {
           length "1 .. 64";
         }
       }
       leaf scheduler-map {
         description "Output scheduler map";
         junos:must "(!(\"interfaces ${interface} hierarchical-scheduler\"))";
         junos:must-message "scheduler-map cannot be configured on a logical interface when the hierarchical-scheduler is configured: use a traffic-control-profile which references the scheduler-map";
         type string {
           length "1 .. 64";
         }
       }
       leaf input-scheduler-map {
         description "Input scheduler map";
         junos:must "(!(\"interfaces ${interface} hierarchical-scheduler\"))";
         junos:must-message "input-scheduler-map cannot be configured on a logical interface when the hierarchical-scheduler is configured";
         type string {
           length "1 .. 64";
         }
       }
       leaf fragmentation-map {
         description "Fragmentation map applied to this logical interface";
         type string {
           length "1 .. 64";
         }
       }
       container shaping-rate {
         presence "enable shaping-rate";
         junos:must "(!(\"interfaces ${interface} hierarchical-scheduler\"))";
         junos:must-message "shaping-rate cannot be configured on a logical interface when the hierarchical-scheduler is configured: use a traffic-control-profile which specifies the shaping-rate";
         description "Output shaping rate";
         choice shaping_rate_choice {
           case case_1 {
             leaf rate {
               description "Shaping rate as an absolute rate";
               units "bits per second";
               junos:must "(!(\"interfaces ${interface} aggregated-ether-options link-speed mixed\"))";
               junos:must-message "Scheduler shaping-rate in bits per second is incompatible with link-speed mixed";
               type string;
             }
           }
           case case_2 {
             leaf percent {
               description "Shaping rate as a percentage";
               type union {
                 type string {
                   pattern "<.*>|$.*";
                 }
                 type uint32 {
                   range "0 .. 100";
                 }
               }
             }
           }
         }
       }
       container input-shaping-rate {
         junos:must "(!(\"interfaces ${interface} hierarchical-scheduler\"))";
         junos:must-message "input-shaping-rate cannot be configured on a logical interface when the hierarchical-scheduler is configured";
         description "Input shaping rate";
         choice shaping_rate_choice {
           case case_1 {
             leaf rate {
               description "Shaping rate as an absolute rate";
               units "bits per second";
               type string;
             }
           }
           case case_2 {
             leaf percent {
               description "Shaping rate as a percentage";
               type union {
                 type string {
                   pattern "<.*>|$.*";
                 }
                 type uint32 {
                   range "0 .. 100";
                 }
               }
             }
           }
         }
       }
       container input-traffic-control-profile {
         junos:must "(!((\"..  input-scheduler-map\" || (\".. input-shaping-rate\" || (\".. adaptive-shaper\" || \".. virtual-channel-group\")))))";
         junos:must-message "input-traffic-control-profile cannot be configured if any of the following are configured under logical interface: input-scheduler-map, input-shaping-rate, adaptive-shaper, virtual-channel-group";
         description "Input traffic control profile";
         leaf profile-name {
           description "Name of traffic control profile";
           type string {
             length "1 .. 64";
           }
         }
         leaf shared-instance {
           description "Name of the shared instance";
           junos:must "(\"interfaces ${interface} shared-scheduler\")";
           junos:must-message "Requires [edit interface <interface name> shared-scheduler]";
           type string {
             length "1 .. 64";
           }
         }
       }
       container output-traffic-control-profile {
         junos:must "(!((\"..  scheduler-map\" || (\".. shaping-rate\" || (\".. adaptive-shaper\" || \"..  virtual-channel-group\")))))";
         junos:must-message "output-traffic-control-profile cannot be configured if any of the following are configured under logical interface: scheduler-map, shaping-rate, adaptive-shaper, virtual-channel-group";
         description "Output traffic control profile";
         leaf profile-name {
           description "Name of the traffic control profile";
           type string {
             length "1 .. 64";
           }
         }
         leaf shared-instance {
           description "Name of the shared instance";
           junos:must "(\"interfaces ${interface} shared-scheduler\")";
           junos:must-message "Requires [edit interface <interface name> shared-scheduler]";
           type string {
             length "1 .. 64";
           }
         }
       }
       container output-traffic-control-profile-remaining {
         junos:must "(!((\"..  scheduler-map\" || \".. shaping-rate\")))";
         junos:must-message "output-traffic-control-profile-remaining cannot be configured if any of the following are configured: scheduler-map, shaping-rate";
         description "Output traffic control profile for remaining traffic on the ifl";
         leaf profile-name {
           description "Name of the traffic control profile";
           type string {
             junos:posix-pattern "^.{1,64}$";
             junos:pattern-message "Must be string of 64 characters or less";
           }
         }
       }
       container report-ingress-shaping-rate {
         description "Report ingress shaping rate";
         choice report_ingress_shaping_rate_choice {
           case case_1 {
             leaf rate {
               description "Ingress shaping rate as an absolute value";
               units "bits per second";
               type string;
             }
           }
         }
       }
       container classifiers {
         description "Classifiers applied to incoming packets";
         uses apply-advanced;
         leaf no-default {
           description "Do not apply default classifiers to this interface";
           type empty;
         }
         list dscp {
           key name;
           description "Differentiated Services code point classifier";
           leaf name {
             description "Name of classifier to be applied";
             type union {
               type string {
                 pattern "default";
               }
               type string {
                 length "1 .. 64";
               }
             }
           }
           uses apply-advanced;
           leaf-list family {
             ordered-by user;
             description "Family for DSCP classifier";
             type string;
           }
         }
         list dscp-ipv6 {
           key name;
           description "Differentiated Services code point classifier IPv6";
           leaf name {
             description "Name of classifier to be applied";
             type union {
               type string {
                 pattern "default";
               }
               type string {
                 length "1 .. 64";
               }
             }
           }
           uses apply-advanced;
           leaf-list family {
             ordered-by user;
             description "Family for DSCP Ipv6 classifier";
             type string;
           }
         }
         container exp {
           description "EXP classifier";
           leaf classifier-name {
             description "Name of classifier to be applied";
             type union {
               type string {
                 pattern "default";
               }
               type string {
                 length "1 .. 64";
               }
             }
           }
         }
         container ieee-802.1 {
           description "IEEE-802.1 classifier";
           leaf classifier-name {
             description "Name of classifier to be applied";
             type union {
               type string {
                 pattern "default";
               }
               type string {
                 length "1 .. 64";
               }
             }
           }
           leaf vlan-tag {
             description "VLAN tag used for classification";
             type enumeration {
               enum "outer" {
                 description "Classification based on outer VLAN tag";
               }
               enum "inner" {
                 description "Classification based on inner VLAN tag";
               }
               enum "transparent" {
                 description "Classification based on hidden VLAN tag";
               }
             }
           }
         }
         container inet-precedence {
           description "IPv4 precedence classifier";
           leaf classifier-name {
             description "Name of classifier to be applied";
             type union {
               type string {
                 pattern "default";
               }
               type string {
                 length "1 .. 64";
               }
             }
           }
         }
         container ieee-802.1ad {
           junos:must "(!(\".. ieee-802.1\"))";
           junos:must-message "ieee-802.1ad and ieee-802.1 not allowed on same unit";
           description "IEEE-802.1ad (DEI) classifier";
           leaf classifier-name {
             description "Name of classifier to be applied";
             type union {
               type string {
                 pattern "default";
               }
               type string {
                 length "1 .. 64";
               }
             }
           }
           leaf vlan-tag {
             description "VLAN tag used for classification";
             type enumeration {
               enum "outer" {
                 description "Classification based on outer VLAN tag";
               }
               enum "inner" {
                 description "Classification based on inner VLAN tag";
               }
             }
           }
         }
       }
       container rewrite-rules {
         description "Rewrite rules applied to outgoing packets";
         uses apply-advanced;
         list dscp {
           key name;
           description "Differentiated Services code point rewrite rule";
           junos:must "(!(\".. inet-precedence\"))";
           junos:must-message "DSCP and inet-precedence not allowed on same unit";
           leaf name {
             description "Name of rewrite rule to be applied";
             type union {
               type string {
                 pattern "default";
               }
               type string {
                 length "1 .. 64";
               }
             }
           }
           leaf-list protocol {
             ordered-by user;
             description "Specify protocol matching criteria";
             type enumeration {
               enum "mpls" {
                 description "Apply to IPv4 packets entering MPLS tunnel";
               }
               enum "gtp-inet-outer" {
                 description "Apply to outer IP header";
               }
               enum "gtp-inet-both" {
                 description "Apply to both IP header";
               }
               enum "inet-outer" {
                 description "Apply to outer IP header";
               }
               enum "inet-both" {
                 description "Apply to both IP header";
               }
             }
           }
         }
         list dscp-ipv6 {
           key name;
           description "Differentiated Services code point rewrite rule IPv6";
           junos:must "(!(\".. inet6-precedence\"))";
           junos:must-message "IPv6 DSCP and inet6-precedence not allowed on same unit";
           junos:must "(!(\"interfaces ${interface} vlan-tagging\"))";
           junos:must-message "DSCP-IPv6 Rewrite Rules cannot be configured on Vlan-Tagged interfaces";
           leaf name {
             description "Name of rewrite rule to be applied";
             type union {
               type string {
                 pattern "default";
               }
               type string {
                 length "1 .. 64";
               }
             }
           }
           leaf-list protocol {
             ordered-by user;
             description "Specify protocol matching criteria";
             type enumeration {
               enum "mpls" {
                 description "Apply to IPv6 packets entering MPLS tunnel";
               }
               enum "gtp-inet-outer" {
                 description "Apply to outer IP header";
               }
               enum "gtp-inet-both" {
                 description "Apply to both IP header";
               }
             }
           }
         }
         list exp {
           key name;
           description "EXP rewrite rule";
           leaf name {
             description "Name of rewrite rule to be applied";
             type union {
               type string {
                 pattern "default";
               }
               type string {
                 length "1 .. 64";
               }
             }
           }
           leaf-list protocol {
             ordered-by user;
             description "Specify protocol matching criteria";
             type enumeration {
               enum "mpls-any" {
                 description "Apply to MPLS packets, write MPLS header only";
               }
               enum "mpls-inet-both" {
                 description "Apply to IPv4 MPLS packets, write MPLS and IPv4 header";
               }
               enum "mpls-inet-both-non-vpn" {
                 description "Apply to IPv4 MPLS packets, write MPLS and IPv4 header for only non VPN traffic";
               }
             }
           }
         }
         container ieee-802.1 {
           description "IEEE-802.1 rewrite rule";
           leaf rewrite-rule-name {
             description "Name of rewrite rule to be applied";
             type union {
               type string {
                 pattern "default";
               }
               type string {
                 length "1 .. 64";
               }
             }
           }
           leaf vlan-tag {
             description "One or more VLAN tags to which rewrite rule applies";
             type enumeration {
               enum "outer" {
                 description "Rewrite rule applies to outer VLAN tag";
               }
               enum "outer-and-inner" {
                 description "Rewrite rule applies to both outer and inner VLAN tags";
               }
             }
           }
         }
         list inet-precedence {
           key name;
           description "IPv4 precedence rewrite rule";
           leaf name {
             description "Name of rewrite rule to be applied";
             type union {
               type string {
                 pattern "default";
               }
               type string {
                 length "1 .. 64";
               }
             }
           }
           leaf-list protocol {
             ordered-by user;
             description "Specify protocol matching criteria";
             type enumeration {
               enum "mpls" {
                 description "Apply to IPv4 packets entering MPLS tunnel";
               }
               enum "gtp-inet-outer" {
                 description "Apply to outer IP header";
               }
               enum "gtp-inet-both" {
                 description "Apply to both IP header";
               }
               enum "inet-outer" {
                 description "Apply to outer IP header";
               }
               enum "inet-both" {
                 description "Apply to both IP header";
               }
             }
           }
         }
         container ieee-802.1ad {
           junos:must "(!(\".. ieee-802.1\"))";
           junos:must-message "ieee-802.1ad and ieee-802.1 not allowed on same unit";
           description "IEEE-802.1ad (DEI) rewrite rule";
           uses apply-advanced;
           leaf rewrite-rule-name {
             description "Name of rewrite rule to be applied";
             type union {
               type string {
                 pattern "default";
               }
               type string {
                 length "1 .. 64";
               }
             }
           }
           leaf vlan-tag {
             description "One or more VLAN tags to which rewrite rule applies";
             type enumeration {
               enum "outer" {
                 description "Rewrite rule applies to outer VLAN tag";
               }
               enum "outer-and-inner" {
                 description "Rewrite rule applies to both outer and inner VLAN tags";
               }
             }
           }
         }
       }
     }
   }
   grouping macro-data-type {
     leaf name {
       description "Keyword part of the keyword-value pair";
       type string;
     }
     leaf value {
       description "Value part of the keyword-value pair";
       type string;
     }
   }
 }
