/*
 * Copyright (c) 2024 Juniper Networks, Inc.
 * All rights reserved.
 */
 module junos-rpc-ping {
   namespace "http://yang.juniper.net/junos/rpc/ping";

   prefix ping;

   import junos-common-ddl-extensions {
     prefix junos;
     revision-date 2024-01-01;
   }

   import junos-common-types {
     prefix jt;
     revision-date 2024-01-01;
   }

   organization "Juniper Networks, Inc.";

   contact "yang-support@juniper.net";

   description "Junos RPC YANG module for ping command(s)";

   revision 2024-01-01 {
     description "Junos: 24.4R1.8-EVO";
   }

   rpc ping {
     description "Ping remote target";
     junos:command "ping";
     input {
       leaf count {
         description "Number of ping requests to send";
         units "packets";
         type union {
           type string {
             pattern "<.*>|$.*";
           }
           type uint32 {
             range "1 .. 2000000000";
           }
         }
       }
       leaf wait {
         description "Maximum wait time after sending final packet";
         units "seconds";
         type union {
           type uint32;
           type string {
             pattern "<.*>|$.*";
           }
         }
       }
       leaf no-resolve {
         description "Don't attempt to print addresses symbolically";
         type empty;
       }
       leaf rapid {
         description "Send requests rapidly (default count of 5)";
         type empty;
       }
       leaf record-route {
         description "Record and report packet's path (IPv4)";
         type empty;
       }
       leaf brief {
         status deprecated;
         type empty;
       }
       leaf detail {
         description "Display incoming interface of received packet";
         type empty;
       }
       leaf do-not-fragment {
         description "Don't fragment echo request packets (IPv4)";
         type empty;
       }
       leaf-list loose-source {
         ordered-by user;
         description "Intermediate loose source route entry (IPv4)";
         type string;
       }
       leaf interface {
         description "Source interface (multicast, all-ones, unrouted packets)";
         type string;
       }
       leaf interval {
         description "Delay between ping requests";
         units "seconds";
         type string;
       }
       leaf source {
         description "Source address of echo request";
         type string;
       }
       leaf pattern {
         description "Hexadecimal fill pattern";
         type string;
       }
       leaf size {
         description "Size of request packets";
         units "bytes";
         type union {
           type string {
             pattern "<.*>|$.*";
           }
           type uint32 {
             range "0 .. 65468";
           }
         }
       }
       leaf strict {
         description "Use strict source route option (IPv4)";
         type empty;
       }
       leaf-list strict-source {
         ordered-by user;
         description "Intermediate strict source route entry (IPv4)";
         type string;
       }
       leaf ttl {
         description "IP time-to-live value (IPv6 hop-limit value)";
         units "hops";
         type union {
           type string {
             pattern "<.*>|$.*";
           }
           type uint32 {
             range "1 .. 255";
           }
         }
       }
       leaf verbose {
         description "Display detailed output";
         type empty;
       }
       leaf tos {
         description "IP type-of-service value";
         type union {
           type string {
             pattern "<.*>|$.*";
           }
           type uint32 {
             range "0 .. 255";
           }
         }
       }
       leaf bypass-routing {
         description "Bypass routing table, use specified interface";
         type empty;
       }
       leaf inet {
         description "Force ping to IPv4 destination";
         type empty;
       }
       leaf inet6 {
         description "Force ping to IPv6 destination";
         type empty;
       }
       leaf routing-instance {
         description "Routing instance for ping attempt";
         type string;
       }
       leaf mac-address {
         description "MAC address of the nexthop in xx:xx:xx:xx:xx:xx format";
         type jt:mac-unicast;
       }
       leaf gateway {
         description "Nexthop/Gateway address to use in outgoing packets";
         type string;
       }
       leaf host {
         description "Hostname or IP address of remote host";
         junos:cli-feature "nokeyword";
         type string;
         mandatory true;
       }
       leaf logical-system {
         description "Name of logical system";
         type string {
           junos:posix-pattern "^[a-zA-Z0-9_-]{1,63}$";
           junos:pattern-message "Logical-system name is a string consisting of up to 63 letters, numbers, dashes and underscores";
         }
       }
     }
     output {
       container ping-results {
         uses ping-results-block;
       }
     }
   }
   rpc request-ping-ethernet {
     description "Ping to an ethernet host by unicast mac address";
     junos:command "ping ethernet";
     input {
       leaf wait {
         description "Delay after sending last packet";
         units "seconds";
         type union {
           type string {
             pattern "<.*>|$.*";
           }
           type int32 {
             range "1 .. 255";
           }
         }
       }
       leaf size {
         description "Size of data TLV in request packets";
         units "bytes";
         type union {
           type string {
             pattern "<.*>|$.*";
           }
           type int32 {
             range "1 .. 1400";
           }
         }
       }
       leaf count {
         description "Number of ping requests to send";
         type union {
           type string {
             pattern "<.*>|$.*";
           }
           type int32 {
             range "1 .. 65535";
           }
         }
       }
       leaf maintenance-domain {
         description "Name of maintenance domain";
         type string {
           length "1 .. 45";
         }
         mandatory true;
       }
       leaf maintenance-association {
         description "Name of maintenance association";
         type string {
           length "1 .. 45";
         }
         mandatory true;
       }
       leaf host {
         description "MAC address of remote host in xx:xx:xx:xx:xx:xx format";
         junos:cli-feature "nokeyword";
         type jt:mac-addr;
       }
       leaf mep {
         description "MEP identifier of remote host (default 1)";
         type union {
           type string {
             pattern "<.*>|$.*";
           }
           type int32 {
             range "1 .. 8191";
           }
         }
       }
       leaf local-mep {
         description "MEP identifier of local host";
         type union {
           type string {
             pattern "<.*>|$.*";
           }
           type int32 {
             range "1 .. 8191";
           }
         }
       }
       leaf priority {
         description "Frame priority (802.1p) value";
         type union {
           type string {
             pattern "<.*>|$.*";
           }
           type int32 {
             range "0 .. 7";
           }
         }
       }
       leaf rapid {
         description "Send requests rapidly ";
         type empty;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       container ethping-results {
         uses ethping-results-block;
       }
     }
   }
   rpc request-ping-ce-ip {
     junos:command "ping ce-ip";
     input {
       leaf ip {
         description "IPv4/IPv6 address or prefix of CE to be pinged";
         junos:cli-feature "nokeyword";
         type string;
         mandatory true;
       }
       leaf instance {
         description "VPLS or EVPN instance name";
         type string;
         mandatory true;
       }
       leaf source-ip {
         description "Source IP address";
         type string;
         mandatory true;
       }
       leaf count {
         description "Number of ping requests to send";
         default "1000000";
         units "packets";
         type union {
           type string {
             pattern "<.*>|$.*";
           }
           type uint32 {
             range "1 .. 1000000";
           }
         }
       }
       leaf vni {
         description "VXLAN Network Identifier";
         type union {
           type string {
             pattern "<.*>|$.*";
           }
           type uint32 {
             range "1 .. 16777215";
           }
         }
       }
       leaf l3-vni {
         description "VXLAN L3 Network Identifier";
         type union {
           type string {
             pattern "<.*>|$.*";
           }
           type uint32 {
             range "1 .. 16777215";
           }
         }
       }
     }
     output {
       container lsping-results {
         uses lsping-results-block;
       }
     }
   }
   rpc request-ping-overlay {
     description "Ping overlay path";
     junos:command "ping overlay";
     input {
       leaf tunnel-type {
         description "Tunnel type";
         type enumeration {
           enum "vxlan" {
             description "Vxlan tunnel-type";
           }
         }
       }
       leaf vni {
         description "Value of the vni that identifies the overlay segment";
         type union {
           type string {
             pattern "<.*>|$.*";
           }
           type uint32 {
             range "1 .. 16777215";
           }
         }
       }
       leaf l3-vni {
         description "Value of the L3 VNI that identifies the overlay segment";
         type union {
           type string {
             pattern "<.*>|$.*";
           }
           type uint32 {
             range "1 .. 16777215";
           }
         }
       }
       leaf tunnel-src {
         description "Source VTEP IP address";
         type string;
       }
       leaf tunnel-dst {
         description "Remote VTEP IP address";
         type string;
       }
       leaf hash {
         description "User supplied hash to be used as UDP source port in the VXLAN packet";
         type union {
           type string {
             pattern "<.*>|$.*";
           }
           type uint32 {
             range "49152 .. 65535";
           }
         }
       }
       leaf udp-destination-port {
         description "User supplied value to be used as UDP destination port in the VXLAN packet";
         type union {
           type string {
             pattern "<.*>|$.*";
           }
           type uint32 {
             range "1 .. 65535";
           }
         }
       }
       leaf ingress-ifl {
         description "Ifl receiving the packet";
         type union {
           type jt:interface-unit;
           type string {
             pattern "<.*>|$.*";
           }
         }
       }
       choice address {
         case mac {
           leaf mac {
             description "Validate MAC address";
             type jt:mac-unicast;
           }
         }
       }
       leaf count {
         description "Number of pings to send";
         default "5";
         type union {
           type string {
             pattern "<.*>|$.*";
           }
           type uint32 {
             range "1 .. 65535";
           }
         }
       }
       leaf ttl {
         description "TTL to use in the ping packets";
         default "255";
         type union {
           type string {
             pattern "<.*>|$.*";
           }
           type uint32 {
             range "1 .. 255";
           }
         }
       }
       leaf hash-input-interface {
         type union {
           type jt:interface-device;
           type string {
             pattern "<.*>|$.*";
           }
         }
       }
       leaf hash-source-mac {
         type jt:mac-unicast;
       }
       leaf hash-destination-mac {
         type jt:mac-unicast;
       }
       leaf hash-protocol {
         type union {
           type string {
             pattern "<.*>|$.*";
           }
           type uint32 {
             range "1 .. 255";
           }
         }
       }
       leaf hash-source-address {
         description "IPv4 or IPv6 address";
         type string;
       }
       leaf hash-destination-address {
         description "IPv4 or IPv6 address";
         type string;
       }
       leaf hash-source-port {
         type union {
           type string {
             pattern "<.*>|$.*";
           }
           type uint32 {
             range "1 .. 65535";
           }
         }
       }
       leaf hash-destination-port {
         type union {
           type string {
             pattern "<.*>|$.*";
           }
           type uint32 {
             range "1 .. 65535";
           }
         }
       }
       leaf hash-vlan {
         type union {
           type string {
             pattern "<.*>|$.*";
           }
           type uint32 {
             range "1 .. 4094";
           }
         }
       }
     }
   }
   rpc request-ping-rsvp-lsp {
     description "Ping RSVP-signaled LSP";
     junos:command "ping mpls rsvp";
     input {
       leaf lsp-name {
         description "Name of LSP";
         junos:cli-feature "nokeyword";
         type string {
           length "1 .. 64";
         }
         mandatory true;
       }
       leaf standby {
         description "Name of standby path";
         type string;
       }
       leaf multipoint {
         description "Probe multipoint LSP";
         type empty;
       }
       leaf egress {
         description "Request only a specific multipoint egress to respond";
         type jt:ipv4addr;
       }
       leaf instance {
         description "Routing-instance name";
         type string;
       }
       leaf count {
         description "Number of ping requests to send";
         units "packets";
         type union {
           type string {
             pattern "<.*>|$.*";
           }
           type uint32 {
             range "1 .. 1000000";
           }
         }
       }
       leaf source {
         description "IP source address of echo request";
         type jt:ipprefix;
       }
       leaf destination {
         description "IP address of destination for echo request";
         type jt:ipprefix;
       }
       leaf exp {
         description "Forwarding class";
         type union {
           type string {
             pattern "<.*>|$.*";
           }
           type uint32 {
             range "0 .. 7";
           }
         }
       }
       leaf detail {
         description "Display detailed output";
         type empty;
       }
       leaf size {
         description "Size of lsp ping request packet";
         units "bytes";
         type union {
           type string {
             pattern "<.*>|$.*";
           }
           type uint32 {
             range "1 .. 65468";
           }
         }
       }
       leaf sweep {
         description "Incremental ping to find MTU";
         type empty;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
       leaf reply-mode {
         description "Reply mode for ping request";
         type enumeration {
           enum "no-reply" {
             description "Do not reply";
           }
           enum "ip-udp" {
             description "Reply via an IPv4 or IPv6 UDP packet";
           }
           enum "application-level-control-channel" {
             description "Reply via application level control channel";
           }
         }
       }
     }
     output {
       container lsping-results {
         uses lsping-results-block;
       }
     }
   }
   rpc request-ping-rsvp-dynamic-bypass-lsp {
     description "Dynamically created LSP, used for protecting other LSPs";
     junos:command "ping mpls rsvp dynamic-bypass";
     input {
       leaf lsp-name {
         description "Name of dynamic bypass LSP";
         junos:cli-feature "nokeyword";
         type string {
           length "1 .. 64";
         }
         mandatory true;
       }
       leaf count {
         description "Number of ping requests to send";
         units "packets";
         type union {
           type string {
             pattern "<.*>|$.*";
           }
           type uint32 {
             range "1 .. 1000000";
           }
         }
       }
       leaf source {
         description "IP source address of echo request";
         type jt:ipprefix;
       }
       leaf destination {
         description "IP address of destination for echo request";
         type jt:ipprefix;
       }
       leaf exp {
         description "Forwarding class";
         type union {
           type string {
             pattern "<.*>|$.*";
           }
           type uint32 {
             range "0 .. 7";
           }
         }
       }
       leaf detail {
         description "Display detailed output";
         type empty;
       }
       leaf size {
         description "Size of lsp ping request packet";
         units "bytes";
         type union {
           type string {
             pattern "<.*>|$.*";
           }
           type uint32 {
             range "1 .. 65468";
           }
         }
       }
       leaf sweep {
         description "Incremental ping to find MTU";
         type empty;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       container lsping-results {
         uses lsping-results-block;
       }
     }
   }
   rpc request-ping-rsvp-manual-bypass-lsp {
     description "Manually configured LSP, used for protecting other LSPs";
     junos:command "ping mpls rsvp manual-bypass";
     input {
       leaf lsp-name {
         description "Name of manual bypass LSP";
         junos:cli-feature "nokeyword";
         type string {
           length "1 .. 64";
         }
         mandatory true;
       }
       leaf interface {
         description "Name of the interface, which is protected by this bypass";
         type union {
           type jt:interface-name;
           type string {
             pattern "<.*>|$.*";
           }
         }
         mandatory true;
       }
       leaf count {
         description "Number of ping requests to send";
         units "packets";
         type union {
           type string {
             pattern "<.*>|$.*";
           }
           type uint32 {
             range "1 .. 1000000";
           }
         }
       }
       leaf source {
         description "IP source address of echo request";
         type jt:ipprefix;
       }
       leaf destination {
         description "IP address of destination for echo request";
         type jt:ipprefix;
       }
       leaf exp {
         description "Forwarding class";
         type union {
           type string {
             pattern "<.*>|$.*";
           }
           type uint32 {
             range "0 .. 7";
           }
         }
       }
       leaf detail {
         description "Display detailed output";
         type empty;
       }
       leaf size {
         description "Size of lsp ping request packet";
         units "bytes";
         type union {
           type string {
             pattern "<.*>|$.*";
           }
           type uint32 {
             range "1 .. 65468";
           }
         }
       }
       leaf sweep {
         description "Incremental ping to find MTU";
         type empty;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       container lsping-results {
         uses lsping-results-block;
       }
     }
   }
   rpc request-ping-ldp-lsp {
     description "Ping LDP-signaled LSP";
     junos:command "ping mpls ldp";
     input {
       leaf fec {
         description "IP prefix/length of forwarding equivalence class";
         junos:cli-feature "nokeyword";
         type jt:ipprefix;
         mandatory true;
       }
       leaf instance {
         description "Routing-instance name";
         type string;
       }
       leaf stitched-protocol {
         description "Protocol  stitched on intermidiate node";
         type enumeration {
           enum "ospf" {
             description "OSPF protocol";
           }
           enum "isis" {
             description "ISIS protocol";
           }
           enum "bgp" {
             description "BGP protocol";
           }
         }
       }
       leaf count {
         description "Number of ping requests to send";
         units "packets";
         type union {
           type string {
             pattern "<.*>|$.*";
           }
           type uint32 {
             range "1 .. 1000000";
           }
         }
       }
       leaf source {
         description "IP source address of echo request";
         type jt:ipprefix;
       }
       leaf destination {
         description "IP address of destination for echo request";
         type jt:ipprefix;
       }
       leaf exp {
         description "Forwarding class";
         type union {
           type string {
             pattern "<.*>|$.*";
           }
           type uint32 {
             range "0 .. 7";
           }
         }
       }
       leaf detail {
         description "Display detailed output";
         type empty;
       }
       leaf size {
         description "Size of lsp ping request packet";
         units "bytes";
         type union {
           type string {
             pattern "<.*>|$.*";
           }
           type uint32 {
             range "1 .. 65468";
           }
         }
       }
       leaf sweep {
         description "Incremental ping to find MTU";
         type empty;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       container lsping-results {
         uses lsping-results-block;
       }
     }
   }
   rpc request-ping-ldp-p2mp-lsp {
     description "Ping LDP-signaled P2MP LSP";
     junos:command "ping mpls ldp p2mp";
     input {
       leaf root-addr {
         description "IP address of p2mp lsp root";
         type jt:ipv4addr;
         mandatory true;
       }
       leaf lsp-id {
         description "LSP ID of p2mp lsp";
         type union {
           type string {
             pattern "<.*>|$.*";
           }
           type uint32 {
             range "1 .. 4294967295";
           }
         }
         mandatory true;
       }
       leaf egress {
         description "Request only a specific multipoint egress to respond";
         type jt:ipv4addr;
       }
       leaf instance {
         description "Routing-instance name";
         type string;
       }
       leaf count {
         description "Number of ping requests to send";
         units "packets";
         type union {
           type string {
             pattern "<.*>|$.*";
           }
           type uint32 {
             range "1 .. 1000000";
           }
         }
       }
       leaf source {
         description "IP source address of echo request";
         type jt:ipprefix;
       }
       leaf destination {
         description "IP address of destination for echo request";
         type jt:ipprefix;
       }
       leaf exp {
         description "Forwarding class";
         type union {
           type string {
             pattern "<.*>|$.*";
           }
           type uint32 {
             range "0 .. 7";
           }
         }
       }
       leaf detail {
         description "Display detailed output";
         type empty;
       }
       leaf size {
         description "Size of lsp ping request packet";
         units "bytes";
         type union {
           type string {
             pattern "<.*>|$.*";
           }
           type uint32 {
             range "1 .. 65468";
           }
         }
       }
       leaf sweep {
         description "Incremental ping to find MTU";
         type empty;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       container lsping-results {
         uses lsping-results-block;
       }
     }
   }
   rpc request-ping-ospf-lsp {
     description "Ping L-OSPF prefix";
     junos:command "ping mpls segment-routing ospf";
     input {
       leaf fec {
         description "IP prefix/length of forwarding equivalence class";
         junos:cli-feature "nokeyword";
         type jt:ipprefix;
         mandatory true;
       }
       leaf instance {
         description "Routing-instance name";
         type string;
       }
       leaf stitched-protocol {
         description "Protocol  stitched on intermediate node";
         type enumeration {
           enum "ldp" {
             description "LDP protocol";
           }
         }
       }
       leaf algorithm {
         description "Algorithm ID";
         type union {
           type string {
             pattern "<.*>|$.*";
           }
           type uint32 {
             range "0 .. 255";
           }
         }
       }
       leaf count {
         description "Number of ping requests to send";
         units "packets";
         type union {
           type string {
             pattern "<.*>|$.*";
           }
           type uint32 {
             range "1 .. 1000000";
           }
         }
       }
       leaf source {
         description "IP source address of echo request";
         type jt:ipprefix;
       }
       leaf destination {
         description "IP address of destination for echo request";
         type jt:ipprefix;
       }
       leaf exp {
         description "Forwarding class";
         type union {
           type string {
             pattern "<.*>|$.*";
           }
           type uint32 {
             range "0 .. 7";
           }
         }
       }
       leaf detail {
         description "Display detailed output";
         type empty;
       }
       leaf size {
         description "Size of lsp ping request packet";
         units "bytes";
         type union {
           type string {
             pattern "<.*>|$.*";
           }
           type uint32 {
             range "1 .. 65468";
           }
         }
       }
       leaf sweep {
         description "Incremental ping to find MTU";
         type empty;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       container lsping-results {
         uses lsping-results-block;
       }
     }
   }
   rpc request-ping-isis-lsp {
     description "Ping L-ISIS prefix";
     junos:command "ping mpls segment-routing isis";
     input {
       leaf fec {
         description "IP prefix/length of forwarding equivalence class";
         junos:cli-feature "nokeyword";
         type jt:ipprefix;
         mandatory true;
       }
       leaf instance {
         description "Routing-instance name";
         type string;
       }
       leaf stitched-protocol {
         description "Protocol  stitched on intermidiate node";
         type enumeration {
           enum "ldp" {
             description "LDP protocol";
           }
         }
       }
       leaf algorithm {
         description "Algorithm ID";
         type union {
           type string {
             pattern "<.*>|$.*";
           }
           type uint32 {
             range "0 .. 255";
           }
         }
       }
       leaf count {
         description "Number of ping requests to send";
         units "packets";
         type union {
           type string {
             pattern "<.*>|$.*";
           }
           type uint32 {
             range "1 .. 1000000";
           }
         }
       }
       leaf source {
         description "IP source address of echo request";
         type jt:ipprefix;
       }
       leaf destination {
         description "IP address of destination for echo request";
         type jt:ipprefix;
       }
       leaf exp {
         description "Forwarding class";
         type union {
           type string {
             pattern "<.*>|$.*";
           }
           type uint32 {
             range "0 .. 7";
           }
         }
       }
       leaf detail {
         description "Display detailed output";
         type empty;
       }
       leaf size {
         description "Size of lsp ping request packet";
         units "bytes";
         type union {
           type string {
             pattern "<.*>|$.*";
           }
           type uint32 {
             range "1 .. 65468";
           }
         }
       }
       leaf sweep {
         description "Incremental ping to find MTU";
         type empty;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       container lsping-results {
         uses lsping-results-block;
       }
     }
   }
   rpc request-ping-static-lsp {
     description "Ping PRPD-programmed LSP";
     junos:command "ping mpls segment-routing static egress-ip";
     input {
       leaf fec {
         description "IP prefix/length of forwarding equivalence class";
         junos:cli-feature "nokeyword";
         type jt:ipprefix;
         mandatory true;
       }
       leaf instance {
         description "Routing-instance name";
         type string;
       }
       leaf count {
         description "Number of ping requests to send";
         units "packets";
         type union {
           type string {
             pattern "<.*>|$.*";
           }
           type uint32 {
             range "1 .. 1000000";
           }
         }
       }
       leaf source {
         description "IP source address of echo request";
         type jt:ipprefix;
       }
       leaf destination {
         description "IP address of destination for echo request";
         type jt:ipprefix;
       }
       leaf exp {
         description "Forwarding class";
         type union {
           type string {
             pattern "<.*>|$.*";
           }
           type uint32 {
             range "0 .. 7";
           }
         }
       }
       leaf detail {
         description "Display detailed output";
         type empty;
       }
       leaf size {
         description "Size of lsp ping request packet";
         units "bytes";
         type union {
           type string {
             pattern "<.*>|$.*";
           }
           type uint32 {
             range "1 .. 65468";
           }
         }
       }
       leaf sweep {
         description "Incremental ping to find MTU";
         type empty;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       container lsping-results {
         uses lsping-results-block;
       }
     }
   }
   rpc request-ping-segment-routing-egress-ip {
     description "Ping to/install IP address to use when sending probes";
     junos:command "ping mpls segment-routing spring-te egress-ip";
     input {
       leaf egress-ip {
         description "To/Install IP address";
         junos:cli-feature "nokeyword";
         type jt:ipprefix;
         mandatory true;
       }
       leaf color {
         description "Color identifier for the tunnel end-point";
         type union {
           type string {
             pattern "<.*>|$.*";
           }
           type uint32 {
             range "1 .. 4294967295";
           }
         }
       }
       leaf tunnel-source {
         description "Source protocol used to create tunnel";
         type enumeration {
           enum "static" {
             description "Static configuration";
           }
           enum "bgp-sr-te" {
             description "BGP-SR-TE configuration";
           }
         }
       }
       leaf skip-fec-validation {
         description "Skip fec validation";
         type empty;
       }
       leaf active {
         description "Use forwarding path/nexthops from the RIB table";
         type empty;
       }
       leaf secondary {
         description "Use configured secondary segment list for the given SR path";
         type empty;
       }
       leaf segment-list {
         description "Segment list to use when sending probes";
         type string {
           length "1 .. 64";
         }
       }
       leaf instance {
         description "Routing-instance name";
         type string;
       }
       leaf count {
         description "Number of ping requests to send";
         units "packets";
         type union {
           type string {
             pattern "<.*>|$.*";
           }
           type uint32 {
             range "1 .. 1000000";
           }
         }
       }
       leaf source {
         description "IP source address of echo request";
         type jt:ipprefix;
       }
       leaf destination {
         description "IP address of destination for echo request";
         type jt:ipprefix;
       }
       leaf exp {
         description "Forwarding class";
         type union {
           type string {
             pattern "<.*>|$.*";
           }
           type uint32 {
             range "0 .. 7";
           }
         }
       }
       leaf detail {
         description "Display detailed output";
         type empty;
       }
       leaf size {
         description "Size of lsp ping request packet";
         units "bytes";
         type union {
           type string {
             pattern "<.*>|$.*";
           }
           type uint32 {
             range "1 .. 65468";
           }
         }
       }
       leaf sweep {
         description "Incremental ping to find MTU";
         type empty;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       container lsping-results {
         uses lsping-results-block;
       }
     }
   }
   rpc request-ping-segment-source-routing-path {
     description "Ping Source Path routing to use when sending probes";
     junos:command "ping mpls segment-routing spring-te source-routing-path";
     input {
       leaf lsp-name {
         description "Source path routing name";
         junos:cli-feature "nokeyword";
         type string {
           length "1 .. 64";
         }
         mandatory true;
       }
       leaf tunnel-source {
         description "Source protocol used to create tunnel";
         type enumeration {
           enum "static" {
             description "Static configuration";
           }
           enum "pcep" {
             description "PCEP configuration";
           }
         }
       }
       leaf skip-fec-validation {
         description "Skip fec validation";
         type empty;
       }
       leaf active {
         description "Use forwarding path/nexthops from the RIB table";
         type empty;
       }
       leaf secondary {
         description "Use configured secondary segment list for the given SR path";
         type empty;
       }
       leaf egress-ip {
         description "To/Install address to use when sending probes";
         type jt:ipprefix;
       }
       leaf color {
         description "Color identifier for the tunnel end-point";
         type union {
           type string {
             pattern "<.*>|$.*";
           }
           type uint32 {
             range "1 .. 4294967295";
           }
         }
       }
       leaf segment-list {
         description "Segment list to use when sending probes";
         type string {
           length "1 .. 64";
         }
       }
       leaf instance {
         description "Routing-instance name";
         type string;
       }
       leaf count {
         description "Number of ping requests to send";
         units "packets";
         type union {
           type string {
             pattern "<.*>|$.*";
           }
           type uint32 {
             range "1 .. 1000000";
           }
         }
       }
       leaf source {
         description "IP source address of echo request";
         type jt:ipprefix;
       }
       leaf destination {
         description "IP address of destination for echo request";
         type jt:ipprefix;
       }
       leaf exp {
         description "Forwarding class";
         type union {
           type string {
             pattern "<.*>|$.*";
           }
           type uint32 {
             range "0 .. 7";
           }
         }
       }
       leaf detail {
         description "Display detailed output";
         type empty;
       }
       leaf size {
         description "Size of lsp ping request packet";
         units "bytes";
         type union {
           type string {
             pattern "<.*>|$.*";
           }
           type uint32 {
             range "1 .. 65468";
           }
         }
       }
       leaf sweep {
         description "Incremental ping to find MTU";
         type empty;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       container lsping-results {
         uses lsping-results-block;
       }
     }
   }
   rpc request-ping-label-stack {
     description "Label stack for ping packets";
     junos:command "ping mpls segment-routing spring-te label-stack";
     input {
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
       leaf-list labels {
         ordered-by user;
         description "Labels value range 16..1048575 in label stack - [label1 label2 ... label(top)]";
         type string {
           length "2 .. 64";
         }
       }
       leaf nexthop-interface {
         description "Outgoing interface for the ping packet";
         type string;
         mandatory true;
       }
       leaf nexthop-address {
         description "Nexthop IP address for the ping packet";
         type jt:ipaddr;
         mandatory true;
       }
       leaf egress {
         description "Egress IP address";
         type jt:ipaddr;
       }
       leaf detail {
         description "Display detailed output";
         type empty;
       }
       leaf count {
         description "Number of ping requests to send";
         units "packets";
         type union {
           type string {
             pattern "<.*>|$.*";
           }
           type uint32 {
             range "1 .. 1000000";
           }
         }
       }
       leaf source {
         description "IP source address of echo request";
         type jt:ipprefix;
       }
       leaf destination {
         description "IP address of destination for echo request";
         type jt:ipprefix;
       }
       leaf exp {
         description "Forwarding class";
         type union {
           type string {
             pattern "<.*>|$.*";
           }
           type uint32 {
             range "0 .. 7";
           }
         }
       }
       leaf size {
         description "Size of lsp ping request packet";
         units "bytes";
         type union {
           type string {
             pattern "<.*>|$.*";
           }
           type uint32 {
             range "1 .. 65468";
           }
         }
       }
       leaf sweep {
         description "Incremental ping to find MTU";
         type empty;
       }
     }
     output {
       container lsping-results {
         uses lsping-results-block;
       }
     }
   }
   rpc request-ping-bgp-lsp {
     description "Ping BGP-signaled LSP";
     junos:command "ping mpls bgp";
     input {
       leaf fec {
         description "IP prefix/length of forwarding equivalence class";
         junos:cli-feature "nokeyword";
         type jt:ipprefix;
         mandatory true;
       }
       leaf bottom-label-ttl {
         description "Time to live for the bottom label in the label stack";
         type union {
           type string {
             pattern "<.*>|$.*";
           }
           type uint32 {
             range "1 .. 255";
           }
         }
       }
       leaf instance {
         description "Routing-instance name";
         type string;
       }
       leaf stitched-protocol {
         description "Protocol  stitched on intermediate node";
         type enumeration {
           enum "ldp" {
             description "LDP protocol";
           }
         }
       }
       leaf count {
         description "Number of ping requests to send";
         units "packets";
         type union {
           type string {
             pattern "<.*>|$.*";
           }
           type uint32 {
             range "1 .. 1000000";
           }
         }
       }
       leaf source {
         description "IP source address of echo request";
         type jt:ipprefix;
       }
       leaf destination {
         description "IP address of destination for echo request";
         type jt:ipprefix;
       }
       leaf exp {
         description "Forwarding class";
         type union {
           type string {
             pattern "<.*>|$.*";
           }
           type uint32 {
             range "0 .. 7";
           }
         }
       }
       leaf detail {
         description "Display detailed output";
         type empty;
       }
       leaf size {
         description "Size of lsp ping request packet";
         units "bytes";
         type union {
           type string {
             pattern "<.*>|$.*";
           }
           type uint32 {
             range "1 .. 65468";
           }
         }
       }
       leaf sweep {
         description "Incremental ping to find MTU";
         type empty;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       container lsping-results {
         uses lsping-results-block;
       }
     }
   }
   rpc request-ping-l3vpn {
     description "Ping LSP to Layer 3 VPN prefix";
     junos:command "ping mpls l3vpn";
     input {
       leaf l3vpn-name {
         description "Name of Layer 3 VPN";
         junos:cli-feature "nokeyword";
         type string;
         mandatory true;
       }
       leaf prefix {
         description "IP prefix/length of Layer 3 VPN";
         type jt:ipprefix;
         mandatory true;
       }
       leaf bottom-label-ttl {
         description "Time to live for the bottom label in the label stack";
         type union {
           type string {
             pattern "<.*>|$.*";
           }
           type uint32 {
             range "1 .. 255";
           }
         }
       }
       leaf count {
         description "Number of ping requests to send";
         units "packets";
         type union {
           type string {
             pattern "<.*>|$.*";
           }
           type uint32 {
             range "1 .. 1000000";
           }
         }
       }
       leaf source {
         description "IP source address of echo request";
         type jt:ipprefix;
       }
       leaf destination {
         description "IP address of destination for echo request";
         type jt:ipprefix;
       }
       leaf exp {
         description "Forwarding class";
         type union {
           type string {
             pattern "<.*>|$.*";
           }
           type uint32 {
             range "0 .. 7";
           }
         }
       }
       leaf detail {
         description "Display detailed output";
         type empty;
       }
       leaf size {
         description "Size of lsp ping request packet";
         units "bytes";
         type union {
           type string {
             pattern "<.*>|$.*";
           }
           type uint32 {
             range "1 .. 65468";
           }
         }
       }
       leaf sweep {
         description "Incremental ping to find MTU";
         type empty;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       container lsping-results {
         uses lsping-results-block;
       }
     }
   }
   rpc request-ping-l2vpn-interface {
     description "Locate LSP using interface name";
     junos:command "ping mpls l2vpn interface";
     input {
       leaf interface-name {
         description "Interface name";
         junos:cli-feature "nokeyword";
         type union {
           type jt:interface-name;
           type string {
             pattern "<.*>|$.*";
           }
         }
         mandatory true;
       }
       leaf bottom-label-ttl {
         description "Time to live for the bottom label in the label stack";
         type union {
           type string {
             pattern "<.*>|$.*";
           }
           type uint32 {
             range "1 .. 255";
           }
         }
       }
       leaf reply-mode {
         description "Reply mode for ping request";
         type enumeration {
           enum "no-reply" {
             description "Do not reply";
           }
           enum "ip-udp" {
             description "Reply via an IPv4 or IPv6 UDP packet";
           }
           enum "application-level-control-channel" {
             description "Reply via application level control channel";
           }
         }
       }
       leaf count {
         description "Number of ping requests to send";
         units "packets";
         type union {
           type string {
             pattern "<.*>|$.*";
           }
           type uint32 {
             range "1 .. 1000000";
           }
         }
       }
       leaf source {
         description "IP source address of echo request";
         type jt:ipprefix;
       }
       leaf destination {
         description "IP address of destination for echo request";
         type jt:ipprefix;
       }
       leaf exp {
         description "Forwarding class";
         type union {
           type string {
             pattern "<.*>|$.*";
           }
           type uint32 {
             range "0 .. 7";
           }
         }
       }
       leaf detail {
         description "Display detailed output";
         type empty;
       }
       leaf size {
         description "Size of lsp ping request packet";
         units "bytes";
         type union {
           type string {
             pattern "<.*>|$.*";
           }
           type uint32 {
             range "1 .. 65468";
           }
         }
       }
       leaf sweep {
         description "Incremental ping to find MTU";
         type empty;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       container lsping-results {
         uses lsping-results-block;
       }
     }
   }
   rpc request-ping-l2vpn-instance {
     description "Instance to which this connection belongs";
     junos:command "ping mpls l2vpn instance";
     input {
       leaf instance-name {
         description "Layer 2 VPN name";
         junos:cli-feature "nokeyword";
         type string;
         mandatory true;
       }
       leaf local-site-id {
         description "Layer 2 VPN local site identifier";
         type union {
           type string {
             pattern "<.*>|$.*";
           }
           type uint32 {
             range "1 .. 65534";
           }
         }
         mandatory true;
       }
       leaf remote-site-id {
         description "Layer 2 VPN remote site identifier";
         type union {
           type string {
             pattern "<.*>|$.*";
           }
           type uint32 {
             range "1 .. 65534";
           }
         }
         mandatory true;
       }
       leaf bottom-label-ttl {
         description "Time to live for the bottom label in the label stack";
         type union {
           type string {
             pattern "<.*>|$.*";
           }
           type uint32 {
             range "1 .. 255";
           }
         }
       }
       leaf reply-mode {
         description "Reply mode for ping request";
         type enumeration {
           enum "no-reply" {
             description "Do not reply";
           }
           enum "ip-udp" {
             description "Reply via an IPv4 or IPv6 UDP packet";
           }
           enum "application-level-control-channel" {
             description "Reply via application level control channel";
           }
         }
       }
       leaf count {
         description "Number of ping requests to send";
         units "packets";
         type union {
           type string {
             pattern "<.*>|$.*";
           }
           type uint32 {
             range "1 .. 1000000";
           }
         }
       }
       leaf source {
         description "IP source address of echo request";
         type jt:ipprefix;
       }
       leaf destination {
         description "IP address of destination for echo request";
         type jt:ipprefix;
       }
       leaf exp {
         description "Forwarding class";
         type union {
           type string {
             pattern "<.*>|$.*";
           }
           type uint32 {
             range "0 .. 7";
           }
         }
       }
       leaf detail {
         description "Display detailed output";
         type empty;
       }
       leaf size {
         description "Size of lsp ping request packet";
         units "bytes";
         type union {
           type string {
             pattern "<.*>|$.*";
           }
           type uint32 {
             range "1 .. 65468";
           }
         }
       }
       leaf sweep {
         description "Incremental ping to find MTU";
         type empty;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       container lsping-results {
         uses lsping-results-block;
       }
     }
   }
   rpc request-ping-l2vpn-fec129-interface {
     description "Locate Pseudowire using interface name";
     junos:command "ping mpls l2vpn fec129 interface";
     input {
       leaf interface-name {
         description "Interface name";
         junos:cli-feature "nokeyword";
         type union {
           type jt:interface-name;
           type string {
             pattern "<.*>|$.*";
           }
         }
         mandatory true;
       }
       leaf bottom-label-ttl {
         description "Time to live for the bottom label in the label stack";
         type union {
           type string {
             pattern "<.*>|$.*";
           }
           type uint32 {
             range "1 .. 255";
           }
         }
       }
       leaf reply-mode {
         description "Reply mode for ping request";
         type enumeration {
           enum "no-reply" {
             description "Do not reply";
           }
           enum "ip-udp" {
             description "Reply via an IPv4 or IPv6 UDP packet";
           }
           enum "application-level-control-channel" {
             description "Reply via application level control channel";
           }
         }
       }
       leaf count {
         description "Number of ping requests to send";
         units "packets";
         type union {
           type string {
             pattern "<.*>|$.*";
           }
           type uint32 {
             range "1 .. 1000000";
           }
         }
       }
       leaf source {
         description "IP source address of echo request";
         type jt:ipprefix;
       }
       leaf destination {
         description "IP address of destination for echo request";
         type jt:ipprefix;
       }
       leaf exp {
         description "Forwarding class";
         type union {
           type string {
             pattern "<.*>|$.*";
           }
           type uint32 {
             range "0 .. 7";
           }
         }
       }
       leaf detail {
         description "Display detailed output";
         type empty;
       }
       leaf size {
         description "Size of lsp ping request packet";
         units "bytes";
         type union {
           type string {
             pattern "<.*>|$.*";
           }
           type uint32 {
             range "1 .. 65468";
           }
         }
       }
       leaf sweep {
         description "Incremental ping to find MTU";
         type empty;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       container lsping-results {
         uses lsping-results-block;
       }
     }
   }
   rpc request-ping-l2vpn-fec129-instance {
     description "Instance to which this connection belongs";
     junos:command "ping mpls l2vpn fec129 instance";
     input {
       leaf instance-name {
         description "Layer 2 VPN name";
         junos:cli-feature "nokeyword";
         type string;
         mandatory true;
       }
       leaf local-id {
         description "Layer 2 VPN Source Attachment Individual Identifier (SAII)";
         type string {
           junos:posix-pattern "^([[:digit:].]){0,15}$|^([[:digit:]]){0,10}:([[:digit:].]){0,15}:([[:digit:]]){1,10}$";
           junos:pattern-message "Invalid Local-id";
         }
         mandatory true;
       }
       leaf remote-id {
         description "Layer 2 VPN Target Attachment Individual Identifier (TAII)";
         type string {
           junos:posix-pattern "^([[:digit:].]){0,15}$|^([[:digit:]]){0,10}:([[:digit:].]){0,15}:([[:digit:]]){1,10}$";
           junos:pattern-message "Invalid Remode-id";
         }
         mandatory true;
       }
       leaf remote-pe-address {
         description "Layer 2 Remote PE address";
         type jt:ipv4addr;
         mandatory true;
       }
       leaf bottom-label-ttl {
         description "Time to live for the bottom label in the label stack";
         type union {
           type string {
             pattern "<.*>|$.*";
           }
           type uint32 {
             range "1 .. 255";
           }
         }
       }
       leaf reply-mode {
         description "Reply mode for ping request";
         type enumeration {
           enum "no-reply" {
             description "Do not reply";
           }
           enum "ip-udp" {
             description "Reply via an IPv4 or IPv6 UDP packet";
           }
           enum "application-level-control-channel" {
             description "Reply via application level control channel";
           }
         }
       }
       leaf count {
         description "Number of ping requests to send";
         units "packets";
         type union {
           type string {
             pattern "<.*>|$.*";
           }
           type uint32 {
             range "1 .. 1000000";
           }
         }
       }
       leaf source {
         description "IP source address of echo request";
         type jt:ipprefix;
       }
       leaf destination {
         description "IP address of destination for echo request";
         type jt:ipprefix;
       }
       leaf exp {
         description "Forwarding class";
         type union {
           type string {
             pattern "<.*>|$.*";
           }
           type uint32 {
             range "0 .. 7";
           }
         }
       }
       leaf detail {
         description "Display detailed output";
         type empty;
       }
       leaf size {
         description "Size of lsp ping request packet";
         units "bytes";
         type union {
           type string {
             pattern "<.*>|$.*";
           }
           type uint32 {
             range "1 .. 65468";
           }
         }
       }
       leaf sweep {
         description "Incremental ping to find MTU";
         type empty;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       container lsping-results {
         uses lsping-results-block;
       }
     }
   }
   rpc request-ping-l2circuit-interface {
     description "Locate LSP from interface name";
     junos:command "ping mpls l2circuit interface";
     input {
       leaf v1 {
         description "Ping using Layer 2 circuit TLV (type 9)";
         type empty;
       }
       leaf interface-name {
         description "Interface name";
         junos:cli-feature "nokeyword";
         type union {
           type jt:interface-name;
           type string {
             pattern "<.*>|$.*";
           }
         }
         mandatory true;
       }
       leaf reply-mode {
         description "Reply mode for ping request";
         type enumeration {
           enum "no-reply" {
             description "Do not reply";
           }
           enum "ip-udp" {
             description "Reply via an IPv4 or IPv6 UDP packet";
           }
           enum "application-level-control-channel" {
             description "Reply via application level control channel";
           }
         }
       }
       leaf count {
         description "Number of ping requests to send";
         units "packets";
         type union {
           type string {
             pattern "<.*>|$.*";
           }
           type uint32 {
             range "1 .. 1000000";
           }
         }
       }
       leaf source {
         description "IP source address of echo request";
         type jt:ipprefix;
       }
       leaf destination {
         description "IP address of destination for echo request";
         type jt:ipprefix;
       }
       leaf exp {
         description "Forwarding class";
         type union {
           type string {
             pattern "<.*>|$.*";
           }
           type uint32 {
             range "0 .. 7";
           }
         }
       }
       leaf detail {
         description "Display detailed output";
         type empty;
       }
       leaf size {
         description "Size of lsp ping request packet";
         units "bytes";
         type union {
           type string {
             pattern "<.*>|$.*";
           }
           type uint32 {
             range "1 .. 65468";
           }
         }
       }
       leaf sweep {
         description "Incremental ping to find MTU";
         type empty;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       container lsping-results {
         uses lsping-results-block;
       }
     }
   }
   rpc request-ping-l2circuit-virtual-circuit {
     description "Locate LSP from virtual circuit information";
     junos:command "ping mpls l2circuit virtual-circuit";
     input {
       leaf v1 {
         description "Ping using Layer 2 circuit TLV (type 9)";
         type empty;
       }
       leaf neighbor {
         description "Address of remote neighbor";
         type jt:ipprefix;
         mandatory true;
       }
       leaf virtual-circuit-id {
         description "Layer 2 circuit identifier";
         junos:cli-feature "nokeyword";
         type union {
           type string {
             pattern "<.*>|$.*";
           }
           type uint32 {
             range "1 .. 4294967295";
           }
         }
         mandatory true;
       }
       leaf reply-mode {
         description "Reply mode for ping request";
         type enumeration {
           enum "no-reply" {
             description "Do not reply";
           }
           enum "ip-udp" {
             description "Reply via an IPv4 or IPv6 UDP packet";
           }
           enum "application-level-control-channel" {
             description "Reply via application level control channel";
           }
         }
       }
       leaf count {
         description "Number of ping requests to send";
         units "packets";
         type union {
           type string {
             pattern "<.*>|$.*";
           }
           type uint32 {
             range "1 .. 1000000";
           }
         }
       }
       leaf source {
         description "IP source address of echo request";
         type jt:ipprefix;
       }
       leaf destination {
         description "IP address of destination for echo request";
         type jt:ipprefix;
       }
       leaf exp {
         description "Forwarding class";
         type union {
           type string {
             pattern "<.*>|$.*";
           }
           type uint32 {
             range "0 .. 7";
           }
         }
       }
       leaf detail {
         description "Display detailed output";
         type empty;
       }
       leaf size {
         description "Size of lsp ping request packet";
         units "bytes";
         type union {
           type string {
             pattern "<.*>|$.*";
           }
           type uint32 {
             range "1 .. 65468";
           }
         }
       }
       leaf sweep {
         description "Incremental ping to find MTU";
         type empty;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       container lsping-results {
         uses lsping-results-block;
       }
     }
   }
   rpc request-ping-lsp-end-point {
     description "Ping end point of LSP";
     junos:command "ping mpls lsp-end-point";
     input {
       leaf prefix {
         description "IP prefix/length of end point";
         junos:cli-feature "nokeyword";
         type jt:ipprefix;
         mandatory true;
       }
       leaf instance {
         description "Routing-instance name";
         type string;
       }
       leaf count {
         description "Number of ping requests to send";
         units "packets";
         type union {
           type string {
             pattern "<.*>|$.*";
           }
           type uint32 {
             range "1 .. 1000000";
           }
         }
       }
       leaf source {
         description "IP source address of echo request";
         type jt:ipprefix;
       }
       leaf destination {
         description "IP address of destination for echo request";
         type jt:ipprefix;
       }
       leaf exp {
         description "Forwarding class";
         type union {
           type string {
             pattern "<.*>|$.*";
           }
           type uint32 {
             range "0 .. 7";
           }
         }
       }
       leaf detail {
         description "Display detailed output";
         type empty;
       }
       leaf size {
         description "Size of lsp ping request packet";
         units "bytes";
         type union {
           type string {
             pattern "<.*>|$.*";
           }
           type uint32 {
             range "1 .. 65468";
           }
         }
       }
       leaf sweep {
         description "Incremental ping to find MTU";
         type empty;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       container lsping-results {
         uses lsping-results-block;
       }
     }
   }
   rpc request-ping-vpls-instance {
     description "Instance to which this VPLS connection belongs";
     junos:command "ping vpls instance";
     input {
       leaf instance-name {
         description "Layer 2 VPLS name";
         junos:cli-feature "nokeyword";
         type string;
         mandatory true;
       }
       leaf destination-mac {
         description "Destination MAC address";
         type jt:mac-addr;
         mandatory true;
       }
       leaf source-ip {
         description "Source IP address";
         type jt:ipv4addr;
         mandatory true;
       }
       leaf learning-vlan-id {
         description "Learning VLAN identifier";
         type union {
           type string {
             pattern "<.*>|$.*";
           }
           type int32 {
             range "0 .. 4094";
           }
         }
       }
       leaf control-plane-response {
         description "Request VPLS OAM responses using the control plane ";
         type empty;
       }
       leaf bd-name {
         description "Name of bridge domain";
         type string;
       }
       leaf count {
         description "Number of ping requests to send";
         units "packets";
         type union {
           type string {
             pattern "<.*>|$.*";
           }
           type uint32 {
             range "1 .. 1000000";
           }
         }
       }
       leaf detail {
         description "Display detailed output";
         type empty;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       container lsping-results {
         uses lsping-results-block;
       }
     }
   }
   rpc request-ping-isis-sids {
     description "Ping SRv6 SIDs/IPv6 address installed by ISIS";
     junos:command "ping srv6 isis";
     input {
       leaf host {
         description "IPv6 loopback address or SRv6 SID of remote host";
         junos:cli-feature "nokeyword";
         type jt:ipaddr;
         mandatory true;
       }
       leaf count {
         description "Number of ping requests to send";
         units "packets";
         type union {
           type string {
             pattern "<.*>|$.*";
           }
           type uint32 {
             range "1 .. 1000000";
           }
         }
       }
       leaf source {
         description "Source address of echo request";
         type jt:ipv6addr;
       }
       leaf detail {
         description "Display detailed output";
         type empty;
       }
       leaf size {
         description "Size of request packets";
         units "bytes";
         type union {
           type string {
             pattern "<.*>|$.*";
           }
           type uint32 {
             range "0 .. 65468";
           }
         }
       }
       leaf ttl {
         description "IPv6 hop-limit value";
         type union {
           type string {
             pattern "<.*>|$.*";
           }
           type uint32 {
             range "1 .. 255";
           }
         }
       }
       leaf instance {
         description "Routing-instance name";
         type string;
       }
       leaf pattern {
         description "Hexadecimal fill pattern";
         type string;
       }
       leaf tos {
         description "IPv6 type-of-service value";
         type union {
           type string {
             pattern "<.*>|$.*";
           }
           type uint32 {
             range "0 .. 255";
           }
         }
       }
       leaf interval {
         description "Delay between ping requests";
         units "seconds";
         type union {
           type string {
             pattern "<.*>|$.*";
           }
           type uint32 {
             range "0 .. 2147483647";
           }
         }
       }
       leaf sweep {
         description "Incremental ping to find MTU";
         type empty;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       container lsping-srv6-results {
         uses lsping-srv6-results-block;
       }
     }
   }
   rpc request-ping-srv6-stack {
     description "SRv6 SID stack";
     junos:command "ping srv6 spring-te sids-stack";
     input {
       leaf count {
         description "Number of ping requests to send";
         units "packets";
         type union {
           type string {
             pattern "<.*>|$.*";
           }
           type uint32 {
             range "1 .. 1000000";
           }
         }
       }
       leaf source {
         description "Source address of echo request";
         type jt:ipv6addr;
       }
       leaf detail {
         description "Display detailed output";
         type empty;
       }
       leaf size {
         description "Size of request packets";
         units "bytes";
         type union {
           type string {
             pattern "<.*>|$.*";
           }
           type uint32 {
             range "0 .. 65468";
           }
         }
       }
       leaf ttl {
         description "IPv6 hop-limit value";
         type union {
           type string {
             pattern "<.*>|$.*";
           }
           type uint32 {
             range "1 .. 255";
           }
         }
       }
       leaf instance {
         description "Routing-instance name";
         type string;
       }
       leaf pattern {
         description "Hexadecimal fill pattern";
         type string;
       }
       leaf tos {
         description "IPv6 type-of-service value";
         type union {
           type string {
             pattern "<.*>|$.*";
           }
           type uint32 {
             range "0 .. 255";
           }
         }
       }
       leaf interval {
         description "Delay between ping requests";
         units "seconds";
         type union {
           type string {
             pattern "<.*>|$.*";
           }
           type uint32 {
             range "0 .. 2147483647";
           }
         }
       }
       leaf sweep {
         description "Incremental ping to find MTU";
         type empty;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
       leaf-list sids {
         ordered-by user;
         description "SRv6 SIDs in srv6-stack - [sid0 sid1 sid2 ... sidn(top)]";
         type jt:ipv6addr;
       }
       leaf nexthop-interface {
         description "Outgoing interface for the ping packet";
         type string;
         mandatory true;
       }
       leaf nexthop-address {
         description "Nexthop IPv6 address for the ping packet";
         type jt:ipv6addr;
         mandatory true;
       }
     }
     output {
       container lsping-srv6-results {
         uses lsping-srv6-results-block;
       }
     }
   }
   rpc request-ping-srv6-usid-stack {
     description "SRv6 uSID stack";
     junos:command "ping srv6 spring-te micro-sids-stack";
     input {
       leaf count {
         description "Number of ping requests to send";
         units "packets";
         type union {
           type string {
             pattern "<.*>|$.*";
           }
           type uint32 {
             range "1 .. 1000000";
           }
         }
       }
       leaf source {
         description "Source address of echo request";
         type jt:ipv6addr;
       }
       leaf detail {
         description "Display detailed output";
         type empty;
       }
       leaf size {
         description "Size of request packets";
         units "bytes";
         type union {
           type string {
             pattern "<.*>|$.*";
           }
           type uint32 {
             range "0 .. 65468";
           }
         }
       }
       leaf ttl {
         description "IPv6 hop-limit value";
         type union {
           type string {
             pattern "<.*>|$.*";
           }
           type uint32 {
             range "1 .. 255";
           }
         }
       }
       leaf instance {
         description "Routing-instance name";
         type string;
       }
       leaf pattern {
         description "Hexadecimal fill pattern";
         type string;
       }
       leaf tos {
         description "IPv6 type-of-service value";
         type union {
           type string {
             pattern "<.*>|$.*";
           }
           type uint32 {
             range "0 .. 255";
           }
         }
       }
       leaf interval {
         description "Delay between ping requests";
         units "seconds";
         type union {
           type string {
             pattern "<.*>|$.*";
           }
           type uint32 {
             range "0 .. 2147483647";
           }
         }
       }
       leaf sweep {
         description "Incremental ping to find MTU";
         type empty;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
       leaf-list usids {
         ordered-by user;
         description "SRv6 uSIDs in stack - [usid0 ... usidn(top)]";
         type jt:ipv6addr;
       }
       leaf nexthop-interface {
         description "Outgoing interface for the ping packet";
         type string;
         mandatory true;
       }
       leaf nexthop-address {
         description "Nexthop IPv6 address for the ping packet";
         type jt:ipv6addr;
         mandatory true;
       }
     }
     output {
       container lsping-srv6-results {
         uses lsping-srv6-results-block;
       }
     }
   }
   grouping command-forwarding {
     leaf no-forwarding {
       description "No forwarding";
       type empty;
     }
     choice chassis-selector {
       case case_1 {
         leaf all-chassis {
           description "All chassis";
           type empty;
         }
       }
       case case_2 {
         leaf all-lcc {
           description "All LCC chassis";
           type empty;
         }
       }
       case case_3 {
         leaf scc {
           description "SCC";
           type empty;
         }
       }
       case case_4 {
         leaf sfc {
           description "SFC";
           type union {
             type string {
               pattern "<.*>|$.*";
             }
             type uint32;
           }
         }
       }
       case case_5 {
         leaf lcc {
           description "Specific LCC";
           type union {
             type string {
               pattern "<.*>|$.*";
             }
             type uint32;
           }
         }
       }
       case case_6 {
         leaf node {
           description "Specific node";
           type string;
         }
       }
       case case_7 {
         leaf bsys {
           description "Base system";
           type empty;
         }
       }
       case case_8 {
         leaf gnf {
           description "Specific guest network function";
           type union {
             type string {
               pattern "<.*>|$.*";
             }
             type uint32 {
               range "1 .. 10";
             }
           }
         }
       }
       case case_9 {
         leaf all-gnfs {
           description "All guest network functions";
           type empty;
         }
       }
       case case_10 {
         leaf all-system {
           description "All system (BSYS and GNFs)";
           type empty;
         }
       }
       case case_11 {
         leaf server {
           description "Specific server slot";
           type union {
             type string {
               pattern "<.*>|$.*";
             }
             type uint32 {
               range "0 .. 1";
             }
           }
         }
       }
       case case_12 {
         leaf all-servers {
           description "All servers";
           type empty;
         }
       }
       case case_13 {
         leaf vnf {
           description "Specific virtual-network-function";
           type string;
         }
       }
       case case_14 {
         leaf all-vnfs {
           description "All virtual-network-functions";
           type empty;
         }
       }
     }
     choice re-selector {
       case case_1 {
         leaf re0 {
           description "RE0";
           type empty;
         }
       }
       case case_2 {
         leaf re1 {
           description "RE1";
           type empty;
         }
       }
       case case_3 {
         leaf routing-engine {
           description "Specific routing engine";
           type enumeration {
             enum "local" {
               description "Local routing engine";
             }
             enum "other" {
               description "Other routing engine";
             }
             enum "master" {
               description "Master routing engine";
             }
             enum "backup" {
               description "Backup routing engine";
             }
             enum "both" {
               description "Both routing engines";
             }
           }
         }
       }
     }
     choice lr-selector {
       case case_1 {
         leaf logical-system {
           description "Name of logical system, or 'all'";
           type string;
         }
       }
     }
     choice tenant-selector {
       case case_1 {
         leaf tenant {
           description "Name of tenant, or 'all'";
           type string;
         }
       }
     }
     choice vc-selector {
       case case_1 {
         leaf local {
           description "Local virtual chassis member";
           type empty;
         }
       }
       case case_2 {
         leaf all-members {
           description "All virtual chassis members";
           type empty;
         }
       }
       case case_3 {
         leaf member {
           description "Specific virtual chassis member which is master";
           type union {
             type string {
               pattern "<.*>|$.*";
             }
             type uint32;
           }
         }
       }
     }
   }
   grouping ping-results-block {
     leaf target-host {
       type string;
       description "Specified target address or hostname";
     }
     leaf source {
       type string;
       description "Specified source address or hostname";
     }
     leaf target-ip {
       type string;
       description "Resolved target IP address";
     }
     leaf packet-size {
       type int32;
       description "Packet size of probes (bytes)";
     }
     leaf ping-success {
       type empty;
       description "Destination was reached";
     }
     leaf ping-failure {
       type string;
       description "Ping failed";
     }
     leaf ping-error-message {
       type string;
       description "Error message for ping";
     }
     leaf-list ping-warning-message {
       type string;
       description "Warning message for ping";
     }
     list probe-result {
       description "Result of one probe";
       leaf date-determined {
         type string;
         description "UTC time when the result was determined, as number of seconds since 1 January 1970";
       }
       leaf probe-index {
         type int32;
         description "Sequence number of probe";
       }
       leaf sequence-number {
         type int32;
         description "Sequence number in response packet";
       }
       leaf time-to-live {
         type int32;
         description "Time-to-live (TTL) value in response packet";
       }
       leaf response-size {
         type int32;
         description "Size of response (bytes)";
       }
       leaf rtt {
         type uint64;
         description "Route trip time for probe (microseconds)";
       }
       leaf ingress-interface {
         type string;
         description "Interface that received the response";
       }
       leaf ip-address {
         type jt:ipaddr;
         description "IP address of interface that received probe";
       }
       leaf host-name {
         type string;
         description "Hostname of interface that received probe";
       }
       leaf probe-success {
         type empty;
         description "A valid response was received";
       }
       leaf probe-duplicate {
         type empty;
         description "A duplicate response was received";
       }
       leaf probe-reached {
         type empty;
         description "Probe reached destination host";
       }
       leaf probe-failure {
         type string;
         description "No valid response received";
       }
       container icmp-type {
         description "Type of ICMP message";
         leaf icmp-type-none {
           type empty;
         }
         leaf icmp-echoreply {
           type empty;
         }
         leaf icmp-unreach {
           type empty;
         }
         leaf icmp-sourcequench {
           type empty;
         }
         leaf icmp-redirect {
           type empty;
         }
         leaf icmp-echo {
           type empty;
         }
         leaf icmp-routeradvert {
           type empty;
         }
         leaf icmp-routersolicit {
           type empty;
         }
         leaf icmp-timxceed {
           type empty;
         }
         leaf icmp-paramprob {
           type empty;
         }
         leaf icmp-tstamp {
           type empty;
         }
         leaf icmp-tstampreply {
           type empty;
         }
         leaf icmp-ireq {
           type empty;
         }
         leaf icmp-ireqreply {
           type empty;
         }
         leaf icmp-maskreq {
           type empty;
         }
         leaf icmp-maskreply {
           type empty;
         }
         leaf icmp6-unreach {
           type empty;
         }
         leaf icmp6-packet-too-big {
           type empty;
         }
         leaf icmp6-time-exceeded {
           type empty;
         }
         leaf icmp6-parameter-problem {
           type empty;
         }
         leaf icmp6-echo-request {
           type empty;
         }
         leaf icmp6-echo-reply {
           type empty;
         }
         leaf icmp6-membership-query {
           type empty;
         }
         leaf icmp6-membership-report {
           type empty;
         }
         leaf icmp6-membership-reduction {
           type empty;
         }
         leaf icmp6-router-solicit {
           type empty;
         }
         leaf icmp6-router-advert {
           type empty;
         }
         leaf icmp6-neighbor-solicit {
           type empty;
         }
         leaf icmp6-neighbor-advert {
           type empty;
         }
         leaf icmp6-redirect {
           type empty;
         }
         leaf icmp6-router-renumbering {
           type empty;
         }
         leaf icmp6-ni-query {
           type empty;
         }
         leaf icmp6-ni-reply {
           type empty;
         }
       }
       container icmp-code {
         description "Type of ICMP message type sub code";
         leaf icmp-code-none {
           type empty;
         }
         leaf icmp-unreach-net {
           type empty;
         }
         leaf icmp-unreach-host {
           type empty;
         }
         leaf icmp-unreach-protocol {
           type empty;
         }
         leaf icmp-unreach-port {
           type empty;
         }
         leaf icmp-unreach-needfrag {
           type empty;
         }
         leaf icmp-unreach-srcfail {
           type empty;
         }
         leaf icmp-unreach-net-unknown {
           type empty;
         }
         leaf icmp-unreach-host-unknown {
           type empty;
         }
         leaf icmp-unreach-isolated {
           type empty;
         }
         leaf icmp-unreach-net-prohib {
           type empty;
         }
         leaf icmp-unreach-host-prohib {
           type empty;
         }
         leaf icmp-unreach-tosnet {
           type empty;
         }
         leaf icmp-unreach-toshost {
           type empty;
         }
         leaf icmp-unreach-filter-prohib {
           type empty;
         }
         leaf icmp-unreach-host-precedence {
           type empty;
         }
         leaf icmp-unreach-precedence-cutoff {
           type empty;
         }
         leaf icmp-redirect-net {
           type empty;
         }
         leaf icmp-redirect-host {
           type empty;
         }
         leaf icmp-redirect-tosnet {
           type empty;
         }
         leaf icmp-redirect-toshost {
           type empty;
         }
         leaf icmp-timxceed-intrans {
           type empty;
         }
         leaf icmp-timxceed-reass {
           type empty;
         }
         leaf icmp-paramprob-optabsent {
           type empty;
         }
         leaf icmp6-unreach-noroute {
           type empty;
         }
         leaf icmp6-unreach-admin {
           type empty;
         }
         leaf icmp6-unreach-beyond-scope {
           type empty;
         }
         leaf icmp6-unreach-address {
           type empty;
         }
         leaf icmp6-unreach-port {
           type empty;
         }
         leaf icmp6-time-exceed-transit {
           type empty;
         }
         leaf icmp6-time-exceed-reassembly {
           type empty;
         }
         leaf icmp6-parameter-problem-header {
           type empty;
         }
         leaf icmp6-parameter-problem-nextheader {
           type empty;
         }
         leaf icmp6-parameter-problem-option {
           type empty;
         }
         leaf icmp6-ni-subject-ipv6 {
           type empty;
         }
         leaf icmp6-ni-subject-fqdn {
           type empty;
         }
         leaf icmp6-ni-subject-ipv4 {
           type empty;
         }
         leaf icmp6-ni-success {
           type empty;
         }
         leaf icmp6-ni-refused {
           type empty;
         }
         leaf icmp6-ni-unknown {
           type empty;
         }
       }
       container ip-options {
         description "IP options contained in the response";
         container record-route {
           description "Record route (RR) IP option";
           list record-route-host {
             description "Host entry in the record route";
             leaf ip-address {
               type jt:ipaddr;
               description "IP address of interface that received probe";
             }
             leaf host-name {
               type string;
               description "Hostname of interface that received probe";
             }
           }
         }
         container loose-source-route {
           description "Loose source route (LSRR) IP option";
           list record-route-host {
             description "Host entry in the record route";
             leaf ip-address {
               type jt:ipaddr;
               description "IP address of interface that received probe";
             }
             leaf host-name {
               type string;
               description "Hostname of interface that received probe";
             }
           }
         }
         container strict-source-route {
           description "Strict source route (SSRR) IP option";
           list record-route-host {
             description "Host entry in the record route";
             leaf ip-address {
               type jt:ipaddr;
               description "IP address of interface that received probe";
             }
             leaf host-name {
               type string;
               description "Hostname of interface that received probe";
             }
           }
         }
       }
     }
     container probe-results-summary {
       description "Summary of probe results";
       leaf probes-sent {
         type int32;
         description "Number of probes sent to target host";
       }
       leaf responses-received {
         type int32;
         description "Number of responses to probes received from target host";
       }
       leaf packet-loss {
         type int32;
         description "Percentage of probes that resulted in no response";
       }
       leaf response-duplicates {
         type int32;
         description "Number of duplicate responses received for one or more probes";
       }
       leaf response-unexpected-sequence {
         type int32;
         description "Number of responses received with unexpected sequence number";
       }
       leaf rtt-minimum {
         type uint64;
         description "Minimum round trip time (microseconds)";
       }
       leaf rtt-average {
         type uint64;
         description "Average round trip time (microseconds)";
       }
       leaf rtt-maximum {
         type uint64;
         description "Maximum round trip time (microseconds)";
       }
       leaf rtt-stddev {
         type uint64;
         description "Standard Deviation of round trip time (microseconds)";
       }
     }
   }
   grouping ethping-results-block {
     container cfm-loopback-error-snapshot {
       leaf cfm-loopback-error-reason {
         type string;
         description "Reason for failure of a loopback request";
       }
     }
     container cfm-loopback-request-snapshot {
       leaf cfm-target-mac-address {
         type string;
         description "MAC address of the target MEP or MIP";
       }
       leaf cfm-interface-name {
         type string;
         description "Name of interface";
       }
       leaf cfm-loopback-requests-bytes {
         type uint32;
         description "Number of bytes transmitted in the loopback request";
       }
       leaf cfm-level {
         type uint32;
         description "Maintenance-domain level";
       }
       leaf cfm-maintenance-domain-name {
         type string;
         description "Name of maintenance domain";
       }
       leaf cfm-maintenance-association-name {
         type string;
         description "Name of maintenance association";
       }
       leaf cfm-local-mep-identifier {
         type uint32;
         description "Identifier of maintenance endpoint";
       }
       leaf cfm-loopback-transaction-identifier {
         type uint32;
         description "Identifier which uniquely identifies a loopback request";
       }
     }
     list cfm-loopback-reply-entry {
       leaf cfm-loopback-responses-bytes {
         type uint32;
         description "Number of bytes received in the loopback response";
       }
       leaf cfm-target-mac-address {
         type string;
         description "MAC address of the target MEP or MIP";
       }
       leaf cfm-loopback-transaction-identifier {
         type uint32;
         description "Identifier which uniquely identifies a loopback request";
       }
     }
     list cfm-loopback-reply-entry-rapid {
       leaf cfm-loopback-responses-rcvd {
         type string;
         description "Loopback rapid response";
       }
     }
     container cfm-loopback-reply-summary {
       leaf cfm-loopback-requests-packets {
         type uint32;
         description "Number of loopback requests transmitted";
       }
       leaf cfm-loopback-responses-packets {
         type uint32;
         description "Number of loopback responses received";
       }
       leaf cfm-loopback-percentage-packet-loss {
         type string;
         description "Percentage of loopback packets lost";
       }
     }
   }
   grouping lsping-results-block {
     leaf lsping-route-comment {
       type string;
       description "Route established using this protocol";
     }
     leaf lsping-success {
       type empty;
       description "Destination reached";
     }
     leaf lsping-failure {
       type string;
       description "Lsping failed";
     }
     leaf lsping-failure-message {
       type string;
       description "Error message for lsping";
     }
     leaf-list lsping-warning-message {
       type string;
       description "Warning message for lsping";
     }
     list lsping-probe-request {
       description "One request probe";
       leaf lsping-sequence-number {
         type int32;
         description "Sequence number in request packet";
       }
       leaf lsping-interface-index {
         type int32;
       }
       leaf-list lsping-label {
         type int32;
         description "Label of MPLS packet";
       }
       leaf lsping-src-address {
         type string;
         description "Ingress prefix of SRV6 packet";
       }
       leaf lsping-packet-size {
         type int32;
         description "Ping request packet size";
       }
     }
     list lsping-probe-reply {
       leaf lsping-sequence-number {
         type int32;
         description "Sequence number in request packet";
       }
       leaf lsping-return-code {
         type string;
         description "Success or failure code";
       }
       leaf lsping-ip-address {
         type string;
         description "IPV4 Egress address";
       }
       leaf lsping-round-trip-time {
         type int32;
         description "Round Trip Time in ms";
       }
       leaf lsping-local-transmit-time {
         type string;
         description "Local transmit time in seconds since Jan 1,1970";
       }
       leaf lsping-local-transmit-time-us {
         type int32;
         description "Local transmit time in micro-seconds since Jan 1,1970";
       }
       leaf lsping-remote-receive-time {
         type string;
         description "Remote receive time in seconds since Jan 1,1970";
       }
       leaf lsping-remote-receive-time-us {
         type int32;
         description "Remote receive time in micro-seconds since Jan 1,1970";
       }
       leaf lsping-ip6-address {
         type string;
         description "IPV6 Destination address";
       }
       leaf lsping-hop-limit {
         type int32;
         description "Hop Limit";
       }
       leaf lsping-in-interface-index {
         type int32;
       }
       leaf lsping-vpls-display-str {
         type string;
         description "VPLS display string";
       }
     }
     list lsping-results-summary {
       description "Summary of lsping probe results";
       leaf lsping-ip-address {
         type string;
         description "IPV4 Egress address";
       }
       leaf lsping-packets-transmitted {
         type int32;
         description "Number of packets sent to target host";
       }
       leaf lsping-packets-received {
         type int32;
         description "Number of packets received from the target host";
       }
       leaf lsping-packet-loss {
         type int32;
         description "Lsping percentage of packets that resulted in no response";
       }
       leaf lsping-packet-time-minimum {
         type uint64;
         description "Minimum round trip time (microseconds)";
       }
       leaf lsping-packet-time-average {
         type uint64;
         description "Average round trip time (microseconds)";
       }
       leaf lsping-packet-time-maximum {
         type uint64;
         description "Maximum round trip time (microseconds)";
       }
       leaf lsping-packet-time-stddev {
         type uint64;
         description "Standard Deviation of round trip time (microseconds)";
       }
       leaf lsping-error-packets {
         type int32;
         description " Number of packets received with error status";
       }
     }
     container vpls-ping-results-summary {
       description "Summary of vpls ping probe results";
       leaf lsping-packets-transmitted {
         type int32;
         description "Number of packets sent to target host";
       }
       leaf lsping-packets-received {
         type int32;
         description "Number of packets received from the target host";
       }
       leaf lsping-packet-loss {
         type int32;
         description "Lsping percentage of packets that resulted in no response";
       }
       leaf lsping-error-packets {
         type int32;
         description " Number of packets received with error status";
       }
     }
     container lsping-sweep-summary {
       description "Ping sweep result";
       leaf lsping-mtu {
         type int32;
         description " Maximum Transmission Unit (MTU)";
       }
     }
     list probe-result {
       description "Result of one probe";
       leaf date-determined {
         type string;
         description "UTC time when the result was determined, as number of seconds since 1 January 1970";
       }
       leaf probe-index {
         type int32;
         description "Sequence number of probe";
       }
       leaf sequence-number {
         type int32;
         description "Sequence number in response packet";
       }
       leaf time-to-live {
         type int32;
         description "Time-to-live (TTL) value in response packet";
       }
       leaf response-size {
         type int32;
         description "Size of response (bytes)";
       }
       leaf rtt {
         type uint64;
         description "Route trip time for probe (microseconds)";
       }
       leaf ingress-interface {
         type string;
         description "Interface that received the response";
       }
       leaf ip-address {
         type jt:ipaddr;
         description "IP address of interface that received probe";
       }
       leaf host-name {
         type string;
         description "Hostname of interface that received probe";
       }
       leaf probe-success {
         type empty;
         description "A valid response was received";
       }
       leaf probe-duplicate {
         type empty;
         description "A duplicate response was received";
       }
       leaf probe-reached {
         type empty;
         description "Probe reached destination host";
       }
       leaf probe-failure {
         type string;
         description "No valid response received";
       }
       container icmp-type {
         description "Type of ICMP message";
         leaf icmp-type-none {
           type empty;
         }
         leaf icmp-echoreply {
           type empty;
         }
         leaf icmp-unreach {
           type empty;
         }
         leaf icmp-sourcequench {
           type empty;
         }
         leaf icmp-redirect {
           type empty;
         }
         leaf icmp-echo {
           type empty;
         }
         leaf icmp-routeradvert {
           type empty;
         }
         leaf icmp-routersolicit {
           type empty;
         }
         leaf icmp-timxceed {
           type empty;
         }
         leaf icmp-paramprob {
           type empty;
         }
         leaf icmp-tstamp {
           type empty;
         }
         leaf icmp-tstampreply {
           type empty;
         }
         leaf icmp-ireq {
           type empty;
         }
         leaf icmp-ireqreply {
           type empty;
         }
         leaf icmp-maskreq {
           type empty;
         }
         leaf icmp-maskreply {
           type empty;
         }
         leaf icmp6-unreach {
           type empty;
         }
         leaf icmp6-packet-too-big {
           type empty;
         }
         leaf icmp6-time-exceeded {
           type empty;
         }
         leaf icmp6-parameter-problem {
           type empty;
         }
         leaf icmp6-echo-request {
           type empty;
         }
         leaf icmp6-echo-reply {
           type empty;
         }
         leaf icmp6-membership-query {
           type empty;
         }
         leaf icmp6-membership-report {
           type empty;
         }
         leaf icmp6-membership-reduction {
           type empty;
         }
         leaf icmp6-router-solicit {
           type empty;
         }
         leaf icmp6-router-advert {
           type empty;
         }
         leaf icmp6-neighbor-solicit {
           type empty;
         }
         leaf icmp6-neighbor-advert {
           type empty;
         }
         leaf icmp6-redirect {
           type empty;
         }
         leaf icmp6-router-renumbering {
           type empty;
         }
         leaf icmp6-ni-query {
           type empty;
         }
         leaf icmp6-ni-reply {
           type empty;
         }
       }
       container icmp-code {
         description "Type of ICMP message type sub code";
         leaf icmp-code-none {
           type empty;
         }
         leaf icmp-unreach-net {
           type empty;
         }
         leaf icmp-unreach-host {
           type empty;
         }
         leaf icmp-unreach-protocol {
           type empty;
         }
         leaf icmp-unreach-port {
           type empty;
         }
         leaf icmp-unreach-needfrag {
           type empty;
         }
         leaf icmp-unreach-srcfail {
           type empty;
         }
         leaf icmp-unreach-net-unknown {
           type empty;
         }
         leaf icmp-unreach-host-unknown {
           type empty;
         }
         leaf icmp-unreach-isolated {
           type empty;
         }
         leaf icmp-unreach-net-prohib {
           type empty;
         }
         leaf icmp-unreach-host-prohib {
           type empty;
         }
         leaf icmp-unreach-tosnet {
           type empty;
         }
         leaf icmp-unreach-toshost {
           type empty;
         }
         leaf icmp-unreach-filter-prohib {
           type empty;
         }
         leaf icmp-unreach-host-precedence {
           type empty;
         }
         leaf icmp-unreach-precedence-cutoff {
           type empty;
         }
         leaf icmp-redirect-net {
           type empty;
         }
         leaf icmp-redirect-host {
           type empty;
         }
         leaf icmp-redirect-tosnet {
           type empty;
         }
         leaf icmp-redirect-toshost {
           type empty;
         }
         leaf icmp-timxceed-intrans {
           type empty;
         }
         leaf icmp-timxceed-reass {
           type empty;
         }
         leaf icmp-paramprob-optabsent {
           type empty;
         }
         leaf icmp6-unreach-noroute {
           type empty;
         }
         leaf icmp6-unreach-admin {
           type empty;
         }
         leaf icmp6-unreach-beyond-scope {
           type empty;
         }
         leaf icmp6-unreach-address {
           type empty;
         }
         leaf icmp6-unreach-port {
           type empty;
         }
         leaf icmp6-time-exceed-transit {
           type empty;
         }
         leaf icmp6-time-exceed-reassembly {
           type empty;
         }
         leaf icmp6-parameter-problem-header {
           type empty;
         }
         leaf icmp6-parameter-problem-nextheader {
           type empty;
         }
         leaf icmp6-parameter-problem-option {
           type empty;
         }
         leaf icmp6-ni-subject-ipv6 {
           type empty;
         }
         leaf icmp6-ni-subject-fqdn {
           type empty;
         }
         leaf icmp6-ni-subject-ipv4 {
           type empty;
         }
         leaf icmp6-ni-success {
           type empty;
         }
         leaf icmp6-ni-refused {
           type empty;
         }
         leaf icmp6-ni-unknown {
           type empty;
         }
       }
       container ip-options {
         description "IP options contained in the response";
         container record-route {
           description "Record route (RR) IP option";
           list record-route-host {
             description "Host entry in the record route";
             leaf ip-address {
               type jt:ipaddr;
               description "IP address of interface that received probe";
             }
             leaf host-name {
               type string;
               description "Hostname of interface that received probe";
             }
           }
         }
         container loose-source-route {
           description "Loose source route (LSRR) IP option";
           list record-route-host {
             description "Host entry in the record route";
             leaf ip-address {
               type jt:ipaddr;
               description "IP address of interface that received probe";
             }
             leaf host-name {
               type string;
               description "Hostname of interface that received probe";
             }
           }
         }
         container strict-source-route {
           description "Strict source route (SSRR) IP option";
           list record-route-host {
             description "Host entry in the record route";
             leaf ip-address {
               type jt:ipaddr;
               description "IP address of interface that received probe";
             }
             leaf host-name {
               type string;
               description "Hostname of interface that received probe";
             }
           }
         }
       }
     }
     container probe-results-summary {
       description "Summary of probe results";
       leaf probes-sent {
         type int32;
         description "Number of probes sent to target host";
       }
       leaf responses-received {
         type int32;
         description "Number of responses to probes received from target host";
       }
       leaf packet-loss {
         type int32;
         description "Percentage of probes that resulted in no response";
       }
       leaf response-duplicates {
         type int32;
         description "Number of duplicate responses received for one or more probes";
       }
       leaf response-unexpected-sequence {
         type int32;
         description "Number of responses received with unexpected sequence number";
       }
       leaf rtt-minimum {
         type uint64;
         description "Minimum round trip time (microseconds)";
       }
       leaf rtt-average {
         type uint64;
         description "Average round trip time (microseconds)";
       }
       leaf rtt-maximum {
         type uint64;
         description "Maximum round trip time (microseconds)";
       }
       leaf rtt-stddev {
         type uint64;
         description "Standard Deviation of round trip time (microseconds)";
       }
     }
   }
   grouping lsping-srv6-results-block {
     leaf lsping-failure {
       type string;
       description "Lsping failed";
     }
     leaf lsping-failure-message {
       type string;
       description "Error message for lsping";
     }
     leaf-list lsping-warning-message {
       type string;
       description "Warning message for lsping";
     }
     list lsping-probe-request {
       description "One request probe";
       leaf lsping-sequence-number {
         type int32;
         description "Sequence number in request packet";
       }
       leaf lsping-interface-index {
         type int32;
       }
       leaf-list lsping-label {
         type int32;
         description "Label of MPLS packet";
       }
       leaf lsping-src-address {
         type string;
         description "Ingress prefix of SRV6 packet";
       }
       leaf lsping-packet-size {
         type int32;
         description "Ping request packet size";
       }
     }
     list lsping-probe-reply {
       leaf lsping-sequence-number {
         type int32;
         description "Sequence number in request packet";
       }
       leaf lsping-return-code {
         type string;
         description "Success or failure code";
       }
       leaf lsping-ip-address {
         type string;
         description "IPV4 Egress address";
       }
       leaf lsping-round-trip-time {
         type int32;
         description "Round Trip Time in ms";
       }
       leaf lsping-local-transmit-time {
         type string;
         description "Local transmit time in seconds since Jan 1,1970";
       }
       leaf lsping-local-transmit-time-us {
         type int32;
         description "Local transmit time in micro-seconds since Jan 1,1970";
       }
       leaf lsping-remote-receive-time {
         type string;
         description "Remote receive time in seconds since Jan 1,1970";
       }
       leaf lsping-remote-receive-time-us {
         type int32;
         description "Remote receive time in micro-seconds since Jan 1,1970";
       }
       leaf lsping-ip6-address {
         type string;
         description "IPV6 Destination address";
       }
       leaf lsping-hop-limit {
         type int32;
         description "Hop Limit";
       }
       leaf lsping-in-interface-index {
         type int32;
       }
       leaf lsping-vpls-display-str {
         type string;
         description "VPLS display string";
       }
     }
     list lsping-results-summary {
       description "Summary of lsping probe results";
       leaf lsping-ip-address {
         type string;
         description "IPV4 Egress address";
       }
       leaf lsping-packets-transmitted {
         type int32;
         description "Number of packets sent to target host";
       }
       leaf lsping-packets-received {
         type int32;
         description "Number of packets received from the target host";
       }
       leaf lsping-packet-loss {
         type int32;
         description "Lsping percentage of packets that resulted in no response";
       }
       leaf lsping-packet-time-minimum {
         type uint64;
         description "Minimum round trip time (microseconds)";
       }
       leaf lsping-packet-time-average {
         type uint64;
         description "Average round trip time (microseconds)";
       }
       leaf lsping-packet-time-maximum {
         type uint64;
         description "Maximum round trip time (microseconds)";
       }
       leaf lsping-packet-time-stddev {
         type uint64;
         description "Standard Deviation of round trip time (microseconds)";
       }
       leaf lsping-error-packets {
         type int32;
         description " Number of packets received with error status";
       }
     }
   }
 }
