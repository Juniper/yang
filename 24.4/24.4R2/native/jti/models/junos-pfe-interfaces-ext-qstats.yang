module junos-pfe-interfaces-ext-qstats {
  yang-version 1;
  namespace "http://juniper.net/yang/junos-telemetry-interfaces-ext-qstats";
  prefix junos-pfe-interfaces-ext-qstats;

// import some basic types
  import ietf-yang-types { prefix "yang"; }

  organization
    "Juniper Networks Inc.";
  contact
    "Juniper Networks, Inc.

     1133 Innovation Way
     Sunnyvale, CA

     +1 888 314-5822

     E-mail: yang-support@juniper.net";
  description
    "Yang definition for Interface Extended Queue stats

  Copyright (c) 2023 Juniper Networks, Inc.
     All rights reserved.";

  revision 2023-08-01 {
    description
      "Initial revision";
  }

grouping jnx-interface-ext-queue-stats {
      leaf queue-number {
        type uint32;
        description
          "queue number";
      }
      leaf queued-pkts {
        type yang:counter64;
        description
          "The total number of packets queued at the queue.";
      }

      leaf queued-bytes {
        type yang:counter64;
        description
          "The total number of bytes queued at the queue.";
      }

      leaf lp-red-drop-pkts {
        type yang:counter64;
        description
          "The total number of low PLP packets RED-droppped at the queue.";
      }

      leaf hp-red-drop-pkts {
        type yang:counter64;
        description
          "The total number of high PLP packets RED-droppped at the queue.";
      }

 }

 grouping pfe-interface-ext-qstats-top {
    description
      "This describes the data exported by PFE jvision for ifd ext qstats sensor";
    container junos {
      description
        "JunOS OS";
      config false;
      container system {
        description
          "Container node for system";
        container linecard {
          description
            "Container node for linecard";
          list interface {
            description
              "Describes interface information";
              key "name";
              leaf name {
                description
                  "Interface name";
                type string;
              }
              container queue {
                description
                  "Describes ifd ext egress queue stats information";
                  list extended-stats {
                     key "queue-number";
                     uses jnx-interface-ext-queue-stats;
                  }
              }
           }
         }
      }
    }
 }
 uses pfe-interface-ext-qstats-top;
}
