/*
 * Copyright (c) 2025 Juniper Networks, Inc.
 * All rights reserved.
 */
 module junos-qfx-conf-forwarding-options {
   namespace "http://yang.juniper.net/junos-qfx/conf/forwarding-options";

   prefix jc-forwarding-options;

   import junos-common-types {
     prefix jt;
     revision-date 2024-01-01;
   }

   import junos-qfx-conf-root {
     prefix jc;
     revision-date 2024-01-01;
   }

   organization "Juniper Networks, Inc.";

   contact "yang-support@juniper.net";

   description "Junos forwarding-options configuration module";

   revision 2024-01-01 {
     description "Junos: 24.4R2.25";
   }

   augment /jc:configuration {
     uses forwarding-options-group;
   }
   augment /jc:configuration/jc:groups {
     uses forwarding-options-group;
   }
   grouping forwarding-options-group {
     container forwarding-options {
       description "Configure options to control packet forwarding";
       uses juniper-forwarding-options;
     }
   }
   grouping juniper-forwarding-options {
     uses apply-advanced;
     list storm-control-profiles {
       key name;
       description "Storm control profile for this instance";
       leaf name {
         description "Storm control profile name";
         type string {
           length "1 .. 127";
         }
       }
       uses apply-advanced;
       container all {
         presence "enable all";
         description "For all BUM traffic";
         uses apply-advanced;
         choice bandwidth {
           case case_1 {
             leaf bandwidth-percentage {
               description "Percentage of link bandwidth";
               type union {
                 type string {
                   pattern "<.*>|$.*";
                 }
                 type uint32 {
                   range "1 .. 100";
                 }
               }
             }
           }
           case case_2 {
             leaf bandwidth-level {
               description "Link bandwidth";
               units "kbps";
               type union {
                 type string {
                   pattern "<.*>|$.*";
                 }
                 type uint32;
               }
             }
           }
         }
         leaf burst-size {
           description "Burst size";
           units "bytes";
           type union {
             type string {
               pattern "<.*>|$.*";
             }
             type uint32;
           }
         }
         leaf no-broadcast {
           description "Disable broadcast storm control";
           type empty;
         }
         leaf no-unknown-unicast {
           description "Disable unknown unicast storm control";
           type empty;
         }
         choice no-multicast-choices {
           case case_1 {
             leaf no-multicast {
               description "Disable multicast storm control";
               type empty;
             }
           }
           case case_2 {
             leaf no-registered-multicast {
               description "Disable registered multicast storm control";
               type empty;
             }
           }
           case case_3 {
             leaf no-unregistered-multicast {
               description "Disable unregistered multicast storm control";
               type empty;
             }
           }
         }
       }
       leaf action-shutdown {
         description "Disable port for excessive storm control errors";
         type empty;
       }
     }
     container loopback {
       description "Configure loopback options for packet forwarding";
       uses apply-advanced;
       container load-balance {
         presence "enable load-balance";
         description "Load balance loopback traffic using all available PFE loopback paths";
         uses apply-advanced;
         leaf mode {
           description "Select load balance mode";
           default "weighted";
           type enumeration {
             enum "equal-cost" {
               description "Use equal cost for all loopback paths";
             }
             enum "weighted" {
               description "Use weights in proportion of pfe loopback bandwidth";
             }
           }
         }
         leaf hash-profile {
           description "Select load balance hash-key profile";
           type enumeration {
             enum "profile1" {
               description "Load balance with hash keys in profile1";
             }
             enum "profile2" {
               description "Load balance with hash keys in profile2";
             }
           }
         }
         container exclude {
           description "Exclude specific PFE from loopback traffic load-balance";
           uses apply-advanced;
           list fpc {
             key name;
             description "FPC Parameters";
             uses loopback-load-balance-exclude-fpc-type;
           }
         }
       }
     }
     leaf tunnel-termination {
       description "Enable tunnel termination for all interfaces";
       type empty;
     }
     container tunnels {
       presence "enable tunnels";
       description "Tunnel port profile";
       uses apply-advanced;
       container udp {
         presence "enable udp";
         uses apply-advanced;
         container payload-port-profile {
           presence "enable payload-port-profile";
           description "Tunnel payload port profile udp, only 1 can exist";
           uses apply-advanced;
           leaf profile-name {
             description "Payload port profile name";
             type string;
           }
           leaf inet {
             description "Tunnel port profile udp inet port";
             type union {
               type string {
                 pattern "<.*>|$.*";
               }
               type uint32 {
                 range "1 .. 65535";
               }
             }
           }
           leaf inet6 {
             description "Tunnel port profile udp inet6 port";
             type union {
               type string {
                 pattern "<.*>|$.*";
               }
               type uint32 {
                 range "1 .. 65535";
               }
             }
           }
           leaf mpls {
             description "Tunnel port profile udp mpls port";
             type union {
               type string {
                 pattern "<.*>|$.*";
               }
               type uint32 {
                 range "1 .. 65535";
               }
             }
           }
           leaf iso {
             description "Tunnel port profile udp iso port";
             type union {
               type string {
                 pattern "<.*>|$.*";
               }
               type uint32 {
                 range "1 .. 65535";
               }
             }
           }
         }
       }
     }
     list mirror-profile {
       key name;
       description "Mirror profile of mirror instance";
       uses mirror-profile-attributes;
     }
     choice sampling-or-packet-capture {
       case case_1 {
         container sampling {
           description "Statistical traffic sampling options";
           uses juniper-sampling-options;
         }
       }
       case case_2 {
       }
     }
     list accounting {
       key name;
       description "Configure accounting of traffic";
       uses juniper-packet-accounting-options;
     }
     list analyzer {
       key name;
       description "Analyzer options";
       uses smpl-analyzer-type;
     }
     container port-mirroring {
       description "Configure port mirroring of traffic";
       uses juniper-port-mirror-options;
     }
     container pfe-sensor {
       description "Enable sensor for pfe resources";
       uses apply-advanced;
       container npu-memory {
         description "Gather npu memory information";
         uses apply-advanced;
         container resource-list {
           description "List of resources monitored for pfe sensors";
           uses apply-advanced;
           leaf l3-next-hop {
             description "Fetch l3 next hop information";
             type empty;
           }
           leaf host-ipv4 {
             description "Fetch host ipv4 information";
             type empty;
           }
           leaf host-ipv6 {
             description "Fetch host ipv6 information";
             type empty;
           }
           leaf lpm-table-ipv4 {
             description "Fetch lpm table ipv4 information";
             type empty;
           }
           leaf lpm-table-ipv6-64 {
             description "Fetch lpm table ipv6 information for /64 prefix routes";
             type empty;
           }
           leaf lpm-table-ipv6-128 {
             description "Fetch lpm table ipv6 information for /128 prefix routes";
             type empty;
           }
           leaf egress-l3-interface {
             description "Fetch egress l3 interface information";
             type empty;
           }
           leaf vport {
             description "Fetch vport information";
             type empty;
           }
           leaf mpls-swap-table {
             description "Fetch mpls swap table information";
             type empty;
           }
           leaf mpls-ingress-table {
             description "Fetch mpls ingress table information";
             type empty;
           }
           leaf tunnel-table {
             description "Fetch mpls/Ip tunnel table information";
             type empty;
           }
           leaf vfp {
             description "Fetch vlan filter information";
             type empty;
           }
           leaf ifp {
             description "Fetch ingress filter information";
             type empty;
           }
           leaf efp {
             description "Fetch egress filter information";
             type empty;
           }
           leaf ecmp-group-table {
             description "Fetch ecmp group table information";
             type empty;
           }
           leaf ecmp-member-table {
             description "Fetch ecmp member table information";
             type empty;
           }
         }
       }
     }
     container evpn-vxlan {
       description "EVPN VXLAN configurations";
       uses apply-advanced;
       leaf shared-tunnels {
         description "Create VTEP tunnels to EVPN PE";
         type empty;
       }
       leaf bridge-domain-index-ecmp {
         description "Bridge Domain Index based control plane ECMP";
         type empty;
       }
       container host-originated-packets {
         presence "enable host-originated-packets";
         description "Host Originated Packets";
         uses apply-advanced;
         leaf gbp-src-tag {
           description "GBP source tag for host originated packets";
           type union {
             type string {
               pattern "<.*>|$.*";
             }
             type uint32 {
               range "1 .. 65535";
             }
           }
         }
       }
       container reroute-address {
         description "Reroute IP address for vxlan encapsulation";
         uses apply-advanced;
         choice family {
           case case_1 {
             container inet {
               presence "enable inet";
               description "IPv4 address family";
               uses apply-advanced;
               leaf address {
                 description "Reroute address for IPV4 FRR";
                 type jt:ipv4addr;
               }
             }
           }
           case case_2 {
             container inet6 {
               presence "enable inet6";
               description "IPv6 address family";
               uses apply-advanced;
               leaf address {
                 description "Reroute address for IPV6 FRR";
                 type jt:ipv6addr;
               }
             }
           }
         }
       }
       container gbp {
         description "Group Based Policy options";
         uses apply-advanced;
         leaf ingress-enforcement {
           description "Enable GBP ingress policy enforcement (restarts PFE if standalone and need reboot for VC)";
           type empty;
         }
         leaf tag-only-policy {
           description "Support only src and dst GBP tag match (restarts PFE if standalone and need reboot for VC)";
           type empty;
         }
         leaf mac-ip-inter-tagging {
           description "Enable MAC/IP inter GBP tagging (restarts PFE if standalone and need reboot for VC)";
           type empty;
         }
         container ingress-src-tag {
           description "Assign source tag to filter matched pfx routes under this routing instance";
           uses apply-advanced;
           choice filter_choice {
             case case_1 {
               leaf-list filter {
                 ordered-by user;
                 description "List of filter modules having src tag";
                 type string;
               }
             }
           }
         }
       }
       leaf vxlan-trans-vni-enable {
         description "Enable VxLAN Translated VNI in DCI. This will restart PFE";
         type empty;
       }
       leaf vxlan-dci-enable {
         description "Enable VxLAN DCI Egr Xlate carvings. This will restart PFE";
         type empty;
       }
     }
     container multicast-replication {
       description "Set mode of multicast replication";
       uses apply-advanced;
       container evpn {
         description "EVPN IRB multicast related options";
         uses apply-advanced;
         leaf irb {
           type enumeration {
             enum "local-only" {
               description "Multicast forward in local-only mode";
             }
             enum "local-remote" {
               description "Multicast forward in local-remote mode";
             }
             enum "oism" {
               description "Optimized inter subnet multicast mode";
             }
             enum "enhanced-oism" {
               description "Enhanced OISM to support asymmetric bridge domains";
             }
           }
         }
         leaf smet-forwarding {
           description "Enable SMET forwarding";
           type empty;
         }
         leaf smet-nexthop-limit {
           description "Flood traffic to all egress when count goes above limit";
           type union {
             type string {
               pattern "<.*>|$.*";
             }
             type uint32 {
               range "10000 .. 40000";
             }
           }
         }
       }
     }
     container load-balance {
       description "Configure load-balancing attributes on the forwarding path";
       uses apply-advanced;
       container indexed-load-balance {
         presence "enable indexed-load-balance";
         description "Use indexed permuted next hop lists for unilist and aggregate next hops";
         uses apply-advanced;
       }
       container per-flow {
         uses apply-advanced;
       }
       container per-prefix {
         presence "enable per-prefix";
         uses apply-advanced;
         leaf hash-seed {
           description "Specifies per-router input value for per-prefix load-balancing hash function";
           default "0";
           type union {
             type string {
               pattern "<.*>|$.*";
             }
             type uint16 {
               range "0 .. 65534";
             }
           }
         }
       }
     }
     container hash-key {
       description "Select data used in the hash key";
       uses junos_hash_key;
     }
     container local-bias {
       presence "enable local-bias";
       description "Turn on local bias functionality";
       uses apply-advanced;
       leaf disable {
         description "Disable local-bias";
         type empty;
       }
     }
     container enhance-fp-thread {
       presence "enable enhance-fp-thread";
       description "Set fpc fast thread options";
       uses apply-advanced;
       leaf fp-thread-ttp {
         description "Set number of packet to process in one thread shedule";
         type union {
           type string {
             pattern "<.*>|$.*";
           }
           type uint32 {
             range "50 .. 100";
           }
         }
       }
     }
     leaf ospf2-flow-check-disable {
       description "To disable ospf flow check";
       type empty;
     }
     leaf vrrp-flow-check-disable {
       description "To disable vrrp flow check";
       type empty;
     }
     container global-load-balancing {
       presence "enable global-load-balancing";
       description "Glb paramters";
       uses apply-advanced;
       leaf msg-tx-interval {
         description "Msg tx interval";
         units "milliseconds";
         type union {
           type string {
             pattern "<.*>|$.*";
           }
           type uint32 {
             range "5 .. 1000";
           }
         }
       }
       leaf monitor-interval {
         description "Monitor interval";
         units "microseconds";
         type union {
           type string {
             pattern "<.*>|$.*";
           }
           type uint32 {
             range "10 .. 1000";
           }
         }
       }
       leaf update-interval {
         description "Update interval";
         units "microseconds";
         type union {
           type string {
             pattern "<.*>|$.*";
           }
           type uint32 {
             range "10 .. 1000";
           }
         }
       }
       container ipv4-encap {
         presence "enable ipv4-encap";
         uses apply-advanced;
         leaf udp-destination-port {
           description "Udp destination port";
           type union {
             type string {
               pattern "<.*>|$.*";
             }
             type uint16 {
               range "0 .. 65535";
             }
           }
         }
         leaf dscp {
           description "Numeric dscp value in the range 0 to 63";
           type union {
             type string {
               pattern "<.*>|$.*";
             }
             type uint16 {
               range "0 .. 63";
             }
           }
         }
         leaf udp-source-port {
           description "Udp source port";
           type union {
             type string {
               pattern "<.*>|$.*";
             }
             type uint16 {
               range "0 .. 65535";
             }
           }
         }
         leaf ttl {
           description "Ttl";
           type union {
             type string {
               pattern "<.*>|$.*";
             }
             type uint16 {
               range "0 .. 255";
             }
           }
         }
         leaf ipv4-source-address {
           description "Source ipv4 address";
           type jt:ipv4addr;
         }
         leaf ipv4-destination-address {
           description "Destination ipv4 address";
           type jt:ipv4addr;
         }
         leaf source-mac-address {
           description "Source mac address";
           type jt:mac-addr;
         }
       }
     }
     container enhanced-hash-key {
       description "Select data used in the hash key for Enhanced IP Forwarding Engines";
       uses apply-advanced;
       leaf ecmp-resilient-hash {
         description "Set resilient hashing for ECMP";
         type empty;
       }
       container lag-dlb {
         presence "enable lag-dlb";
         description "Setting dynamic load balancing options for LAG";
         uses apply-advanced;
         container ether-type {
           presence "enable ether-type";
           description "Setting ether type for LAG DLB";
           uses apply-advanced;
           leaf ipv4 {
             description "Ether type is ipv4";
             type empty;
           }
           leaf ipv6 {
             description "Ether type is ipv6";
             type empty;
           }
           leaf mpls {
             description "Ether type is mpls";
             type empty;
           }
         }
       }
       container fabric-load-balance {
         presence "enable fabric-load-balance";
         description "Set load balancing options for VC-Fabric forwarding";
         status deprecated;
         uses apply-advanced;
         choice mode {
           case case_1 {
             container flowlet {
               presence "enable flowlet";
               description "Inactivity-based flowlet link assignment (default)";
               status deprecated;
               uses apply-advanced;
               leaf inactivity-interval {
                 description "Minimum inactivity interval for flowlet detection";
                 status deprecated;
                 type enumeration {
                   enum "16us" {
                     description "16 microseconds (default)";
                     status deprecated;
                   }
                   enum "64us" {
                     description "64 microseconds";
                     status deprecated;
                   }
                   enum "512us" {
                     description "512 microseconds";
                     status deprecated;
                   }
                   enum "32ms" {
                     description "32 milliseconds";
                     status deprecated;
                   }
                 }
               }
             }
           }
           case case_2 {
             leaf per-packet {
               description "Per-packet optimal spraying";
               status deprecated;
               type empty;
             }
           }
         }
       }
       container ecmp-dlb {
         description "Set load balancing options for VC-Fabric forwarding";
         uses apply-advanced;
         container egress-quantization {
           description "Configure egress attributes quantization";
           uses apply-advanced;
           leaf min {
             description "Min in percentage";
             default "50";
             type union {
               type string {
                 pattern "<.*>|$.*";
               }
               type uint32 {
                 range "1 .. 100";
               }
             }
           }
           leaf max {
             description "Max in percentage";
             default "90";
             type union {
               type string {
                 pattern "<.*>|$.*";
               }
               type uint32 {
                 range "1 .. 100";
               }
             }
           }
           leaf rate-weightage {
             description "Weightage between rate versus buffer";
             default "0";
             type union {
               type string {
                 pattern "<.*>|$.*";
               }
               type uint32 {
                 range "0 .. 100";
               }
             }
           }
         }
         choice mode {
           case case_1 {
             leaf assigned-flow {
               description "Flow-based fixed link assignment";
               type empty;
             }
           }
           case case_2 {
             container flowlet {
               presence "enable flowlet";
               description "Inactivity-based flowlet link assignment (default)";
               uses apply-advanced;
               leaf inactivity-interval {
                 description "Minimum inactivity interval in micro-seconds for flowlet detection";
                 default "256";
                 type union {
                   type string {
                     pattern "<.*>|$.*";
                   }
                   type uint32;
                 }
               }
               leaf flowset-table-size {
                 description "Number of flowset (MacroFlow) entries in DLB hash bucket";
                 default "256";
                 type enumeration {
                   enum "256" {
                     description "Flowset size assigned to DLB group is 256 (default)";
                   }
                   enum "512" {
                     description "Flowset size assigned to DLB group is 512";
                   }
                   enum "1024" {
                     description "Flowset size assigned to DLB group is 1024";
                   }
                   enum "2048" {
                     description "Flowset size assigned to DLB group is 2048";
                   }
                   enum "4096" {
                     description "Flowset size assigned to DLB group is 4096";
                   }
                   enum "8192" {
                     description "Flowset size assigned to DLB group is 8192";
                   }
                   enum "16384" {
                     description "Flowset size assigned to DLB group is 16384";
                   }
                   enum "32768" {
                     description "Flowset size assigned to DLB group is 32768";
                   }
                 }
               }
               container reassignment {
                 description "Configure flow reassigment attributes when better quality link is available";
                 uses apply-advanced;
                 leaf prob-threshold {
                   description "Probability threshold for flows";
                   default "0";
                   type union {
                     type string {
                       pattern "<.*>|$.*";
                     }
                     type uint32 {
                       range "0 .. 255";
                     }
                   }
                 }
                 leaf quality-delta {
                   description "Quality difference between members";
                   default "0";
                   type union {
                     type string {
                       pattern "<.*>|$.*";
                     }
                     type uint32 {
                       range "0 .. 7";
                     }
                   }
                 }
               }
             }
           }
           case case_3 {
             leaf per-packet {
               description "Per-packet optimal spraying";
               type empty;
             }
           }
         }
         container ether-type {
           presence "enable ether-type";
           description "Ether type";
           uses apply-advanced;
           leaf ipv4 {
             description "Set DLB for ipv4";
             type empty;
           }
           leaf ipv6 {
             description "Set DLB for ipv6";
             type empty;
           }
           leaf mpls {
             description "Set DLB for mpls";
             type empty;
           }
           leaf none {
             description "None of the ether type qualify for DLB";
             type empty;
           }
         }
         leaf sampling-rate {
           description "Set sampled rate for DLB";
           units "per second";
           type union {
             type string {
               pattern "<.*>|$.*";
             }
             type uint32;
           }
         }
       }
       container hash-mode {
         description "Hashing mode";
         uses apply-advanced;
         choice instance {
           case case_1 {
             leaf layer2-header {
               description "Only layer2 header fields are considered for hashing";
               type empty;
             }
           }
           case case_2 {
             leaf layer2-payload {
               description "Only layer2 payload fields are considered for hashing";
               type empty;
             }
           }
           case case_3 {
             leaf gtp-header-offset {
               description "Gtp header first byte offset";
               type union {
                 type uint8;
                 type string {
                   pattern "<.*>|$.*";
                 }
               }
             }
           }
         }
       }
       container hash-parameters {
         description "Set traffic hashing parameters";
         uses apply-advanced;
         container ecmp {
           description "Configure hashing parameters for ECMP Traffic";
           uses apply-advanced;
           leaf offset {
             description "Set hashing offset for ECMP Traffic";
             type union {
               type string {
                 pattern "<.*>|$.*";
               }
               type uint32 {
                 range "0 .. 199";
               }
             }
           }
           container preprocess {
             description "Enable/Disable the preprocess parameter for ECMP traffic";
             uses apply-advanced;
             choice instance {
               case case_1 {
                 leaf enable {
                   description "Enable preprocess for ECMP";
                   type empty;
                 }
               }
               case case_2 {
                 leaf disable {
                   description "Disable preprocess for ECMP";
                   type empty;
                 }
               }
             }
           }
           container function {
             description "Configure hash functions for ECMP traffic";
             uses apply-advanced;
             choice instance {
               case case_1 {
                 leaf crc16-bisync {
                   description "Use CRC16-BISYNC function for ECMP traffic rcvd on xe";
                   type empty;
                 }
               }
               case case_2 {
                 leaf crc16-ccitt {
                   description "Use CRC16-CCITT function for ECMP traffic rcvd on xe";
                   type empty;
                 }
               }
               case case_3 {
                 leaf crc32-hi {
                   description "Use CRC32-HI function for ECMP traffic rcvd on xe";
                   type empty;
                 }
               }
               case case_4 {
                 leaf crc32-lo {
                   description "Use CRC32-LO function for ECMP traffic rcvd on xe";
                   type empty;
                 }
               }
             }
           }
         }
         container lag {
           description "Configure hashing parameters for LAG Traffic";
           uses apply-advanced;
           leaf offset {
             description "Set hashing offset for LAG Traffic";
             type union {
               type string {
                 pattern "<.*>|$.*";
               }
               type uint32 {
                 range "0 .. 199";
               }
             }
           }
           container preprocess {
             description "Enable/Disable the preprocess parameter for LAG traffic";
             uses apply-advanced;
             choice instance {
               case case_1 {
                 leaf enable {
                   description "Enable preprocess for LAG";
                   type empty;
                 }
               }
               case case_2 {
                 leaf disable {
                   description "Disable preprocess for LAG";
                   type empty;
                 }
               }
             }
           }
           container function {
             description "Configure hash functions for LAG traffic";
             uses apply-advanced;
             choice instance {
               case case_1 {
                 leaf crc16-bisync {
                   description "Use CRC16-BISYNC function for LAG traffic rcvd on xe";
                   type empty;
                 }
               }
               case case_2 {
                 leaf crc16-ccitt {
                   description "Use CRC16-CCITT function for LAG traffic rcvd on xe";
                   type empty;
                 }
               }
               case case_3 {
                 leaf crc32-hi {
                   description "Use CRC32-HI function for LAG traffic rcvd on xe";
                   type empty;
                 }
               }
               case case_4 {
                 leaf crc32-lo {
                   description "Use CRC32-LO function for LAG traffic rcvd on xe";
                   type empty;
                 }
               }
             }
           }
         }
       }
       container hash-seed {
         presence "enable hash-seed";
         description "Hash seed";
         uses apply-advanced;
         leaf seed-value {
           description "Hash seed value";
           type union {
             type string {
               pattern "<.*>|$.*";
             }
             type uint32 {
               range "0 .. 4294967295";
             }
           }
         }
       }
       container resilient-hash-seed {
         presence "enable resilient-hash-seed";
         description "Resilient hash seed";
         uses apply-advanced;
         leaf resilient-seed-value {
           description "Hash seed value for resilient ECMP and LAG";
           type union {
             type string {
               pattern "<.*>|$.*";
             }
             type uint32 {
               range "0 .. 4294967295";
             }
           }
         }
       }
       container mpls {
         description "Configure mpls fields";
         uses apply-advanced;
         leaf no-incoming-port {
           description "Exclude incoming port from the hash key";
           type empty;
         }
         leaf no-incoming-device {
           description "Exclude incoming device from the hash key";
           type empty;
         }
       }
       container layer2 {
         description "Configure layer2 fields";
         uses apply-advanced;
         leaf no-incoming-port {
           description "Exclude incoming port from the hash key";
           type empty;
         }
         leaf no-incoming-device {
           description "Exclude incoming device from the hash key";
           type empty;
         }
         leaf no-source-mac-address {
           description "Exclude source MAC address from the hash key";
           type empty;
         }
         leaf source-mac-address {
           description "Include source MAC address from the hash key";
           type empty;
         }
         leaf no-destination-mac-address {
           description "Exclude destination MAC address from the hash key";
           type empty;
         }
         leaf destination-mac-address {
           description "Include destination MAC address from the hash key";
           type empty;
         }
         leaf no-ether-type {
           description "Exclude ether type from the hash key";
           type empty;
         }
         leaf vlan-id {
           description "Include incoming vlan-id in hash key";
           type empty;
         }
         leaf no-vlan-id {
           description "Not include vlan-id in hash key";
           type empty;
         }
         leaf inner-vlan-id {
           description "Include incoming inner-vlan-id in hash key";
           type empty;
         }
       }
       container inet {
         description "Configure inet4 fields";
         uses apply-advanced;
         leaf no-incoming-port {
           description "Exclude incoming port from the hash key";
           type empty;
         }
         leaf no-incoming-device {
           description "Exclude incoming device from the hash key";
           type empty;
         }
         leaf no-l4-source-port {
           description "Exclude l4 source port from the hash key";
           type empty;
         }
         leaf no-l4-destination-port {
           description "Exclude l4 dest port from the hash key";
           type empty;
         }
         leaf no-protocol {
           description "Exclude protocol from the hash key";
           type empty;
         }
         leaf no-ipv4-source-address {
           description "Exclude IPv4 source address";
           type empty;
         }
         leaf no-ipv4-destination-address {
           description "Exclude IPv4 destination address";
           type empty;
         }
         leaf vlan-id {
           description "Include incoming vlan-id in hash key";
           type empty;
         }
       }
       container inet6 {
         description "Configure inet6 fields";
         uses apply-advanced;
         leaf no-incoming-port {
           description "Exclude incoming port from the hash key";
           type empty;
         }
         leaf no-incoming-device {
           description "Exclude incoming device from the hash key";
           type empty;
         }
         leaf no-l4-source-port {
           description "Exclude l4 source port from the hash key";
           type empty;
         }
         leaf no-l4-destination-port {
           description "Exclude l4 dest port from the hash key";
           type empty;
         }
         leaf ipv6-flow-label {
           description "Include IPv6 flow label";
           type empty;
         }
         leaf no-next-header {
           description "Exclude next header from the hash key";
           type empty;
         }
         leaf no-ipv6-source-address {
           description "Exclude IPv6 source address";
           type empty;
         }
         leaf no-ipv6-destination-address {
           description "Exclude IPv6 destination address";
           type empty;
         }
         leaf vlan-id {
           description "Include vlan-id in hash key";
           type empty;
         }
       }
       leaf no-mpls {
         description "Disable mpls in hash key";
         type empty;
       }
       container gre {
         description "Configure for GRE ";
         uses apply-advanced;
         leaf key {
           description "Include key in hash key";
           type empty;
         }
         leaf protocol {
           description "Include protocol in hash key";
           type empty;
         }
       }
       leaf vxlan-vnid {
         description "Enable vxlan-vnid";
         type empty;
       }
       container symmetric-hash {
         description "Enable symmetric hash for load-balancing";
         uses apply-advanced;
         leaf inet {
           description "Enable symmetric hash on ipv4 flows";
           type empty;
         }
         leaf inet6 {
           description "Enable symmetric hash on ipv6 flows";
           type empty;
         }
       }
       container services-loadbalancing {
         description "Select key to load balance across service PICs";
         uses apply-advanced;
         container family {
           description "Protocol family";
           container inet {
             description "IPv4 protocol family";
             uses apply-advanced;
             container layer-3-services {
               description "Include Layer 3 (IP) data in the hash key";
               uses apply-advanced;
               leaf source-address {
                 description "Include IP source address in the hash key";
                 type empty;
               }
               leaf destination-address {
                 description "Include IP destination address in the hash key";
                 type empty;
               }
               leaf incoming-interface-index {
                 description "Include incoming interface index in the hash key";
                 type empty;
               }
             }
           }
           container inet6 {
             description "IPv6 protocol family";
             uses apply-advanced;
             container layer-3-services {
               description "Include Layer 3 (IP) data in the hash key";
               uses apply-advanced;
               leaf source-address {
                 description "Include IP source address in the hash key";
                 type empty;
               }
               leaf destination-address {
                 description "Include IP destination address in the hash key";
                 type empty;
               }
               leaf incoming-interface-index {
                 description "Include incoming interface index in the hash key";
                 type empty;
               }
               leaf src-prefix-len {
                 description "Enhanced hash key inet6 source prefix length";
                 default "127";
                 units "bits";
                 type union {
                   type string {
                     pattern "<.*>|$.*";
                   }
                   type uint32 {
                     range "56 .. 127";
                   }
                 }
               }
             }
           }
         }
       }
       container family {
         description "Protocol family";
         container any {
           description "Applicable to all protocol families";
           uses apply-advanced;
           leaf incoming-interface-index {
             description "Include incoming interface index in the hash key";
             type empty;
           }
           leaf no-source-mac {
             description "Omit source mac in the hash key";
             type empty;
           }
           leaf no-destination-mac {
             description "Omit destination mac in the hash key";
             type empty;
           }
           leaf no-tunnel-payload {
             description "Omit tunnel payload in the hash key";
             type empty;
           }
         }
         container inet {
           description "IPv4 protocol family";
           uses apply-advanced;
           leaf incoming-interface-index {
             description "Include incoming interface index in the hash key";
             type empty;
           }
           leaf no-destination-port {
             description "Omit IP destination port in the hash key";
             type empty;
           }
           leaf no-source-port {
             description "Omit IP source port in the hash key";
             type empty;
           }
           leaf type-of-service {
             description "Include TOS byte in the hash key";
             type empty;
           }
           leaf gtp-tunnel-endpoint-identifier {
             description "Include TEID in the hash key for GTP-U packets";
             type empty;
           }
           leaf l2tp-tunnel-session-identifier {
             description "Include TID SID in the hash key for L2TP packets";
             type empty;
           }
           leaf session-id {
             description "Include session ID in the enhanced hash key";
             type empty;
           }
         }
         container inet6 {
           description "IPv6 protocol family";
           uses apply-advanced;
           leaf incoming-interface-index {
             description "Include incoming interface index in the hash key";
             type empty;
           }
           leaf traffic-class {
             description "Include Traffic Class byte in the hash key";
             type empty;
           }
           leaf no-destination-port {
             description "Omit IP destination port in the hash key";
             type empty;
           }
           leaf no-source-port {
             description "Omit IP source port in the hash key";
             type empty;
           }
           leaf gtp-tunnel-endpoint-identifier {
             description "Include TEID in the hash key for GTP-U packets";
             type empty;
           }
           leaf session-id {
             description "Include session ID in the enhanced hash key";
             type empty;
           }
           leaf no-flow-label {
             description "Omit Flow label in the hash key";
             type empty;
           }
           leaf type-of-service {
             description "Include TOS byte in the hash key";
             status deprecated;
             type empty;
           }
         }
         container mpls {
           description "MPLS protocol family";
           uses apply-advanced;
           leaf label-1-exp {
             description "Include EXP of first MPLS label from the hash key";
             type empty;
           }
           leaf incoming-interface-index {
             description "Include incoming interface index in the hash key";
             type empty;
           }
           choice pseudowire_option {
             case case_1 {
               leaf no-ether-pseudowire {
                 description "Omit IP payload over ethernet PW from the hash-key";
                 type empty;
               }
             }
             case case_2 {
               container ether-pseudowire {
                 description "Load-balance ethernet over ethernet PW";
                 leaf zero-control-word {
                   description "Parse zero control word in packet header";
                   type empty;
                 }
               }
             }
           }
           leaf no-labels {
             description "Exclude all MPLS labels from hash key";
             type empty;
           }
           leaf no-payload {
             description "Omit MPLS payload data from the hash key";
             type empty;
           }
         }
         container multiservice {
           description "Multiservice protocol (bridged/CCC/VPLS) family";
           uses apply-advanced;
           leaf incoming-interface-index {
             description "Include incoming interface index in hash key";
             type empty;
           }
           leaf outer-priority {
             description "Include Outer 802.1 Priority bits in the hash key";
             type empty;
           }
           leaf no-payload {
             description "Omit payload data from the hash key";
             type empty;
           }
           leaf no-mac-addresses {
             description "Omit source and destination MAC addresses from the hash key";
             type empty;
           }
         }
       }
       container vxlan {
         description "Vxlan traffic";
         uses apply-advanced;
         leaf no-inner-payload {
           description "To enable load-balancing on Vxlan traffic based on outer IP/UDP header";
           type empty;
         }
       }
       list conditional-match {
         key name;
         ordered-by user;
         description "Configures a conditional match";
         leaf name {
           description "Name identifier";
           type string;
         }
         uses apply-advanced;
         container offset1 {
           presence "enable offset1";
           description "Configure offset 1";
           uses apply-advanced;
           leaf base-offset1 {
             description "Configure base-offset";
             type enumeration {
               enum "start-of-L2Header" {
                 description "Offset will be extracted from start of L2 header";
               }
               enum "start-of-L3-OuterHeader" {
                 description "Offset will be extracted from start of outer L3 header";
               }
               enum "start-of-L3-InnerHeader" {
                 description "Offset will be extracted from start of inner L3 header";
               }
               enum "start-of-L4-Header" {
                 description "Offset will be extracted from start of L4 header";
               }
             }
           }
           leaf offset1-value {
             description "Offset of the data to be extracted from the base offset. Only even number";
             type union {
               type string {
                 pattern "<.*>|$.*";
               }
               type uint8 {
                 range "0 .. 126";
               }
             }
           }
           leaf matchdata1 {
             description "Data to be matched";
             type string {
               length 4;
             }
           }
           leaf matchdata1-mask {
             description "Matchdata mask";
             type string {
               length 4;
             }
           }
         }
         container offset2 {
           presence "enable offset2";
           description "Configure offset 2";
           uses apply-advanced;
           leaf base-offset2 {
             description "Configure base-offset";
             type enumeration {
               enum "start-of-L2Header" {
                 description "Offset will be extracted from start of L2 header";
               }
               enum "start-of-L3-OuterHeader" {
                 description "Offset will be extracted from start of outer L3 header";
               }
               enum "start-of-L3-InnerHeader" {
                 description "Offset will be extracted from start of inner L3 header";
               }
               enum "start-of-L4-Header" {
                 description "Offset will be extracted from start of L4 header";
               }
             }
           }
           leaf offset2-value {
             description "Offset of the data to be extracted from the base offset. Only even number";
             type union {
               type string {
                 pattern "<.*>|$.*";
               }
               type uint8 {
                 range "0 .. 126";
               }
             }
           }
           leaf matchdata2 {
             description "Data to be matched";
             type string {
               length 4;
             }
           }
           leaf matchdata2-mask {
             description "Matchdata mask";
             type string {
               length 4;
             }
           }
         }
         container offset3 {
           presence "enable offset3";
           description "Configure offset 3";
           uses apply-advanced;
           leaf base-offset3 {
             description "Configure base-offset";
             type enumeration {
               enum "start-of-L2Header" {
                 description "Offset will be extracted from start of L2 header";
               }
               enum "start-of-L3-OuterHeader" {
                 description "Offset will be extracted from start of outer L3 header";
               }
               enum "start-of-L3-InnerHeader" {
                 description "Offset will be extracted from start of inner L3 header";
               }
               enum "start-of-L4-Header" {
                 description "Offset will be extracted from start of L4 header";
               }
             }
           }
           leaf offset3-value {
             description "Offset of the data to be extracted from the base offset. Only even number";
             type union {
               type string {
                 pattern "<.*>|$.*";
               }
               type uint8 {
                 range "0 .. 126";
               }
             }
           }
           leaf matchdata3 {
             description "Data to be matched";
             type string {
               length 4;
             }
           }
           leaf matchdata3-mask {
             description "Matchdata mask";
             type string {
               length 4;
             }
           }
         }
         container offset4 {
           presence "enable offset4";
           description "Configure offset 4";
           uses apply-advanced;
           leaf base-offset4 {
             description "Configure base-offset";
             type enumeration {
               enum "start-of-L2Header" {
                 description "Offset will be extracted from start of L2 header";
               }
               enum "start-of-L3-OuterHeader" {
                 description "Offset will be extracted from start of outer L3 header";
               }
               enum "start-of-L3-InnerHeader" {
                 description "Offset will be extracted from start of inner L3 header";
               }
               enum "start-of-L4-Header" {
                 description "Offset will be extracted from start of L4 header";
               }
             }
           }
           leaf offset4-value {
             description "Offset of the data to be extracted from the base offset. Only even number";
             type union {
               type string {
                 pattern "<.*>|$.*";
               }
               type uint8 {
                 range "0 .. 126";
               }
             }
           }
           leaf matchdata4 {
             description "Data to be matched";
             type string {
               length 4;
             }
           }
           leaf matchdata4-mask {
             description "Matchdata mask";
             type string {
               length 4;
             }
           }
         }
       }
       list flex-hashing {
         key name;
         ordered-by user;
         description "Set flex hashing";
         leaf name {
           description "Name identifier";
           type string;
         }
         uses apply-advanced;
         container ethtype {
           presence "enable ethtype";
           description "Configure ether-type of packet";
           uses apply-advanced;
           container inet {
             description "Enable flex-hashing on ipv4";
             uses apply-advanced;
             leaf interface {
               description "Incoming interface name. This is optional parameter";
               type union {
                 type jt:interface-name;
                 type string {
                   pattern "<.*>|$.*";
                 }
               }
             }
             leaf conditional-match {
               description "Conditional match to be matched in the packet";
               type string;
             }
             container hash-offset {
               description "Configure the offsets for hashing";
               uses apply-advanced;
               container offset1 {
                 presence "enable offset1";
                 description "Configure offset 1 value";
                 uses apply-advanced;
                 leaf base-offset1 {
                   description "Configure base-offset";
                   type enumeration {
                     enum "start-of-L2Header" {
                       description "Offset will be extracted from start of L2 header";
                     }
                     enum "start-of-L3-OuterHeader" {
                       description "Offset will be extracted from start of outer L3 header";
                     }
                     enum "start-of-L3-InnerHeader" {
                       description "Offset will be extracted from start of inner L3 header";
                     }
                     enum "start-of-L4-Header" {
                       description "Offset will be extracted from start of L4 header";
                     }
                   }
                 }
                 leaf offset1-value {
                   description "Offset of the data to be extracted from the base offset. Only even number";
                   type union {
                     type string {
                       pattern "<.*>|$.*";
                     }
                     type uint8 {
                       range "0 .. 126";
                     }
                   }
                 }
                 leaf offset1-mask {
                   description "Mask for the hash data extracted. 2 byte mask";
                   type string {
                     length 4;
                   }
                 }
                 container offset2 {
                   presence "enable offset2";
                   description "Configure offset 2 value";
                   uses apply-advanced;
                   leaf base-offset2 {
                     description "Configure base-offset";
                     type enumeration {
                       enum "start-of-L2Header" {
                         description "Offset will be extracted from start of L2 header";
                       }
                       enum "start-of-L3-OuterHeader" {
                         description "Offset will be extracted from start of outer L3 header";
                       }
                       enum "start-of-L3-InnerHeader" {
                         description "Offset will be extracted from start of inner L3 header";
                       }
                       enum "start-of-L4-Header" {
                         description "Offset will be extracted from start of L4 header";
                       }
                     }
                   }
                   leaf offset2-value {
                     description "Offset of the data to be extracted from the base offset. Only even number";
                     type union {
                       type string {
                         pattern "<.*>|$.*";
                       }
                       type uint8 {
                         range "0 .. 126";
                       }
                     }
                   }
                   leaf offset2-mask {
                     description "Mask for the hash data extracted. 2 byte mask";
                     type string {
                       length 4;
                     }
                   }
                 }
               }
             }
           }
           container inet6 {
             description "Enable flex-hashing on ipv6";
             uses apply-advanced;
             leaf interface {
               description "Incoming interface name. This is optional parameter";
               type union {
                 type jt:interface-name;
                 type string {
                   pattern "<.*>|$.*";
                 }
               }
             }
             leaf conditional-match {
               description "Conditional match to be matched in the packet";
               type string;
             }
             container hash-offset {
               description "Configure the offsets for hashing";
               uses apply-advanced;
               container offset1 {
                 presence "enable offset1";
                 description "Configure offset 1 value";
                 uses apply-advanced;
                 leaf base-offset1 {
                   description "Configure base-offset";
                   type enumeration {
                     enum "start-of-L2Header" {
                       description "Offset will be extracted from start of L2 header";
                     }
                     enum "start-of-L3-OuterHeader" {
                       description "Offset will be extracted from start of outer L3 header";
                     }
                     enum "start-of-L3-InnerHeader" {
                       description "Offset will be extracted from start of inner L3 header";
                     }
                     enum "start-of-L4-Header" {
                       description "Offset will be extracted from start of L4 header";
                     }
                   }
                 }
                 leaf offset1-value {
                   description "Offset of the data to be extracted from the base offset. Only even number";
                   type union {
                     type string {
                       pattern "<.*>|$.*";
                     }
                     type uint8 {
                       range "0 .. 126";
                     }
                   }
                 }
                 leaf offset1-mask {
                   description "Mask for the hash data extracted. 2 byte mask";
                   type string {
                     length 4;
                   }
                 }
                 container offset2 {
                   presence "enable offset2";
                   description "Configure offset 2 value";
                   uses apply-advanced;
                   leaf base-offset2 {
                     description "Configure base-offset";
                     type enumeration {
                       enum "start-of-L2Header" {
                         description "Offset will be extracted from start of L2 header";
                       }
                       enum "start-of-L3-OuterHeader" {
                         description "Offset will be extracted from start of outer L3 header";
                       }
                       enum "start-of-L3-InnerHeader" {
                         description "Offset will be extracted from start of inner L3 header";
                       }
                       enum "start-of-L4-Header" {
                         description "Offset will be extracted from start of L4 header";
                       }
                     }
                   }
                   leaf offset2-value {
                     description "Offset of the data to be extracted from the base offset. Only even number";
                     type union {
                       type string {
                         pattern "<.*>|$.*";
                       }
                       type uint8 {
                         range "0 .. 126";
                       }
                     }
                   }
                   leaf offset2-mask {
                     description "Mask for the hash data extracted. 2 byte mask";
                     type string {
                       length 4;
                     }
                   }
                 }
               }
             }
           }
           container mpls {
             description "Configure number of MPLS labels";
             uses apply-advanced;
             leaf num-labels {
               description "Configure number of MPLS labels";
               type union {
                 type string {
                   pattern "<.*>|$.*";
                 }
                 type uint8 {
                   range "1 .. 5";
                 }
               }
             }
             leaf interface {
               description "Incoming interface name. This is optional parameter";
               type union {
                 type jt:interface-name;
                 type string {
                   pattern "<.*>|$.*";
                 }
               }
             }
             leaf conditional-match {
               description "Conditional match to be matched in the packet";
               type string;
             }
             container hash-offset {
               description "Configure the offsets for hashing";
               uses apply-advanced;
               container offset1 {
                 presence "enable offset1";
                 description "Configure offset 1 value";
                 uses apply-advanced;
                 leaf base-offset1 {
                   description "Configure base-offset";
                   type enumeration {
                     enum "start-of-L2Header" {
                       description "Offset will be extracted from start of L2 header";
                     }
                     enum "start-of-L3-OuterHeader" {
                       description "Offset will be extracted from start of outer L3 header";
                     }
                     enum "start-of-L3-InnerHeader" {
                       description "Offset will be extracted from start of inner L3 header";
                     }
                     enum "start-of-L4-Header" {
                       description "Offset will be extracted from start of L4 header";
                     }
                   }
                 }
                 leaf offset1-value {
                   description "Offset of the data to be extracted from the base offset. Only even number";
                   type union {
                     type string {
                       pattern "<.*>|$.*";
                     }
                     type uint8 {
                       range "0 .. 126";
                     }
                   }
                 }
                 leaf offset1-mask {
                   description "Mask for the hash data extracted. 2 byte mask";
                   type string {
                     length 4;
                   }
                 }
                 container offset2 {
                   presence "enable offset2";
                   description "Configure offset 2 value";
                   uses apply-advanced;
                   leaf base-offset2 {
                     description "Configure base-offset";
                     type enumeration {
                       enum "start-of-L2Header" {
                         description "Offset will be extracted from start of L2 header";
                       }
                       enum "start-of-L3-OuterHeader" {
                         description "Offset will be extracted from start of outer L3 header";
                       }
                       enum "start-of-L3-InnerHeader" {
                         description "Offset will be extracted from start of inner L3 header";
                       }
                       enum "start-of-L4-Header" {
                         description "Offset will be extracted from start of L4 header";
                       }
                     }
                   }
                   leaf offset2-value {
                     description "Offset of the data to be extracted from the base offset. Only even number";
                     type union {
                       type string {
                         pattern "<.*>|$.*";
                       }
                       type uint8 {
                         range "0 .. 126";
                       }
                     }
                   }
                   leaf offset2-mask {
                     description "Mask for the hash data extracted. 2 byte mask";
                     type string {
                       length 4;
                     }
                   }
                 }
               }
             }
           }
         }
       }
     }
     container next-hop {
       description "Next hop throttle";
       uses apply-advanced;
     }
     container sflow {
       description "Sflow related";
       uses apply-advanced;
       container egress-multicast {
         description "Sflow for egress multicast";
         uses apply-advanced;
         leaf enable {
           description "To enable sflow for egress multicast";
           type empty;
         }
         leaf max-replication-rate {
           description "To configure max replication rate";
           type union {
             type string {
               pattern "<.*>|$.*";
             }
             type uint32;
           }
         }
       }
       container flow-sample {
         description "Flow sample input";
         uses apply-advanced;
         leaf ae-parent-index {
           description "To enable sending ae parent index with SFLOW datagram";
           type empty;
         }
       }
     }
     container multicast {
       description "Multicast resolve and mismatch rate";
       uses apply-advanced;
       leaf resolve-rate {
         description "Multicast resolve rate";
         units "per second";
         type union {
           type string {
             pattern "<.*>|$.*";
           }
           type uint32 {
             range "100 .. 1000";
           }
         }
       }
       leaf mismatch-rate {
         description "Multicast interface mismatch rate";
         units "per second";
         type union {
           type string {
             pattern "<.*>|$.*";
           }
           type uint32 {
             range "50 .. 1000";
           }
         }
       }
       container policer {
         presence "enable policer";
         uses apply-advanced;
         leaf bandwidth-limit {
           description "Bandwidth limit";
           units "bits per second";
           type string;
         }
         leaf burst-size-limit {
           description "Burst size limit";
           units "bytes";
           type string;
         }
       }
     }
     container packet-capture-telemetry {
       description "Packet capture telemetry options";
       uses apply-advanced;
       container egress {
         description "Egress options";
         uses packet-capture-egress-intf-type;
       }
     }
     container rpf-loose-mode-discard {
       description "Configure rpf loose mode behavior";
       uses apply-advanced;
       container family {
         description "Protocol family";
         uses apply-advanced;
         leaf inet {
           description "Configure rpf loose mode behavior for IPv4";
           type empty;
         }
         leaf inet6 {
           description "Configure rpf loose mode behavior for IPv6";
           type empty;
         }
       }
     }
     container explicit-null-cos {
       presence "enable explicit-null-cos";
       description "Configure to use MPLS explicit null exp for COS classification";
       uses apply-advanced;
       leaf inet {
         description "Include family inet";
         type empty;
       }
       leaf inet6 {
         description "Include family inet6";
         type empty;
       }
     }
     container helpers {
       description "Port forwarding configuration";
       uses apply-advanced;
       container traceoptions {
         description "Trace options for helper";
         uses apply-advanced;
         leaf no-remote-trace {
           description "Disable remote tracing";
           type empty;
         }
         container file {
           description "Trace file information";
           leaf filename {
             description "Name of file in which to write trace information";
             type string {
               length "1 .. 1024";
             }
           }
           leaf size {
             description "Maximum trace file size";
             type string;
           }
           leaf files {
             description "Maximum number of trace files";
             default "3";
             type union {
               type string {
                 pattern "<.*>|$.*";
               }
               type uint32 {
                 range "2 .. 1000";
               }
             }
           }
           choice world-readable-choice {
             leaf world-readable {
               description "Allow any user to read the log file";
               type empty;
             }
             leaf no-world-readable {
               description "Don't allow any user to read the log file";
               type empty;
             }
           }
           leaf match {
             description "Regular expression for lines to be logged";
             type jt:regular-expression;
           }
         }
         leaf level {
           description "Level of debugging output";
           default "error";
           type enumeration {
             enum "error" {
               description "Match error conditions";
             }
             enum "warning" {
               description "Match warning messages";
             }
             enum "notice" {
               description "Match conditions that should be handled specially";
             }
             enum "info" {
               description "Match informational messages";
             }
             enum "verbose" {
               description "Match verbose messages";
             }
             enum "all" {
               description "Match all levels";
             }
           }
         }
         list flag {
           key name;
           ordered-by user;
           description "Area of UDP forwarding helper process on which to enable debugging output";
           leaf name {
             type enumeration {
               enum "trace" {
                 description "Trace tracing code";
               }
               enum "address" {
                 description "Trace address management code";
               }
               enum "main" {
                 description "Trace main loop code";
               }
               enum "config" {
                 description "Trace configuration code";
               }
               enum "ifdb" {
                 description "Trace interface database code";
               }
               enum "io" {
                 description "Trace I/O code";
               }
               enum "rtsock" {
                 description "Trace routing socket code";
               }
               enum "ui" {
                 description "Trace user interface code";
               }
               enum "util" {
                 description "Trace miscellaneous utility code";
               }
               enum "gencfg" {
                 description "Trace fud gencfg message";
               }
               enum "domain" {
                 description "Trace DNS service-specific code";
               }
               enum "tftp" {
                 description "Trace TFTP service-specific code";
               }
               enum "bootp" {
                 description "Trace BOOTP/DHCP service-specific code";
               }
               enum "port" {
                 description "Trace arbitrary protocol code";
               }
               enum "if-rtsdb" {
                 description "Trace interface hierarchy rtsdb";
               }
               enum "all" {
                 description "Trace all areas of code";
               }
             }
           }
         }
       }
       container rtsdb-client-traceoptions {
         presence "enable rtsdb-client-traceoptions";
         description "SHM rtsock database client library trace options";
         status deprecated;
         uses apply-advanced;
         container if-rtsdb {
           presence "enable if-rtsdb";
           description "Trace interface hierarchy rtsdb";
           uses apply-advanced;
           list flag {
             key name;
             ordered-by user;
             description "Tracing parameters";
             leaf name {
               type enumeration {
                 enum "init" {
                   description "Trace initialization";
                 }
                 enum "routing-socket" {
                   description "Trace routing socket messages";
                 }
                 enum "map" {
                   description "Trace shared memory mapping";
                 }
                 enum "all" {
                   description "Trace all";
                 }
               }
             }
             leaf disable {
               description "Disable this trace flag";
               type empty;
             }
           }
         }
       }
       container domain {
         description "Incoming DNS request forwarding configuration";
         uses apply-advanced;
         leaf description {
           description "Text description of server";
           type string;
         }
         container server {
           description "Server information";
           leaf address {
             description "Name or address of server to which to forward";
             type jt:ipv4addr;
           }
           choice instance {
             case case_1 {
               container logical-system {
                 description "Logical system of server to which to forward";
                 leaf logical-system-name {
                   description "Name of logical system";
                   type string {
                   }
                 }
                 leaf routing-instance {
                   description "Routing instance of server to which to forward";
                   type union {
                     type string {
                       pattern "default";
                     }
                     type string {
                     }
                   }
                 }
               }
             }
             case case_2 {
               leaf routing-instance {
                 description "Routing instance of server to which to forward";
                 type union {
                   type string {
                     pattern "default";
                   }
                   type string {
                   }
                 }
               }
             }
           }
         }
         list interface {
           key name;
           ordered-by user;
           description "Incoming DNS request forwarding interface configuration";
           leaf name {
             description "Name of interface or group of interfaces";
             type union {
               type jt:interface-wildcard;
               type string {
                 pattern "<.*>|$.*";
               }
             }
           }
           uses apply-advanced;
           leaf no-listen {
             description "Do not listen on this interface";
             type empty;
           }
           leaf broadcast {
             description "If the layer 2 interface is unknown then broadcast";
             type empty;
           }
           leaf description {
             description "Text description of server";
             type string;
           }
           container server {
             description "Server information";
             leaf address {
               description "Name or address of server to which to forward";
               type jt:ipv4addr;
             }
             choice instance {
               case case_1 {
                 container logical-system {
                   description "Logical system of server to which to forward";
                   leaf logical-system-name {
                     description "Name of logical system";
                     type string {
                     }
                   }
                   leaf routing-instance {
                     description "Routing instance of server to which to forward";
                     type union {
                       type string {
                         pattern "default";
                       }
                       type string {
                       }
                     }
                   }
                 }
               }
               case case_2 {
                 leaf routing-instance {
                   description "Routing instance of server to which to forward";
                   type union {
                     type string {
                       pattern "default";
                     }
                     type string {
                     }
                   }
                 }
               }
             }
           }
         }
       }
       container tftp {
         description "Incoming TFTP request forwarding configuration";
         uses apply-advanced;
         leaf description {
           description "Text description of server";
           type string;
         }
         container server {
           description "Server information";
           leaf address {
             description "Name or address of server to which to forward";
             type jt:ipv4addr;
           }
           choice instance {
             case case_1 {
               container logical-system {
                 description "Logical system of server to which to forward";
                 leaf logical-system-name {
                   description "Name of logical system";
                   type string {
                   }
                 }
                 leaf routing-instance {
                   description "Routing instance of server to which to forward";
                   type union {
                     type string {
                       pattern "default";
                     }
                     type string {
                     }
                   }
                 }
               }
             }
             case case_2 {
               leaf routing-instance {
                 description "Routing instance of server to which to forward";
                 type union {
                   type string {
                     pattern "default";
                   }
                   type string {
                   }
                 }
               }
             }
           }
         }
         list interface {
           key name;
           ordered-by user;
           description "Incoming TFTP request forwarding interface configuration";
           leaf name {
             description "Name of interface or group of interfaces";
             type union {
               type jt:interface-wildcard;
               type string {
                 pattern "<.*>|$.*";
               }
             }
           }
           uses apply-advanced;
           leaf no-listen {
             description "Do not listen on this interface";
             type empty;
           }
           leaf broadcast {
             description "If the layer 2 interface is unknown then broadcast";
             type empty;
           }
           leaf description {
             description "Text description of server";
             type string;
           }
           container server {
             description "Server information";
             leaf address {
               description "Name or address of server to which to forward";
               type jt:ipv4addr;
             }
             choice instance {
               case case_1 {
                 container logical-system {
                   description "Logical system of server to which to forward";
                   leaf logical-system-name {
                     description "Name of logical system";
                     type string {
                     }
                   }
                   leaf routing-instance {
                     description "Routing instance of server to which to forward";
                     type union {
                       type string {
                         pattern "default";
                       }
                       type string {
                       }
                     }
                   }
                 }
               }
               case case_2 {
                 leaf routing-instance {
                   description "Routing instance of server to which to forward";
                   type union {
                     type string {
                       pattern "default";
                     }
                     type string {
                     }
                   }
                 }
               }
             }
           }
         }
       }
       container bootp {
         description "Incoming BOOTP/DHCP request forwarding configuration";
         uses apply-advanced;
         leaf relay-agent-option {
           description "Use DHCP Relay Agent option in relayed BOOTP/DHCP messages";
           type empty;
         }
         container dhcp-option82 {
           description "Configure DHCP option 82";
           presence "enable dhcp-option82";
           uses dhcp-option82-type;
         }
         leaf description {
           description "Text description of servers";
           type string;
         }
         list server {
           key name;
           ordered-by user;
           description "Server information";
           leaf name {
             description "Name or address of servers to which to forward";
             type jt:ipv4addr;
           }
           uses apply-advanced;
           list logical-system {
             key name;
             ordered-by user;
             description "Logical system of server to which to forward";
             leaf name {
               description "Name of logical system";
               type string {
               }
             }
             leaf-list routing-instance {
               ordered-by user;
               description "Routing instance of server to which to forward";
               type string;
             }
           }
           leaf-list routing-instance {
             ordered-by user;
             description "Routing instance of server to which to forward";
             type string;
           }
         }
         leaf maximum-hop-count {
           description "Maximum number of hops per packet";
           default "4";
           type union {
             type string {
               pattern "<.*>|$.*";
             }
             type uint32 {
               range "1 .. 16";
             }
           }
         }
         leaf minimum-wait-time {
           description "Minimum number of seconds before requests are forwarded";
           default "0";
           type union {
             type string {
               pattern "<.*>|$.*";
             }
             type uint32 {
               range "0 .. 30000";
             }
           }
         }
         leaf client-response-ttl {
           description "IP time-to-live value to set in responses to client";
           type union {
             type string {
               pattern "<.*>|$.*";
             }
             type uint32 {
               range "1 .. 255";
             }
           }
         }
         leaf apply-secondary-as-giaddr {
           description "Enable DHCP relay to use secondary gateway ip on all interfaces";
           type empty;
         }
         list interface {
           key name;
           ordered-by user;
           description "Incoming BOOTP/DHCP request forwarding interface configuration";
           leaf name {
             description "Name of interface or group of interfaces";
             type union {
               type jt:interface-wildcard;
               type string {
                 pattern "<.*>|$.*";
               }
             }
           }
           uses apply-advanced;
           leaf no-listen {
             description "Do not listen on this interface";
             type empty;
           }
           leaf broadcast {
             description "If the layer 2 interface is unknown then broadcast";
             type empty;
           }
           leaf description {
             description "Text description of servers";
             type string;
           }
           list server {
             key name;
             ordered-by user;
             description "Server information";
             leaf name {
               description "Name or address of servers to which to forward";
               type jt:ipv4addr;
             }
             uses apply-advanced;
             list logical-system {
               key name;
               ordered-by user;
               description "Logical system of server to which to forward";
               leaf name {
                 description "Name of logical system";
                 type string {
                 }
               }
               leaf-list routing-instance {
                 ordered-by user;
                 description "Routing instance of server to which to forward";
                 type string;
               }
             }
             leaf-list routing-instance {
               ordered-by user;
               description "Routing instance of server to which to forward";
               type string;
             }
           }
           leaf maximum-hop-count {
             description "Maximum number of hops per packet";
             default "4";
             type union {
               type string {
                 pattern "<.*>|$.*";
               }
               type uint32 {
                 range "1 .. 16";
               }
             }
           }
           leaf minimum-wait-time {
             description "Minimum number of seconds before requests are forwarded";
             default "0";
             type union {
               type string {
                 pattern "<.*>|$.*";
               }
               type uint32 {
                 range "0 .. 30000";
               }
             }
           }
           leaf client-response-ttl {
             description "IP time-to-live value to set in responses to client";
             type union {
               type string {
                 pattern "<.*>|$.*";
               }
               type uint32 {
                 range "1 .. 255";
               }
             }
           }
           container dhcp-option82 {
             description "Configure DHCP option 82";
             presence "enable dhcp-option82";
             uses dhcp-option82-type;
           }
           leaf apply-secondary-as-giaddr {
             description "Enable DHCP relay to use secondary gateway ip on this interface";
             type empty;
           }
         }
       }
       list port {
         key name;
         ordered-by user;
         description "Incoming arbitrary protocol request forwarding configuration";
         leaf name {
           description "Port number of the protocol to listen";
           type union {
             type string {
               pattern "<.*>|$.*";
             }
             type uint32 {
               range "1 .. 65535";
             }
           }
         }
         uses apply-advanced;
         leaf description {
           description "Text description of server";
           type string;
         }
         list server {
           key name;
           ordered-by user;
           description "Server information";
           leaf name {
             description "Name or address of server to which to forward";
             type jt:ipv4addr;
           }
           uses apply-advanced;
           choice instance {
             case case_1 {
               container logical-system {
                 description "Logical system of server to which to forward";
                 leaf logical-system-name {
                   description "Name of logical system";
                   type string {
                   }
                 }
                 leaf routing-instance {
                   description "Routing instance of server to which to forward";
                   type union {
                     type string {
                       pattern "default";
                     }
                     type string {
                     }
                   }
                 }
               }
             }
             case case_2 {
               leaf routing-instance {
                 description "Routing instance of server to which to forward";
                 type union {
                   type string {
                     pattern "default";
                   }
                   type string {
                   }
                 }
               }
             }
           }
         }
         list interface {
           key name;
           ordered-by user;
           description "Incoming request forwarding interface configuration";
           leaf name {
             description "Name of interface or group of interfaces";
             type union {
               type jt:interface-wildcard;
               type string {
                 pattern "<.*>|$.*";
               }
             }
           }
           uses apply-advanced;
           leaf no-listen {
             description "Do not listen on this interface";
             type empty;
           }
           leaf broadcast {
             description "If the layer 2 interface is unknown then broadcast";
             type empty;
           }
           leaf description {
             description "Text description of server";
             type string;
           }
           list server {
             key name;
             ordered-by user;
             description "Server information";
             leaf name {
               description "Name or address of server to which to forward";
               type jt:ipv4addr;
             }
             uses apply-advanced;
             choice instance {
               case case_1 {
                 container logical-system {
                   description "Logical system of server to which to forward";
                   leaf logical-system-name {
                     description "Name of logical system";
                     type string {
                     }
                   }
                   leaf routing-instance {
                     description "Routing instance of server to which to forward";
                     type union {
                       type string {
                         pattern "default";
                       }
                       type string {
                       }
                     }
                   }
                 }
               }
               case case_2 {
                 leaf routing-instance {
                   description "Routing instance of server to which to forward";
                   type union {
                     type string {
                       pattern "default";
                     }
                     type string {
                     }
                   }
                 }
               }
             }
           }
         }
       }
       leaf relay-agent-option {
         description "Use DHCP Relay Agent option in relayed BOOTP/DHCP messages";
         status deprecated;
         type empty;
       }
     }
     container family {
       description "Protocol family";
       container inet {
         description "IPv4 parameters";
         uses apply-advanced;
         container dscp-mapping-classifier {
           description "Bind classifier name Globally";
           leaf classifier-name {
             description "Ipv4 classifier-name";
             type union {
               type string {
                 pattern "default";
               }
               type string {
                 length "1 .. 64";
               }
             }
           }
         }
         container filter {
           description "Filtering for forwarding table";
           uses apply-advanced;
           leaf input {
             description "Name of input filter to apply for forwarded packets";
             type string;
           }
           leaf output {
             description "Name of output filter to apply for forwarded packets";
             type string;
           }
         }
         leaf route-accounting {
           description "Enable IPv4 route accounting";
           type empty;
         }
       }
       container inet6 {
         description "IPv6 parameters";
         uses apply-advanced;
         container dscp-ipv6-mapping-classifier {
           description "Bind classifier name Globally";
           leaf classifier-name {
             description "Ipv6 classifier-name";
             type union {
               type string {
                 pattern "default";
               }
               type string {
                 length "1 .. 64";
               }
             }
           }
         }
         container filter {
           description "Filtering for forwarding table";
           uses apply-advanced;
           leaf input {
             description "Name of input filter to apply for forwarded packets";
             type string;
           }
           leaf output {
             description "Name of output filter to apply for forwarded packets";
             type string;
           }
         }
         leaf route-accounting {
           description "Enable IPv6 route accounting";
           type empty;
         }
         leaf source-checking {
           description "Discard IPv6 packet when source address type is unspecified, loopback, multicast or link-local ";
           type empty;
         }
       }
       container mpls {
         description "MPLS parameters";
         uses apply-advanced;
         container filter {
           description "Filtering for forwarding table";
           uses apply-advanced;
           leaf input {
             description "Name of input filter to apply for forwarded packets";
             type string;
           }
           leaf output {
             description "Name of output filter to apply for forwarded packets";
             type string;
           }
         }
       }
       container vpls {
         description "VPLS parameters";
         uses apply-advanced;
         container filter {
           description "Filtering for VPLS DMAC forwarding table";
           uses apply-advanced;
           leaf input {
             description "Name of input filter to apply for forwarded packets";
             type string;
           }
         }
         container flood {
           description "Filtering for VPLS flood table";
           uses apply-advanced;
           leaf input {
             description "Name of input filter to apply for VPLS flood packets";
             type string;
           }
         }
       }
       container evpn {
         description "EVPN parameters";
         uses apply-advanced;
         container filter {
           description "Filtering for EVPN DMAC forwarding table";
           uses apply-advanced;
           leaf input {
             description "Name of input filter to apply for forwarded packets";
             type string;
           }
         }
         container flood {
           description "Filtering for EVPN flood table";
           uses apply-advanced;
           leaf input {
             description "Name of input filter to apply for EVPN flood packets";
             type string;
           }
         }
       }
     }
     list next-hop-group {
       key name;
       description "Next hop group forwarding option";
       uses juniper-next-hop-group-options;
     }
     container dhcp-relay {
       description "Dynamic Host Configuration Protocol relay configuration";
       uses jdhcp-relay-type;
     }
     choice load-balance-label-capability-choice {
       leaf load-balance-label-capability {
         description "Load balance label capability";
         type empty;
       }
       leaf no-load-balance-label-capability {
         description "Don't load balance label capability";
         type empty;
       }
     }
     leaf fast-reroute-priority {
       description "Fast-reroute repair priority";
       type enumeration {
         enum "low" {
           description "Set priority to low";
         }
         enum "medium" {
           description "Set priority to medium";
         }
         enum "high" {
           description "Set priority to high";
         }
       }
     }
     list ip-options-protocol-queue {
       key name;
       ordered-by user;
       description "IP Options protocol logical queue parameters";
       leaf name {
         description "Protocol name";
         type string;
       }
       uses apply-advanced;
       leaf protocol-id {
         description "Protocol Identifier";
         type union {
           type string {
             pattern "<.*>|$.*";
           }
           type uint8 {
             range "1 .. 254";
           }
         }
       }
       leaf queue-depth {
         description "Size of the protocol logical options queue";
         type union {
           type string {
             pattern "<.*>|$.*";
           }
           type uint32 {
             range "1 .. 807";
           }
         }
       }
     }
     leaf cut-through {
       description "Enable cut-through forwarding";
       type empty;
     }
     container storm-control {
       presence "enable storm-control";
       description "Storm control config";
       uses apply-advanced;
       leaf enhanced {
         description "Enable enhanced storm control feature";
         type empty;
       }
     }
     leaf vrf-fallback {
       description "Enable vrf-fallback forwarding. This will restart PFE";
       type empty;
     }
     leaf mpls-tunnel-extend {
       description "Extend MPLS Tunnel table usage. This config will restart PFE";
       type empty;
     }
     leaf vxlan-bum-bit-disable {
       description "Disable setting BUM traffic bit in VxLAN header";
       type empty;
     }
     leaf vxlan-disable-copy-tos-encap {
       description "Disable copy of TOS bits from Outer IP to Inner IP at VxLAN Tunnel Encap";
       type empty;
     }
     leaf vxlan-disable-copy-tos-decap {
       description "Disable copy of TOS bits from Outer IP to Inner IP at VxLAN Tunnel Decap";
       type empty;
     }
     leaf vxlan-tos-copy-filter {
       description "To enable TOS copy at VxLAN Tunnel Encap";
       type empty;
     }
     container count {
       description "To enable count of a specfic feature";
       uses apply-advanced;
       leaf ecn-per-queue {
         description "To enable count of ecn packets per queue";
         type empty;
       }
     }
     leaf no-hierarchical-ecmp {
       description "Disable hierarchical ecmp. This will restart PFE";
       type empty;
     }
     leaf ipmc-miss-do-l2mc {
       description "Do L2MC forwarding when IPMC miss";
       type empty;
     }
     leaf port-mac-in-tcam {
       description "Enable Port+mac knob in my_station_tcam. This will restart PFE";
       type empty;
     }
     leaf vxlan-flexflow {
       description "Enable VxLAN flexflow. This will restart PFE";
       type empty;
     }
     leaf inline-bfd-sw-based {
       description "Enable inline BFD as SW based. This will restart PFE";
       type empty;
     }
     leaf ecmp-do-local-lookup {
       description "Do ECMP local lookup only";
       type empty;
     }
     container access-security {
       description "Access security configuration";
       uses jdhcp-access-security-type;
     }
     list forwarding-sandbox {
       key name;
       description "Create forwarding sandbox";
       max-elements 8;
       uses juniper-forwarding-sandbox-options;
     }
     container vxlan-routing {
       description "VXLAN Routing forwarding options";
       uses apply-advanced;
       leaf next-hop {
         description "Next-hop. Must be multiple of 4096. This will restart PFE";
         type union {
           type string {
             pattern "<.*>|$.*";
           }
           type uint32;
         }
       }
       leaf interface-num {
         description "Interface. Must be multiple of 2048. This will restart PFE";
         type union {
           type string {
             pattern "<.*>|$.*";
           }
           type uint32;
         }
       }
       leaf overlay-ecmp {
         description "Enable overlay ecmp for vxlan L3. This will restart PFE";
         type empty;
       }
       leaf loopback-port {
         description "AE loopback interface used for VXLAN routing. This will restart PFE";
         type string;
       }
     }
     container satellite {
       description "Satellite forwarding options";
       uses apply-advanced;
       container traceoptions {
         description "Global tracing options for satellite control plane";
         uses apply-advanced;
         leaf no-remote-trace {
           description "Disable remote tracing";
           type empty;
         }
         container file {
           description "Trace file information";
           leaf filename {
             description "Name of file in which to write trace information";
             type string {
               length "1 .. 1024";
             }
           }
           leaf size {
             description "Maximum trace file size";
             type string;
           }
           leaf files {
             description "Maximum number of trace files";
             default "3";
             type union {
               type string {
                 pattern "<.*>|$.*";
               }
               type uint32 {
                 range "2 .. 1000";
               }
             }
           }
           choice world-readable-choice {
             leaf world-readable {
               description "Allow any user to read the log file";
               type empty;
             }
             leaf no-world-readable {
               description "Don't allow any user to read the log file";
               type empty;
             }
           }
           leaf match {
             description "Regular expression for lines to be logged";
             type jt:regular-expression;
           }
         }
         list flag {
           key name;
           ordered-by user;
           description "Tracing parameters";
           leaf name {
             type enumeration {
               enum "all" {
                 description "Trace everything";
               }
               enum "bd" {
                 description "Trace BD events";
               }
               enum "config-internal" {
                 description "Trace configuration internals";
               }
               enum "interface" {
                 description "Trace interface events";
               }
               enum "interface-vlan" {
                 description "Trace IFBD events";
               }
               enum "ipc" {
                 description "Trace internal IPC messages";
               }
               enum "kernel" {
                 description "Trace Kernel messages";
               }
               enum "krt" {
                 description "Trace communication over routing socket";
               }
               enum "mac" {
                 description "Trace MAC events ";
               }
               enum "nh" {
                 description "Trace NH events";
               }
               enum "normal" {
                 description "Trace normal events";
               }
               enum "parse" {
                 description "Trace configuration parsing";
               }
               enum "stp" {
                 description "Trace STP events";
               }
               enum "task" {
                 description "Trace task processing";
               }
               enum "timer" {
                 description "Trace task timer processing";
               }
               enum "firewall" {
                 description "Trace firewall processing";
               }
               enum "l3" {
                 description "Trace Layer-3 processing";
               }
               enum "fip-snooping" {
                 description "Trace FIP-Snooping processing";
               }
             }
           }
         }
       }
       leaf local-replication {
         description "Enable satellite multicast replication";
         type empty;
       }
       list fpc {
         key name;
         leaf name {
           description "Satellite slot identifier";
           type union {
             type string {
               pattern "<.*>|$.*";
             }
             type uint32 {
               range "65 .. 254";
             }
           }
         }
         uses apply-advanced;
         choice local-switching-mode-choice {
           case case_1 {
             container local-switching {
               presence "enable local-switching";
               description "Enable local-switching on Satellite device";
               uses apply-advanced;
               leaf l3 {
                 description "Enable L3 local switching on the Satellite device";
                 type empty;
               }
             }
           }
           case case_2 {
             container selective-vlan-switching {
               description "Enable selective-vlan-switching on Satellite device";
               uses apply-advanced;
               leaf routing-instance {
                 description "Associated Routing instance name";
                 type string {
                 }
               }
             }
           }
         }
       }
       container vlan-auto-sense {
         description "Vlan-auto-sense attributes provisioning";
         uses apply-advanced;
         leaf expiry-time {
           description "Expiry time (in seconds) after last MAC aged out";
           default "600";
           units "seconds";
           type union {
             type string {
               pattern "<.*>|$.*";
             }
             type uint32 {
               range "30 .. 3600";
             }
           }
         }
       }
       container analyzer-vlan {
         description "Output VLAN for Analyzer";
         uses apply-advanced;
         leaf vlan-name {
           description "Name of the analyzer VLAN";
           type string;
         }
       }
     }
   }
   grouping apply-advanced {
     description "Apply advanced configuration logic";
     leaf-list apply-groups {
       ordered-by user;
       description "Groups from which to inherit configuration data";
       type string;
     }
     leaf-list apply-groups-except {
       ordered-by user;
       description "Don't inherit configuration data from these groups";
       type string;
     }
     list apply-macro {
       key name;
       ordered-by user;
       description "Macro and parameters for commit script expansion";
       uses apply-macro-type;
     }
   }
   grouping apply-macro-type {
     description "Macro data for commit-script expansion";
     leaf name {
       description "Name of the macro to be expanded";
       type string;
     }
     list data {
       key name;
       uses macro-data-type;
     }
   }
   grouping dhcp-option82-type {
     uses apply-advanced;
     leaf disable {
       description "Disable DHCP option 82 on this VLAN";
       type empty;
     }
     container circuit-id {
       presence "enable circuit-id";
       description "Configure DHCP option 82 circuit id";
       uses apply-advanced;
       leaf prefix {
         description "Configure DHCP option 82 circuit id prefix";
         type enumeration {
           enum "hostname" {
             description "Set hostname as the prefix";
           }
         }
       }
       leaf use-interface-description {
         description "Use interface description instead of name";
         type empty;
       }
       leaf use-vlan-id {
         description "Use VLAN id instead of name";
         type empty;
       }
     }
     container remote-id {
       presence "enable remote-id";
       description "Configure DHCP option 82 remote id";
       uses apply-advanced;
       leaf prefix {
         description "Configure DHCP option 82 remote id prefix";
         type enumeration {
           enum "none" {
             description "Set no prefix";
           }
           enum "hostname" {
             description "Set hostname as the prefix";
           }
           enum "mac" {
             description "Set chassis MAC as the prefix";
           }
         }
       }
       leaf use-interface-description {
         description "Use interface description instead of name";
         type empty;
       }
       leaf use-string {
         description "Use raw string instead of the default remote id";
         type string;
       }
     }
     container vendor-id {
       presence "enable vendor-id";
       description "Configure DHCP option 82 vendor id";
       uses apply-advanced;
       leaf use-string {
         description "Use raw string instead of the default vendor id";
         type string;
       }
     }
   }
   grouping jdhcp-access-security-type {
     description "Access security configuration";
     uses apply-advanced;
     container slaac-snooping {
       description "Stateless address auto configuration options";
       uses slaacd-config-type;
     }
     container router-advertisement-guard {
       presence "enable router-advertisement-guard";
       description "Router Advertisement Guard Configuration";
       uses apply-advanced;
       list policy {
         key name;
         ordered-by user;
         description "Router Advertisement Guard policy";
         leaf name {
           description "Router Advertisement Guard policy name";
           type string {
             length "1 .. 64";
           }
         }
         uses apply-advanced;
         container discard {
           description "Discard parameters";
           uses apply-advanced;
           leaf source-ip-address-list {
             description "IPv6 Source address list name";
             type string;
           }
           leaf source-mac-address-list {
             description "Source mac address list name";
             type string;
           }
           leaf prefix-list-name {
             description "Prefix-list Name";
             type string;
           }
         }
         container accept {
           description "Accept parameters";
           uses apply-advanced;
           container match-list {
             description "List of parameters to check";
             uses apply-advanced;
             leaf source-ip-address-list {
               description "IPv6 Source address list name";
               type string;
             }
             leaf source-mac-address-list {
               description "Source mac address list name";
               type string;
             }
             leaf prefix-list-name {
               description "Prefix-list Name";
               type string;
             }
             leaf match-criteria {
               description "Match Criteria";
               type enumeration {
                 enum "match-all" {
                   description "A match from every list";
                 }
                 enum "match-any" {
                   description "A match from any list";
                 }
               }
             }
           }
           container match-options {
             presence "enable match-options";
             description "List of Options to check";
             uses apply-advanced;
             container hop-limit {
               description "Hop limit";
               uses apply-advanced;
               leaf maximum {
                 description "Maximum hop limit";
                 type union {
                   type string {
                     pattern "<.*>|$.*";
                   }
                   type uint32 {
                     range "1 .. 255";
                   }
                 }
               }
               leaf minimum {
                 description "Minimum hop limit";
                 type union {
                   type string {
                     pattern "<.*>|$.*";
                   }
                   type uint32 {
                     range "1 .. 255";
                   }
                 }
               }
             }
             container route-preference {
               description "Accept route preference";
               uses apply-advanced;
               leaf maximum {
                 description "Maximum route preference";
                 type enumeration {
                   enum "low" {
                     description "Route preference low";
                   }
                   enum "medium" {
                     description "Route preference medium";
                   }
                   enum "high" {
                     description "Route preference high";
                   }
                 }
               }
             }
             leaf managed-config-flag {
               description "Check Managed config flag";
               type empty;
             }
             leaf other-config-flag {
               description "Check Other config flag";
               type empty;
             }
           }
         }
       }
       container interface {
         description "RA Guard config on Interface";
         uses apply-advanced;
         list intf-config {
           key name;
           description "Interface Configuration";
           uses interface-policy;
         }
       }
       container vlans {
         description "RA Guard config on Vlan";
         uses apply-advanced;
         list vlan-config {
           key name;
           description "Virtual LAN Configuration";
           uses vlan-policy;
         }
       }
     }
   }
   grouping interface-policy {
     description "Interface Name";
     leaf name {
       description "Interface Name";
       type union {
         type jt:interface-name;
         type string {
           pattern "<.*>|$.*";
         }
       }
     }
     uses apply-advanced;
     container policy {
       description "Attach policy";
       uses apply-advanced;
       leaf policy-name {
         description "Router Advertisement Guard policy name";
         type string;
       }
       choice policy-type {
         case case_1 {
           leaf stateful {
             description "Stateful router advertisement guard";
             type empty;
           }
         }
         case case_2 {
           leaf stateless {
             description "Stateless router advertisement guard";
             type empty;
           }
         }
       }
     }
     container mark-interface {
       description "Mark interface";
       uses apply-advanced;
       choice mark-intf-type {
         case case_1 {
           leaf trusted {
             description "Mark interface trusted";
             type empty;
           }
         }
         case case_2 {
           leaf block {
             description "Block router-advertisement";
             type empty;
           }
         }
       }
     }
   }
   grouping jdhcp-relay-type {
     description "Dynamic Host Configuration Protocol relay configuration";
     uses apply-advanced;
     container traceoptions {
       description "DHCP relay trace options";
       status deprecated;
       uses jdhcp-traceoptions-type;
     }
     container persistent-storage {
       description "Trigger to enable flat file storage";
       leaf automatic {
         description "Trigger automatically";
         type empty;
       }
     }
     leaf duplicate-clients-on-interface {
       description "Allow duplicate clients on different interfaces in a subnet";
       status deprecated;
       type empty;
     }
     container duplicate-clients-in-subnet {
       description "Allow duplicate clients in a subnet";
       uses jdhcp-duplicate-clients-in-subnet-type;
     }
     container interface-traceoptions {
       description "DHCP relay interface trace options";
       status deprecated;
       uses jdhcp-interface-traceoptions-type;
     }
     container dhcpv6 {
       description "DHCPv6 configuration";
       uses dhcpv6-relay-type;
     }
     leaf arp-inspection {
       description "Enable Dynamic ARP Inspection";
       type empty;
     }
     container forward-snooped-clients {
       description "Forward snooped (unicast) packets";
       choice interface-type {
         case case_1 {
           leaf configured-interfaces {
             description "Forward snooped (unicast) packets on configured interfaces";
             type empty;
           }
         }
         case case_2 {
           leaf non-configured-interfaces {
             description "Forward snooped (unicast) packets on non-configured interfaces";
             type empty;
           }
         }
         case case_3 {
           leaf all-interfaces {
             description "Forward snooped (unicast) packets on configured and non-configured interfaces";
             type empty;
           }
         }
       }
     }
     container authentication {
       description "DHCP authentication";
       uses authentication-type;
     }
     container liveness-detection {
       description "DHCP client liveness detection processing";
       uses dhcp-liveness-detection-type;
     }
     container dynamic-profile {
       description "Dynamic profile to use";
       uses dynamic-profile-type;
     }
     leaf service-profile {
       description "Dynamic profile to use for default service activation";
       type string {
         length "1 .. 128";
       }
     }
     leaf access-profile {
       description "Access profile to use for AAA services";
       type string {
         length "1 .. 128";
       }
     }
     container short-cycle-protection {
       description "Short cycle lockout configuration";
       leaf lockout-min-time {
         description "Short cycle lockout time in seconds";
         type union {
           type string {
             pattern "<.*>|$.*";
           }
           type uint32 {
             range "1 .. 86400";
           }
         }
       }
       leaf lockout-max-time {
         description "Short cycle lockout time in seconds";
         type union {
           type string {
             pattern "<.*>|$.*";
           }
           type uint32 {
             range "1 .. 86400";
           }
         }
       }
     }
     container overrides {
       description "DHCP override processing";
       presence "enable overrides";
       uses override-type;
     }
     container relay-option {
       description "DHCP option processing";
       presence "enable relay-option";
       uses dhcp-generic-v4-option;
     }
     container server-match {
       description "Server match processing";
       uses apply-advanced;
       container default-action {
         description "Server match default action";
         presence "enable default-action";
         uses server-match-action-choice;
       }
       list address {
         key name;
         description "Server address";
         leaf name {
           description "Server address for matching";
           type jt:ipv4prefix;
         }
         uses apply-advanced;
         choice server-match-action-choice {
           case case_1 {
             leaf forward-only {
               description "Forward without subscriber services when a match is made";
               type empty;
             }
           }
           case case_2 {
             leaf create-relay-entry {
               description "Create relay entry and allow subscriber services";
               type empty;
             }
           }
         }
       }
     }
     container relay-option-60 {
       description "DHCP option-60 processing";
       presence "enable relay-option-60";
       status deprecated;
       uses relay-option-60-type-top;
     }
     container relay-option-82 {
       description "DHCP option-82 processing";
       presence "enable relay-option-82";
       uses relay-option-82-type;
     }
     container forward-only {
       description "Forward DHCP packets without creating binding";
       presence "enable forward-only";
       uses forward-only-to-rc-type;
     }
     leaf description {
       description "Text description of servers";
       type string;
     }
     leaf maximum-hop-count {
       description "Maximum number of hops per packet";
       type union {
         type string {
           pattern "<.*>|$.*";
         }
         type uint32 {
           range "1 .. 16";
         }
       }
     }
     leaf minimum-wait-time {
       description "Minimum number of seconds before requests are forwarded";
       type union {
         type string {
           pattern "<.*>|$.*";
         }
         type uint32 {
           range "0 .. 30000";
         }
       }
     }
     leaf client-response-ttl {
       description "IP time-to-live value to set in responses to client";
       type union {
         type string {
           pattern "<.*>|$.*";
         }
         type uint32 {
           range "1 .. 255";
         }
       }
     }
     leaf source-ip-change {
       description "Use address of egress interface as source ip";
       type empty;
     }
     leaf forward-only-replies {
       description "Forward-only replies from server to appropriate logical-system:routing-instance based on options";
       type empty;
     }
     container server-group {
       description "Define a DHCP server group";
       uses server-group-type;
     }
     container active-server-group {
       description "Name of DHCP server group";
       uses dhcpv4-gbl-active-sg-type;
     }
     container route-suppression {
       description "Suppress access-internal and/or destination route addition";
       uses dhcp-route-suppression-type;
     }
     list group {
       key name;
       description "Define a DHCP group";
       uses dhcp-group;
     }
     list dual-stack-group {
       key name;
       description "Define a DHCP dual stack group";
       uses dhcp-dual-stack-group;
     }
     leaf no-snoop {
       description "Do not snoop DHCP packets";
       type empty;
     }
     leaf server-response-time {
       description "Number of seconds in a period of activity between the last server response and an unaswered request";
       default "0";
       type union {
         type uint32;
         type string {
           pattern "<.*>|$.*";
         }
       }
     }
     container lease-time-validation {
       presence "enable lease-time-validation";
       description "Configure lease time violation validation";
       uses apply-advanced;
       leaf lease-time-threshold {
         description "Threshold for lease time violation in seconds";
         units "seconds";
         type union {
           type string {
             pattern "<.*>|$.*";
           }
           type uint32 {
             range "60 .. 2147483647";
           }
         }
       }
       container violation-action {
         description "Lease time validation violation action";
         leaf drop {
           description "Drop dhcpv4 offer and ack packets";
           type empty;
         }
       }
     }
     container leasequery {
       description "DHCP leasequery configuration";
       presence "enable leasequery";
       uses relay-leasequery-type;
     }
     container bulk-leasequery {
       description "DHCP bulk leasequery configuration";
       presence "enable bulk-leasequery";
       uses relay-bulk-leasequery-v4-type;
     }
     container active-leasequery {
       description "DHCPv4 active leasequery configuration";
       presence "enable active-leasequery";
       uses active-leasequery-v4-type;
     }
     container remote-id-mismatch {
       description "DHCP client remote-id mismatch";
       presence "enable remote-id-mismatch";
       uses dhcp-remote-id-mismatch-type;
     }
   }
   grouping active-leasequery-v4-type {
     description "Configure active leasequery";
     uses apply-advanced;
     leaf topology-discover {
       description "Topology discovery";
       type empty;
     }
     list peer-address {
       key name;
       description "Server ip address";
       leaf name {
         description "Peer ip address";
         type jt:ipaddr;
       }
       uses apply-advanced;
     }
     list exclude-interface {
       key name;
       ordered-by user;
       description "Exclude interface participating in active leasequery";
       leaf name {
         description "Interface name";
         type union {
           type jt:interface-name;
           type string {
             pattern "<.*>|$.*";
           }
         }
       }
       uses apply-advanced;
     }
     leaf timeout {
       description "Read/write timeout in seconds";
       default "120";
       units "seconds";
       type union {
         type string {
           pattern "<.*>|$.*";
         }
         type uint32 {
           range "10 .. 3600";
         }
       }
     }
     leaf idle-timeout {
       description "Idle timeout in seconds";
       default "60";
       units "seconds";
       type union {
         type string {
           pattern "<.*>|$.*";
         }
         type uint32 {
           range "10 .. 3600";
         }
       }
     }
   }
   grouping authentication-type {
     description "DHCP authentication";
     uses apply-advanced;
     leaf password {
       description "Username password to use";
       type string {
         length "1 .. 64";
       }
     }
     container username-include {
       description "Add username options";
       uses apply-advanced;
       leaf delimiter {
         description "Change delimiter/separator character";
         type string {
           length 1;
         }
       }
       leaf domain-name {
         description "Add domain name";
         type string {
           length "1 .. 64";
         }
       }
       leaf user-prefix {
         description "Add user defined prefix";
         type string {
           length "1 .. 64";
         }
       }
       leaf mac-address {
         description "Include MAC address";
         type empty;
       }
       container option-82 {
         presence "enable option-82";
         description "Include option 82";
         leaf circuit-id {
           description "Include option 82 circuit-id (sub option 1)";
           type empty;
         }
         leaf remote-id {
           description "Include option 82 remote-id (sub option 2)";
           type empty;
         }
       }
       leaf logical-system-name {
         description "Include logical system name";
         type empty;
       }
       leaf routing-instance-name {
         description "Include routing instance name";
         type empty;
       }
       container client-id {
         presence "enable client-id";
         description "Include client ID";
         leaf exclude-headers {
           description "Exclude all the headers";
           type empty;
         }
         leaf use-automatic-ascii-hex-encoding {
           description "Use automatic ascii hex username encoding";
           type empty;
         }
       }
       leaf option-60 {
         description "Include option 60";
         type empty;
       }
       leaf circuit-type {
         description "Include circuit type";
         type empty;
       }
       leaf interface-name {
         description "Include interface name";
         type empty;
       }
       leaf interface-description {
         description "Include interface description";
         type enumeration {
           enum "device" {
             description "Add the device interface description";
           }
           enum "logical" {
             description "Add the logical interface description";
           }
         }
       }
       leaf vlan-tags {
         description "Include the vlan tag(s)";
         type empty;
       }
     }
   }
   grouping dhcp-dual-stack-group {
     description "DHCP dual stack groups";
     leaf name {
       description "Dual stack group name";
       type string {
         length "1 .. 64";
       }
     }
     uses apply-advanced;
     container authentication {
       description "DHCP authentication";
       uses dual-stack-authentication-type;
     }
     leaf service-profile {
       description "Dynamic profile to use for default service activation";
       type string {
         length "1 .. 128";
       }
     }
     leaf access-profile {
       description "Access profile to be used for jdhcpd";
       type string {
         length "1 .. 128";
       }
     }
     container dynamic-profile {
       description "Dynamic profile to use";
       uses dynamic-profile-type;
     }
     container liveness-detection {
       description "DHCP client liveness detection processing";
       uses dhcp-liveness-detection-dualstack-type;
     }
     container relay-agent-interface-id {
       description "Interface-id option processing";
       presence "enable relay-agent-interface-id";
       uses v6-relay-option-interface-id-type;
     }
     container relay-agent-remote-id {
       description "Remote-id option processing";
       presence "enable relay-agent-remote-id";
       uses v6-relay-option-remote-id-type;
     }
     container classification-key {
       description "Classification key for identifying dual stack household";
       uses classification-types;
     }
     leaf dual-stack-interface-client-limit {
       description "Limit the number of client allowed on an interface";
       type union {
         type string {
           pattern "<.*>|$.*";
         }
         type uint32 {
           range "1 .. 500000";
         }
       }
     }
     container protocol-master {
       description "Select family as protocol master";
       uses jdhcp-dual-stack-protocol-mstr-type;
     }
     container short-cycle-protection {
       description "Short cycle lockout configuration";
       leaf lockout-min-time {
         description "Short cycle lockout time in seconds";
         type union {
           type string {
             pattern "<.*>|$.*";
           }
           type uint32 {
             range "1 .. 86400";
           }
         }
       }
       leaf lockout-max-time {
         description "Short cycle lockout time in seconds";
         type union {
           type string {
             pattern "<.*>|$.*";
           }
           type uint32 {
             range "1 .. 86400";
           }
         }
       }
     }
   }
   grouping classification-types {
     description "Different mechanisms to identify a single household";
     uses apply-advanced;
     leaf mac-address {
       description "MAC address of client";
       type empty;
     }
     leaf circuit-id {
       description "Circuit-id as key";
       type empty;
     }
     leaf remote-id {
       description "Remote-id as key";
       type empty;
     }
   }
   grouping dhcp-generic-v4-option {
     description "Generic DHCP options processing";
     uses apply-advanced;
     leaf option-number {
       description "Option number";
       status deprecated;
       type enumeration {
         enum "60" {
           description "Option 60";
           status deprecated;
         }
         enum "77" {
           description "Option 77";
           status deprecated;
         }
       }
     }
     container equals {
       description "Generic option equals";
       status deprecated;
       uses relay-v4-option-ascii-hex;
     }
     container default-action {
       description "Generic option default action";
       status deprecated;
       uses dhcp-v4-option-default-action;
     }
     container starts-with {
       description "Generic option starts with";
       status deprecated;
       uses relay-v4-option-ascii-hex;
     }
     container option-60 {
       description "Add option 60 processing";
       presence "enable option-60";
       uses dhcp-generic-v4-option-type;
     }
     container option-77 {
       description "Add option 77 processing";
       presence "enable option-77";
       uses dhcp-generic-v4-option-type;
     }
     list option-order {
       key name;
       ordered-by user;
       description "Options precedence order";
       leaf name {
         description "Option number";
         type enumeration {
           enum "60" {
             description "Option 60";
           }
           enum "77" {
             description "Option 77";
           }
         }
       }
       uses apply-advanced;
     }
   }
   grouping dhcp-generic-v4-option-type {
     uses apply-advanced;
     container equals {
       description "Generic option equals";
       uses relay-v4-option-ascii-hex;
     }
     container default-action {
       description "Generic option default action";
       uses dhcp-v4-option-default-action;
     }
     container starts-with {
       description "Generic option starts with";
       uses relay-v4-option-ascii-hex;
     }
   }
   grouping dhcp-group {
     description "DHCP groups";
     leaf name {
       description "Group name";
       type string {
         length "1 .. 64";
       }
     }
     uses apply-advanced;
     container active-server-group {
       description "Name of DHCP server group";
       uses dhcpv4-gp-active-sg-type;
     }
     container authentication {
       description "DHCP authentication";
       uses authentication-type;
     }
     container liveness-detection {
       description "DHCP client liveness detection processing";
       uses dhcp-liveness-detection-type;
     }
     container dynamic-profile {
       description "Dynamic profile to use";
       uses dynamic-profile-type;
     }
     leaf service-profile {
       description "Dynamic profile to use for default service activation";
       type string {
         length "1 .. 128";
       }
     }
     leaf access-profile {
       description "Access profile to use for AAA services";
       type string {
         length "1 .. 128";
       }
     }
     container overrides {
       description "DHCP override processing";
       presence "enable overrides";
       uses override-type;
     }
     container short-cycle-protection {
       description "Short cycle lockout configuration";
       leaf lockout-min-time {
         description "Short cycle lockout time in seconds";
         type union {
           type string {
             pattern "<.*>|$.*";
           }
           type uint32 {
             range "1 .. 86400";
           }
         }
       }
       leaf lockout-max-time {
         description "Short cycle lockout time in seconds";
         type union {
           type string {
             pattern "<.*>|$.*";
           }
           type uint32 {
             range "1 .. 86400";
           }
         }
       }
     }
     container server-match {
       description "Server match processing";
       uses apply-advanced;
       container default-action {
         description "Server match default action";
         presence "enable default-action";
         uses server-match-action-choice;
       }
       list address {
         key name;
         description "Server address";
         leaf name {
           description "Server address for matching";
           type jt:ipv4prefix;
         }
         uses apply-advanced;
         choice server-match-action-choice {
           case case_1 {
             leaf forward-only {
               description "Forward without subscriber services when a match is made";
               type empty;
             }
           }
           case case_2 {
             leaf create-relay-entry {
               description "Create relay entry and allow subscriber services";
               type empty;
             }
           }
         }
       }
     }
     container relay-option {
       description "DHCP option processing";
       presence "enable relay-option";
       uses dhcp-generic-v4-option;
     }
     container relay-option-60 {
       description "DHCP option-60 processing";
       presence "enable relay-option-60";
       status deprecated;
       uses relay-option-60-type-group;
     }
     container relay-option-82 {
       description "DHCP option-82 processing";
       presence "enable relay-option-82";
       uses relay-option-82-type;
     }
     container forward-only {
       description "Forward DHCP packets without creating binding";
       presence "enable forward-only";
       uses forward-only-to-rc-type;
     }
     container route-suppression {
       description "Suppress access-internal and/or destination route addition";
       uses dhcp-route-suppression-type;
     }
     leaf description {
       description "Text description of servers";
       type string;
     }
     leaf maximum-hop-count {
       description "Maximum number of hops per packet";
       type union {
         type string {
           pattern "<.*>|$.*";
         }
         type uint32 {
           range "1 .. 16";
         }
       }
     }
     leaf minimum-wait-time {
       description "Minimum number of seconds before requests are forwarded";
       type union {
         type string {
           pattern "<.*>|$.*";
         }
         type uint32 {
           range "0 .. 30000";
         }
       }
     }
     leaf client-response-ttl {
       description "IP time-to-live value to set in responses to client";
       type union {
         type string {
           pattern "<.*>|$.*";
         }
         type uint32 {
           range "1 .. 255";
         }
       }
     }
     leaf source-ip-change {
       description "Use address of egress interface as source ip";
       type empty;
     }
     list interface {
       key name;
       description "One or more interfaces";
       leaf name {
         description "Interface name";
         type union {
           type jt:interface-name;
           type string {
             pattern "<.*>|$.*";
           }
         }
       }
       uses apply-advanced;
       leaf upto {
         description "Interface up to";
         type union {
           type jt:interface-name;
           type string {
             pattern "<.*>|$.*";
           }
         }
       }
       leaf exclude {
         description "Exclude this interface range";
         type empty;
       }
       leaf trace {
         description "Enable tracing for this interface";
         type empty;
       }
       container overrides {
         description "DHCP override processing";
         uses override-type;
       }
       container dynamic-profile {
         description "Dynamic profile to use";
         uses dynamic-profile-type;
       }
       leaf service-profile {
         description "Dynamic profile to use for default service activation";
         type string {
           length "1 .. 128";
         }
       }
       leaf access-profile {
         description "Access profile to use for AAA services";
         type string {
           length "1 .. 128";
         }
       }
       container short-cycle-protection {
         description "Short cycle lockout configuration";
         leaf lockout-min-time {
           description "Short cycle lockout time in seconds";
           type union {
             type string {
               pattern "<.*>|$.*";
             }
             type uint32 {
               range "1 .. 86400";
             }
           }
         }
         leaf lockout-max-time {
           description "Short cycle lockout time in seconds";
           type union {
             type string {
               pattern "<.*>|$.*";
             }
             type uint32 {
               range "1 .. 86400";
             }
           }
         }
       }
     }
     list interface-tag {
       key name;
       description "Interfae tag configuration";
       leaf name {
         description "Interface tag name";
         type string {
           length "1 .. 64";
         }
       }
       uses apply-advanced;
       container overrides {
         description "DHCP override processing";
         uses override-type;
       }
       container dynamic-profile {
         description "Dynamic profile to use";
         uses dynamic-profile-type;
       }
       leaf service-profile {
         description "Dynamic profile to use for default service activation";
         type string {
           length "1 .. 128";
         }
       }
       leaf access-profile {
         description "Access profile to use for AAA services";
         type string {
           length "1 .. 128";
         }
       }
       container short-cycle-protection {
         description "Short cycle lockout configuration";
         leaf lockout-min-time {
           description "Short cycle lockout time in seconds";
           type union {
             type string {
               pattern "<.*>|$.*";
             }
             type uint32 {
               range "1 .. 86400";
             }
           }
         }
         leaf lockout-max-time {
           description "Short cycle lockout time in seconds";
           type union {
             type string {
               pattern "<.*>|$.*";
             }
             type uint32 {
               range "1 .. 86400";
             }
           }
         }
       }
     }
     container remote-id-mismatch {
       description "DHCP client remote-id mismatch";
       presence "enable remote-id-mismatch";
       uses dhcp-remote-id-mismatch-type;
     }
     container lease-time-validation {
       presence "enable lease-time-validation";
       description "Configure lease time violation validation";
       uses apply-advanced;
       leaf lease-time-threshold {
         description "Threshold for lease time violation in seconds";
         units "seconds";
         type union {
           type string {
             pattern "<.*>|$.*";
           }
           type uint32 {
             range "60 .. 2147483647";
           }
         }
       }
       container violation-action {
         description "Lease time validation violation action";
         leaf drop {
           description "Drop dhcpv4 offer and ack packets";
           type empty;
         }
       }
     }
   }
   grouping dhcp-liveness-detection-dualstack-type {
     description "DHCP client liveness detection processing";
     uses apply-advanced;
     container failure-action {
       description "Liveness detection failure action options";
       uses dhcp-liveness-detection-failure-action-type;
     }
     container method {
       description "Liveness detection method options";
       uses apply-advanced;
       choice method-choice {
         case case_1 {
           container layer2-liveness-detection {
             description "Address resolution options";
             uses dhcp-arp-nud-liveness-detection-type;
           }
         }
       }
     }
   }
   grouping dhcp-arp-nud-liveness-detection-type {
     description "Address Resolution detection options";
     uses apply-advanced;
     leaf transmit-interval {
       description "Transmit interval for address resolution";
       default "300";
       units "seconds";
       type union {
         type string {
           pattern "<.*>|$.*";
         }
         type uint32 {
           range "300 .. 1800";
         }
       }
     }
     leaf max-consecutive-retries {
       description "Retry attempts";
       default "3";
       type union {
         type string {
           pattern "<.*>|$.*";
         }
         type uint32 {
           range "3 .. 6";
         }
       }
     }
   }
   grouping dhcp-liveness-detection-failure-action-type {
     description "Liveness detection failure action options";
     uses apply-advanced;
     choice failure-action-type {
       case case_1 {
         leaf clear-binding {
           description "Clear the client binding";
           type empty;
         }
       }
       case case_2 {
         leaf clear-binding-if-interface-up {
           description "Clear the client binding only if the incoming interface is up";
           type empty;
         }
       }
       case case_3 {
         leaf log-only {
           description "Maintain the client binding and log the failure event";
           type empty;
         }
       }
     }
   }
   grouping dhcp-liveness-detection-type {
     description "DHCP client liveness detection processing";
     uses apply-advanced;
     container failure-action {
       description "Liveness detection failure action options";
       uses dhcp-liveness-detection-failure-action-type;
     }
     container method {
       description "Liveness detection method options";
       uses apply-advanced;
       choice method-choice {
         case case_1 {
           container bfd {
             description "Bidirectional Forwarding Detection (BFD) options";
             uses dhcp-bfd-liveness-detection-type;
           }
         }
         case case_2 {
           container layer2-liveness-detection {
             description "Address resolution options";
             uses dhcp-arp-nud-liveness-detection-type;
           }
         }
       }
     }
   }
   grouping dhcp-bfd-liveness-detection-type {
     description "Bidirectional Forwarding Detection (BFD) options";
     uses apply-advanced;
     leaf version {
       description "BFD protocol version number";
       default "automatic";
       type enumeration {
         enum "0" {
           description "BFD version 0 (deprecated)";
         }
         enum "1" {
           description "BFD version 1";
         }
         enum "automatic" {
           description "Choose BFD version automatically";
         }
       }
     }
     leaf minimum-interval {
       description "Minimum transmit and receive interval";
       units "milliseconds";
       type union {
         type string {
           pattern "<.*>|$.*";
         }
         type uint32 {
           range "30000 .. 255000";
         }
       }
     }
     leaf minimum-transmit-interval {
       description "Minimum transmit interval";
       status deprecated;
       units "milliseconds";
       type union {
         type string {
           pattern "<.*>|$.*";
         }
         type uint32 {
           range "30000 .. 255000";
         }
       }
     }
     leaf minimum-receive-interval {
       description "Minimum receive interval";
       units "milliseconds";
       type union {
         type string {
           pattern "<.*>|$.*";
         }
         type uint32 {
           range "30000 .. 255000";
         }
       }
     }
     leaf multiplier {
       description "Detection time multiplier";
       default "3";
       type union {
         type string {
           pattern "<.*>|$.*";
         }
         type uint32 {
           range "1 .. 255";
         }
       }
     }
     leaf inline-disable {
       description "Disable inline mode for this BFD session";
       type empty;
     }
     leaf pdu-size {
       description "BFD transport protocol payload size";
       default "24";
       type union {
         type string {
           pattern "<.*>|$.*";
         }
         type uint32 {
           range "24 .. 16000";
         }
       }
     }
     choice adaptation-choice {
       case case_1 {
         leaf no-adaptation {
           description "Disable adaptation";
           type empty;
         }
       }
     }
     container transmit-interval {
       description "Transmit-interval options";
       uses apply-advanced;
       leaf minimum-interval {
         description "Minimum transmit interval";
         units "milliseconds";
         type union {
           type string {
             pattern "<.*>|$.*";
           }
           type uint32 {
             range "30000 .. 255000";
           }
         }
       }
       leaf threshold {
         description "High transmit interval triggering a trap";
         units "milliseconds";
         type union {
           type uint32;
           type string {
             pattern "<.*>|$.*";
           }
         }
       }
     }
     container detection-time {
       description "Detection-time options";
       uses apply-advanced;
       leaf threshold {
         description "High detection-time triggering a trap";
         units "milliseconds";
         type union {
           type uint32;
           type string {
             pattern "<.*>|$.*";
           }
         }
       }
     }
     leaf session-mode {
       description "BFD single-hop or multihop session-mode";
       default "automatic";
       type enumeration {
         enum "automatic" {
           description "Choose session-mode automatically";
         }
         enum "single-hop" {
           description "Use single-hop";
         }
         enum "multihop" {
           description "Use multihop";
         }
       }
     }
     leaf holddown-interval {
       description "Time to hold the session-UP notification to the client";
       default "0";
       units "milliseconds";
       type union {
         type string {
           pattern "<.*>|$.*";
         }
         type uint32 {
           range "0 .. 255000";
         }
       }
     }
   }
   grouping dhcp-remote-id-mismatch-type {
     description "DHCP client remote-id-mismatch processing";
     uses apply-advanced;
     leaf disconnect {
       description "Disconnect session on remote-id mismatch";
       type empty;
     }
   }
   grouping dhcp-route-suppression-type {
     uses apply-advanced;
     choice dhcp-route-suppression-choice {
       case case_1 {
         leaf access-internal {
           description "Suppress access-internal and destination route addition";
           type empty;
         }
       }
       case case_2 {
         leaf destination {
           description "Suppress destination route addition";
           type empty;
         }
       }
     }
   }
   grouping dhcp-v4-option-default-action {
     description "Default action";
     uses apply-advanced;
     choice server-group-choice {
       case case_1 {
         leaf relay-server-group {
           description "Name of DHCP relay server group when match is made";
           type string {
             length "1 .. 64";
           }
         }
       }
       case case_2 {
         leaf local-server-group {
           description "Name of DHCP local server group when match is made";
           type string {
             length "1 .. 64";
           }
         }
       }
       case case_3 {
         leaf drop {
           description "Discard when a match is made";
           type empty;
         }
       }
       case case_4 {
         leaf forward-only {
           description "Forward without subscriber services when a match is made";
           type empty;
         }
       }
     }
   }
   grouping dhcpv4-gbl-active-sg-type {
     leaf active-server-group {
       description "Name of DHCP server group";
       type string {
         length "1 .. 64";
       }
     }
     leaf allow-server-change {
       description "Accept DHCP-ACK from any server in this group";
       type empty;
     }
   }
   grouping dhcpv4-gp-active-sg-type {
     leaf active-server-group {
       description "Name of DHCP server group";
       type string {
         length "1 .. 64";
       }
     }
     leaf allow-server-change {
       description "Accept DHCP-ACK from any server in this group";
       type empty;
     }
   }
   grouping dhcpv6-relay-type {
     description "DHCPv6 relay configuration";
     uses apply-advanced;
     container authentication {
       description "DHCPv6 authentication";
       uses dhcpv6-authentication-type;
     }
     container persistent-storage {
       description "Trigger to enable flat file storage";
       leaf automatic {
         description "Trigger automatically";
         type empty;
       }
     }
     container liveness-detection {
       description "DHCPv6 client liveness detection processing";
       uses dhcpv6-liveness-detection-type;
     }
     container dynamic-profile {
       description "Dynamic profile to use";
       uses dynamic-profile-type;
     }
     leaf service-profile {
       description "Dynamic profile to use for default service activation";
       type string {
         length "1 .. 128";
       }
     }
     leaf access-profile {
       description "Access profile to use for AAA services";
       type string {
         length "1 .. 128";
       }
     }
     container short-cycle-protection {
       description "Short cycle lockout configuration";
       leaf lockout-min-time {
         description "Short cycle lockout time in seconds";
         type union {
           type string {
             pattern "<.*>|$.*";
           }
           type uint32 {
             range "1 .. 86400";
           }
         }
       }
       leaf lockout-max-time {
         description "Short cycle lockout time in seconds";
         type union {
           type string {
             pattern "<.*>|$.*";
           }
           type uint32 {
             range "1 .. 86400";
           }
         }
       }
     }
     container overrides {
       description "DHCPv6 override processing";
       presence "enable overrides";
       uses dhcpv6-override-relay-type;
     }
     container relay-option {
       description "DHCPv6 option processing";
       presence "enable relay-option";
       uses dhcp-generic-v6-option;
     }
     leaf exclude-relay-agent-identifier {
       description "Exclude relay agent identifier from packets to server";
       type empty;
     }
     container server-match {
       description "Server match processing";
       uses apply-advanced;
       container default-action {
         description "Server match default action";
         uses server-match-action-choice;
       }
       container duid {
         description "Match duid processing";
         uses apply-advanced;
         container equals {
           description "Duid equals";
           uses server-match-v6-ascii-hex;
         }
         container starts-with {
           description "Duid starts with";
           uses server-match-v6-ascii-hex;
         }
       }
       list address {
         key name;
         description "Server ipv6 address";
         leaf name {
           description "Server ipv6 address for matching";
           type jt:ipv6prefix;
         }
         uses apply-advanced;
         choice server-match-action-choice {
           case case_1 {
             leaf forward-only {
               description "Forward without subscriber services when a match is made";
               type empty;
             }
           }
           case case_2 {
             leaf create-relay-entry {
               description "Create relay entry and allow subscriber services";
               type empty;
             }
           }
         }
       }
     }
     leaf relay-agent-option-79 {
       description "Add the client MAC address to the Relay Forward header.";
       type empty;
     }
     container vendor-specific-information {
       description "DHCPv6 option 17 vendor-specific processing";
       uses jdhcp-vendor-specific-type;
     }
     container forward-only {
       description "Forward DHCPv6 packets without creating binding";
       presence "enable forward-only";
       uses forward-only-to-rc-type;
     }
     leaf forward-only-replies {
       description "Forward-only replies from server to appropriate logical-system:routing-instance based on options";
       type empty;
     }
     container forward-snooped-clients {
       description "Forward snooped (unicast) packets";
       choice interface-type {
         case case_1 {
           leaf configured-interfaces {
             description "Forward snooped (unicast) packets on configured interfaces";
             type empty;
           }
         }
         case case_2 {
           leaf non-configured-interfaces {
             description "Forward snooped (unicast) packets on non-configured interfaces";
             type empty;
           }
         }
         case case_3 {
           leaf all-interfaces {
             description "Forward snooped (unicast) packets on configured and non-configured interfaces";
             type empty;
           }
         }
       }
     }
     container route-suppression {
       description "Suppress access-internal and/or access route addition";
       uses dhcpv6-route-suppression-type;
     }
     list group {
       key name;
       description "Define a DHCPv6 relay group";
       uses dhcpv6-relay-group;
     }
     container relay-agent-interface-id {
       description "DHCPv6 interface-id option processing";
       presence "enable relay-agent-interface-id";
       uses v6-relay-option-interface-id-type;
     }
     container relay-agent-remote-id {
       description "DHCPv6 remote-id option processing";
       presence "enable relay-agent-remote-id";
       uses v6-relay-option-remote-id-type;
     }
     container server-group {
       description "Define a DHCPv6 server group";
       uses v6-server-group-type;
     }
     container active-server-group {
       description "Name of DHCPv6 server group";
       uses dhcpv6-gbl-active-sg-type;
     }
     leaf server-response-time {
       description "Number of seconds in a period of activity between the last server response and an unaswered request";
       default "0";
       type union {
         type uint32;
         type string {
           pattern "<.*>|$.*";
         }
       }
     }
     container lease-time-validation {
       presence "enable lease-time-validation";
       description "Configure lease time violation validation";
       uses apply-advanced;
       leaf lease-time-threshold {
         description "Threshold for lease time violation in seconds";
         units "seconds";
         type union {
           type string {
             pattern "<.*>|$.*";
           }
           type uint32 {
             range "60 .. 2147483647";
           }
         }
       }
       container violation-action {
         description "Lease time validation violation action";
         leaf drop {
           description "Drop dhcpv6 advertise and reply packets";
           type empty;
         }
       }
     }
     leaf no-snoop {
       description "Do not snoop DHCPV6 packets";
       type empty;
     }
     container leasequery {
       description "DHCPv6 leasequery configuration";
       presence "enable leasequery";
       uses relay-leasequery-type;
     }
     container bulk-leasequery {
       description "DHCPv6 bulk leasequery configuration";
       presence "enable bulk-leasequery";
       uses relay-bulk-leasequery-v6-type;
     }
     container active-leasequery {
       description "DHCPv6 active leasequery configuration";
       presence "enable active-leasequery";
       uses active-leasequery-v6-type;
     }
     container remote-id-mismatch {
       description "DHCP client remote-id mismatch";
       presence "enable remote-id-mismatch";
       uses dhcp-remote-id-mismatch-type;
     }
     container duplicate-clients {
       description "Allow duplicate clients";
       uses dhcpv6-duplicate-clients-type;
     }
   }
   grouping active-leasequery-v6-type {
     description "Configure active leasequery";
     uses apply-advanced;
     leaf topology-discover {
       description "Topology discovery";
       type empty;
     }
     list exclude-interface {
       key name;
       ordered-by user;
       description "Exclude interface participating in active leasequery";
       leaf name {
         description "Interface name";
         type union {
           type jt:interface-name;
           type string {
             pattern "<.*>|$.*";
           }
         }
       }
       uses apply-advanced;
     }
     leaf timeout {
       description "Read/write timeout in seconds";
       default "120";
       units "seconds";
       type union {
         type string {
           pattern "<.*>|$.*";
         }
         type uint32 {
           range "10 .. 3600";
         }
       }
     }
     leaf idle-timeout {
       description "Idle timeout in seconds";
       default "60";
       units "seconds";
       type union {
         type string {
           pattern "<.*>|$.*";
         }
         type uint32 {
           range "10 .. 3600";
         }
       }
     }
     list peer-address {
       key name;
       description "Peer ipv6 address";
       leaf name {
         description "Peer ipv6 address";
         type jt:ipv6addr;
       }
       uses apply-advanced;
     }
   }
   grouping dhcp-generic-v6-option {
     description "Generic DHCPv6 options processing";
     uses apply-advanced;
     leaf option-number {
       description "Option number";
       status deprecated;
       type enumeration {
         enum "15" {
           description "Option 15";
           status deprecated;
         }
         enum "16" {
           description "Option 16";
           status deprecated;
         }
       }
     }
     container equals {
       description "Generic option equals";
       status deprecated;
       uses relay-v6-option-ascii-hex;
     }
     container default-action {
       description "Generic option default action";
       status deprecated;
       uses dhcp-v6-option-default-action;
     }
     container starts-with {
       description "Generic option starts with";
       status deprecated;
       uses relay-v6-option-ascii-hex;
     }
     container option-15 {
       description "Add option 15 processing";
       presence "enable option-15";
       uses dhcp-generic-v6-option-type;
     }
     container option-16 {
       description "Add option 16 processing";
       presence "enable option-16";
       uses dhcp-generic-v6-option-type;
     }
     list option-order {
       key name;
       ordered-by user;
       description "Options precedence order";
       leaf name {
         description "Option number";
         type enumeration {
           enum "15" {
             description "Option 15";
           }
           enum "16" {
             description "Option 16";
           }
         }
       }
       uses apply-advanced;
     }
   }
   grouping dhcp-generic-v6-option-type {
     uses apply-advanced;
     container equals {
       description "Generic option equals";
       uses relay-v6-option-ascii-hex;
     }
     container default-action {
       description "Generic option default action";
       uses dhcp-v6-option-default-action;
     }
     container starts-with {
       description "Generic option starts with";
       uses relay-v6-option-ascii-hex;
     }
   }
   grouping dhcp-v6-option-default-action {
     description "Default action";
     uses apply-advanced;
     choice server-group-choice {
       case case_1 {
         leaf relay-server-group {
           description "Name of DHCP relay server group when match is made";
           type string {
             length "1 .. 64";
           }
         }
       }
       case case_2 {
         leaf drop {
           description "Discard when a match is made";
           type empty;
         }
       }
       case case_3 {
         leaf forward-only {
           description "Forward without subscriber services when a match is made";
           type empty;
         }
       }
     }
   }
   grouping dhcpv6-authentication-type {
     description "DHCPv6 authentication";
     uses apply-advanced;
     leaf password {
       description "Username password to use";
       type string {
         length "1 .. 64";
       }
     }
     container username-include {
       description "Add username options";
       uses apply-advanced;
       leaf delimiter {
         description "Change delimiter/separator character";
         type string {
           length 1;
         }
       }
       leaf domain-name {
         description "Add domain name";
         type string {
           length "1 .. 64";
         }
       }
       leaf user-prefix {
         description "Add user defined prefix";
         type string {
           length "1 .. 64";
         }
       }
       leaf mac-address {
         description "Include MAC address";
         type empty;
       }
       container client-id {
         presence "enable client-id";
         description "Include client ID";
         leaf exclude-headers {
           description "Exclude all the headers";
           type empty;
         }
         leaf use-automatic-ascii-hex-encoding {
           description "Use automatic ascii hex username encoding";
           type empty;
         }
       }
       container relay-agent-remote-id {
         presence "enable relay-agent-remote-id";
         description "Include the relay agent remote ID";
         uses apply-advanced;
         choice relay-agent-remote-id-choice {
           case case_1 {
             leaf enterprise-id {
               description "Only use enterprise-id portion of option-37";
               status deprecated;
               type empty;
             }
           }
           case case_2 {
             leaf remote-id {
               description "Only use remote-id portion of option-37";
               status deprecated;
               type empty;
             }
           }
         }
       }
       leaf logical-system-name {
         description "Include logical system name";
         type empty;
       }
       leaf routing-instance-name {
         description "Include routing instance name";
         type empty;
       }
       leaf relay-agent-subscriber-id {
         description "Include the relay agent subscriber ID";
         type empty;
       }
       leaf relay-agent-interface-id {
         description "Include the relay agent interface ID";
         type empty;
       }
       leaf circuit-type {
         description "Include circuit type";
         type empty;
       }
       leaf interface-name {
         description "Include interface name";
         type empty;
       }
       leaf interface-description {
         description "Include interface description";
         type enumeration {
           enum "device" {
             description "Add the device interface description";
           }
           enum "logical" {
             description "Add the logical interface description";
           }
         }
       }
       leaf vlan-tags {
         description "Include the vlan tag(s)";
         type empty;
       }
     }
   }
   grouping dhcpv6-duplicate-clients-type {
     description "Allow duplicate clients";
     choice distinguish-with {
       case case_1 {
         leaf incoming-interface {
           description "Allow duplicate clients on different underlying interfaces";
           type empty;
         }
       }
     }
   }
   grouping dhcpv6-gbl-active-sg-type {
     uses apply-advanced;
     leaf active-server-group {
       description "Name of DHCPv6 server group";
       type string {
         length "1 .. 64";
       }
     }
   }
   grouping dhcpv6-liveness-detection-type {
     description "DHCPv6 client liveness detection processing";
     uses apply-advanced;
     container failure-action {
       description "Liveness detection failure action options";
       uses dhcp-liveness-detection-failure-action-type;
     }
     container method {
       description "Liveness detection method options";
       uses apply-advanced;
       choice method-choice {
         case case_1 {
           container bfd {
             description "Bidirectional Forwarding Detection (BFD) options";
             uses dhcp-bfd-liveness-detection-type;
           }
         }
         case case_2 {
           container layer2-liveness-detection {
             description "Neighbor discovery options";
             uses dhcp-arp-nud-liveness-detection-type;
           }
         }
       }
     }
   }
   grouping dhcpv6-override-relay-type {
     description "DHCPv6 relay override processing";
     uses apply-advanced;
     choice allow-snooped-clients-choice {
       leaf allow-snooped-clients {
         description "Allow client creation from snooped PDUs";
         type empty;
       }
       leaf no-allow-snooped-clients {
         description "Don't allow client creation from snooped PDUs";
         type empty;
       }
     }
     leaf delay-authentication {
       description "Delay subscriber authentication in DHCP protocol processing until request packet";
       type empty;
     }
     leaf interface-client-limit {
       description "Limit the number of clients allowed on an interface";
       type union {
         type string {
           pattern "<.*>|$.*";
         }
         type uint32 {
           range "1 .. 500000";
         }
       }
     }
     leaf dual-stack {
       description "Dual stack group to use.";
       type string {
         length "1 .. 64";
       }
     }
     leaf no-bind-on-request {
       description "Do not bind if stray DHCPv6 RENEW, REBIND is received";
       type empty;
     }
     container client-negotiation-match {
       description "Use secondary match criteria for SOLICIT PDU";
       choice match-with {
         case case_1 {
           leaf incoming-interface {
             description "Use incoming interface";
             type empty;
           }
         }
       }
     }
     leaf send-release-on-delete {
       description "Always send RELEASE to the server when a binding is deleted";
       type empty;
     }
     leaf always-process-option-request-option {
       description "Always process option even after address allocation failure";
       type empty;
     }
     leaf relay-source {
       description "Interface for relay source";
       type union {
         type jt:interface-name;
         type string {
           pattern "<.*>|$.*";
         }
       }
     }
     leaf delete-binding-on-renegotiation {
       description "Delete binding on renegotiation";
       type empty;
     }
     leaf asymmetric-lease-time {
       description "Use a reduced lease time for the client. In seconds";
       units "seconds";
       type union {
         type string {
           pattern "<.*>|$.*";
         }
         type uint32 {
           range "600 .. 86400";
         }
       }
     }
     leaf asymmetric-prefix-lease-time {
       description "Use a reduced prefix lease time for the client. In seconds";
       units "seconds";
       type union {
         type string {
           pattern "<.*>|$.*";
         }
         type uint32 {
           range "600 .. 86400";
         }
       }
     }
   }
   grouping dhcpv6-relay-group {
     description "DHCPv6 groups";
     leaf name {
       description "Group name";
       type string {
         length "1 .. 64";
       }
     }
     uses apply-advanced;
     container active-server-group {
       description "Name of DHCPv6 server group";
       uses dhcpv6-gp-active-sg-type;
     }
     list dual-stack-group {
       key name;
       description "Define a DHCP dual stack group";
       uses dhcp-dual-stack-group;
     }
     container authentication {
       description "DHCPv6 authentication";
       uses dhcpv6-authentication-type;
     }
     container liveness-detection {
       description "DHCPv6 client liveness detection processing";
       uses dhcpv6-liveness-detection-type;
     }
     container dynamic-profile {
       description "Dynamic profile to use";
       uses dynamic-profile-type;
     }
     leaf service-profile {
       description "Dynamic profile to use for default service activation";
       type string {
         length "1 .. 128";
       }
     }
     leaf access-profile {
       description "Access profile to use for AAA services";
       type string {
         length "1 .. 128";
       }
     }
     container short-cycle-protection {
       description "Short cycle lockout configuration";
       leaf lockout-min-time {
         description "Short cycle lockout time in seconds";
         type union {
           type string {
             pattern "<.*>|$.*";
           }
           type uint32 {
             range "1 .. 86400";
           }
         }
       }
       leaf lockout-max-time {
         description "Short cycle lockout time in seconds";
         type union {
           type string {
             pattern "<.*>|$.*";
           }
           type uint32 {
             range "1 .. 86400";
           }
         }
       }
     }
     container overrides {
       description "DHCPv6 override processing";
       presence "enable overrides";
       uses dhcpv6-override-relay-type;
     }
     container relay-option {
       description "DHCPv6 option processing";
       presence "enable relay-option";
       uses dhcp-generic-v6-option;
     }
     container vendor-specific-information {
       description "DHCPv6 option 17 vendor-specific processing";
       uses jdhcp-vendor-specific-type;
     }
     container forward-only {
       description "Forward DHCPv6 packets without creating binding";
       presence "enable forward-only";
       uses forward-only-to-rc-type;
     }
     container relay-agent-interface-id {
       description "DHCPv6 interface-id option processing";
       presence "enable relay-agent-interface-id";
       uses v6-relay-option-interface-id-type;
     }
     container relay-agent-remote-id {
       description "DHCPv6 remote-id option processing";
       presence "enable relay-agent-remote-id";
       uses v6-relay-option-remote-id-type;
     }
     container route-suppression {
       description "Suppress access-internal and/or access route addition";
       uses dhcpv6-route-suppression-type;
     }
     leaf relay-agent-option-79 {
       description "Add the client MAC address to the Relay Forward header.";
       type empty;
     }
     list interface {
       key name;
       description "One or more interfaces";
       leaf name {
         description "Interface name";
         type union {
           type jt:interface-name;
           type string {
             pattern "<.*>|$.*";
           }
         }
       }
       uses apply-advanced;
       leaf upto {
         description "Interface up to";
         type union {
           type jt:interface-name;
           type string {
             pattern "<.*>|$.*";
           }
         }
       }
       leaf exclude {
         description "Exclude this interface range";
         type empty;
       }
       leaf trace {
         description "Enable tracing for this interface";
         type empty;
       }
       container overrides {
         description "DHCPv6 override processing";
         uses dhcpv6-override-relay-type;
       }
       container dynamic-profile {
         description "Dynamic profile to use";
         uses dynamic-profile-type;
       }
       leaf service-profile {
         description "Dynamic profile to use for default service activation";
         type string {
           length "1 .. 128";
         }
       }
       leaf access-profile {
         description "Access profile to use for AAA services";
         type string {
           length "1 .. 128";
         }
       }
       container short-cycle-protection {
         description "Short cycle lockout configuration";
         leaf lockout-min-time {
           description "Short cycle lockout time in seconds";
           type union {
             type string {
               pattern "<.*>|$.*";
             }
             type uint32 {
               range "1 .. 86400";
             }
           }
         }
         leaf lockout-max-time {
           description "Short cycle lockout time in seconds";
           type union {
             type string {
               pattern "<.*>|$.*";
             }
             type uint32 {
               range "1 .. 86400";
             }
           }
         }
       }
     }
     list interface-tag {
       key name;
       description "Interface tag configurations";
       leaf name {
         description "Interface tag name";
         type string {
           length "1 .. 64";
         }
       }
       uses apply-advanced;
       container overrides {
         description "DHCPv6 override processing";
         uses dhcpv6-override-relay-type;
       }
       container dynamic-profile {
         description "Dynamic profile to use";
         uses dynamic-profile-type;
       }
       leaf service-profile {
         description "Dynamic profile to use for default service activation";
         type string {
           length "1 .. 128";
         }
       }
       leaf access-profile {
         description "Access profile to use for AAA services";
         type string {
           length "1 .. 128";
         }
       }
       container short-cycle-protection {
         description "Short cycle lockout configuration";
         leaf lockout-min-time {
           description "Short cycle lockout time in seconds";
           type union {
             type string {
               pattern "<.*>|$.*";
             }
             type uint32 {
               range "1 .. 86400";
             }
           }
         }
         leaf lockout-max-time {
           description "Short cycle lockout time in seconds";
           type union {
             type string {
               pattern "<.*>|$.*";
             }
             type uint32 {
               range "1 .. 86400";
             }
           }
         }
       }
     }
     container lease-time-validation {
       presence "enable lease-time-validation";
       description "Configure lease time violation validation";
       uses apply-advanced;
       leaf lease-time-threshold {
         description "Threshold for lease time violation in seconds";
         units "seconds";
         type union {
           type string {
             pattern "<.*>|$.*";
           }
           type uint32 {
             range "60 .. 2147483647";
           }
         }
       }
       container violation-action {
         description "Lease time validation violation action";
         leaf drop {
           description "Drop dhcpv6 advertise and reply packets";
           type empty;
         }
       }
     }
     container remote-id-mismatch {
       description "DHCP client remote-id mismatch";
       presence "enable remote-id-mismatch";
       uses dhcp-remote-id-mismatch-type;
     }
     container server-match {
       description "Server match processing";
       uses apply-advanced;
       container default-action {
         description "Server match default action";
         uses server-match-action-choice;
       }
       container duid {
         description "Match duid processing";
         uses apply-advanced;
         container equals {
           description "Duid equals";
           uses server-match-v6-ascii-hex;
         }
         container starts-with {
           description "Duid starts with";
           uses server-match-v6-ascii-hex;
         }
       }
       list address {
         key name;
         description "Server ipv6 address";
         leaf name {
           description "Server ipv6 address for matching";
           type jt:ipv6prefix;
         }
         uses apply-advanced;
         choice server-match-action-choice {
           case case_1 {
             leaf forward-only {
               description "Forward without subscriber services when a match is made";
               type empty;
             }
           }
           case case_2 {
             leaf create-relay-entry {
               description "Create relay entry and allow subscriber services";
               type empty;
             }
           }
         }
       }
     }
   }
   grouping dhcpv6-gp-active-sg-type {
     uses apply-advanced;
     leaf active-server-group {
       description "Name of DHCPv6 server group";
       type string {
         length "1 .. 64";
       }
     }
   }
   grouping dhcpv6-route-suppression-type {
     description "Suppress access-internal and/or access route addition";
     leaf access {
       description "Suppress access route addition";
       type empty;
     }
     leaf access-internal {
       description "Suppress access-internal route addition";
       type empty;
     }
   }
   grouping dual-stack-authentication-type {
     description "DHCP dual stack authentication";
     uses apply-advanced;
     leaf password {
       description "Username password to use";
       type string {
         length "1 .. 64";
       }
     }
     container username-include {
       description "Add username options";
       uses apply-advanced;
       leaf delimiter {
         description "Change delimiter/separator character";
         type string {
           length 1;
         }
       }
       leaf domain-name {
         description "Add domain name";
         type string {
           length "1 .. 64";
         }
       }
       leaf user-prefix {
         description "Add user defined prefix";
         type string {
           length "1 .. 64";
         }
       }
       leaf mac-address {
         description "Include MAC address";
         type empty;
       }
       container client-id {
         presence "enable client-id";
         description "Include client ID";
         leaf exclude-headers {
           description "Exclude all the headers";
           type empty;
         }
         leaf use-automatic-ascii-hex-encoding {
           description "Use automatic ascii hex username encoding";
           type empty;
         }
       }
       leaf relay-agent-remote-id {
         description "Include the relay agent remote ID";
         type empty;
       }
       leaf logical-system-name {
         description "Include logical system name";
         type empty;
       }
       leaf routing-instance-name {
         description "Include routing instance name";
         type empty;
       }
       leaf relay-agent-interface-id {
         description "Include the relay agent interface ID";
         type empty;
       }
       leaf interface-name {
         description "Include interface name";
         type empty;
       }
       leaf interface-description {
         description "Include interface description";
         type enumeration {
           enum "device" {
             description "Add the device interface description";
           }
           enum "logical" {
             description "Add the logical interface description";
           }
         }
       }
       leaf circuit-type {
         description "Include circuit type";
         type empty;
       }
       leaf vlan-tags {
         description "Include the vlan tag(s)";
         type empty;
       }
     }
   }
   grouping dynamic-profile-type {
     description "Dynamic profile to use";
     uses apply-advanced;
     leaf dynamic-profile {
       description "Dynamic profile to use";
       type string {
         length "1 .. 80";
       }
     }
     choice dynamic-profile-type-choice {
       case case_1 {
         leaf use-primary {
           description "Dynamic profile to use on the primary interface";
           type string {
             length "1 .. 80";
           }
         }
       }
       case case_2 {
         container aggregate-clients {
           presence "enable aggregate-clients";
           description "Aggregate client profiles";
           uses apply-advanced;
           choice aggregate-type {
             case case_1 {
               leaf merge {
                 description "Merge the client dynamic profiles";
                 type empty;
               }
             }
             case case_2 {
               leaf replace {
                 description "Replace client dynamic profiles";
                 type empty;
               }
             }
           }
         }
       }
     }
   }
   grouping forward-only-to-rc-type {
     description "Forward DHCP packets without creating binding";
     uses apply-advanced;
     leaf logical-system {
       default "current";
       type string;
     }
     leaf routing-instance {
       default "current";
       type string;
     }
   }
   grouping jdhcp-dual-stack-protocol-mstr-type {
     description "Select family as protocol master";
     choice addr-fam {
       case case_1 {
         leaf inet {
           description "INET family has protocol master behavior";
           type empty;
         }
       }
       case case_2 {
         leaf inet6 {
           description "INET6 family has protocol master behavior";
           type empty;
         }
       }
     }
   }
   grouping jdhcp-duplicate-clients-in-subnet-type {
     description "Allow duplicate clients in a subnet";
     choice distinguish-with {
       case case_1 {
         leaf incoming-interface {
           description "Allow duplicate clients on different interfaces in a subnet";
           type empty;
         }
       }
       case case_2 {
         leaf option-82 {
           description "Allow duplicate clients using different option-82 options in a subnet";
           type empty;
         }
       }
     }
   }
   grouping jdhcp-interface-traceoptions-type {
     description "Interface trace options for DHCP";
     uses apply-advanced;
     leaf no-remote-trace {
       description "Disable remote tracing";
       type empty;
     }
     container file {
       description "Trace file information";
       leaf filename {
         description "Name of file in which to write trace information";
         type string {
           length "1 .. 1024";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     list flag {
       key name;
       ordered-by user;
       description "Interface trace categories";
       leaf name {
         type enumeration {
           enum "state" {
             description "State-transition operations";
           }
           enum "packet" {
             description "Packet-decoding operations";
           }
           enum "flow" {
             description "Flow-decoding operations";
           }
           enum "packet-option" {
             description "DHCP option-decoding operations";
           }
           enum "dhcpv6-state" {
             description "State-transition operations for dhcpv6";
           }
           enum "dhcpv6-packet" {
             description "Packet-decoding operations for dhcpv6";
           }
           enum "dhcpv6-packet-option" {
             description "DHCP option-decoding operations for dhcpv6";
           }
           enum "all" {
             description "All operations";
           }
         }
       }
     }
   }
   grouping jdhcp-traceoptions-type {
     description "Trace options for DHCP";
     uses apply-advanced;
     leaf no-remote-trace {
       description "Disable remote tracing";
       type empty;
     }
     container file {
       description "Trace file information";
       leaf filename {
         description "Name of file in which to write trace information";
         type string {
           length "1 .. 1024";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     list flag {
       key name;
       ordered-by user;
       description "DHCP operations to include in debugging trace";
       leaf name {
         type enumeration {
           enum "state" {
             description "State-transition operations";
           }
           enum "packet" {
             description "Packet-decoding operations";
           }
           enum "flow" {
             description "Flow-decoding operations";
           }
           enum "packet-option" {
             description "DHCP option-decoding operations";
           }
           enum "dhcpv6-state" {
             description "State-transition operations for dhcpv6";
           }
           enum "dhcpv6-packet" {
             description "Packet-decoding operations for dhcpv6";
           }
           enum "dhcpv6-packet-option" {
             description "DHCP option-decoding operations for dhcpv6";
           }
           enum "all" {
             description "All operations";
           }
           enum "database" {
             description "Database operations";
           }
           enum "persistent" {
             description "Persitent file operations";
           }
           enum "lockout-db" {
             description "Lockout database operations";
           }
           enum "interface" {
             description "Interface operations";
           }
           enum "rtsock" {
             description "Routing socket operations";
           }
           enum "flow-notify" {
             description "Flow notification operations";
           }
           enum "io" {
             description "I/O operations";
           }
           enum "ha" {
             description "High Availability-related operations";
           }
           enum "ui" {
             description "User Interface operations";
           }
           enum "general" {
             description "Miscellaneous operations";
           }
           enum "fwd" {
             description "Firewall process operations";
           }
           enum "rpd" {
             description "Routing Protocol process operations";
           }
           enum "auth" {
             description "Authentication operations";
           }
           enum "profile" {
             description "Profile operations";
           }
           enum "session-db" {
             description "Session database operations";
           }
           enum "performance" {
             description "Performance measurement operations";
           }
           enum "statistics" {
             description "Baseline statistics operations";
           }
           enum "dhcpv6-io" {
             description "I/O operations for dhcpv6";
           }
           enum "dhcpv6-rpd" {
             description "Routing Protocol process operations for dhcpv6";
           }
           enum "dhcpv6-session-db" {
             description "Session database operations for dhcpv6";
           }
           enum "dhcpv6-general" {
             description "Miscellaneous operations for dhcpv6";
           }
           enum "liveness-detection" {
             description "Liveness detection operations";
           }
           enum "security-persistence" {
             description "Liveness detection operations";
           }
           enum "mclag" {
             description "Multichassis LAG";
           }
           enum "ra-guard" {
             description "DHCP RA guard option for dhcpv6";
           }
           enum "era" {
             description "DHCP ERA logging option dhcp";
           }
           enum "telemetry" {
             description "Telemetry operation";
           }
         }
       }
     }
   }
   grouping jdhcp-vendor-specific-type {
     description "Add vendor-specific option processing";
     uses apply-advanced;
     leaf host-name {
       description "Add router host name";
       type empty;
     }
     leaf location {
       description "Add location information expressed as interface name format";
       type empty;
     }
   }
   grouping juniper-forwarding-sandbox-options {
     leaf name {
       description "Sandbox name";
       type string;
     }
     uses apply-advanced;
     leaf size {
       description "Size of the sandbox";
       default "small";
       type enumeration {
         enum "small" {
           description "Sandbox size small";
         }
         enum "medium" {
           description "Sandbox size medium";
         }
         enum "large" {
           description "Sandbox size large";
         }
       }
     }
     list port {
       key name;
       description "Sandbox port";
       max-elements 64;
       uses juniper-forwarding-sandbox-port-options;
     }
   }
   grouping juniper-forwarding-sandbox-port-options {
     leaf name {
       description "Port name";
       type string;
     }
     uses apply-advanced;
     list interface {
       key name;
       ordered-by user;
       description "Interface to which the port is mapped";
       max-elements 1;
       leaf name {
         description "Interface name";
         type union {
           type jt:interface-device;
           type string {
             pattern "<.*>|$.*";
           }
         }
       }
       uses apply-advanced;
     }
   }
   grouping juniper-next-hop-group-options {
     leaf name {
       description "Next hop group name";
       type string;
     }
     uses apply-advanced;
     leaf group-type {
       description "Next hop group type";
       default "inet";
       type enumeration {
         enum "inet" {
           description "Group of family inet next-hops";
         }
         enum "layer-2" {
           description "Layer-2 next-hop group";
         }
         enum "inet6" {
           description "Group of family inet6 next-hops";
         }
       }
     }
     list interface {
       key name;
       description "Interfaces through which to send sampled traffic";
       uses next_hop_group_intf_type;
     }
     list next-hop-subgroup {
       key name;
       description "Group of interfaces through which to send sampled traffic";
       uses juniper-next-hop-subgroup-options;
     }
   }
   grouping juniper-next-hop-subgroup-options {
     leaf name {
       description "Next-hop sub-group name";
       type string;
     }
     uses apply-advanced;
     list interface {
       key name;
       description "Interface through which to send the sampled traffic";
       max-elements 16;
       uses next_hop_subgroup_intf_type;
     }
   }
   grouping juniper-packet-accounting-options {
     leaf name {
       description "Name for accounting group";
       type string;
     }
     uses apply-advanced;
     container output {
       description "Accounting data disposition";
       uses packet_accounting_output_type;
     }
   }
   grouping juniper-port-mirror-options {
     uses apply-advanced;
     container traceoptions {
       description "Port-mirroring trace options";
       uses sampling_traceoptions_type;
     }
     leaf disable {
       description "Disable the global port-mirroring instance";
       type empty;
     }
     leaf disable-all-instances {
       description "Disable the all port-mirroring instances";
       type empty;
     }
     leaf remote-port-mirroring {
       description "Flag to specify about remote-port-mirroring";
       type empty;
     }
     container input {
       description "Settings for sampling of input packets";
       uses pm_family_input_type;
     }
     container family {
       description "Address family of packets to mirror";
       container inet {
         description "Mirror IPv4 packets";
         uses apply-advanced;
         container input {
           description "Settings for sampling of input packets";
           status deprecated;
           uses pm_family_input_type;
         }
         container output {
           description "One or more next hops for port-mirrored packets";
           uses inet_pm_family_output_type;
         }
       }
       container inet6 {
         description "Mirror IPv6 packets";
         uses apply-advanced;
         container input {
           description "Settings for sampling of input packets";
           status deprecated;
           uses pm_family_input_type;
         }
         container output {
           description "One or more next hops for port-mirrored packets";
           uses inet6_pm_family_output_type;
         }
       }
       container mpls {
         description "Mirror MPLS packets";
         uses apply-advanced;
         container input {
           description "Settings for sampling of input packets";
           status deprecated;
           uses pm_family_input_type;
         }
         container output {
           description "One or more next hops for port-mirrored packets";
           uses mpls_pm_family_output_type;
         }
       }
       container vpls {
         description "Mirror Layer-2 bridged/vpls packets";
         uses apply-advanced;
         container input {
           description "Settings for sampling of input packets";
           status deprecated;
           uses pm_family_input_type;
         }
         container output {
           description "Destination for port-mirrored packets";
           uses layer2_pm_family_output_type;
         }
       }
       container ethernet-switching {
         description "Mirror Layer-2 ethernet-switched packets";
         uses apply-advanced;
         container output {
           description "Destination for port-mirrored packets";
           uses layer2_pm_family_output_type;
         }
       }
       container ccc {
         description "Mirror layer-2 ccc packets";
         uses apply-advanced;
         container input {
           description "Settings for sampling of input packets";
           status deprecated;
           uses pm_family_input_type;
         }
         container output {
           description "Destination for port-mirrored packets";
           uses layer2_pm_family_output_type;
         }
       }
     }
     list instance {
       key name;
       ordered-by user;
       description "Instance of port-mirroring parameters";
       leaf name {
         description "Name for port-mirroring instance";
         type string {
           length "1 .. 63";
         }
       }
       uses apply-advanced;
       leaf disable {
         description "Disable the this port-mirroring instance";
         type empty;
       }
       choice input_params_or_instance {
         case case_1 {
           container input {
             description "Settings for sampling of input packets";
             uses pm_family_input_type;
           }
         }
         case case_2 {
           leaf input-parameters-instance {
             description "Name of port-mirroring instance to use for input parameters";
             type string;
           }
         }
       }
       container output {
         description "One or more next hops for port-mirrored packets";
         uses inet_pm_output_type;
       }
       container family {
         description "Address family of packets to mirror";
         container inet {
           description "Mirror IPv4 packets";
           uses apply-advanced;
           container input {
             description "Settings for sampling of input packets";
             status deprecated;
             uses pm_family_input_type;
           }
           container output {
             description "One or more next hops for port-mirrored packets";
             uses inet_pm_family_output_type;
           }
         }
         container inet6 {
           description "Mirror IPv6 packets";
           uses apply-advanced;
           container input {
             description "Settings for sampling of input packets";
             status deprecated;
             uses pm_family_input_type;
           }
           container output {
             description "One or more next hops for port-mirrored packets";
             uses inet6_pm_family_output_type;
           }
         }
         container mpls {
           description "Mirror MPLS packets";
           uses apply-advanced;
           container input {
             description "Settings for sampling of input packets";
             status deprecated;
             uses pm_family_input_type;
           }
           container output {
             description "One or more next hops for port-mirrored packets";
             uses mpls_pm_family_output_type;
           }
         }
         container vpls {
           description "Mirror Layer-2 bridged/vpls packets";
           uses apply-advanced;
           container input {
             description "Settings for sampling of input packets";
             status deprecated;
             uses pm_family_input_type;
           }
           container output {
             description "Destination for port-mirrored packets";
             uses layer2_pm_family_output_type;
           }
         }
         container ethernet-switching {
           description "Mirror Layer-2 ethernet-switched packets";
           uses apply-advanced;
           container output {
             description "Destination for port-mirrored packets";
             uses layer2_pm_family_output_type;
           }
         }
         container ccc {
           description "Mirror layer-2 ccc packets";
           uses apply-advanced;
           container input {
             description "Settings for sampling of input packets";
             status deprecated;
             uses pm_family_input_type;
           }
           container output {
             description "Destination for port-mirrored packets";
             uses layer2_pm_family_output_type;
           }
         }
       }
       container mirror-profile {
         description "Mirror profile to be attached to the instance";
         uses apply-advanced;
         leaf profile-name {
           description "Name of profile";
           type string {
             length "1 .. 63";
           }
         }
       }
     }
   }
   grouping inet6_pm_family_output_type {
     uses apply-advanced;
     choice interface-or-next-hop-index {
       case case_1 {
         list interface {
           key name;
           description "Interfaces through which to send sampled traffic";
           uses inet6_pm_intf_type;
         }
       }
       case case_2 {
       }
     }
     leaf forwarding-class {
       description "Forwarding-class for TOS";
       type string {
         length "1 .. 64";
       }
     }
     leaf no-filter-check {
       description "Do not check for filters on port-mirroring interface";
       type empty;
     }
     leaf ipv6-address {
       description "ERSPAN Destination IPv6 Address";
       type jt:ipv6addr;
     }
     leaf source-ipv6-address {
       description "ERSPAN source IPv6 address";
       type jt:ipv6addr;
     }
     leaf dscp {
       description "DSCP value from 0-63";
       default "0";
       type union {
         type string {
           pattern "<.*>|$.*";
         }
         type uint32 {
           range "0 .. 63";
         }
       }
     }
     list routing-instance {
       key name;
       description "Routing instances";
       max-elements 1;
       uses inet6_pm_output-routing-instance-type;
     }
   }
   grouping inet6_pm_intf_type {
     leaf name {
       description "Interface through which to send sampled traffic";
       type union {
         type jt:interface-name;
         type string {
           pattern "<.*>|$.*";
         }
       }
     }
     uses apply-advanced;
     list next-hop {
       key name;
       ordered-by user;
       description "Address of next hop through which to send sampled traffic";
       uses inet6_next_hop_type;
     }
   }
   grouping inet6_next_hop_type {
     description "Address of next hop through which to send sampled traffic";
     leaf name {
       type jt:ipv6addr;
     }
     uses apply-advanced;
   }
   grouping inet6_pm_output-routing-instance-type {
     leaf name {
       description "Routing instance name";
       type string {
       }
     }
     uses apply-advanced;
     leaf ipv6-address {
       description "ERSPAN Destination IPv6 Address";
       type jt:ipv6addr;
     }
     leaf source-ipv6-address {
       description "ERSPAN source IPv6 address";
       type jt:ipv6addr;
     }
     leaf dscp {
       description "DSCP value from 0-63";
       default "0";
       type union {
         type string {
           pattern "<.*>|$.*";
         }
         type uint32 {
           range "0 .. 63";
         }
       }
     }
   }
   grouping inet_pm_family_output_type {
     uses apply-advanced;
     choice interface-or-next-hop-index {
       case case_1 {
         list interface {
           key name;
           description "Interfaces through which to send sampled traffic";
           uses inet_pm_intf_type;
         }
       }
       case case_2 {
       }
     }
     leaf no-filter-check {
       description "Do not check for filters on port-mirroring interface";
       type empty;
     }
     leaf ip-address {
       description "ERSPAN Destination IP Address";
       type jt:ipv4addr;
     }
     leaf source-ip-address {
       description "ERSPAN source IP address";
       type jt:ipv4addr;
     }
     leaf dscp {
       description "DSCP value from 0-63";
       default "0";
       type union {
         type string {
           pattern "<.*>|$.*";
         }
         type uint32 {
           range "0 .. 63";
         }
       }
     }
     list routing-instance {
       key name;
       description "Routing instances";
       max-elements 1;
       uses inet_pm_output-routing-instance-type;
     }
     leaf forwarding-class {
       description "Forwarding-class for TOS";
       type string {
         length "1 .. 64";
       }
     }
   }
   grouping inet_pm_intf_type {
     leaf name {
       description "Interface through which to send sampled traffic";
       type union {
         type jt:interface-name;
         type string {
           pattern "<.*>|$.*";
         }
       }
     }
     uses apply-advanced;
     list next-hop {
       key name;
       ordered-by user;
       description "Address of next hop through which to send sampled traffic";
       uses inet_next_hop_type;
     }
   }
   grouping inet_next_hop_type {
     description "Address of next hop through which to send sampled traffic";
     leaf name {
       type jt:ipv4addr;
     }
     uses apply-advanced;
   }
   grouping inet_pm_output-routing-instance-type {
     leaf name {
       description "Routing instance name";
       type string {
       }
     }
     uses apply-advanced;
     leaf ip-address {
       description "ERSPAN Destination IP Address";
       type jt:ipv4addr;
     }
     leaf source-ip-address {
       description "ERSPAN source IP address";
       type jt:ipv4addr;
     }
     leaf dscp {
       description "DSCP value from 0-63";
       default "0";
       type union {
         type string {
           pattern "<.*>|$.*";
         }
         type uint32 {
           range "0 .. 63";
         }
       }
     }
   }
   grouping inet_pm_output_type {
     uses apply-advanced;
     leaf ip-source-address {
       description "IP source address";
       type jt:ipv4addr;
     }
     leaf ip-destination-address {
       description "IP destination address";
       type jt:ipv4addr;
     }
     leaf policer {
       description "Name of policer to use to rate-limit traffic";
       type string {
       }
     }
     leaf dscp {
       description "Numeric DSCP value in the range 0 to 63";
       type union {
         type string {
           pattern "<.*>|$.*";
         }
         type uint8 {
           range "0 .. 63";
         }
       }
     }
     leaf forwarding-class {
       description "Forwarding-class for TOS";
       type string {
         length "1 .. 64";
       }
     }
   }
   grouping juniper-sampling-options {
     uses apply-advanced;
     choice enable-disable {
       case case_1 {
         leaf disable {
           description "Disable global sampling instance";
           type empty;
         }
       }
     }
     container traceoptions {
       description "Traffic sampling trace options";
       uses sampling_traceoptions_type;
     }
     container input {
       description "Traffic Sampling data acquisition";
       uses sampling_input_type;
     }
     container output {
       description "Traffic sampling data disposition";
       status deprecated;
       uses sampling_output_type;
     }
     container family {
       description "Address family of packets to sample";
       container inet {
         description "Sample IPv4 packets";
         uses apply-advanced;
         choice enable-disable {
           case case_1 {
             leaf disable {
               description "Disable sampling family inet";
               type empty;
             }
           }
         }
         container input {
           description "Settings for sampling of input packets";
           uses sampling_family_input_type;
         }
         container output {
           description "Traffic sampling data disposition";
           uses sampling_instance_inet_global_output_type;
         }
       }
       container inet6 {
         description "Sample IPv6 packets";
         uses apply-advanced;
         choice enable-disable {
           case case_1 {
             leaf disable {
               description "Disable sampling family inet6";
               type empty;
             }
           }
         }
         container input {
           description "Settings for sampling of input packets";
           uses sampling_family_input_type;
         }
         container output {
           description "Traffic sampling data disposition";
           uses sampling_family_inet6_output_type;
         }
       }
       container mpls {
         description "Sample mpls packets";
         uses apply-advanced;
         choice enable-disable {
           case case_1 {
             leaf disable {
               description "Disable sampling family mpls";
               type empty;
             }
           }
         }
         container input {
           description "Settings for sampling of input packets";
           uses sampling_family_input_type;
         }
         container output {
           description "Traffic sampling data disposition";
           uses sampling_global_mpls_output_type;
         }
       }
     }
     list instance {
       key name;
       ordered-by user;
       description "Instance of sampling parameters";
       leaf name {
         description "Name for sampling instance";
         type string;
       }
       uses apply-advanced;
       choice enable-disable {
         case case_1 {
           leaf disable {
             description "Disable sampling instance";
             type empty;
           }
         }
       }
       container input {
         description "Traffic Sampling data acquisition";
         uses sampling_instance_input_type;
       }
       container family {
         description "Address family of packets to sample";
         container inet {
           description "Sample IPv4 packets";
           uses apply-advanced;
           choice enable-disable {
             case case_1 {
               leaf disable {
                 description "Disable instance family inet";
                 status deprecated;
                 type empty;
               }
             }
           }
           container input {
             description "Settings for sampling of input packets";
             uses sampling_family_input_type;
           }
           container output {
             description "Traffic sampling data disposition";
             uses sampling_instance_inet_output_type;
           }
         }
         container inet6 {
           description "Sample IPv6 packets";
           uses apply-advanced;
           choice enable-disable {
             case case_1 {
               leaf disable {
                 description "Disable instance family inet6";
                 status deprecated;
                 type empty;
               }
             }
           }
           container input {
             description "Settings for sampling of input packets";
             uses sampling_family_input_type;
           }
           container output {
             description "Traffic sampling data disposition";
             uses sampling_instance_inet6_output_type;
           }
         }
         container mpls {
           description "Sample mpls packets";
           uses apply-advanced;
           choice enable-disable {
             case case_1 {
               leaf disable {
                 description "Disable instance family mpls";
                 status deprecated;
                 type empty;
               }
             }
           }
           container input {
             description "Settings for sampling of input packets";
             uses sampling_family_input_type;
           }
           container output {
             description "Traffic sampling data disposition";
             uses sampling_instance_mpls_output_type;
           }
         }
         container vpls {
           description "Sample vpls packets";
           status deprecated;
           uses apply-advanced;
           choice enable-disable {
             case case_1 {
               leaf disable {
                 description "Disable instance family vpls";
                 type empty;
               }
             }
           }
           container input {
             description "Settings for sampling of input packets";
             uses sampling_family_input_type;
           }
           container output {
             description "Traffic sampling data disposition";
             uses sampling_instance_vpls_output_type;
           }
         }
         container bridge {
           description "Sample bridge packets";
           uses apply-advanced;
           choice enable-disable {
             case case_1 {
               leaf disable {
                 description "Disable instance family bridge";
                 type empty;
               }
             }
           }
           container input {
             description "Settings for sampling of input packets";
             uses sampling_family_input_type;
           }
           container output {
             description "Traffic sampling data disposition";
             uses sampling_instance_bridge_output_type;
           }
         }
       }
     }
     container jflow-service {
       description "Jflow service configuration";
       uses apply-advanced;
       container traceoptions {
         description "Jflow service trace options";
         uses jflow_service_traceoptions;
       }
     }
     container route-record {
       description "Sampling route record configuration";
       uses apply-advanced;
       container traceoptions {
         description "Sampling route record trace options";
         uses route_record_traceoptions;
       }
     }
   }
   grouping jflow_service_traceoptions {
     description "Traceoptions for jflow-service";
     uses apply-advanced;
     leaf no-remote-trace {
       description "Disable remote tracing";
       type empty;
     }
     container file {
       description "Trace file information";
       leaf filename {
         description "Name of file in which to write trace information";
         type string {
           length "1 .. 1024";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     leaf level {
       description "Level of debugging output";
       default "error";
       type enumeration {
         enum "error" {
           description "Match error conditions";
         }
         enum "warning" {
           description "Match warning messages";
         }
         enum "notice" {
           description "Match conditions that should be handled specially";
         }
         enum "info" {
           description "Match informational messages";
         }
         enum "verbose" {
           description "Match verbose messages";
         }
         enum "all" {
           description "Match all levels";
         }
       }
     }
     list flag {
       key name;
       ordered-by user;
       description "Area of jflow-service to enable debuging output";
       leaf name {
         type enumeration {
           enum "parse" {
             description "Trace parsing code";
           }
           enum "rtsock" {
             description "Trace rtsock code";
           }
           enum "sm" {
             description "Trace State machine code";
           }
           enum "all" {
             description "Trace all area of jflow-service code";
           }
         }
       }
     }
   }
   grouping junos_hash_key {
     description "Select data used in the hash key";
     uses apply-advanced;
     container hash-seed {
       presence "enable hash-seed";
       description "Hash seed";
       uses apply-advanced;
       leaf seed-value {
         description "Hash seed value";
         type union {
           type string {
             pattern "<.*>|$.*";
           }
           type uint32 {
             range "0 .. 4294967295";
           }
         }
       }
     }
     container family {
       description "Protocol family";
       container fcoe {
         description "FCoE protocol family";
         uses apply-advanced;
         container ethernet-interfaces {
           description "FCoE hash-key configuration on ethernet interfaces";
           uses apply-advanced;
           leaf oxid {
             description "Originator Exchange ID";
             type enumeration {
               enum "enable" {
                 description "Include Originator Exchange ID in the hash key";
               }
               enum "disable" {
                 description "Do not include Originator Exchange ID in the hash key";
               }
             }
           }
         }
         container fabric-interfaces {
           description "FCoE hash-key configuration on fabric interfaces";
           uses apply-advanced;
           leaf oxid {
             description "Originator Exchange ID";
             type enumeration {
               enum "enable" {
                 description "Include Originator Exchange ID in the hash key";
               }
               enum "disable" {
                 description "Do not include Originator Exchange ID in the hash key";
               }
             }
           }
         }
         leaf oxid {
           description "Originator Exchange ID";
           type enumeration {
             enum "enable" {
               description "Include Originator Exchange ID in the hash key";
             }
             enum "disable" {
               description "Do not include Originator Exchange ID in the hash key";
             }
           }
         }
       }
       container inet {
         description "IPv4 protocol family";
         uses apply-advanced;
         container layer-3 {
           presence "enable layer-3";
           description "Include Layer 3 (IP) data in the hash key";
           uses apply-advanced;
           leaf destination-address {
             description "Include IP destination address in the hash key";
             type empty;
           }
         }
         container layer-4 {
           presence "enable layer-4";
           description "Include Layer 4 (TCP or UDP) data in the hash key";
           uses apply-advanced;
           leaf gtp-tunnel-endpoint-identifier {
             description "Include GTP TEID in the hash key";
             type empty;
           }
         }
       }
       container inet6 {
         description "IPv6 protocol family";
         uses apply-advanced;
         container layer-3 {
           presence "enable layer-3";
           description "Include Layer 3 (IP) data in the hash key";
           uses apply-advanced;
           leaf destination-address {
             description "Include IP destination address in the hash key";
             type empty;
           }
           leaf incoming-interface-index {
             description "Include incoming interface index in the hash key";
             type empty;
           }
           leaf next-header {
             description "Include IP Next Header field in the hash key";
             type empty;
           }
           leaf source-address {
             description "Include IP source address in the hash key";
             type empty;
           }
           leaf traffic-class {
             description "Include Traffic Class field in the hash key";
             type empty;
           }
           leaf ipv6-flow-label {
             description "Include IPV6 flow label field in the hash key";
             type empty;
           }
         }
         container layer-4 {
           presence "enable layer-4";
           description "Include Layer 4 (TCP or UDP) data in the hash key";
           uses apply-advanced;
           leaf destination-port {
             description "Include IP destination port in the hash key";
             type empty;
           }
           leaf source-port {
             description "Include IP source port in the hash key";
             type empty;
           }
           leaf gtp-tunnel-endpoint-identifier {
             description "Include GTP TEID in the hash key";
             type empty;
           }
         }
       }
       container mpls {
         description "MPLS protocol family";
         uses apply-advanced;
         choice label {
           case case_1 {
             leaf label-1 {
               description "Include the first MPLS label in the hash key";
               type empty;
             }
           }
           case case_2 {
             leaf all-labels {
               description "Include all MPLS labels in hash key";
               type empty;
             }
           }
           case case_3 {
             leaf no-labels {
               description "Exclude all MPLS labels from hash key";
               type empty;
             }
           }
           case case_4 {
             leaf bottom-label-1 {
               description "Include the first MPLS label from bottom-of-stack in the hash key";
               type empty;
             }
           }
         }
         leaf label-2 {
           description "Include the second MPLS label in the hash key";
           type empty;
         }
         leaf label-3 {
           description "Include the third MPLS label in the hash key";
           type empty;
         }
         container payload {
           description "Include payload data in the hash key";
           uses apply-advanced;
           container ether-pseudowire {
             presence "enable ether-pseudowire";
             description "Load-balance ethernet over ethernet PW";
             uses apply-advanced;
             leaf zero-control-word {
               description "MPLS ether-pseudowire payload with zero-control-word preceding ethernet packet";
               type empty;
             }
           }
           container ip {
             presence "enable ip";
             description "Include IPv4 or IPv6 payload data in the hash key";
             uses apply-advanced;
             choice layer-4-select {
               case case_1 {
                 choice ip-payload {
                   case case_1 {
                     leaf layer-3-only {
                       description "Include only layer-3 IP information";
                       type empty;
                     }
                   }
                   case case_2 {
                     leaf enable {
                       description "Include layer3/4 IP payload in the hash key";
                       type empty;
                     }
                   }
                   case case_3 {
                     leaf disable {
                       description "Exclude layer3/4 IP payload in the hash key";
                       type empty;
                     }
                   }
                 }
               }
               case case_2 {
                 container port-data {
                   presence "enable port-data";
                   uses apply-advanced;
                   leaf source-msb {
                     description "Include the most significant byte of the source port";
                     type empty;
                   }
                   leaf source-lsb {
                     description "Include the least significant byte of the source port";
                     type empty;
                   }
                   leaf destination-msb {
                     description "Include the most significant byte of the destination port";
                     type empty;
                   }
                   leaf destination-lsb {
                     description "Include the least significant byte of the destination port";
                     type empty;
                   }
                 }
               }
             }
           }
         }
       }
       container multiservice {
         description "Multiservice protocol family";
         uses apply-advanced;
         leaf source-mac {
           description "Include source MAC address in hash key";
           type empty;
         }
         leaf destination-mac {
           description "Include destination MAC address in hash key";
           type empty;
         }
       }
     }
   }
   grouping layer2_pm_family_output_type {
     uses apply-advanced;
     choice interface-or-next-hop-index {
       case case_1 {
         leaf interface {
           description "Interface through which to send sampled traffic";
           type union {
             type jt:interface-name;
             type string {
               pattern "<.*>|$.*";
             }
           }
         }
       }
       case case_2 {
         leaf next-hop-group {
           description "Next-hop-group through which to send port-mirror traffic";
           type string;
         }
       }
       case case_3 {
         list routing-instance {
           key name;
           description "Routing instances";
           max-elements 1;
           uses layer2_pm_output-routing-instance-type;
         }
       }
       case case_4 {
         list vlan {
           key name;
           description "Outgoing VLAN for mirrored packets";
           max-elements 1;
           uses pm-rspan-vlan;
         }
       }
       case case_5 {
       }
     }
     leaf no-filter-check {
       description "Do not check for filters on port-mirroring interface";
       type empty;
     }
   }
   grouping layer2_pm_output-routing-instance-type {
     leaf name {
       description "Routing instance name";
       type string {
       }
     }
     uses apply-advanced;
     list vlan {
       key name;
       description "Outgoing VLAN for mirrored packets";
       max-elements 1;
       uses pm-rspan-vlan;
     }
   }
   grouping loopback-load-balance-exclude-fpc-type {
     leaf name {
       description "FPC slot number";
       type union {
         type string {
           pattern "<.*>|$.*";
         }
         type uint32;
       }
     }
     uses apply-advanced;
     list pfe {
       key name;
       description "PFE Parameters";
       uses loopback-load-balance-exclude-pfe-type;
     }
   }
   grouping loopback-load-balance-exclude-pfe-type {
     leaf name {
       description "PFE instance";
       type union {
         type string {
           pattern "<.*>|$.*";
         }
         type uint32;
       }
     }
     uses apply-advanced;
     list data-path {
       key name;
       description "Data path Parameters";
       uses loopback-load-balance-exclude-dp-type;
     }
   }
   grouping loopback-load-balance-exclude-dp-type {
     leaf name {
       description "Data path instance";
       type union {
         type string {
           pattern "<.*>|$.*";
         }
         type uint32 {
           range "0 .. 1";
         }
       }
     }
     uses apply-advanced;
   }
   grouping macro-data-type {
     leaf name {
       description "Keyword part of the keyword-value pair";
       type string;
     }
     leaf value {
       description "Value part of the keyword-value pair";
       type string;
     }
   }
   grouping mirror-profile-attributes {
     description "Mirror profile attributes";
     leaf name {
       description "Mirror profile name";
       type string {
         length "1 .. 63";
       }
     }
     uses apply-advanced;
     leaf ptp-packet-timestamp {
       description "Enable precision-time-protocol packet timestamp";
       type empty;
     }
     container collector {
       description "Send mirrored traffic to collector";
       uses apply-advanced;
       leaf ip-address {
         description "Collector destination ip-address";
         type jt:ipaddr;
       }
       leaf l4-port {
         description "Layer 4 UDP/TCP port number of the collector";
         type union {
           type uint16;
           type string {
             pattern "<.*>|$.*";
           }
         }
       }
       container routing-instance {
         presence "enable routing-instance";
         description "Routing instances";
         uses apply-advanced;
         leaf routing-instance-name {
           description "Routing instance name";
           type string {
           }
         }
         leaf ip-address {
           description "Collector destination ip-address";
           type jt:ipaddr;
         }
         leaf l4-port {
           description "Layer 4 UDP/TCP port number of the collector";
           type union {
             type uint16;
             type string {
               pattern "<.*>|$.*";
             }
           }
         }
       }
     }
     leaf observation-domain-id {
       description "Observation domain Id";
       type union {
         type uint16;
         type string {
           pattern "<.*>|$.*";
         }
       }
     }
   }
   grouping mpls_pm_family_output_type {
     uses apply-advanced;
     leaf server-profile {
       description "Server profile name";
       type string {
         length "3 .. 32";
       }
     }
   }
   grouping next_hop_group_intf_type {
     leaf name {
       description "Interface through which to send sampled traffic";
       type union {
         type jt:interface-name;
         type string {
           pattern "<.*>|$.*";
         }
       }
     }
     uses apply-advanced;
     list next-hop {
       key name;
       ordered-by user;
       description "Address of next hop through which to send sampled traffic";
       uses next_hop_type;
     }
   }
   grouping next_hop_subgroup_intf_type {
     leaf name {
       description "Interface through which to send sampled traffic";
       type union {
         type jt:interface-name;
         type string {
           pattern "<.*>|$.*";
         }
       }
     }
     uses apply-advanced;
     list next-hop {
       key name;
       ordered-by user;
       description "Address of next hop through which to send sampled traffic";
       uses next_hop_type;
     }
   }
   grouping next_hop_type {
     description "Address of next hop through which to send sampled traffic";
     leaf name {
       type jt:ipaddr;
     }
     uses apply-advanced;
   }
   grouping override-type {
     description "DHCP override processing";
     uses apply-advanced;
     leaf no-unicast-replies {
       description "Overwrite unicast bit in incoming packet, when present";
       type empty;
     }
     choice allow-snooped-clients-choice {
       leaf allow-snooped-clients {
         description "Allow client creation from snooped PDUs";
         type empty;
       }
       leaf no-allow-snooped-clients {
         description "Don't allow client creation from snooped PDUs";
         type empty;
       }
     }
     leaf allow-no-end-option {
       description "Allow packets without end-of-option";
       type empty;
     }
     leaf always-write-giaddr {
       description "Overwrite existing 'giaddr' field, when present";
       type empty;
     }
     container always-write-option-82 {
       description "Overwrite existing value of option 82, when present";
       presence "enable always-write-option-82";
       uses write-option-82-type;
     }
     leaf user-defined-option-82 {
       description "Set user defined description for option-82";
       status deprecated;
       type string {
         length "1 .. 252";
       }
     }
     leaf include-option-82-in-vsa {
       description "Include option 82 in Dhcp-Options RADIUS VSA";
       type empty;
     }
     leaf layer2-unicast-replies {
       description "Do not broadcast client responses";
       type empty;
     }
     leaf trust-option-82 {
       description "Trust options-82 option";
       type empty;
     }
     leaf delay-authentication {
       description "Delay subscriber authentication in DHCP protocol processing until request packet";
       type empty;
     }
     leaf disable-relay {
       description "Disable DHCP relay processing";
       type empty;
     }
     leaf no-bind-on-request {
       description "Do not bind if stray DHCP request is received";
       type empty;
     }
     leaf interface-client-limit {
       description "Limit the number of client allowed on an interface";
       type union {
         type string {
           pattern "<.*>|$.*";
         }
         type uint32 {
           range "1 .. 500000";
         }
       }
     }
     leaf no-arp {
       description "Disable DHCP ARP table population";
       status deprecated;
       type empty;
     }
     leaf bootp-support {
       description "Allows relay of bootp req and reply";
       type empty;
     }
     leaf dual-stack {
       description "Dual stack group to use.";
       type string {
         length "1 .. 64";
       }
     }
     container client-discover-match {
       presence "enable client-discover-match";
       description "Use secondary match criteria for DISCOVER PDU";
       choice match-with {
         case case_1 {
           leaf option60-and-option82 {
             description "Use option 60 and option 82";
             type empty;
           }
         }
         case case_2 {
           leaf incoming-interface {
             description "Use incoming interface";
             type empty;
           }
         }
       }
     }
     container proxy-mode {
       presence "enable proxy-mode";
       description "Put the relay in proxy mode";
     }
     leaf asymmetric-lease-time {
       description "Use a reduced lease time for the client. In seconds";
       units "seconds";
       type union {
         type string {
           pattern "<.*>|$.*";
         }
         type uint32 {
           range "600 .. 86400";
         }
       }
     }
     container replace-ip-source-with {
       description "Replace IP source address in request and release packets";
       choice replacement-type {
         case case_1 {
           leaf giaddr {
             description "Replace IP source address with giaddr";
             type empty;
           }
         }
       }
     }
     leaf send-release-on-delete {
       description "Always send RELEASE to the server when a binding is deleted";
       type empty;
     }
     leaf apply-secondary-as-giaddr {
       description "Enable DHCP relay to use secondary gateway ip for relay interfaces";
       type empty;
     }
     leaf relay-source {
       description "Interface for relay source";
       type union {
         type jt:interface-name;
         type string {
           pattern "<.*>|$.*";
         }
       }
     }
     leaf delete-binding-on-renegotiation {
       description "Delete binding on rengotiation";
       type empty;
     }
   }
   grouping packet-capture-egress-intf-type {
     uses apply-advanced;
     list interface {
       key name;
       description "Interface options";
       leaf name {
         description "Interface name";
         type union {
           type jt:interface-device;
           type string {
             pattern "<.*>|$.*";
           }
         }
       }
       uses apply-advanced;
     }
   }
   grouping packet_accounting_output_type {
     uses apply-advanced;
     leaf aggregate-export-interval {
       description "Interval of exporting aggregate accounting information";
       default "90";
       units "seconds";
       type union {
         type string {
           pattern "<.*>|$.*";
         }
         type uint32 {
           range "90 .. 1800";
         }
       }
     }
     leaf flow-inactive-timeout {
       description "Interval of inactivity that marks a flow inactive";
       default "60";
       units "seconds";
       type union {
         type string {
           pattern "<.*>|$.*";
         }
         type uint32 {
           range "15 .. 1800";
         }
       }
     }
     leaf flow-active-timeout {
       description "Interval after which an active flow is exported";
       default "1800";
       units "seconds";
       type union {
         type string {
           pattern "<.*>|$.*";
         }
         type uint32 {
           range "60 .. 1800";
         }
       }
     }
     list cflowd {
       key name;
       description "Cflowd collector where flow records are sent";
       uses cflowd_packet_accounting_type;
     }
     list interface {
       key name;
       description "Interfaces used to send monitored information";
       uses packet_export_intf_type;
     }
   }
   grouping cflowd_packet_accounting_type {
     leaf name {
       description "Name of host collecting cflowd packets";
       type jt:ipaddr;
     }
     uses apply-advanced;
     leaf port {
       description "UDP port number on host collecting cflowd packets";
       type union {
         type uint16;
         type string {
           pattern "<.*>|$.*";
         }
       }
     }
     leaf dscp {
       description "Numeric DSCP value in the range 0 to 63";
       default "0";
       type union {
         type string {
           pattern "<.*>|$.*";
         }
         type uint8 {
           range "0 .. 63";
         }
       }
     }
     leaf forwarding-class {
       description "Forwarding-class for exported jflow packets, applicable only for inline-jflow";
       type string {
         length "1 .. 64";
       }
     }
     leaf routing-instance {
       description "Name of routing instance on which flow collector is reachable";
       type string;
     }
     leaf version {
       description "Format of exported cflowd aggregates";
       default "5";
       type enumeration {
         enum "5" {
           description "Export cflowd aggregates in version 5 format";
         }
         enum "8" {
           description "Export cflowd aggregates in version 8 format";
         }
       }
     }
     leaf autonomous-system-type {
       description "Type of autonomous system number to export";
       default "origin";
       type enumeration {
         enum "origin" {
           description "Export origin-AS numbers";
         }
         enum "peer" {
           description "Export peer-AS numbers";
         }
       }
     }
     container aggregation {
       description "Aggregations to perform for exported flows (version 8 only)";
       uses aggregation_type;
     }
   }
   grouping aggregation_type {
     uses apply-advanced;
     leaf autonomous-system {
       description "Aggregate by autonomous system number";
       type empty;
     }
     leaf protocol-port {
       description "Aggregate by protocol and port number";
       type empty;
     }
     leaf source-prefix {
       description "Aggregate by source prefix";
       type empty;
     }
     leaf destination-prefix {
       description "Aggregate by destination prefix";
       type empty;
     }
     container source-destination-prefix {
       presence "enable source-destination-prefix";
       description "Aggregate by source and destination prefix";
       uses apply-advanced;
       leaf caida-compliant {
         description "Compatible with Caida record format for prefix aggregation (v8)";
         type empty;
       }
     }
   }
   grouping packet_export_intf_type {
     leaf name {
       description "Interfaces used to send monitored information";
       type union {
         type jt:interface-unit;
         type string {
           pattern "<.*>|$.*";
         }
       }
     }
     uses apply-advanced;
     leaf engine-id {
       description "Identity (number) of this accounting interface";
       type union {
         type uint8;
         type string {
           pattern "<.*>|$.*";
         }
       }
     }
     leaf engine-type {
       description "Type (number) of this accounting interface";
       type union {
         type uint8;
         type string {
           pattern "<.*>|$.*";
         }
       }
     }
     leaf source-address {
       description "Address to use for generating monitored packets";
       type jt:ipaddr;
     }
     container export-port {
       description "Jflow export port configuration";
       presence "enable export-port";
       uses export_port_address_type;
     }
   }
   grouping export_port_address_type {
     uses apply-advanced;
     leaf address {
       description "Address to use for jflow export port";
       type jt:ipv4prefix;
     }
     leaf gateway {
       description "Gateway address to reach jflow server";
       type jt:ipv4addr;
     }
   }
   grouping pm-rspan-vlan {
     description "RSPAN vlan for pm";
     leaf name {
       description "VLAN name or VLAN id";
       type string {
       }
     }
     uses apply-advanced;
     leaf no-tag {
       description "Removes extra RSPAN tag from mirrored packets";
       type empty;
     }
   }
   grouping pm_family_input_type {
     description "Input options for port mirroring";
     uses apply-advanced;
     leaf rate {
       description "Ratio of packets to be sampled (1 out of N)";
       type union {
         type string {
           pattern "<.*>|$.*";
         }
         type uint32;
       }
     }
     leaf run-length {
       description "Number of samples after initial trigger";
       type union {
         type string {
           pattern "<.*>|$.*";
         }
         type uint32 {
           range "0 .. 20";
         }
       }
     }
     leaf maximum-packet-length {
       description "Maximum length of the mirrored packet";
       default "0";
       units "bytes";
       type union {
         type string {
           pattern "<.*>|$.*";
         }
         type uint32 {
           range "0 .. 9216";
         }
       }
     }
   }
   grouping relay-bulk-leasequery-v4-type {
     description "Configure bulk leasequery";
     uses apply-advanced;
     leaf attempts {
       description "Number of retry attempts";
       default "360";
       type union {
         type string {
           pattern "<.*>|$.*";
         }
         type uint32 {
           range "1 .. 720";
         }
       }
     }
     leaf timeout {
       description "Number of seconds";
       default "10";
       units "seconds";
       type union {
         type string {
           pattern "<.*>|$.*";
         }
         type uint32 {
           range "1 .. 10";
         }
       }
     }
   }
   grouping relay-bulk-leasequery-v6-type {
     description "Configure bulk leasequery";
     uses apply-advanced;
     leaf attempts {
       description "Number of retry attempts";
       default "6";
       type union {
         type string {
           pattern "<.*>|$.*";
         }
         type uint32 {
           range "1 .. 10";
         }
       }
     }
     leaf timeout {
       description "Number of seconds";
       default "10";
       units "seconds";
       type union {
         type string {
           pattern "<.*>|$.*";
         }
         type uint32 {
           range "1 .. 10";
         }
       }
     }
     container trigger {
       description "Trigger for bulk leasequery";
       leaf automatic {
         description "Trigger automatically";
         type empty;
       }
     }
   }
   grouping relay-leasequery-type {
     description "Configure leasequery";
     uses apply-advanced;
     leaf attempts {
       description "Number of retry attempts";
       default "6";
       type union {
         type string {
           pattern "<.*>|$.*";
         }
         type uint32 {
           range "1 .. 10";
         }
       }
     }
     leaf timeout {
       description "Number of seconds";
       default "10";
       units "seconds";
       type union {
         type string {
           pattern "<.*>|$.*";
         }
         type uint32 {
           range "1 .. 10";
         }
       }
     }
   }
   grouping relay-option-60-type-group {
     description "DHCP option-60 processing";
     uses apply-advanced;
     container vendor-option {
       description "Add vendor option";
       uses apply-advanced;
       container equals {
         description "Option 60 equals";
         uses relay-option-60-match-group;
       }
       container not-equals {
         description "Option 60 does not equal";
         status deprecated;
         uses relay-option-60-match-group;
       }
       container starts-with {
         description "Option 60 starts with";
         uses relay-option-60-match-group;
       }
       choice server-group-choice {
         case case_1 {
           leaf default-relay-server-group {
             description "Name of DHCP relay server group when match is not made";
             type string {
               length "1 .. 64";
             }
           }
         }
         case case_2 {
           leaf default-local-server-group {
             description "Name of DHCP local server group when match is not made";
             type string {
               length "1 .. 64";
             }
           }
         }
         case case_3 {
           leaf drop {
             description "Discard when a match is not made";
             type empty;
           }
         }
         case case_4 {
           leaf forward-only {
             description "Forward without subscriber services when a match is not made";
             type empty;
           }
         }
       }
     }
   }
   grouping relay-option-60-match-group {
     uses apply-advanced;
     list ascii {
       key name;
       description "ASCII string";
       leaf name {
         description "ASCII string";
         type string {
           length "1 .. 256";
         }
       }
       uses apply-advanced;
       choice server-group-choice {
         case case_1 {
           leaf relay-server-group {
             description "Name of DHCP relay server group when match is made";
             type string {
               length "1 .. 64";
             }
           }
         }
         case case_2 {
           leaf local-server-group {
             description "Name of DHCP local server group when match is made";
             type string {
               length "1 .. 64";
             }
           }
         }
         case case_3 {
           leaf drop {
             description "Discard when a match is made";
             type empty;
           }
         }
         case case_4 {
           leaf forward-only {
             description "Forward without subscriber services when a match is made";
             type empty;
           }
         }
       }
     }
     list hexadecimal {
       key name;
       description "Hexadecimal string";
       leaf name {
         description "Hexadecimal string";
         type string {
           length "1 .. 512";
         }
       }
       uses apply-advanced;
       choice server-group-choice {
         case case_1 {
           leaf relay-server-group {
             description "Name of DHCP relay server group when match is made";
             type string {
               length "1 .. 64";
             }
           }
         }
         case case_2 {
           leaf local-server-group {
             description "Name of DHCP local server group when match is made";
             type string {
               length "1 .. 64";
             }
           }
         }
         case case_3 {
           leaf drop {
             description "Discard when a match is made";
             type empty;
           }
         }
         case case_4 {
           leaf forward-only {
             description "Forward without subscriber services when a match is made";
             type empty;
           }
         }
       }
     }
   }
   grouping relay-option-60-type-top {
     description "DHCP option-60 processing";
     uses apply-advanced;
     container vendor-option {
       description "Add vendor option";
       uses apply-advanced;
       container equals {
         description "Option 60 equals";
         uses relay-option-60-match-top;
       }
       container not-equals {
         description "Option 60 does not equal";
         status deprecated;
         uses relay-option-60-match-top;
       }
       container starts-with {
         description "Option 60 starts with";
         uses relay-option-60-match-top;
       }
       choice server-group-choice {
         case case_1 {
           leaf default-relay-server-group {
             description "Name of DHCP relay server group when match is not made";
             type string {
               length "1 .. 64";
             }
           }
         }
         case case_2 {
           leaf default-local-server-group {
             description "Name of DHCP local server group when match is not made";
             type string {
               length "1 .. 64";
             }
           }
         }
         case case_3 {
           leaf drop {
             description "Discard when a match is not made";
             type empty;
           }
         }
         case case_4 {
           leaf forward-only {
             description "Forward without subscriber services when a match is not made";
             type empty;
           }
         }
       }
     }
   }
   grouping relay-option-60-match-top {
     uses apply-advanced;
     list ascii {
       key name;
       description "ASCII string";
       leaf name {
         description "ASCII string";
         type string {
           length "1 .. 256";
         }
       }
       uses apply-advanced;
       choice server-group-choice {
         case case_1 {
           leaf relay-server-group {
             description "Name of DHCP relay server group when match is made";
             type string {
               length "1 .. 64";
             }
           }
         }
         case case_2 {
           leaf local-server-group {
             description "Name of DHCP local server group when match is made";
             type string {
               length "1 .. 64";
             }
           }
         }
         case case_3 {
           leaf drop {
             description "Discard when a match is made";
             type empty;
           }
         }
         case case_4 {
           leaf forward-only {
             description "Forward without subscriber services when a match is made";
             type empty;
           }
         }
       }
     }
     list hexadecimal {
       key name;
       description "Hexadecimal string";
       leaf name {
         description "Hexadecimal string";
         type string {
           length "1 .. 512";
         }
       }
       uses apply-advanced;
       choice server-group-choice {
         case case_1 {
           leaf relay-server-group {
             description "Name of DHCP relay server group when match is made";
             type string {
               length "1 .. 64";
             }
           }
         }
         case case_2 {
           leaf local-server-group {
             description "Name of DHCP local server group when match is made";
             type string {
               length "1 .. 64";
             }
           }
         }
         case case_3 {
           leaf drop {
             description "Discard when a match is made";
             type empty;
           }
         }
         case case_4 {
           leaf forward-only {
             description "Forward without subscriber services when a match is made";
             type empty;
           }
         }
       }
     }
   }
   grouping relay-option-82-type {
     description "DHCP option-82 processing";
     uses apply-advanced;
     container circuit-id {
       presence "enable circuit-id";
       description "Add circuit identifier";
       uses apply-advanced;
       container prefix {
         description "Add prefix to circuit/interface-id or remote-id";
         uses apply-advanced;
         leaf host-name {
           description "Add router host name to circuit / interface-id or remote-id";
           type empty;
         }
         leaf logical-system-name {
           description "Add logical system name to circuit / interface-id or remote-id";
           type empty;
         }
         leaf routing-instance-name {
           description "Add routing instance name to circuit / interface-id or remote-id";
           type empty;
         }
       }
       leaf use-interface-description {
         description "Use interface description instead of circuit identifier";
         type enumeration {
           enum "logical" {
             description "Use the logical interface description";
           }
           enum "device" {
             description "Use the device interface description";
           }
         }
       }
       leaf use-vlan-id {
         description "Use VLAN id instead of name";
         type empty;
       }
       container vlan-id-only {
         presence "enable vlan-id-only";
         description "Use only VLAN id";
         uses apply-advanced;
       }
       leaf no-vlan-interface-name {
         description "Not include vlan or interface name";
         type empty;
       }
       leaf include-irb-and-l2 {
         description "Include IRB and L2 interface name";
         type empty;
       }
       container user-defined {
         presence "enable user-defined";
         description "Include user defined string";
         uses apply-advanced;
         leaf string {
           description "Set user-defined character string description";
           type string {
             length "1 .. 252";
           }
         }
         leaf hex-string {
           description "Set user-defined hexadecimal string description";
           type string {
             length "1 .. 510";
           }
         }
       }
       leaf keep-incoming-circuit-id {
         description "Keep incoming circuit identifier";
         type empty;
       }
     }
     container remote-id {
       presence "enable remote-id";
       description "Add remote identifier";
       uses apply-advanced;
       container prefix {
         description "Add prefix to circuit/interface-id or remote-id";
         uses apply-advanced;
         leaf host-name {
           description "Add router host name to circuit / interface-id or remote-id";
           type empty;
         }
         leaf logical-system-name {
           description "Add logical system name to circuit / interface-id or remote-id";
           type empty;
         }
         leaf routing-instance-name {
           description "Add routing instance name to circuit / interface-id or remote-id";
           type empty;
         }
       }
       leaf use-interface-description {
         description "Use interface description instead of circuit identifier";
         type enumeration {
           enum "logical" {
             description "Use the logical interface description";
           }
           enum "device" {
             description "Use the device interface description";
           }
         }
       }
       leaf use-vlan-id {
         description "Use VLAN id instead of name";
         type empty;
       }
       leaf no-vlan-interface-name {
         description "Not include vlan or interface name";
         type empty;
       }
       leaf include-irb-and-l2 {
         description "Include IRB and L2 interface name";
         type empty;
       }
       container hostname-only {
         presence "enable hostname-only";
         description "Include hostname only";
         uses apply-advanced;
       }
       container user-defined {
         presence "enable user-defined";
         description "Include user defined string";
         uses apply-advanced;
         leaf string {
           description "Set user-defined character string description";
           type string {
             length "1 .. 252";
           }
         }
         leaf hex-string {
           description "Set user-defined hexadecimal string description";
           type string {
             length "1 .. 510";
           }
         }
       }
       leaf keep-incoming-remote-id {
         description "Keep incoming remote identifier";
         type empty;
       }
       leaf use-string {
         description "Use raw string instead of the default remote id";
         status deprecated;
         type string;
       }
     }
     leaf server-id-override {
       description "Add link-selection and server-id sub-options on packets to server";
       type empty;
     }
     leaf link-selection {
       description "Add link-selection suboption on packets to server";
       type empty;
     }
     leaf exclude-relay-agent-identifier {
       description "Exclude relay agent identifier from packets to server";
       type empty;
     }
     container vendor-specific {
       description "Add vendor-specific information";
       uses jdhcp-vendor-specific-type;
     }
   }
   grouping relay-v4-option-ascii-hex {
     uses apply-advanced;
     list ascii {
       key name;
       description "ASCII string";
       leaf name {
         description "ASCII string";
         type string {
           length "1 .. 256";
         }
       }
       uses apply-advanced;
       choice server-group-choice {
         case case_1 {
           leaf relay-server-group {
             description "Name of DHCP relay server group when match is made";
             type string {
               length "1 .. 64";
             }
           }
         }
         case case_2 {
           leaf local-server-group {
             description "Name of DHCP local server group when match is made";
             type string {
               length "1 .. 64";
             }
           }
         }
         case case_3 {
           leaf drop {
             description "Discard when a match is made";
             type empty;
           }
         }
         case case_4 {
           leaf forward-only {
             description "Forward without subscriber services when a match is made";
             type empty;
           }
         }
       }
     }
     list hexadecimal {
       key name;
       description "Hexadecimal string";
       leaf name {
         description "Hexadecimal string";
         type string {
           length "1 .. 512";
         }
       }
       uses apply-advanced;
       choice server-group-choice {
         case case_1 {
           leaf relay-server-group {
             description "Name of DHCP relay server group when match is made";
             type string {
               length "1 .. 64";
             }
           }
         }
         case case_2 {
           leaf local-server-group {
             description "Name of DHCP local server group when match is made";
             type string {
               length "1 .. 64";
             }
           }
         }
         case case_3 {
           leaf drop {
             description "Discard when a match is made";
             type empty;
           }
         }
         case case_4 {
           leaf forward-only {
             description "Forward without subscriber services when a match is made";
             type empty;
           }
         }
       }
     }
   }
   grouping relay-v6-option-ascii-hex {
     uses apply-advanced;
     list ascii {
       key name;
       description "ASCII string";
       leaf name {
         description "ASCII string";
         type string {
           length "1 .. 256";
         }
       }
       uses apply-advanced;
       choice server-group-choice {
         case case_1 {
           leaf relay-server-group {
             description "Name of DHCP relay server group when match is made";
             type string {
               length "1 .. 64";
             }
           }
         }
         case case_2 {
           leaf drop {
             description "Discard when a match is made";
             type empty;
           }
         }
         case case_3 {
           leaf forward-only {
             description "Forward without subscriber services when a match is made";
             type empty;
           }
         }
       }
     }
     list hexadecimal {
       key name;
       description "Hexadecimal string";
       leaf name {
         description "Hexadecimal string";
         type string {
           length "1 .. 512";
         }
       }
       uses apply-advanced;
       choice server-group-choice {
         case case_1 {
           leaf relay-server-group {
             description "Name of DHCP relay server group when match is made";
             type string {
               length "1 .. 64";
             }
           }
         }
         case case_2 {
           leaf drop {
             description "Discard when a match is made";
             type empty;
           }
         }
         case case_3 {
           leaf forward-only {
             description "Forward without subscriber services when a match is made";
             type empty;
           }
         }
       }
     }
   }
   grouping route_record_traceoptions {
     description "Traceoptions for sampling route record";
     uses apply-advanced;
     leaf no-remote-trace {
       description "Disable remote tracing";
       type empty;
     }
     container file {
       description "Trace file information";
       leaf filename {
         description "Name of file in which to write trace information";
         type string {
           length "1 .. 1024";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     leaf level {
       description "Level of debugging output";
       default "error";
       type enumeration {
         enum "error" {
           description "Match error conditions";
         }
         enum "warning" {
           description "Match warning messages";
         }
         enum "notice" {
           description "Match conditions that should be handled specially";
         }
         enum "info" {
           description "Match informational messages";
         }
         enum "verbose" {
           description "Match verbose messages";
         }
         enum "all" {
           description "Match all levels";
         }
       }
     }
     list flag {
       key name;
       ordered-by user;
       description "Area of route-record to enable debuging output";
       leaf name {
         type enumeration {
           enum "parse" {
             description "Trace parsing code";
           }
           enum "all" {
             description "Trace all area of jflow-service code";
           }
         }
       }
     }
   }
   grouping sampling_family_inet6_output_type {
     description "Configure output options for packet sampling";
     uses apply-advanced;
     leaf aggregate-export-interval {
       description "Interval of exporting aggregate accounting information";
       default "90";
       units "seconds";
       type union {
         type string {
           pattern "<.*>|$.*";
         }
         type uint32 {
           range "90 .. 1800";
         }
       }
     }
     leaf flow-inactive-timeout {
       description "Interval of inactivity that marks a flow inactive";
       default "60";
       units "seconds";
       type union {
         type string {
           pattern "<.*>|$.*";
         }
         type uint32 {
           range "15 .. 1800";
         }
       }
     }
     leaf flow-active-timeout {
       description "Interval after which an active flow is exported";
       default "1800";
       units "seconds";
       type union {
         type string {
           pattern "<.*>|$.*";
         }
         type uint32 {
           range "60 .. 1800";
         }
       }
     }
     list flow-server {
       key name;
       description "Configure sending traffic aggregates in cflowd format";
       max-elements 8;
       uses cflowd_sampling_inet6_sampling_type;
     }
     list interface {
       key name;
       description "Interfaces used to send monitored information";
       max-elements 1;
       uses packet_export_intf_type;
     }
     container inline-jflow {
       description "Inline processing of sampled packets";
       presence "enable inline-jflow";
       uses packet_export_inline;
     }
     list extension-service {
       key name;
       ordered-by user;
       description "Define the customer specific sampling configuration";
       leaf name {
         description "Customer prefixed sampling service name";
         type string {
           length "1 .. 63";
         }
       }
       uses apply-advanced;
     }
   }
   grouping cflowd_sampling_inet6_sampling_type {
     leaf name {
       description "Name of host collecting cflowd packets";
       type jt:ipaddr;
     }
     uses apply-advanced;
     leaf port {
       description "UDP port number on host collecting cflowd packets";
       type union {
         type uint16;
         type string {
           pattern "<.*>|$.*";
         }
       }
     }
     leaf dscp {
       description "Numeric DSCP value in the range 0 to 63";
       default "0";
       type union {
         type string {
           pattern "<.*>|$.*";
         }
         type uint8 {
           range "0 .. 63";
         }
       }
     }
     leaf forwarding-class {
       description "Forwarding-class for exported jflow packets, applicable only for inline-jflow";
       type string {
         length "1 .. 64";
       }
     }
     leaf routing-instance {
       description "Name of routing instance on which flow collector is reachable";
       type string;
     }
     leaf autonomous-system-type {
       description "Type of autonomous system number to export";
       default "origin";
       type enumeration {
         enum "origin" {
           description "Export origin-AS numbers";
         }
         enum "peer" {
           description "Export peer-AS numbers";
         }
       }
     }
     container aggregation {
       description "Aggregations to perform for exported flows (version 8 only)";
       uses aggregation_type;
     }
     choice local-dump-choice {
       leaf local-dump {
         description "Dump cflowd records to log file before exporting";
         type empty;
       }
       leaf no-local-dump {
         description "Don't dump cflowd records to log file before exporting";
         type empty;
       }
     }
     leaf source-address {
       description "Source IPv4 address for cflowd packets";
       type jt:ipv4addr;
     }
     container version9 {
       presence "enable version9";
       description "Export data in version 9 format";
       uses apply-advanced;
       container template {
         description "Template configuration";
         uses apply-advanced;
         leaf template-name {
           description "Template name";
           type string;
         }
       }
     }
   }
   grouping packet_export_inline {
     uses apply-advanced;
     leaf source-address {
       description "Address to use for generating monitored packets";
       type jt:ipaddr;
     }
     leaf flow-export-rate {
       description "Flow export rate of monitored packets in kpps";
       type union {
         type string {
           pattern "<.*>|$.*";
         }
         type uint32 {
           range "1 .. 3200";
         }
       }
     }
   }
   grouping sampling_family_input_type {
     description "Configure input options for packet sampling";
     uses apply-advanced;
     leaf rate {
       description "Ratio of packets to be sampled (1 out of N)";
       type union {
         type string {
           pattern "<.*>|$.*";
         }
         type uint32;
       }
     }
     leaf run-length {
       description "Number of samples after initial trigger";
       default "0";
       type union {
         type string {
           pattern "<.*>|$.*";
         }
         type uint32 {
           range "0 .. 20";
         }
       }
     }
     leaf max-packets-per-second {
       description "Threshold of samples per second before dropping";
       default "1000";
       type union {
         type uint16;
         type string {
           pattern "<.*>|$.*";
         }
       }
     }
     leaf maximum-packet-length {
       description "Maximum length of the sampled packet";
       default "0";
       units "bytes";
       type union {
         type string {
           pattern "<.*>|$.*";
         }
         type uint32 {
           range "0 .. 9192";
         }
       }
     }
   }
   grouping sampling_global_mpls_output_type {
     description "Configure output options for packet sampling";
     uses apply-advanced;
     leaf aggregate-export-interval {
       description "Interval of exporting aggregate accounting information";
       default "90";
       units "seconds";
       type union {
         type string {
           pattern "<.*>|$.*";
         }
         type uint32 {
           range "90 .. 1800";
         }
       }
     }
     leaf flow-inactive-timeout {
       description "Interval of inactivity that marks a flow inactive";
       default "60";
       units "seconds";
       type union {
         type string {
           pattern "<.*>|$.*";
         }
         type uint32 {
           range "15 .. 1800";
         }
       }
     }
     leaf flow-active-timeout {
       description "Interval after which an active flow is exported";
       default "1800";
       units "seconds";
       type union {
         type string {
           pattern "<.*>|$.*";
         }
         type uint32 {
           range "60 .. 1800";
         }
       }
     }
     list flow-server {
       key name;
       description "Configure sending traffic aggregates in cflowd format";
       max-elements 8;
       uses cflowd_global_mpls_sampling_type;
     }
     list interface {
       key name;
       description "Interfaces used to send monitored information";
       max-elements 1;
       uses packet_export_intf_type;
     }
   }
   grouping cflowd_global_mpls_sampling_type {
     leaf name {
       description "Name of host collecting cflowd packets";
       type jt:ipaddr;
     }
     uses apply-advanced;
     leaf port {
       description "UDP port number on host collecting cflowd packets";
       type union {
         type uint16;
         type string {
           pattern "<.*>|$.*";
         }
       }
     }
     leaf dscp {
       description "Numeric DSCP value in the range 0 to 63";
       default "0";
       type union {
         type string {
           pattern "<.*>|$.*";
         }
         type uint8 {
           range "0 .. 63";
         }
       }
     }
     leaf forwarding-class {
       description "Forwarding-class for exported jflow packets, applicable only for inline-jflow";
       type string {
         length "1 .. 64";
       }
     }
     leaf routing-instance {
       description "Name of routing instance on which flow collector is reachable";
       type string;
     }
     leaf autonomous-system-type {
       description "Type of autonomous system number to export";
       default "origin";
       type enumeration {
         enum "origin" {
           description "Export origin-AS numbers";
         }
         enum "peer" {
           description "Export peer-AS numbers";
         }
       }
     }
     container aggregation {
       description "Aggregations to perform for exported flows (version 8 only)";
       uses aggregation_type;
     }
     choice local-dump-choice {
       leaf local-dump {
         description "Dump cflowd records to log file before exporting";
         type empty;
       }
       leaf no-local-dump {
         description "Don't dump cflowd records to log file before exporting";
         type empty;
       }
     }
     leaf source-address {
       description "Source IPv4 address for cflowd packets";
       type jt:ipv4addr;
     }
     container version9 {
       presence "enable version9";
       description "Export data in version 9 format";
       uses apply-advanced;
       container template {
         description "Template configuration";
         uses apply-advanced;
         leaf template-name {
           description "Template name";
           type string;
         }
       }
     }
   }
   grouping sampling_input_type {
     description "Configure input options for packet sampling";
     uses apply-advanced;
     leaf rate {
       description "Ratio of packets to be sampled (1 out of N)";
       type union {
         type string {
           pattern "<.*>|$.*";
         }
         type uint32;
       }
     }
     leaf run-length {
       description "Number of samples after initial trigger";
       default "0";
       type union {
         type string {
           pattern "<.*>|$.*";
         }
         type uint32 {
           range "0 .. 20";
         }
       }
     }
     leaf max-packets-per-second {
       description "Threshold of samples per second before dropping";
       default "1000";
       type union {
         type uint16;
         type string {
           pattern "<.*>|$.*";
         }
       }
     }
     leaf maximum-packet-length {
       description "Maximum length of the sampled packet";
       default "0";
       units "bytes";
       type union {
         type string {
           pattern "<.*>|$.*";
         }
         type uint32 {
           range "0 .. 9192";
         }
       }
     }
     container family {
       presence "enable family";
       description "Protocol family";
       status deprecated;
       container inet {
         description "Sampling parameters for IPv4";
         uses apply-advanced;
         leaf rate {
           description "Ratio of packets to be sampled (1 out of N)";
           type union {
             type string {
               pattern "<.*>|$.*";
             }
             type uint32;
           }
         }
         leaf run-length {
           description "Number of samples after initial trigger";
           default "0";
           type union {
             type string {
               pattern "<.*>|$.*";
             }
             type uint32 {
               range "0 .. 20";
             }
           }
         }
         leaf max-packets-per-second {
           description "Threshold of samples per second before dropping";
           default "1000";
           type union {
             type uint16;
             type string {
               pattern "<.*>|$.*";
             }
           }
         }
         leaf maximum-packet-length {
           description "Maximum length of the sampled packet";
           default "0";
           units "bytes";
           type union {
             type string {
               pattern "<.*>|$.*";
             }
             type uint32 {
               range "0 .. 9192";
             }
           }
         }
       }
       container mpls {
         description "Sampling parameters for MPLS";
         uses apply-advanced;
         leaf rate {
           description "Ratio of packets to be sampled (1 out of N)";
           type union {
             type string {
               pattern "<.*>|$.*";
             }
             type uint32;
           }
         }
         leaf run-length {
           description "Number of samples after initial trigger";
           default "0";
           type union {
             type string {
               pattern "<.*>|$.*";
             }
             type uint32 {
               range "0 .. 20";
             }
           }
         }
         leaf max-packets-per-second {
           description "Threshold of samples per second before dropping";
           default "1000";
           type union {
             type uint16;
             type string {
               pattern "<.*>|$.*";
             }
           }
         }
         leaf maximum-packet-length {
           description "Maximum length of the sampled packet";
           default "0";
           units "bytes";
           type union {
             type string {
               pattern "<.*>|$.*";
             }
             type uint32 {
               range "0 .. 9192";
             }
           }
         }
       }
       container inet6 {
         description "Sampling parameters for IPv6";
         uses apply-advanced;
         leaf rate {
           description "Ratio of packets to be sampled (1 out of N)";
           type union {
             type string {
               pattern "<.*>|$.*";
             }
             type uint32;
           }
         }
         leaf run-length {
           description "Number of samples after initial trigger";
           default "0";
           type union {
             type string {
               pattern "<.*>|$.*";
             }
             type uint32 {
               range "0 .. 20";
             }
           }
         }
         leaf max-packets-per-second {
           description "Threshold of samples per second before dropping";
           default "1000";
           type union {
             type uint16;
             type string {
               pattern "<.*>|$.*";
             }
           }
         }
         leaf maximum-packet-length {
           description "Maximum length of the sampled packet";
           default "0";
           units "bytes";
           type union {
             type string {
               pattern "<.*>|$.*";
             }
             type uint32 {
               range "0 .. 9192";
             }
           }
         }
       }
     }
   }
   grouping sampling_instance_bridge_output_type {
     description "Configure output options for packet sampling";
     uses apply-advanced;
     list flow-server {
       key name;
       description "Configure sending traffic aggregates in cflowd format";
       max-elements 8;
       uses cflowd_instance_bridge_sampling_type;
     }
     container inline-jflow {
       description "Inline processing of sampled packets";
       presence "enable inline-jflow";
       uses packet_export_inline_instance;
     }
   }
   grouping cflowd_instance_bridge_sampling_type {
     leaf name {
       description "Name of host collecting cflowd packets";
       type jt:ipaddr;
     }
     uses apply-advanced;
     leaf port {
       description "UDP port number on host collecting cflowd packets";
       type union {
         type uint16;
         type string {
           pattern "<.*>|$.*";
         }
       }
     }
     leaf dscp {
       description "Numeric DSCP value in the range 0 to 63";
       default "0";
       type union {
         type string {
           pattern "<.*>|$.*";
         }
         type uint8 {
           range "0 .. 63";
         }
       }
     }
     leaf forwarding-class {
       description "Forwarding-class for exported jflow packets, applicable only for inline-jflow";
       type string {
         length "1 .. 64";
       }
     }
     leaf routing-instance {
       description "Name of routing instance on which flow collector is reachable";
       type string;
     }
     container version9 {
       presence "enable version9";
       description "Export data in version 9 format";
       uses apply-advanced;
       container template {
         description "Template configuration";
         uses apply-advanced;
         leaf template-name {
           description "Template name";
           type string;
         }
       }
     }
     container version-ipfix {
       presence "enable version-ipfix";
       description "Export data in version ipfix format";
       uses apply-advanced;
       container template {
         description "Template configuration";
         uses apply-advanced;
         leaf template-name {
           description "Template name";
           type string;
         }
       }
     }
   }
   grouping packet_export_inline_instance {
     uses apply-advanced;
     leaf source-address {
       description "Address to use for generating monitored packets";
       type jt:ipaddr;
     }
     leaf flow-export-rate {
       description "Flow export rate of monitored packets in kpps";
       type union {
         type string {
           pattern "<.*>|$.*";
         }
         type uint32 {
           range "1 .. 3200";
         }
       }
     }
   }
   grouping sampling_instance_inet6_output_type {
     description "Configure output options for packet sampling";
     uses apply-advanced;
     leaf aggregate-export-interval {
       description "Interval of exporting aggregate accounting information";
       default "90";
       units "seconds";
       type union {
         type string {
           pattern "<.*>|$.*";
         }
         type uint32 {
           range "90 .. 1800";
         }
       }
     }
     leaf flow-inactive-timeout {
       description "Interval of inactivity that marks a flow inactive";
       default "60";
       units "seconds";
       type union {
         type string {
           pattern "<.*>|$.*";
         }
         type uint32 {
           range "15 .. 1800";
         }
       }
     }
     leaf flow-active-timeout {
       description "Interval after which an active flow is exported";
       default "1800";
       units "seconds";
       type union {
         type string {
           pattern "<.*>|$.*";
         }
         type uint32 {
           range "60 .. 1800";
         }
       }
     }
     list flow-server {
       key name;
       description "Configure sending traffic aggregates in cflowd format";
       max-elements 8;
       uses cflowd_instance_inet6_sampling_type;
     }
     list interface {
       key name;
       description "Interfaces used to send monitored information";
       max-elements 1;
       uses packet_export_intf_type;
     }
     container inline-jflow {
       description "Inline processing of sampled packets";
       presence "enable inline-jflow";
       uses packet_export_inline_instance;
     }
     list extension-service {
       key name;
       ordered-by user;
       description "Define the customer specific sampling configuration";
       leaf name {
         description "Customer prefixed sampling service name";
         type string {
           length "1 .. 63";
         }
       }
       uses apply-advanced;
     }
   }
   grouping cflowd_instance_inet6_sampling_type {
     leaf name {
       description "Name of host collecting cflowd packets";
       type jt:ipaddr;
     }
     uses apply-advanced;
     leaf port {
       description "UDP port number on host collecting cflowd packets";
       type union {
         type uint16;
         type string {
           pattern "<.*>|$.*";
         }
       }
     }
     leaf dscp {
       description "Numeric DSCP value in the range 0 to 63";
       default "0";
       type union {
         type string {
           pattern "<.*>|$.*";
         }
         type uint8 {
           range "0 .. 63";
         }
       }
     }
     leaf forwarding-class {
       description "Forwarding-class for exported jflow packets, applicable only for inline-jflow";
       type string {
         length "1 .. 64";
       }
     }
     leaf routing-instance {
       description "Name of routing instance on which flow collector is reachable";
       type string;
     }
     leaf autonomous-system-type {
       description "Type of autonomous system number to export";
       default "origin";
       type enumeration {
         enum "origin" {
           description "Export origin-AS numbers";
         }
         enum "peer" {
           description "Export peer-AS numbers";
         }
       }
     }
     container aggregation {
       description "Aggregations to perform for exported flows (version 8 only)";
       uses aggregation_type;
     }
     choice local-dump-choice {
       leaf local-dump {
         description "Dump cflowd records to log file before exporting";
         type empty;
       }
       leaf no-local-dump {
         description "Don't dump cflowd records to log file before exporting";
         type empty;
       }
     }
     leaf source-address {
       description "Source IPv4 address for cflowd packets";
       type jt:ipv4addr;
     }
     container version9 {
       presence "enable version9";
       description "Export data in version 9 format";
       uses apply-advanced;
       container template {
         description "Template configuration";
         uses apply-advanced;
         leaf template-name {
           description "Template name";
           type string;
         }
       }
     }
     container version-ipfix {
       presence "enable version-ipfix";
       description "Export data in version ipfix format";
       uses apply-advanced;
       container template {
         description "Template configuration";
         uses apply-advanced;
         leaf template-name {
           description "Template name";
           type string;
         }
       }
     }
   }
   grouping sampling_instance_inet_global_output_type {
     description "Configure output options for packet sampling";
     uses apply-advanced;
     leaf aggregate-export-interval {
       description "Interval of exporting aggregate accounting information";
       default "90";
       units "seconds";
       type union {
         type string {
           pattern "<.*>|$.*";
         }
         type uint32 {
           range "90 .. 1800";
         }
       }
     }
     leaf flow-inactive-timeout {
       description "Interval of inactivity that marks a flow inactive";
       default "60";
       units "seconds";
       type union {
         type string {
           pattern "<.*>|$.*";
         }
         type uint32 {
           range "15 .. 1800";
         }
       }
     }
     leaf flow-active-timeout {
       description "Interval after which an active flow is exported";
       default "1800";
       units "seconds";
       type union {
         type string {
           pattern "<.*>|$.*";
         }
         type uint32 {
           range "60 .. 1800";
         }
       }
     }
     container file {
       description "Configure parameters for dumping sampled packets";
       choice enable-disable {
         case case_1 {
           leaf disable {
             description "Disable sampled packet dumps";
             type empty;
           }
         }
       }
       leaf filename {
         description "Name of file to contain sampled packet dumps";
         type string {
           length "1 .. 1024";
         }
       }
       leaf files {
         description "Maximum number of sampled packet dump files";
         default "10";
         type union {
           type string {
             pattern "<.*>|$.*";
           }
           type uint32 {
             range "2 .. 10000";
           }
         }
       }
       leaf size {
         description "Maximum sample dump file size";
         type string;
       }
       choice world-readable-choice {
         leaf world-readable {
           description "Allow any user to read the sampled dump";
           type empty;
         }
         leaf no-world-readable {
           description "Don't allow any user to read the sampled dump";
           type empty;
         }
       }
       choice stamp-choice {
         leaf stamp {
           description "Timestamp every packet in the dump";
           type empty;
         }
         leaf no-stamp {
           description "Don't timestamp every packet in the dump";
           type empty;
         }
       }
     }
     container port-mirroring {
       description "Configure sending sampled traffic out through an interface";
       presence "enable port-mirroring";
       uses inet_pm_family_output_type;
     }
     list flow-server {
       key name;
       description "Configure sending traffic aggregates in cflowd format";
       max-elements 8;
       uses cflowd_sampling_inet_type;
     }
     list interface {
       key name;
       description "Interfaces used to send monitored information";
       max-elements 1;
       uses packet_export_intf_type;
     }
     container inline-jflow {
       description "Inline processing of sampled packets";
       presence "enable inline-jflow";
       uses packet_export_inline;
     }
     list extension-service {
       key name;
       ordered-by user;
       description "Define the customer specific sampling configuration";
       leaf name {
         description "Customer prefixed sampling service name";
         type string {
           length "1 .. 63";
         }
       }
       uses apply-advanced;
     }
   }
   grouping cflowd_sampling_inet_type {
     leaf name {
       description "Name of host collecting cflowd packets";
       type jt:ipaddr;
     }
     uses apply-advanced;
     leaf port {
       description "UDP port number on host collecting cflowd packets";
       type union {
         type uint16;
         type string {
           pattern "<.*>|$.*";
         }
       }
     }
     leaf dscp {
       description "Numeric DSCP value in the range 0 to 63";
       default "0";
       type union {
         type string {
           pattern "<.*>|$.*";
         }
         type uint8 {
           range "0 .. 63";
         }
       }
     }
     leaf forwarding-class {
       description "Forwarding-class for exported jflow packets, applicable only for inline-jflow";
       type string {
         length "1 .. 64";
       }
     }
     leaf routing-instance {
       description "Name of routing instance on which flow collector is reachable";
       type string;
     }
     leaf autonomous-system-type {
       description "Type of autonomous system number to export";
       default "origin";
       type enumeration {
         enum "origin" {
           description "Export origin-AS numbers";
         }
         enum "peer" {
           description "Export peer-AS numbers";
         }
       }
     }
     container aggregation {
       description "Aggregations to perform for exported flows (version 8 only)";
       uses aggregation_type;
     }
     choice local-dump-choice {
       leaf local-dump {
         description "Dump cflowd records to log file before exporting";
         type empty;
       }
       leaf no-local-dump {
         description "Don't dump cflowd records to log file before exporting";
         type empty;
       }
     }
     leaf source-address {
       description "Source IPv4 address for cflowd packets";
       type jt:ipv4addr;
     }
     container version9 {
       presence "enable version9";
       description "Export data in version 9 format";
       uses apply-advanced;
       container template {
         description "Template configuration";
         uses apply-advanced;
         leaf template-name {
           description "Template name";
           type string;
         }
       }
     }
     container version-ipfix {
       presence "enable version-ipfix";
       description "Export data in version ipfix format";
       status deprecated;
       uses apply-advanced;
       container template {
         description "Template configuration";
         uses apply-advanced;
         leaf template-name {
           description "Template name";
           type string;
         }
       }
     }
     leaf version {
       description "Format of exported cflowd aggregates";
       default "5";
       type enumeration {
         enum "5" {
           description "Export cflowd aggregates in version 5 format";
         }
         enum "8" {
           description "Export cflowd aggregates in version 8 format";
         }
         enum "500" {
           description "Export cflowd aggregates in ASN 500 format";
         }
       }
     }
   }
   grouping sampling_instance_inet_output_type {
     description "Configure output options for packet sampling";
     uses apply-advanced;
     leaf aggregate-export-interval {
       description "Interval of exporting aggregate accounting information";
       default "90";
       units "seconds";
       type union {
         type string {
           pattern "<.*>|$.*";
         }
         type uint32 {
           range "90 .. 1800";
         }
       }
     }
     leaf flow-inactive-timeout {
       description "Interval of inactivity that marks a flow inactive";
       default "60";
       units "seconds";
       type union {
         type string {
           pattern "<.*>|$.*";
         }
         type uint32 {
           range "15 .. 1800";
         }
       }
     }
     leaf flow-active-timeout {
       description "Interval after which an active flow is exported";
       default "1800";
       units "seconds";
       type union {
         type string {
           pattern "<.*>|$.*";
         }
         type uint32 {
           range "60 .. 1800";
         }
       }
     }
     list flow-server {
       key name;
       description "Configure sending traffic aggregates in cflowd format";
       max-elements 8;
       uses cflowd_instance_inet_sampling_type;
     }
     list interface {
       key name;
       description "Interfaces used to send monitored information";
       max-elements 1;
       uses packet_export_intf_type;
     }
     container inline-jflow {
       description "Inline processing of sampled packets";
       presence "enable inline-jflow";
       uses packet_export_inline_instance;
     }
     list extension-service {
       key name;
       ordered-by user;
       description "Define the customer specific sampling configuration";
       leaf name {
         description "Customer prefixed sampling service name";
         type string {
           length "1 .. 63";
         }
       }
       uses apply-advanced;
     }
   }
   grouping cflowd_instance_inet_sampling_type {
     leaf name {
       description "Name of host collecting cflowd packets";
       type jt:ipaddr;
     }
     uses apply-advanced;
     leaf port {
       description "UDP port number on host collecting cflowd packets";
       type union {
         type uint16;
         type string {
           pattern "<.*>|$.*";
         }
       }
     }
     leaf dscp {
       description "Numeric DSCP value in the range 0 to 63";
       default "0";
       type union {
         type string {
           pattern "<.*>|$.*";
         }
         type uint8 {
           range "0 .. 63";
         }
       }
     }
     leaf forwarding-class {
       description "Forwarding-class for exported jflow packets, applicable only for inline-jflow";
       type string {
         length "1 .. 64";
       }
     }
     leaf routing-instance {
       description "Name of routing instance on which flow collector is reachable";
       type string;
     }
     leaf autonomous-system-type {
       description "Type of autonomous system number to export";
       default "origin";
       type enumeration {
         enum "origin" {
           description "Export origin-AS numbers";
         }
         enum "peer" {
           description "Export peer-AS numbers";
         }
       }
     }
     container aggregation {
       description "Aggregations to perform for exported flows (version 8 only)";
       uses aggregation_type;
     }
     choice local-dump-choice {
       leaf local-dump {
         description "Dump cflowd records to log file before exporting";
         type empty;
       }
       leaf no-local-dump {
         description "Don't dump cflowd records to log file before exporting";
         type empty;
       }
     }
     leaf source-address {
       description "Source IPv4 address for cflowd packets";
       type jt:ipv4addr;
     }
     container version9 {
       presence "enable version9";
       description "Export data in version 9 format";
       uses apply-advanced;
       container template {
         description "Template configuration";
         uses apply-advanced;
         leaf template-name {
           description "Template name";
           type string;
         }
       }
     }
     container version-ipfix {
       presence "enable version-ipfix";
       description "Export data in version ipfix format";
       uses apply-advanced;
       container template {
         description "Template configuration";
         uses apply-advanced;
         leaf template-name {
           description "Template name";
           type string;
         }
       }
     }
     leaf version {
       description "Format of exported cflowd aggregates";
       default "5";
       type enumeration {
         enum "5" {
           description "Export cflowd aggregates in version 5 format";
         }
         enum "8" {
           description "Export cflowd aggregates in version 8 format";
         }
       }
     }
   }
   grouping sampling_instance_input_type {
     description "Configure input options for packet sampling";
     uses apply-advanced;
     leaf rate {
       description "Ratio of packets to be sampled (1 out of N)";
       type union {
         type string {
           pattern "<.*>|$.*";
         }
         type uint32;
       }
     }
     leaf run-length {
       description "Number of samples after initial trigger";
       default "0";
       type union {
         type string {
           pattern "<.*>|$.*";
         }
         type uint32 {
           range "0 .. 20";
         }
       }
     }
     leaf max-packets-per-second {
       description "Threshold of samples per second before dropping";
       default "1000";
       type union {
         type uint16;
         type string {
           pattern "<.*>|$.*";
         }
       }
     }
     leaf maximum-packet-length {
       description "Maximum length of the sampled packet";
       default "0";
       units "bytes";
       type union {
         type string {
           pattern "<.*>|$.*";
         }
         type uint32 {
           range "0 .. 9192";
         }
       }
     }
   }
   grouping sampling_instance_mpls_output_type {
     description "Configure output options for packet sampling";
     uses apply-advanced;
     leaf aggregate-export-interval {
       description "Interval of exporting aggregate accounting information";
       default "90";
       units "seconds";
       type union {
         type string {
           pattern "<.*>|$.*";
         }
         type uint32 {
           range "90 .. 1800";
         }
       }
     }
     leaf flow-inactive-timeout {
       description "Interval of inactivity that marks a flow inactive";
       default "60";
       units "seconds";
       type union {
         type string {
           pattern "<.*>|$.*";
         }
         type uint32 {
           range "15 .. 1800";
         }
       }
     }
     leaf flow-active-timeout {
       description "Interval after which an active flow is exported";
       default "1800";
       units "seconds";
       type union {
         type string {
           pattern "<.*>|$.*";
         }
         type uint32 {
           range "60 .. 1800";
         }
       }
     }
     list flow-server {
       key name;
       description "Configure sending traffic aggregates in cflowd format";
       max-elements 8;
       uses cflowd_instance_mpls_sampling_type;
     }
     list interface {
       key name;
       description "Interfaces used to send monitored information";
       max-elements 1;
       uses packet_export_intf_type;
     }
     container inline-jflow {
       description "Inline processing of sampled packets";
       presence "enable inline-jflow";
       uses packet_export_inline_instance;
     }
   }
   grouping cflowd_instance_mpls_sampling_type {
     leaf name {
       description "Name of host collecting cflowd packets";
       type jt:ipaddr;
     }
     uses apply-advanced;
     leaf port {
       description "UDP port number on host collecting cflowd packets";
       type union {
         type uint16;
         type string {
           pattern "<.*>|$.*";
         }
       }
     }
     leaf dscp {
       description "Numeric DSCP value in the range 0 to 63";
       default "0";
       type union {
         type string {
           pattern "<.*>|$.*";
         }
         type uint8 {
           range "0 .. 63";
         }
       }
     }
     leaf forwarding-class {
       description "Forwarding-class for exported jflow packets, applicable only for inline-jflow";
       type string {
         length "1 .. 64";
       }
     }
     leaf routing-instance {
       description "Name of routing instance on which flow collector is reachable";
       type string;
     }
     leaf autonomous-system-type {
       description "Type of autonomous system number to export";
       default "origin";
       type enumeration {
         enum "origin" {
           description "Export origin-AS numbers";
         }
         enum "peer" {
           description "Export peer-AS numbers";
         }
       }
     }
     container aggregation {
       description "Aggregations to perform for exported flows (version 8 only)";
       uses aggregation_type;
     }
     choice local-dump-choice {
       leaf local-dump {
         description "Dump cflowd records to log file before exporting";
         type empty;
       }
       leaf no-local-dump {
         description "Don't dump cflowd records to log file before exporting";
         type empty;
       }
     }
     leaf source-address {
       description "Source IPv4 address for cflowd packets";
       type jt:ipv4addr;
     }
     container version9 {
       presence "enable version9";
       description "Export data in version 9 format";
       uses apply-advanced;
       container template {
         description "Template configuration";
         uses apply-advanced;
         leaf template-name {
           description "Template name";
           type string;
         }
       }
     }
     container version-ipfix {
       presence "enable version-ipfix";
       description "Export data in version ipfix format";
       uses apply-advanced;
       container template {
         description "Template configuration";
         uses apply-advanced;
         leaf template-name {
           description "Template name";
           type string;
         }
       }
     }
   }
   grouping sampling_instance_vpls_output_type {
     description "Configure output options for packet sampling";
     uses apply-advanced;
     list flow-server {
       key name;
       description "Configure sending traffic aggregates in cflowd format";
       max-elements 8;
       uses cflowd_instance_vpls_sampling_type;
     }
     container inline-jflow {
       description "Inline processing of sampled packets";
       presence "enable inline-jflow";
       uses packet_export_inline_instance;
     }
   }
   grouping cflowd_instance_vpls_sampling_type {
     leaf name {
       description "Name of host collecting cflowd packets";
       type jt:ipaddr;
     }
     uses apply-advanced;
     leaf port {
       description "UDP port number on host collecting cflowd packets";
       type union {
         type uint16;
         type string {
           pattern "<.*>|$.*";
         }
       }
     }
     leaf dscp {
       description "Numeric DSCP value in the range 0 to 63";
       default "0";
       type union {
         type string {
           pattern "<.*>|$.*";
         }
         type uint8 {
           range "0 .. 63";
         }
       }
     }
     leaf forwarding-class {
       description "Forwarding-class for exported jflow packets, applicable only for inline-jflow";
       type string {
         length "1 .. 64";
       }
     }
     leaf routing-instance {
       description "Name of routing instance on which flow collector is reachable";
       type string;
     }
     container version9 {
       presence "enable version9";
       description "Export data in version 9 format";
       uses apply-advanced;
       container template {
         description "Template configuration";
         uses apply-advanced;
         leaf template-name {
           description "Template name";
           type string;
         }
       }
     }
     container version-ipfix {
       presence "enable version-ipfix";
       description "Export data in version ipfix format";
       uses apply-advanced;
       container template {
         description "Template configuration";
         uses apply-advanced;
         leaf template-name {
           description "Template name";
           type string;
         }
       }
     }
   }
   grouping sampling_output_type {
     description "Configure output options for packet sampling";
     uses apply-advanced;
     leaf aggregate-export-interval {
       description "Interval of exporting aggregate accounting information";
       default "90";
       units "seconds";
       type union {
         type string {
           pattern "<.*>|$.*";
         }
         type uint32 {
           range "90 .. 1800";
         }
       }
     }
     leaf flow-inactive-timeout {
       description "Interval of inactivity that marks a flow inactive";
       default "60";
       units "seconds";
       type union {
         type string {
           pattern "<.*>|$.*";
         }
         type uint32 {
           range "15 .. 1800";
         }
       }
     }
     leaf flow-active-timeout {
       description "Interval after which an active flow is exported";
       default "1800";
       units "seconds";
       type union {
         type string {
           pattern "<.*>|$.*";
         }
         type uint32 {
           range "60 .. 1800";
         }
       }
     }
     container file {
       description "Configure parameters for dumping sampled packets";
       choice enable-disable {
         case case_1 {
           leaf disable {
             description "Disable sampled packet dumps";
             type empty;
           }
         }
       }
       leaf filename {
         description "Name of file to contain sampled packet dumps";
         type string {
           length "1 .. 1024";
         }
       }
       leaf files {
         description "Maximum number of sampled packet dump files";
         default "10";
         type union {
           type string {
             pattern "<.*>|$.*";
           }
           type uint32 {
             range "2 .. 10000";
           }
         }
       }
       leaf size {
         description "Maximum sample dump file size";
         type string;
       }
       choice world-readable-choice {
         leaf world-readable {
           description "Allow any user to read the sampled dump";
           type empty;
         }
         leaf no-world-readable {
           description "Don't allow any user to read the sampled dump";
           type empty;
         }
       }
       choice stamp-choice {
         leaf stamp {
           description "Timestamp every packet in the dump";
           type empty;
         }
         leaf no-stamp {
           description "Don't timestamp every packet in the dump";
           type empty;
         }
       }
     }
     container port-mirroring {
       description "Configure sending sampled traffic out through an interface";
       presence "enable port-mirroring";
       uses inet_pm_family_output_type;
     }
     list flow-server {
       key name;
       description "Configure sending traffic aggregates in cflowd format";
       max-elements 8;
       uses cflowd_sampling_type;
     }
     list interface {
       key name;
       description "Interfaces used to send monitored information";
       max-elements 1;
       uses packet_export_intf_type;
     }
     container inline-jflow {
       description "Inline processing of sampled packets";
       presence "enable inline-jflow";
       uses packet_export_inline;
     }
     list extension-service {
       key name;
       ordered-by user;
       description "Define the customer specific sampling configuration";
       leaf name {
         description "Customer prefixed sampling service name";
         type string {
           length "1 .. 63";
         }
       }
       uses apply-advanced;
     }
   }
   grouping cflowd_sampling_type {
     leaf name {
       description "Name of host collecting cflowd packets";
       type jt:ipaddr;
     }
     uses apply-advanced;
     leaf port {
       description "UDP port number on host collecting cflowd packets";
       type union {
         type uint16;
         type string {
           pattern "<.*>|$.*";
         }
       }
     }
     leaf dscp {
       description "Numeric DSCP value in the range 0 to 63";
       default "0";
       type union {
         type string {
           pattern "<.*>|$.*";
         }
         type uint8 {
           range "0 .. 63";
         }
       }
     }
     leaf forwarding-class {
       description "Forwarding-class for exported jflow packets, applicable only for inline-jflow";
       type string {
         length "1 .. 64";
       }
     }
     leaf routing-instance {
       description "Name of routing instance on which flow collector is reachable";
       type string;
     }
     leaf autonomous-system-type {
       description "Type of autonomous system number to export";
       default "origin";
       type enumeration {
         enum "origin" {
           description "Export origin-AS numbers";
         }
         enum "peer" {
           description "Export peer-AS numbers";
         }
       }
     }
     container aggregation {
       description "Aggregations to perform for exported flows (version 8 only)";
       uses aggregation_type;
     }
     choice local-dump-choice {
       leaf local-dump {
         description "Dump cflowd records to log file before exporting";
         type empty;
       }
       leaf no-local-dump {
         description "Don't dump cflowd records to log file before exporting";
         type empty;
       }
     }
     leaf source-address {
       description "Source IPv4 address for cflowd packets";
       type jt:ipv4addr;
     }
     container version9 {
       presence "enable version9";
       description "Export data in version 9 format";
       uses apply-advanced;
       container template {
         description "Template configuration";
         uses apply-advanced;
         leaf template-name {
           description "Template name";
           type string;
         }
       }
     }
     container version-ipfix {
       presence "enable version-ipfix";
       description "Export data in version ipfix format";
       status deprecated;
       uses apply-advanced;
       container template {
         description "Template configuration";
         uses apply-advanced;
         leaf template-name {
           description "Template name";
           type string;
         }
       }
     }
     leaf version {
       description "Format of exported cflowd aggregates";
       default "5";
       type enumeration {
         enum "5" {
           description "Export cflowd aggregates in version 5 format";
         }
         enum "8" {
           description "Export cflowd aggregates in version 8 format";
         }
         enum "500" {
           description "Export cflowd aggregates in ASN 500 format";
         }
       }
     }
   }
   grouping sampling_traceoptions_type {
     description "Configure packet sampling traceoptions";
     uses apply-advanced;
     leaf no-remote-trace {
       description "Disable remote tracing";
       type empty;
     }
     container file {
       description "Trace file information";
       leaf filename {
         description "Name of file in which to write trace information";
         type string {
           length "1 .. 1024";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
   }
   grouping server-group-type {
     uses apply-advanced;
     list server-group {
       key name;
       description "One or more server groups";
       leaf name {
         description "Server group name";
         type string {
           length "1 .. 64";
         }
       }
       uses apply-advanced;
       list address {
         key name;
         description "IP Address of one or more DHCP servers";
         max-elements 32;
         leaf name {
           description "IP Address of DHCP server";
           type jt:ipaddr;
         }
         uses apply-advanced;
       }
     }
   }
   grouping server-match-action-choice {
     uses apply-advanced;
     choice v4-action-choice {
       case case_1 {
         leaf forward-only {
           description "Forward without subscriber services";
           type empty;
         }
       }
       case case_2 {
         leaf create-relay-entry {
           description "Create relay entry and allow subscriber services";
           type empty;
         }
       }
     }
   }
   grouping server-match-v6-ascii-hex {
     uses apply-advanced;
     list ascii {
       key name;
       description "ASCII string";
       leaf name {
         description "ASCII string";
         type string {
           length "1 .. 256";
         }
       }
       uses apply-advanced;
       choice server-match-action-choice {
         case case_1 {
           leaf forward-only {
             description "Forward without subscriber services when a match is made";
             type empty;
           }
         }
         case case_2 {
           leaf create-relay-entry {
             description "Create relay entry and allow subscriber services";
             type empty;
           }
         }
       }
     }
     list hexadecimal {
       key name;
       description "Hexadecimal string";
       leaf name {
         description "Hexadecimal string";
         type string {
           length "1 .. 512";
         }
       }
       uses apply-advanced;
       choice server-match-action-choice {
         case case_1 {
           leaf forward-only {
             description "Forward without subscriber services when a match is made";
             type empty;
           }
         }
         case case_2 {
           leaf create-relay-entry {
             description "Create relay entry and allow subscriber services";
             type empty;
           }
         }
       }
     }
   }
   grouping slaacd-config-type {
     description "Slaacd configuration options";
     uses apply-advanced;
     container vlans {
       description "Slaac config on vlan";
       uses apply-advanced;
       list vlan-config {
         key name;
         description "Virtual LAN configuration";
         uses vlan-slaacd;
       }
     }
     container interface {
       description "Slaac config on interface";
       uses apply-advanced;
       list intf-config {
         key name;
         description "Interface configuration";
         uses slaacd-interface;
       }
     }
     container link-local-expiry-interval {
       description "Link local address expiry interval";
       uses apply-advanced;
       leaf interval {
         description "Expiry interval";
         default "86400";
         units "seconds";
         type union {
           type string {
             pattern "<.*>|$.*";
           }
           type uint32 {
             range "60 .. 86400";
           }
         }
       }
     }
     container traceoptions {
       description "Slaac Snooping trace options";
       uses apply-advanced;
       leaf no-remote-trace {
         description "Disable remote tracing";
         type empty;
       }
       container file {
         description "Trace file information";
         leaf filename {
           description "Name of file in which to write trace information";
           type string {
             length "1 .. 1024";
           }
         }
         leaf size {
           description "Maximum trace file size";
           type string;
         }
         leaf files {
           description "Maximum number of trace files";
           default "3";
           type union {
             type string {
               pattern "<.*>|$.*";
             }
             type uint32 {
               range "2 .. 1000";
             }
           }
         }
         choice world-readable-choice {
           leaf world-readable {
             description "Allow any user to read the log file";
             type empty;
           }
           leaf no-world-readable {
             description "Don't allow any user to read the log file";
             type empty;
           }
         }
         leaf match {
           description "Regular expression for lines to be logged";
           type jt:regular-expression;
         }
       }
       list flag {
         key name;
         description "Tracing parameters";
         leaf name {
           type enumeration {
             enum "configuration" {
               description "Log configuration events";
             }
             enum "init" {
               description "Trace init message events";
             }
             enum "state" {
               description "Trace state message events";
             }
             enum "rtsock" {
               description "Trace rtsock message events";
             }
             enum "packet" {
               description "Trace packet events";
             }
             enum "fsm" {
               description "Trace fsm update events";
             }
             enum "io" {
               description "Trace io events";
             }
             enum "verbose" {
               description "Trace verbose events";
             }
             enum "task" {
               description "Trace TASK related events";
             }
             enum "all" {
               description "Trace all events";
             }
           }
         }
       }
     }
   }
   grouping slaacd-interface {
     description "Interface name";
     leaf name {
       description "Interface name";
       type string;
     }
     uses apply-advanced;
     container mark-interface {
       description "Mark interface";
       uses apply-advanced;
       leaf trusted {
         description "Mark interface trusted";
         type empty;
       }
     }
     container max-allowed-contention {
       description "Maximum allowed contention count(will be valid only for un-trusted ports)";
       uses apply-advanced;
       leaf count {
         description "Contention count";
         type union {
           type string {
             pattern "<.*>|$.*";
           }
           type uint16 {
             range "1 .. 10";
           }
         }
       }
       leaf duration {
         description "Contention duration";
         units "seconds";
         type union {
           type string {
             pattern "<.*>|$.*";
           }
           type uint16 {
             range "60 .. 3600";
           }
         }
       }
     }
     container auto-dad {
       description "Auto duplicate address detection";
       uses apply-advanced;
       leaf retries {
         description "DAD retry value";
         default "1";
         type union {
           type string {
             pattern "<.*>|$.*";
           }
           type uint16 {
             range "1 .. 3";
           }
         }
       }
       leaf retrans-interval {
         description "DAD re-transmission interval";
         default "1";
         units "seconds";
         type union {
           type string {
             pattern "<.*>|$.*";
           }
           type uint16 {
             range "1 .. 6";
           }
         }
       }
     }
   }
   grouping smpl-analyzer-type {
     leaf name {
       description "Analyzer name";
       type string {
         length "1 .. 63";
       }
     }
     uses apply-advanced;
     container input {
       description "Ports and VLANs to monitor";
       uses smpl-analyzer-input-type;
     }
     container output {
       description "Outgoing port or VLAN for mirrored packets";
       uses smpl-analyzer-output-type;
     }
   }
   grouping smpl-analyzer-input-type {
     uses apply-advanced;
     leaf rate {
       description "Ratio of packets to be sampled (1 out of N)";
       type union {
         type string {
           pattern "<.*>|$.*";
         }
         type uint32 {
           range "1 .. 65535";
         }
       }
     }
     leaf maximum-packet-length {
       description "Maximum length of the mirrored packet";
       units "bytes";
       type union {
         type string {
           pattern "<.*>|$.*";
         }
         type uint32 {
           range "0 .. 9216";
         }
       }
     }
     container ingress {
       description "Ports and VLANs to monitor incoming traffic";
       uses smpl-analyzer-ingress-type;
     }
     container egress {
       description "Ports and VLANs to monitor outgoing traffic";
       uses smpl-analyzer-egress-type;
     }
   }
   grouping smpl-analyzer-egress-type {
     uses apply-advanced;
     list interface {
       key name;
       ordered-by user;
       description "Port to monitor outgoing traffic";
       uses analyzer-egress-interface-type;
     }
     list routing-instance {
       key name;
       description "Routing instances";
       uses analyzer-egress-routing-instance-type;
     }
     list vlan {
       key name;
       ordered-by user;
       description "VLAN to monitor outgoing traffic";
       uses analyzer-egress-vlan-type;
     }
   }
   grouping analyzer-egress-interface-type {
     leaf name {
       description "Logical interface name";
       type string;
     }
     uses apply-advanced;
   }
   grouping analyzer-egress-routing-instance-type {
     leaf name {
       description "Routing instance name";
       type string {
       }
     }
     uses apply-advanced;
     list vlan {
       key name;
       ordered-by user;
       description "VLAN to monitor outgoing traffic";
       uses analyzer-egress-vlan-type;
     }
   }
   grouping analyzer-egress-vlan-type {
     leaf name {
       description "VLAN name, VLAN id or VLAN range string";
       type string;
     }
     uses apply-advanced;
   }
   grouping smpl-analyzer-ingress-type {
     uses apply-advanced;
     list interface {
       key name;
       ordered-by user;
       description "Port to monitor incoming traffic";
       uses analyzer-ingress-interface-type;
     }
     list routing-instance {
       key name;
       description "Routing instances";
       uses analyzer-ingress-routing-instance-type;
     }
     list vlan {
       key name;
       ordered-by user;
       description "VLAN to monitor incoming traffic";
       uses analyzer-ingress-vlan-type;
     }
   }
   grouping analyzer-ingress-interface-type {
     leaf name {
       description "Logical interface name";
       type string;
     }
     uses apply-advanced;
   }
   grouping analyzer-ingress-routing-instance-type {
     leaf name {
       description "Routing instance name";
       type string {
       }
     }
     uses apply-advanced;
     list vlan {
       key name;
       ordered-by user;
       description "VLAN to monitor incoming traffic";
       uses analyzer-ingress-vlan-type;
     }
   }
   grouping analyzer-ingress-vlan-type {
     leaf name {
       description "VLAN name, VLAN id or VLAN range string";
       type string;
     }
     uses apply-advanced;
   }
   grouping smpl-analyzer-output-type {
     uses apply-advanced;
     choice interface_or_vlan {
       case case_1 {
         leaf interface {
           description "Outgoing port for mirrored packets";
           type union {
             type jt:interface-name;
             type string {
               pattern "<.*>|$.*";
             }
           }
         }
       }
       case case_2 {
         leaf ip-address {
           description "ERSPAN Destination IP Address";
           type jt:ipv4addr;
         }
       }
       case case_3 {
         leaf ipv6-address {
           description "ERSPAN Destination IPv6 Address";
           type jt:ipv6addr;
         }
       }
       case case_4 {
         leaf next-hop-group {
           description "Next-hop-group through which to send port-mirror traffic";
           type string;
         }
       }
       case case_5 {
         list routing-instance {
           key name;
           description "Routing instances";
           max-elements 1;
           uses output-routing-instance-type;
         }
       }
       case case_6 {
         list vlan {
           key name;
           description "Outgoing VLAN for mirrored packets";
           max-elements 1;
           uses pm-rspan-vlan;
         }
       }
       case case_7 {
       }
     }
     leaf source-ip-address {
       description "ERSPAN source IP address";
       type jt:ipv4addr;
     }
     leaf source-ipv6-address {
       description "ERSPAN source IPv6 address";
       type jt:ipv6addr;
     }
     leaf dscp {
       description "DSCP value from 0-63";
       default "0";
       type union {
         type string {
           pattern "<.*>|$.*";
         }
         type uint32 {
           range "0 .. 63";
         }
       }
     }
     leaf forwarding-class {
       description "Forwarding-class for TOS";
       type string {
         length "1 .. 64";
       }
     }
   }
   grouping output-routing-instance-type {
     leaf name {
       description "Routing instance name";
       type string {
       }
     }
     uses apply-advanced;
     choice ipaddr_or_vlan {
       case case_1 {
         leaf ip-address {
           description "ERSPAN Destination IP Address";
           type jt:ipv4addr;
         }
       }
       case case_2 {
         leaf ipv6-address {
           description "ERSPAN Destination IPv6 Address";
           type jt:ipv6addr;
         }
       }
       case case_3 {
         list vlan {
           key name;
           description "Outgoing VLAN for mirrored packets";
           max-elements 1;
           uses pm-rspan-vlan;
         }
       }
       case case_4 {
       }
     }
     leaf source-ip-address {
       description "ERSPAN source IP address";
       type jt:ipv4addr;
     }
     leaf source-ipv6-address {
       description "ERSPAN source IPv6 address";
       type jt:ipv6addr;
     }
     leaf dscp {
       description "DSCP value from 0-63";
       default "0";
       type union {
         type string {
           pattern "<.*>|$.*";
         }
         type uint32 {
           range "0 .. 63";
         }
       }
     }
   }
   grouping v6-relay-option-interface-id-type {
     description "Interface ID processing";
     uses apply-advanced;
     container prefix {
       description "Add prefix to circuit/interface-id or remote-id";
       uses apply-advanced;
       leaf host-name {
         description "Add router host name to circuit / interface-id or remote-id";
         type empty;
       }
       leaf logical-system-name {
         description "Add logical system name to circuit / interface-id or remote-id";
         type empty;
       }
       leaf routing-instance-name {
         description "Add routing instance name to circuit / interface-id or remote-id";
         type empty;
       }
     }
     leaf use-interface-description {
       description "Use interface description instead of circuit identifier";
       type enumeration {
         enum "logical" {
           description "Use the logical interface description";
         }
         enum "device" {
           description "Use the device interface description";
         }
       }
     }
     leaf use-vlan-id {
       description "Use VLAN id instead of name";
       type empty;
     }
     leaf no-vlan-interface-name {
       description "Not include vlan or interface name";
       type empty;
     }
     leaf include-irb-and-l2 {
       description "Include IRB and L2 interface name";
       type empty;
     }
     container user-defined {
       presence "enable user-defined";
       description "Include user defined string";
       uses apply-advanced;
       leaf string {
         description "Set user-defined character string description";
         type string {
           length "1 .. 252";
         }
       }
       leaf hex-string {
         description "Set user-defined hexadecimal string description";
         type string {
           length "1 .. 510";
         }
       }
     }
     container use-option-82 {
       description "Use option-82 circuit-id for interface-id";
       presence "enable use-option-82";
       uses v6-relay-option-cid-rid-action;
     }
     container keep-incoming-interface-id {
       description "Keep incoming interface identifier";
       presence "enable keep-incoming-interface-id";
       uses v6-relay-option-cid-rid-action;
     }
   }
   grouping v6-relay-option-cid-rid-action {
     uses apply-advanced;
     leaf strict {
       description "Drop packet if id not present";
       type empty;
     }
   }
   grouping v6-relay-option-remote-id-type {
     description "Remote ID processing";
     uses apply-advanced;
     container prefix {
       description "Add prefix to circuit/interface-id or remote-id";
       uses apply-advanced;
       leaf host-name {
         description "Add router host name to circuit / interface-id or remote-id";
         type empty;
       }
       leaf logical-system-name {
         description "Add logical system name to circuit / interface-id or remote-id";
         type empty;
       }
       leaf routing-instance-name {
         description "Add routing instance name to circuit / interface-id or remote-id";
         type empty;
       }
     }
     leaf use-interface-description {
       description "Use interface description instead of circuit identifier";
       type enumeration {
         enum "logical" {
           description "Use the logical interface description";
         }
         enum "device" {
           description "Use the device interface description";
         }
       }
     }
     leaf use-vlan-id {
       description "Use VLAN id instead of name";
       type empty;
     }
     leaf no-vlan-interface-name {
       description "Not include vlan or interface name";
       type empty;
     }
     leaf include-irb-and-l2 {
       description "Include IRB and L2 interface name";
       type empty;
     }
     container user-defined {
       presence "enable user-defined";
       description "Include user defined string";
       uses apply-advanced;
       leaf string {
         description "Set user-defined character string description";
         type string {
           length "1 .. 252";
         }
       }
       leaf hex-string {
         description "Set user-defined hexadecimal string description";
         type string {
           length "1 .. 510";
         }
       }
     }
     container use-option-82 {
       description "Use option-82 remote-id for v6 remote-id";
       presence "enable use-option-82";
       uses v6-relay-option-cid-rid-action;
     }
     leaf keep-incoming-remote-id {
       description "Keep incoming remote identifier";
       type empty;
     }
   }
   grouping v6-server-group-type {
     uses apply-advanced;
     list server-group {
       key name;
       description "One or more server groups";
       leaf name {
         description "DHCPv6 Server group name";
         type string {
           length "1 .. 64";
         }
       }
       uses apply-advanced;
       list address {
         key name;
         description "IP Address of one or more DHCP servers";
         max-elements 32;
         leaf name {
           description "IP Address of DHCP server";
           type jt:ipaddr;
         }
         uses apply-advanced;
       }
     }
   }
   grouping vlan-policy {
     description "Virtual LAN";
     leaf name {
       description "VLAN id";
       type string;
     }
     uses apply-advanced;
     container policy {
       description "Attach policy";
       uses apply-advanced;
       leaf policy-name {
         description "Router Advertisement Guard policy name";
         type string;
       }
       choice policy-type {
         case case_1 {
           leaf stateful {
             description "Stateful router advertisement guard";
             type empty;
           }
         }
         case case_2 {
           leaf stateless {
             description "Stateless router advertisement guard";
             type empty;
           }
         }
       }
     }
   }
   grouping vlan-slaacd {
     description "Virtual LAN";
     leaf name {
       description "VLAN id";
       type string;
     }
     uses apply-advanced;
   }
   grouping write-option-82-type {
     uses apply-advanced;
   }
 }
