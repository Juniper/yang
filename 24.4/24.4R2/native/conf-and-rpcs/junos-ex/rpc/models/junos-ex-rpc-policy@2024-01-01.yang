/*
 * Copyright (c) 2025 Juniper Networks, Inc.
 * All rights reserved.
 */
 module junos-ex-rpc-policy {
   namespace "http://yang.juniper.net/junos-ex/rpc/policy";

   prefix policy;

   import junos-common-types {
     prefix jt;
     revision-date 2024-01-01;
   }

   organization "Juniper Networks, Inc.";

   contact "yang-support@juniper.net";

   description "Junos RPC YANG module for policy command(s)";

   revision 2024-01-01 {
     description "Junos: 24.4R2.25";
   }

   rpc get-policy-information {
     description "Show policy information";
     input {
       choice daemon-select {
         case logical-system {
           leaf logical-system {
             description "Name of logical system, or 'all'";
             type string {
             }
           }
         }
         case rib-sharding {
           leaf rib-sharding {
             description "Name of rib shard";
             type string {
             }
           }
         }
       }
       leaf policy {
         description "Name of policy";
         type string;
       }
       leaf statistics {
         description "Statistics for policy";
         type empty;
       }
     }
     output {
       container policy-information {
         uses policy-information-block;
       }
     }
   }
   grouping command-forwarding {
     leaf no-forwarding {
       description "No forwarding";
       type empty;
     }
     choice chassis-selector {
       case case_1 {
         leaf all-chassis {
           description "All chassis";
           type empty;
         }
       }
       case case_2 {
         leaf all-lcc {
           description "All LCC chassis";
           type empty;
         }
       }
       case case_3 {
         leaf scc {
           description "SCC";
           type empty;
         }
       }
       case case_4 {
         leaf sfc {
           description "SFC";
           type union {
             type string {
               pattern "<.*>|$.*";
             }
             type uint32;
           }
         }
       }
       case case_5 {
         leaf lcc {
           description "Specific LCC";
           type union {
             type string {
               pattern "<.*>|$.*";
             }
             type uint32;
           }
         }
       }
       case case_6 {
         leaf node {
           description "Specific node";
           type string;
         }
       }
       case case_7 {
         leaf bsys {
           description "Base system";
           type empty;
         }
       }
       case case_8 {
         leaf gnf {
           description "Specific guest network function";
           type union {
             type string {
               pattern "<.*>|$.*";
             }
             type uint32 {
               range "1 .. 10";
             }
           }
         }
       }
       case case_9 {
         leaf all-gnfs {
           description "All guest network functions";
           type empty;
         }
       }
       case case_10 {
         leaf all-system {
           description "All system (BSYS and GNFs)";
           type empty;
         }
       }
       case case_11 {
         leaf server {
           description "Specific server slot";
           type union {
             type string {
               pattern "<.*>|$.*";
             }
             type uint32 {
               range "0 .. 1";
             }
           }
         }
       }
       case case_12 {
         leaf all-servers {
           description "All servers";
           type empty;
         }
       }
       case case_13 {
         leaf vnf {
           description "Specific virtual-network-function";
           type string;
         }
       }
       case case_14 {
         leaf all-vnfs {
           description "All virtual-network-functions";
           type empty;
         }
       }
     }
     choice re-selector {
       case case_1 {
         leaf re0 {
           description "RE0";
           type empty;
         }
       }
       case case_2 {
         leaf re1 {
           description "RE1";
           type empty;
         }
       }
       case case_3 {
         leaf routing-engine {
           description "Specific routing engine";
           type enumeration {
             enum "local" {
               description "Local routing engine";
             }
             enum "other" {
               description "Other routing engine";
             }
             enum "master" {
               description "Master routing engine";
             }
             enum "backup" {
               description "Backup routing engine";
             }
             enum "both" {
               description "Both routing engines";
             }
           }
         }
       }
     }
     choice lr-selector {
       case case_1 {
         leaf logical-system {
           description "Name of logical system, or 'all'";
           type string;
         }
       }
     }
     choice tenant-selector {
       case case_1 {
         leaf tenant {
           description "Name of tenant, or 'all'";
           type string;
         }
       }
     }
     choice vc-selector {
       case case_1 {
         leaf local {
           description "Local virtual chassis member";
           type empty;
         }
       }
       case case_2 {
         leaf all-members {
           description "All virtual chassis members";
           type empty;
         }
       }
       case case_3 {
         leaf member {
           description "Specific virtual chassis member which is master";
           type union {
             type string {
               pattern "<.*>|$.*";
             }
             type uint32;
           }
         }
       }
     }
   }
   grouping policy-information-block {
     leaf evpn-default-vs-rt {
       type string;
       description "EVPN Deafult virtual switch route as info";
     }
     list policy {
       leaf policy-name {
         type string;
         description "Name of the policy";
       }
       leaf policy-name-stat {
         type string;
         description "Policy statistics";
       }
       leaf orhigher {
         type empty;
       }
       leaf orlower {
         type empty;
       }
       leaf equal {
         type empty;
       }
       leaf aggregate-contributor-stat {
         type string;
         description "Aggregate contributor statistics";
       }
       leaf aggregate-contributor {
         type empty;
         description "Match more specifics of an aggregate";
       }
       leaf area-stat {
         type string;
         description "Area statistics";
       }
       leaf area {
         type uint32;
         description "OSPF area identifier";
       }
       leaf as-list {
         type string;
         description "AS list name";
       }
       leaf as-list-group {
         type string;
         description "AS list group name";
       }
       leaf as-path-stat {
         type string;
         description "AS path statistics";
       }
       leaf as-path {
         type string;
         description "Name of AS path regular expression (BGP only)";
       }
       leaf as-path-group-stat {
         type string;
         description "AS path group statistics";
       }
       leaf as-path-group {
         type string;
         description "Name of AS path group (BGP only)";
       }
       leaf bgp-srte-discriminator-stat {
         type string;
         description "BGP SRTE discriminator statistics";
       }
       leaf bgp-srte-discriminator {
         type uint32;
         description "SRTE discriminator";
       }
       leaf bridge-domain-id {
         type uint32;
         description "Bridge Domain ID";
       }
       leaf bridge-domain-id-stat {
         type string;
         description "Bridge domain id statistics";
       }
       leaf color-stat {
         type string;
         description "Color statistics";
       }
       leaf color1 {
         type uint32;
         description "Color1";
       }
       leaf color2-stat {
         type string;
         description "Color2 statistics";
       }
       leaf color2 {
         type int32;
       }
       leaf color3-stat {
         type string;
         description "Color3 statistics";
       }
       leaf color3 {
         type uint32;
         description "Color 3";
       }
       leaf color4-stat {
         type string;
         description "Color4 statistics";
       }
       leaf color4 {
         type uint32;
         description "Color 4";
       }
       leaf community-stat {
         type string;
         description "Community statistics";
       }
       leaf-list community {
         type string;
         description "Basic community";
       }
       leaf condition-stat {
         type string;
         description "Condition statistics";
       }
       leaf condition {
         type string;
         description "Condition to match on";
       }
       leaf evpn-esi-stat {
         type string;
         description "EVPN esi statistics";
       }
       leaf evpn-mac-route-stat {
         type string;
         description "EVPN mac route statistics";
       }
       leaf evpn-mac-route {
         type uint32;
         description "EVPN Mac Route type";
       }
       leaf evpn-tag-stat {
         type string;
         description "EVPN tag statistics";
       }
       leaf evpn-tag {
         type uint32;
         description "Tag in EVPN Route";
       }
       leaf family-stat {
         type string;
       }
       leaf family {
         type string;
       }
       leaf instance-stat {
         type string;
         description "Instance statistics";
       }
       leaf instance-any-stat {
         type string;
         description "Instance any statistics";
       }
       leaf instance-any {
         type empty;
         description "Any routing protocol instance";
       }
       leaf instance-list-stat {
         type string;
         description "Instance list statistics";
       }
       leaf instance-list {
         type string;
         description "A list of routing protocol instances";
       }
       leaf interface-stat {
         type string;
         description "Interface statistics";
       }
       leaf policy-level-stat {
         type string;
         description "Level statistics";
       }
       leaf policy-level {
         type uint32;
       }
       leaf policy-local-preference-stat {
         type string;
         description "Local preference statistics";
       }
       leaf policy-local-preference {
         type uint32;
         description "Local preference associated with a route";
       }
       leaf lsp-stat {
         type string;
         description "LSP statistics";
       }
       leaf lsp {
         type string;
         description "Label switched path name";
       }
       leaf lsp-regex-stat {
         type string;
         description "LSP regex statistics";
       }
       leaf lsp-regex {
         type string;
         description "Label switched path name regular expression";
       }
       leaf mac-filter-list-stat {
         type string;
         description "MAC filter list statistics";
       }
       leaf mac-filter-list {
         type string;
         description "List of mac-filter-list macs to match";
       }
       leaf metric-stat {
         type string;
         description "Metric statistics";
       }
       leaf metric1 {
         type uint32;
         description "Metric value";
       }
       leaf metric2-stat {
         type string;
         description "Metric2 statistics";
       }
       leaf metric-2 {
         type uint32;
         description "Metric value 2";
       }
       leaf metric3-stat {
         type string;
         description "Metric3 statistics";
       }
       leaf metric3 {
         type uint32;
         description "Metric value 3";
       }
       leaf metric4-stat {
         type string;
         description "Metric4 statistics";
       }
       leaf metric4 {
         type uint32;
         description "Metric value 4";
       }
       leaf metric5-stat {
         type string;
         description "Metric5 statistics";
       }
       leaf metric5 {
         type uint32;
         description "Metric value 5";
       }
       leaf metric6-stat {
         type string;
         description "Metric6 statistics";
       }
       leaf metric6 {
         type uint32;
         description "Metric value 6";
       }
       leaf metric7-stat {
         type string;
         description "Metric7 statistics";
       }
       leaf metric7 {
         type uint32;
         description "Metric value 7";
       }
       leaf metric8-stat {
         type string;
         description "Metric8 statistics";
       }
       leaf metric8 {
         type uint32;
         description "Metric value 8";
       }
       leaf metric9-stat {
         type string;
         description "Metric9 statistics";
       }
       leaf metric9 {
         type uint32;
         description "Metric value 9";
       }
       leaf metric10-stat {
         type string;
         description "Metric10 statistics";
       }
       leaf metric10 {
         type uint32;
         description "Metric value 10";
       }
       leaf metric11-stat {
         type string;
         description "Metric11 statistics";
       }
       leaf metric11 {
         type uint32;
         description "Metric value 11";
       }
       leaf metric12-stat {
         type string;
         description "Metric12 statistics";
       }
       leaf metric12 {
         type uint32;
         description "Metric value 12";
       }
       leaf link-local-stat {
         type string;
         description "Link local statistics";
       }
       leaf link-local {
         type empty;
       }
       leaf node-local-stat {
         type string;
         description "Node local statistics";
       }
       leaf node-local {
         type empty;
       }
       leaf organization-local-stat {
         type string;
         description "Organization local statistics";
       }
       leaf organization-local {
         type empty;
       }
       leaf site-local-stat {
         type string;
         description "Site local statistics";
       }
       leaf site-local {
         type empty;
       }
       leaf policy-neighbor-stat {
         type string;
         description "Policy neighbor statistics";
       }
       leaf policy-neighbor {
         type string;
         description "Neighboring router";
       }
       leaf next-hop-stat {
         type string;
         description "Nexthop statistics";
       }
       leaf next-hop {
         type jt:ipaddr;
         description "Next-hop address";
       }
       leaf next-hop-type-stat {
         type string;
         description "Nexthop type statistics";
       }
       leaf next-hop-type {
         type string;
         description "Next-hop type";
       }
       leaf next-hop-weight-stat {
         type string;
         description "Nexthop weight statistics";
       }
       leaf next-hop-ecmp-stat {
         type string;
         description "Nexthop ecmp statistics";
       }
       leaf nlri-route-type-stat {
         type string;
         description "NLRI route type statistics";
       }
       leaf nlri-route-type {
         type uint32;
         description "Route type from NLRI (1..10)";
       }
       leaf origin-stat {
         type string;
         description "Origin statistics";
       }
       leaf origin {
         type string;
         description "BGP origin attribute";
       }
       leaf preference-stat {
         type string;
         description "Preference statistics";
       }
       leaf preference1 {
         type uint32;
       }
       leaf preference2-stat {
         type string;
         description "Preference2 statistics";
       }
       leaf preference-2 {
         type uint32;
         description "Preference value 2";
       }
       leaf preference3-stat {
         type string;
         description "Preference3 statistics";
       }
       leaf preference3 {
         type uint32;
         description "Preference value 3";
       }
       leaf preference4-stat {
         type string;
         description "Preference4 statistics";
       }
       leaf preference4 {
         type uint32;
         description "Preference value 4";
       }
       leaf preference5-stat {
         type string;
         description "Preference5 statistics";
       }
       leaf preference5 {
         type uint32;
         description "Preference value 5";
       }
       leaf preference6-stat {
         type string;
         description "Preference6 statistics";
       }
       leaf preference6 {
         type uint32;
         description "Preference value 6";
       }
       leaf preference7-stat {
         type string;
         description "Preference7 statistics";
       }
       leaf preference7 {
         type uint32;
         description "Preference value 7";
       }
       leaf preference8-stat {
         type string;
         description "Preference8 statistics";
       }
       leaf preference8 {
         type uint32;
         description "Preference value 8";
       }
       leaf preference9-stat {
         type string;
         description "Preference9 statistics";
       }
       leaf preference9 {
         type uint32;
         description "Preference value 9";
       }
       leaf preference10-stat {
         type string;
         description "Preference10 statistics";
       }
       leaf preference10 {
         type uint32;
         description "Preference value 10";
       }
       leaf preference11-stat {
         type string;
         description "Preference11 statistics";
       }
       leaf preference11 {
         type uint32;
         description "Preference value 11";
       }
       leaf preference12-stat {
         type string;
         description "Preference12 statistics";
       }
       leaf preference12 {
         type uint32;
         description "Preference value 12";
       }
       leaf prefix-list-stat {
         type string;
         description "Prefix list statistics";
       }
       leaf prefix-list {
         type string;
         description "List of prefix-lists of routes to match";
       }
       leaf programmed-stat {
         type string;
         description "Programmed statistics";
       }
       leaf programmed {
         type empty;
         description "API-programmed route";
       }
       leaf protocol-stat {
         type string;
         description "Protocol statistics";
       }
       leaf-list protocol {
         type string;
         description "Protocol from which route was learned";
       }
       leaf tag-stat {
         type string;
         description "Policy tag statistics";
       }
       leaf policy-tag {
         type uint32;
         description "Tag string";
       }
       leaf tag2-stat {
         type string;
         description "Policy tag2 statistics";
       }
       leaf policy-tag2 {
         type uint32;
         description "Tag string 2";
       }
       leaf tag3-stat {
         type string;
         description "Policy tag3 statistics";
       }
       leaf policy-tag3 {
         type uint32;
         description "Tag string 3";
       }
       leaf tag4-stat {
         type string;
         description "Policy tag4 statistics";
       }
       leaf policy-tag4 {
         type uint32;
         description "Tag string 4";
       }
       leaf rib-stat {
         type string;
         description "RIB statistics";
       }
       leaf rib {
         type string;
         description "Routing table";
       }
       leaf route-distinguisher-stat {
         type string;
         description "Route distinguisher statistics";
       }
       leaf route-distinguisher {
         type string;
         description "Name of the route-distinguisher";
       }
       leaf route-type-stat {
         type string;
         description "Route type statistics";
       }
       leaf route-type {
         type string;
         description "Route type";
       }
       leaf route-filter-list-stat {
         type string;
         description "Route filter list statistics";
       }
       leaf rtf-prefix-list-stat {
         type string;
         description "RTF prefix list statistics";
       }
       leaf rtf-prefix-list {
         type string;
         description "List of rtf-prefix-lists of routes to match";
       }
       leaf state-stat {
         type string;
         description "State statistics";
       }
       leaf state {
         type string;
         description "HFRR profile Current state";
       }
       leaf source-address-filter-list-stat {
         type string;
         description "Source address filter list statistics";
       }
       leaf source-address-filter-list {
         type string;
         description "List of source-address-filter-lists of routes to match";
       }
       leaf source-routing-path-stat {
         type string;
         description "Source routing path statistics";
       }
       leaf srte-color-stat {
         type string;
         description "SRTE color statistics";
       }
       leaf srte-color {
         type uint32;
         description "SRTE color";
       }
       leaf as {
         type uint32;
       }
       leaf sys-id {
         type string;
       }
       leaf link-address {
         type string;
       }
       leaf node-type {
         type string;
       }
       leaf any {
         type empty;
       }
       leaf tunnel-type-stat {
         type string;
         description "Tunnel type statistics";
       }
       leaf tunnel-type {
         type string;
         description "Tunnel type";
       }
       leaf validation-state-stat {
         type string;
         description "Validation database statistics";
       }
       leaf validation-database {
         type string;
         description "Name to identify a validation-state";
       }
       leaf validation-database-instance-stat {
         type string;
         description "Validation database instance statistics";
       }
       leaf account-stat {
         type string;
       }
       leaf account {
         type empty;
         description "Account";
       }
       leaf accept-stat {
         type string;
       }
       leaf accept {
         type empty;
         description "Accept a route";
       }
       leaf add-path-stat {
         type string;
       }
       leaf advertise-locator-stat {
         type string;
         description "Advertise locator statistics";
       }
       leaf advertise-locator {
         type empty;
         description "Advertise SRv6 locator";
       }
       leaf advertise-locator-internal {
         type empty;
         description "Advertise SRv6 locator internal";
       }
       leaf aggregate-bandwidth-stat {
         type string;
         description "Aggregate bandwidth statistics";
       }
       leaf auto-link-bandwidth-stat {
         type string;
         description "Auto link bandwidth statistics";
       }
       leaf auto-link-bandwidth {
         type empty;
         description "Auto link bandwidth";
       }
       leaf aigp-adjust-stat {
         type string;
         description "AIGP adjust statistics";
       }
       leaf aigp-originate-stat {
         type string;
         description "AIGP originate statistics";
       }
       leaf analyze-stat {
         type string;
         description "Analyze statistics";
       }
       leaf analyze {
         type empty;
         description "Send to registered controllers for analysis";
       }
       leaf as-path-expand-stat {
         type string;
         description "AS path expand statistics";
       }
       leaf as-path-prepend-stat {
         type string;
         description "AS path prepend statistics";
       }
       leaf as-path-prepend {
         type uint32;
         description "Prepend AS numbers to an AS path (BGP only)";
       }
       leaf bgp-output-queue-priority-stat {
         type string;
         description "BGP output queue priority statistics";
       }
       leaf class-stat {
         type string;
         description "Class statistics";
       }
       leaf cos-next-hop-map-stat {
         type string;
         description "COS next hop map statistics";
       }
       leaf cos-next-hop-map {
         type string;
         description "The CoS-based next-hop map in forwarding table";
       }
       leaf add-metric {
         type uint32;
       }
       leaf subtract-metric {
         type uint32;
       }
       leaf credibility-stat {
         type string;
         description "Credibility statistics";
       }
       leaf damping-stat {
         type string;
         description "Damping statistics";
       }
       leaf damping {
         type string;
         description "Define BGP route flap damping parameters";
       }
       leaf default-action-stat {
         type string;
         description "Default action statistics";
       }
       leaf default-action {
         type string;
         description "The default policy action";
       }
       leaf destination-class-stat {
         type string;
         description "Destination class statistics";
       }
       leaf destination-class {
         type string;
         description "The destination class in forwarding table";
       }
       leaf dynamic-tunnel-attributes-stat {
         type string;
         description "Dynamic tunnel attribute statistics";
       }
       leaf dynamic-tunnel-attributes {
         type string;
         description "The dynamic tunnel attributes used for forwarding";
       }
       leaf filter-stat {
         type string;
         description "Filter statistics";
       }
       leaf filter {
         type string;
         description "Next-hop firewall filter";
       }
       leaf igp-instance-stat {
         type string;
         description "IGP instance statistics";
       }
       leaf igp-instance {
         type string;
         description "IGP instance";
       }
       leaf igp-instance-regex-stat {
         type string;
         description "IGP instance regex statistics";
       }
       leaf igp-instance-regex {
         type string;
         description "IGP instance regex";
       }
       leaf ignore-service-label-stat {
         type string;
         description "Ignore service label statistics";
       }
       leaf ignore-service-label {
         type string;
         description "Ignore service labels";
       }
       leaf install-nexthop-stat {
         type string;
         description "Install nexthop statistics";
       }
       leaf install-to-fib-stat {
         type string;
         description "Install to FIB statistics";
       }
       leaf install-to-fib {
         type string;
         description "Install to FIB";
       }
       leaf label-allocation-stat {
         type string;
         description "Label allocation statistics";
       }
       leaf label-allocation {
         type string;
         description "Label allocation mode";
       }
       leaf label-allocation-fallback-reject-stat {
         type string;
         description "Label allocation fallback reject statistics";
       }
       leaf label-allocation-fallback-reject {
         type string;
         description "Suppress prefix export when label allocation fails";
       }
       leaf limit-bandwidth-stat {
         type string;
         description "Limit bandwidth statistics";
       }
       leaf limit-bandwidth {
         type uint64;
         description "Limit advertised aggregate outbound link bandwidth";
       }
       leaf load-balance-stat {
         type string;
         description "Load balance statistics";
       }
       leaf load-balance {
         type string;
         description "Load-balancing algorithm chosen";
       }
       leaf map-to-interface-stat {
         type string;
         description "Map to interface statistics";
       }
       leaf source-based-forwarding-stat {
         type string;
         description "Source based forwarding statistics";
       }
       leaf metric-offset {
         type uint32;
       }
       leaf effective-aigp-stat {
         type string;
         description "Effective aigp statistics";
       }
       leaf fib-install-priority-stat {
         type string;
         description "FIB install priority statistics";
       }
       leaf fib-install-priority {
         type string;
         description "FIB install priority";
       }
       leaf igp-stat {
         type string;
         description "IGP statistics";
       }
       leaf minimum-effective-aigp-stat {
         type string;
         description "Minimum effective aigp statistics";
       }
       leaf minimum-igp-stat {
         type string;
         description "Minimum IGP statistics";
       }
       leaf mhop-bfd-port-stat {
         type string;
         description "Mhop bfd port statistics";
       }
       leaf mhop-bfd-port {
         type uint32;
         description "Use port number 4784 for MPLS-BFD as per RFC5884";
       }
       leaf multipath-resolve-stat {
         type string;
         description "Multipath resolve statistics";
       }
       leaf multipath-resolve {
         type string;
         description "Use all paths for resolution over this prefix";
       }
       leaf next-stat {
         type string;
         description "Next policy statistics";
       }
       leaf next {
         type string;
         description "Skip to next policy or term";
       }
       leaf no-backup-stat {
         type string;
         description "No backup statistics";
       }
       leaf no-backup {
         type empty;
         description "This prefix should not have backup";
       }
       leaf no-entropy-label-capability-stat {
         type string;
         description "No entropy label capability statistics";
       }
       leaf no-entropy-label-capability {
         type empty;
         description "Don't advertise entropy label capability";
       }
       leaf no-route-localize-stat {
         type string;
         description "No route localize statistics";
       }
       leaf no-route-localize {
         type empty;
         description "No route localize";
       }
       leaf p2mp-lsp-root-stat {
         type string;
         description "P2mp lsp root statistics";
       }
       leaf p2mp-lsp-root {
         type jt:ipaddr;
         description "P2mp lsp root address";
       }
       leaf policy-priority-stat {
         type string;
         description "Policy priority statistics";
       }
       leaf policy-priority {
         type string;
       }
       leaf prefix-attribute-flags-stat {
         type string;
         description "Prefix attribute flag statistics";
       }
       leaf prefix-segment-stat {
         type string;
         description "Prefix segment statistics";
       }
       leaf reject-stat {
         type string;
         description "Reject statistics";
       }
       leaf reject {
         type empty;
         description "Reject a route";
       }
       leaf request-long-lived-ack-stat {
         type string;
         description "Request long lived ack statistics";
       }
       leaf request-long-lived-ack {
         type empty;
         description "Advertise route after forwarding is programmed";
       }
       leaf request-ack-stat {
         type string;
         description "Request acknowledgements statistics";
       }
       leaf resolution-map-stat {
         type string;
         description "Resolution map stat";
       }
       leaf resolution-map {
         type string;
         description "Resolution map";
       }
       leaf resolution-map-mode-stat {
         type string;
         description "Resolution map mode statistics";
       }
       leaf resolution-map-mode {
         type string;
         description "Resolution map modes";
       }
       leaf selected-mldp-egress-stat {
         type string;
         description "Selected mldp egress statistics";
       }
       leaf selected-mldp-egress {
         type string;
         description "This node should act as egress node for MLDP inband signalling";
       }
       leaf send-withdrawal-on-route-change-stat {
         type string;
         description "Send withdrawal on route change statistics";
       }
       leaf send-withdrawal-on-route-change {
         type empty;
         description "Withdrawn route as change is not ack'd from forwarding";
       }
       leaf set-down-bit-stat {
         type string;
         description "Set down bit statistics";
       }
       leaf set-down-bit {
         type empty;
         description "Set down bit";
       }
       leaf slice-stat {
         type string;
         description "Slice statistics";
       }
       leaf slice {
         type string;
         description "Slice name";
       }
       leaf source-class-stat {
         type string;
         description "Source class statistics";
       }
       leaf source-class {
         type string;
         description "The source class in forwarding table";
       }
       leaf sr-te-template-stat {
         type string;
         description "SRTE template statistics";
       }
       leaf sr-te-template {
         type string;
         description "SR TE template to apply";
       }
       leaf ssm-source-stat {
         type string;
         description "SSM source statistics";
       }
       leaf ssm-source {
         type jt:ipaddr;
         description "List of Sources for SSM mapping";
       }
       leaf strip-as-path-stat {
         type string;
         description "Strip Aspath statistics";
       }
       leaf strip-as-path {
         type empty;
         description "Atrip As path";
       }
       leaf trace-stat {
         type string;
         description "Tunnel statistics";
       }
       leaf trace {
         type empty;
         description "Log matches to a trace file";
       }
       leaf tunnel-attribute-stat {
         type string;
         description "Tunnel attribute statistics";
       }
       leaf tunnel-end-point-address-stat {
         type string;
         description "Tunnel end point address statistics";
       }
       leaf tunnel-end-point-address {
         type string;
         description "Set tunnel end-point address of tunnel";
       }
       leaf validation-state {
         type string;
         description "Validation-state of a route";
       }
       list evpn-esi {
         leaf evpn-esi-value {
           type string;
         }
         leaf evpn-interconn-esi {
           type string;
         }
         leaf evpn-esi-status {
           type string;
         }
         leaf evpn-esi-state-bits {
           type int32;
         }
         leaf evpn-esi-min-isid {
           type int32;
         }
         leaf evpn-esi-mac-label {
           type int32;
         }
         leaf evpn-esi-aliasing-label {
           type int32;
         }
         leaf evpn-esi-split-horizon-label {
           type int32;
         }
         leaf evpn-esi-srv6-argument {
           type int32;
         }
         leaf evpn-esi-rt-label {
           type int32;
         }
         leaf evpn-esi-num-mac {
           type int32;
         }
         leaf evpn-esi-num-sgdb {
           type int32;
         }
         leaf evpn-esi-refcount {
           type int32;
         }
         leaf evpn-esi-nh-retry-count {
           type int32;
         }
         leaf evpn-esi-token-rt-nh {
           type int32;
         }
         leaf evpn-esi-srv6-token-rt-nh {
           type int32;
         }
         container evpn-esi-local-intf-information {
           leaf evpn-esi-num-local-intf {
             type int32;
           }
           leaf evpn-esi-local-intf-name {
             type string;
           }
           leaf evpn-esi-local-intf-status {
             type string;
           }
         }
         container evpn-esi-event-history-information {
           list evpn-esi-event-history-database {
             leaf evpn-esi-event-entry {
               type string;
             }
           }
         }
         container evpn-esi-remote-pe-information {
           leaf evpn-esi-num-remote-pe {
             type int32;
           }
           list evpn-esi-remote-pe {
             leaf evpn-esi-remote-pe-ipaddr {
               type jt:ipaddr;
             }
             leaf evpn-esi-remote-mac-label {
               type int32;
             }
             leaf evpn-esi-remote-aliasing-label {
               type int32;
             }
             leaf evpn-esi-remote-pe-mode {
               type string;
             }
             container evpn-srv6-info {
               leaf evpn-srv6-sid {
                 type jt:ipaddr;
               }
               leaf evpn-srv6-behavior {
                 type int32;
               }
               container evpn-srv6-ss {
                 leaf srv6-block-len {
                   type int32;
                 }
                 leaf srv6-node-len {
                   type int32;
                 }
                 leaf srv6-fn-len {
                   type int32;
                 }
                 leaf srv6-arg-len {
                   type int32;
                 }
               }
             }
             leaf evpn-esi-remote-fp-label {
               type int32;
             }
             leaf evpn-esi-remote-flags {
               type int32;
             }
             leaf evpn-esi-num-remote-bd {
               type int32;
             }
             leaf evpn-esi-remote-rd {
               type string;
             }
             leaf evpn-esi-remote-nh {
               type int32;
             }
             leaf evpn-esi-remote-srv6-nh {
               type int32;
             }
             leaf evpn-esi-remote-mac-label-ts {
               type string;
             }
             leaf evpn-esi-remote-token-rt-label {
               type int32;
             }
             leaf evpn-esi-remote-token-rt-nh {
               type int32;
             }
             leaf evpn-esi-remote-mac-count {
               type int32;
             }
             leaf evpn-esi-remote-vlan-id {
               type int32;
             }
             leaf evpn-esi-remote-flow-label-update-pending {
               type string;
             }
           }
         }
         container evpn-esi-df-information {
           leaf esi-df-election-algorithm {
             type string;
           }
           leaf esi-granularity {
             type string;
           }
           leaf esi-lacp-oos-on-ndf {
             type string;
           }
           leaf esi-designated-forwarder {
             type string;
           }
           leaf esi-df-preference {
             type int32;
           }
           leaf esi-df-non-revertive {
             type string;
           }
           leaf-list esi-backup-forwarder {
             type string;
           }
           leaf-list esi-backup-df-preference {
             type int32;
           }
           leaf-list esi-backup-df-non-revertive {
             type string;
           }
           leaf esi-last-df-update-timestamp {
             type string;
           }
         }
         list evpn-esi-bd-remote-pe-information {
           leaf evpn-esi-bd-vlan {
             type int32;
           }
           leaf evpn-esi-bd-status {
             type string;
           }
           leaf evpn-esi-bd-state-bits {
             type int32;
           }
           leaf evpn-esi-bd-refcount {
             type int32;
           }
           leaf evpn-esi-bd-nh-retry-count {
             type int32;
           }
           leaf evpn-esi-bd-remote-prefix {
             type int32;
           }
           leaf evpn-esi-bd-token-rt-nh {
             type int32;
           }
           leaf evpn-esi-bd-num-remote-pe {
             type int32;
           }
           list evpn-esi-bd-remote-pe {
             leaf evpn-esi-bd-remote-pe-ipaddr {
               type jt:ipaddr;
             }
             leaf evpn-esi-bd-remote-mac-label {
               type int32;
             }
             leaf evpn-esi-bd-remote-aliasing-label {
               type int32;
             }
             leaf evpn-esi-bd-remote-pe-mode {
               type string;
             }
           }
         }
       }
       container instance {
         leaf-list instance-name {
           type string;
         }
         leaf instance-display-error {
           type string;
         }
         leaf edge-protection {
           type string;
         }
         leaf edge-protector {
           type string;
         }
         list reference-site {
           leaf automatic-site-name {
             type string;
             description "VPLS automatic site name";
           }
           leaf automatic-site-id-status {
             type string;
             description "VPLS automatic site identifier status";
           }
           leaf automatic-site-claim-id {
             type int32;
             description "Claim site identifier";
           }
           leaf automatic-site-collisions {
             type int32;
             description "Number of collisions";
           }
           leaf automatic-site-timer-status {
             type string;
             description "VPLS automatic site timer status";
           }
           leaf vpls-signaling-protocol-identifier {
             type string;
           }
           leaf local-site-id {
             type string;
           }
           leaf source-attachment-id {
             type string;
             description "Local source attachment identifier";
           }
           leaf vpls-id {
             type int32;
             description "VPLS instance identifier";
           }
           leaf l2vpn-id {
             type string;
           }
           leaf local-id {
             type jt:ipaddr;
           }
           leaf num-local-interfaces {
             type int32;
           }
           leaf num-local-interfaces-up {
             type int32;
           }
           leaf irb-present {
             type string;
           }
           leaf mesh-group-count {
             type int32;
           }
           leaf mesh-group-up-count {
             type int32;
           }
           leaf remote-site-id {
             type string;
           }
           leaf target-attachment-id {
             type string;
             description "Remote target attachment identifier";
           }
           list mesh-group-interfaces {
             leaf mesh-group-name {
               type string;
               description "Name of mesh-group";
             }
             leaf mesh-group-state {
               type string;
               description "Mesh-group state";
             }
             leaf mesh-group-id {
               type int32;
               description "Mesh-group Identifier";
             }
             list interface {
               leaf interface-name {
                 type string;
                 description "Name of interface";
               }
               leaf interface-description {
                 type string;
               }
               leaf interface-flags-description {
                 type string;
               }
               leaf interface-flags {
                 type int32;
               }
             }
           }
           list interface {
             leaf interface-name {
               type string;
               description "Name of interface";
             }
             leaf interface-id {
               type int32;
             }
             leaf interface-description {
               type string;
             }
             leaf interface-flags-description {
               type string;
             }
             leaf interface-flags {
               type int32;
             }
           }
           list label-block {
             leaf-list label-block.heading {
               type string;
             }
             leaf label-block-base {
               type int32;
             }
             leaf label-block-offset {
               type int32;
             }
             leaf label-block-size {
               type int32;
             }
             leaf label-block-range {
               type int32;
             }
             leaf label-block-preference {
               type int32;
             }
             leaf label-block-status-vector {
               type string;
             }
           }
           list connection {
             leaf-list connection.heading {
               type string;
             }
             leaf connection-id {
               type string;
             }
             leaf connection-type {
               type string;
             }
             leaf connection-status {
               type string;
             }
             leaf last-change {
               type string;
             }
             leaf up-transitions {
               type int32;
             }
             leaf remote-pe {
               type jt:ipaddr;
             }
             leaf control-word {
               type string;
             }
             leaf control-word-type {
               type string;
             }
             leaf interface-encapsulation {
               type string;
             }
             leaf inbound-label {
               type string;
             }
             leaf outbound-label {
               type string;
             }
             leaf pw-status-tlv {
               type string;
             }
             leaf local-pw-status-code {
               type int32;
             }
             leaf remote-pw-status-code {
               type int32;
             }
             leaf connection-protection {
               type string;
             }
             leaf mesh-group-name {
               type string;
               description "Name of mesh-group";
             }
             leaf vc-flow-label-transmit {
               type string;
             }
             leaf vc-flow-label-receive {
               type string;
             }
             leaf auto-sensed {
               type empty;
               description "Auto-sensed";
             }
             container local-interface {
               leaf interface-name {
                 type string;
                 description "Name of interface";
               }
               leaf interface-status {
                 type string;
               }
               leaf interface-encapsulation {
                 type string;
               }
               leaf working-status {
                 type string;
               }
               leaf profile-name {
                 type string;
               }
               leaf profile-varset-name {
                 type string;
               }
               leaf interface-description {
                 type string;
               }
             }
             container remote-interface {
               leaf interface-name {
                 type string;
                 description "Name of interface";
               }
               leaf interface-status {
                 type string;
               }
               leaf interface-encapsulation {
                 type string;
               }
             }
             container connection-bandwidth {
               leaf connection-bandwidth.heading {
                 type string;
                 description "Bandwidth of a layer 2 connection";
               }
               leaf bandwidth {
                 type int32;
               }
               leaf class-type {
                 type int32;
               }
               leaf class-bandwidth {
                 type int32;
               }
             }
             container vpls-rsvp-te-p2mp-lsp-information {
               leaf vpls-ingress-p2mp-branch-lsp-name {
                 type string;
                 description "Name of ingress point-to-multipoint branch LSP";
               }
               leaf vpls-ingress-p2mp-branch-lsp-state {
                 type string;
                 description "State of ingress point-to-multipoint branch LSP";
               }
               leaf vpls-egress-p2mp-branch-lsp-name {
                 type string;
                 description "Name of egress point-to-multipoint branch LSP";
               }
               leaf vpls-egress-p2mp-branch-lsp-state {
                 type string;
                 description "State of egress point-to-multipoint branch LSP";
               }
             }
             container spe-info {
               leaf spe-info.heading {
                 type string;
               }
               leaf local-ip-addr {
                 type jt:ipaddr;
               }
               leaf remote-ip-addr {
                 type jt:ipaddr;
               }
               leaf pw-status {
                 type string;
               }
             }
             container history {
               leaf history.category-heading {
                 type string;
               }
               leaf history.heading {
                 type string;
               }
               container history-element {
                 leaf log-time-stamp {
                   type string;
                 }
                 leaf log-event {
                   type string;
                 }
                 leaf changed-entity {
                   type string;
                 }
               }
             }
           }
           list mesh-group-connection {
             leaf mesh-group-name {
               type string;
               description "Name of mesh-group";
             }
             list connection {
               leaf-list connection.heading {
                 type string;
               }
               leaf connection-id {
                 type string;
               }
               leaf connection-type {
                 type string;
               }
               leaf connection-status {
                 type string;
               }
               leaf last-change {
                 type string;
               }
               leaf up-transitions {
                 type int32;
               }
               leaf remote-pe {
                 type jt:ipaddr;
               }
               leaf control-word {
                 type string;
               }
               leaf control-word-type {
                 type string;
               }
               leaf interface-encapsulation {
                 type string;
               }
               leaf inbound-label {
                 type string;
               }
               leaf outbound-label {
                 type string;
               }
               leaf pw-status-tlv {
                 type string;
               }
               leaf local-pw-status-code {
                 type int32;
               }
               leaf remote-pw-status-code {
                 type int32;
               }
               leaf connection-protection {
                 type string;
               }
               leaf mesh-group-name {
                 type string;
                 description "Name of mesh-group";
               }
               leaf vc-flow-label-transmit {
                 type string;
               }
               leaf vc-flow-label-receive {
                 type string;
               }
               leaf auto-sensed {
                 type empty;
                 description "Auto-sensed";
               }
               container local-interface {
                 leaf interface-name {
                   type string;
                   description "Name of interface";
                 }
                 leaf interface-status {
                   type string;
                 }
                 leaf interface-encapsulation {
                   type string;
                 }
                 leaf working-status {
                   type string;
                 }
                 leaf profile-name {
                   type string;
                 }
                 leaf profile-varset-name {
                   type string;
                 }
                 leaf interface-description {
                   type string;
                 }
               }
               container remote-interface {
                 leaf interface-name {
                   type string;
                   description "Name of interface";
                 }
                 leaf interface-status {
                   type string;
                 }
                 leaf interface-encapsulation {
                   type string;
                 }
               }
               container connection-bandwidth {
                 leaf connection-bandwidth.heading {
                   type string;
                   description "Bandwidth of a layer 2 connection";
                 }
                 leaf bandwidth {
                   type int32;
                 }
                 leaf class-type {
                   type int32;
                 }
                 leaf class-bandwidth {
                   type int32;
                 }
               }
               container vpls-rsvp-te-p2mp-lsp-information {
                 leaf vpls-ingress-p2mp-branch-lsp-name {
                   type string;
                   description "Name of ingress point-to-multipoint branch LSP";
                 }
                 leaf vpls-ingress-p2mp-branch-lsp-state {
                   type string;
                   description "State of ingress point-to-multipoint branch LSP";
                 }
                 leaf vpls-egress-p2mp-branch-lsp-name {
                   type string;
                   description "Name of egress point-to-multipoint branch LSP";
                 }
                 leaf vpls-egress-p2mp-branch-lsp-state {
                   type string;
                   description "State of egress point-to-multipoint branch LSP";
                 }
               }
               container history {
                 leaf history.category-heading {
                   type string;
                 }
                 leaf history.heading {
                   type string;
                 }
                 container history-element {
                   leaf log-time-stamp {
                     type string;
                   }
                   leaf log-event {
                     type string;
                   }
                   leaf changed-entity {
                     type string;
                   }
                 }
               }
             }
           }
           container automatic-site-timers {
             leaf automatic-site-timers.heading {
               type string;
             }
             leaf automatic-site-startup-wait-time {
               type string;
             }
             leaf automatic-site-new-site-wait-time {
               type string;
             }
             leaf automatic-site-collision-detect-time {
               type string;
             }
             leaf automatic-site-reclaim-wait-time {
               type string;
             }
           }
           container connections-summary {
             leaf vc-up-count {
               type int32;
             }
             leaf vc-down-count {
               type int32;
             }
           }
         }
         list ldp-vpls-reference-site {
           leaf vpls-signaling-protocol-identifier {
             type string;
           }
           leaf local-site-id {
             type string;
           }
           leaf vpls-id {
             type int32;
             description "VPLS instance identifier";
           }
           leaf l2vpn-id {
             type string;
           }
           leaf local-id {
             type jt:ipaddr;
           }
           leaf num-local-interfaces {
             type int32;
           }
           leaf num-local-interfaces-up {
             type int32;
           }
           leaf irb-present {
             type string;
           }
           leaf mesh-group-count {
             type int32;
           }
           leaf mesh-group-up-count {
             type int32;
           }
           leaf remote-site-id {
             type string;
           }
           list mesh-group-interfaces {
             leaf mesh-group-name {
               type string;
               description "Name of mesh-group";
             }
             leaf mesh-group-state {
               type string;
               description "Mesh-group state";
             }
             leaf mesh-group-id {
               type int32;
               description "Mesh-group Identifier";
             }
             list interface {
               leaf interface-name {
                 type string;
                 description "Name of interface";
               }
               leaf interface-description {
                 type string;
               }
               leaf interface-flags-description {
                 type string;
               }
               leaf interface-flags {
                 type int32;
               }
             }
           }
           list interface {
             leaf interface-name {
               type string;
               description "Name of interface";
             }
             leaf interface-id {
               type int32;
             }
             leaf interface-description {
               type string;
             }
             leaf interface-flags-description {
               type string;
             }
             leaf interface-flags {
               type int32;
             }
           }
           list connection {
             leaf-list connection.heading {
               type string;
             }
             leaf connection-id {
               type string;
             }
             leaf connection-type {
               type string;
             }
             leaf connection-status {
               type string;
             }
             leaf last-change {
               type string;
             }
             leaf up-transitions {
               type int32;
             }
             leaf remote-pe {
               type jt:ipaddr;
             }
             leaf control-word {
               type string;
             }
             leaf control-word-type {
               type string;
             }
             leaf interface-encapsulation {
               type string;
             }
             leaf inbound-label {
               type string;
             }
             leaf outbound-label {
               type string;
             }
             leaf pw-status-tlv {
               type string;
             }
             leaf local-pw-status-code {
               type int32;
             }
             leaf remote-pw-status-code {
               type int32;
             }
             leaf connection-protection {
               type string;
             }
             leaf mesh-group-name {
               type string;
               description "Name of mesh-group";
             }
             leaf vc-flow-label-transmit {
               type string;
             }
             leaf vc-flow-label-receive {
               type string;
             }
             leaf auto-sensed {
               type empty;
               description "Auto-sensed";
             }
             container local-interface {
               leaf interface-name {
                 type string;
                 description "Name of interface";
               }
               leaf interface-status {
                 type string;
               }
               leaf interface-encapsulation {
                 type string;
               }
               leaf working-status {
                 type string;
               }
               leaf profile-name {
                 type string;
               }
               leaf profile-varset-name {
                 type string;
               }
               leaf interface-description {
                 type string;
               }
             }
             container remote-interface {
               leaf interface-name {
                 type string;
                 description "Name of interface";
               }
               leaf interface-status {
                 type string;
               }
               leaf interface-encapsulation {
                 type string;
               }
             }
             container connection-bandwidth {
               leaf connection-bandwidth.heading {
                 type string;
                 description "Bandwidth of a layer 2 connection";
               }
               leaf bandwidth {
                 type int32;
               }
               leaf class-type {
                 type int32;
               }
               leaf class-bandwidth {
                 type int32;
               }
             }
             container vpls-rsvp-te-p2mp-lsp-information {
               leaf vpls-ingress-p2mp-branch-lsp-name {
                 type string;
                 description "Name of ingress point-to-multipoint branch LSP";
               }
               leaf vpls-ingress-p2mp-branch-lsp-state {
                 type string;
                 description "State of ingress point-to-multipoint branch LSP";
               }
               leaf vpls-egress-p2mp-branch-lsp-name {
                 type string;
                 description "Name of egress point-to-multipoint branch LSP";
               }
               leaf vpls-egress-p2mp-branch-lsp-state {
                 type string;
                 description "State of egress point-to-multipoint branch LSP";
               }
             }
             container history {
               leaf history.category-heading {
                 type string;
               }
               leaf history.heading {
                 type string;
               }
               container history-element {
                 leaf log-time-stamp {
                   type string;
                 }
                 leaf log-event {
                   type string;
                 }
                 leaf changed-entity {
                   type string;
                 }
               }
             }
           }
           list mesh-group-connection {
             leaf mesh-group-name {
               type string;
               description "Name of mesh-group";
             }
             list connection {
               leaf-list connection.heading {
                 type string;
               }
               leaf connection-id {
                 type string;
               }
               leaf connection-type {
                 type string;
               }
               leaf connection-status {
                 type string;
               }
               leaf last-change {
                 type string;
               }
               leaf up-transitions {
                 type int32;
               }
               leaf remote-pe {
                 type jt:ipaddr;
               }
               leaf control-word {
                 type string;
               }
               leaf control-word-type {
                 type string;
               }
               leaf interface-encapsulation {
                 type string;
               }
               leaf inbound-label {
                 type string;
               }
               leaf outbound-label {
                 type string;
               }
               leaf pw-status-tlv {
                 type string;
               }
               leaf local-pw-status-code {
                 type int32;
               }
               leaf remote-pw-status-code {
                 type int32;
               }
               leaf connection-protection {
                 type string;
               }
               leaf mesh-group-name {
                 type string;
                 description "Name of mesh-group";
               }
               leaf vc-flow-label-transmit {
                 type string;
               }
               leaf vc-flow-label-receive {
                 type string;
               }
               leaf auto-sensed {
                 type empty;
                 description "Auto-sensed";
               }
               container local-interface {
                 leaf interface-name {
                   type string;
                   description "Name of interface";
                 }
                 leaf interface-status {
                   type string;
                 }
                 leaf interface-encapsulation {
                   type string;
                 }
                 leaf working-status {
                   type string;
                 }
                 leaf profile-name {
                   type string;
                 }
                 leaf profile-varset-name {
                   type string;
                 }
                 leaf interface-description {
                   type string;
                 }
               }
               container remote-interface {
                 leaf interface-name {
                   type string;
                   description "Name of interface";
                 }
                 leaf interface-status {
                   type string;
                 }
                 leaf interface-encapsulation {
                   type string;
                 }
               }
               container connection-bandwidth {
                 leaf connection-bandwidth.heading {
                   type string;
                   description "Bandwidth of a layer 2 connection";
                 }
                 leaf bandwidth {
                   type int32;
                 }
                 leaf class-type {
                   type int32;
                 }
                 leaf class-bandwidth {
                   type int32;
                 }
               }
               container vpls-rsvp-te-p2mp-lsp-information {
                 leaf vpls-ingress-p2mp-branch-lsp-name {
                   type string;
                   description "Name of ingress point-to-multipoint branch LSP";
                 }
                 leaf vpls-ingress-p2mp-branch-lsp-state {
                   type string;
                   description "State of ingress point-to-multipoint branch LSP";
                 }
                 leaf vpls-egress-p2mp-branch-lsp-name {
                   type string;
                   description "Name of egress point-to-multipoint branch LSP";
                 }
                 leaf vpls-egress-p2mp-branch-lsp-state {
                   type string;
                   description "State of egress point-to-multipoint branch LSP";
                 }
               }
               container history {
                 leaf history.category-heading {
                   type string;
                 }
                 leaf history.heading {
                   type string;
                 }
                 container history-element {
                   leaf log-time-stamp {
                     type string;
                   }
                   leaf log-event {
                     type string;
                   }
                   leaf changed-entity {
                     type string;
                   }
                 }
               }
             }
           }
           container connections-summary {
             leaf vc-up-count {
               type int32;
             }
             leaf vc-down-count {
               type int32;
             }
           }
         }
         container vpls-protocol-state {
           leaf vpls-signaling-protocol-identifier {
             type string;
           }
           leaf num-local-interfaces {
             type int32;
           }
           leaf num-local-interfaces-up {
             type int32;
           }
           leaf irb-present {
             type string;
           }
           leaf mesh-group-count {
             type int32;
           }
           leaf mesh-group-up-count {
             type int32;
           }
           list mesh-group-interfaces {
             list interface {
               leaf interface-name {
                 type string;
                 description "Name of interface";
               }
               leaf interface-flags {
                 type int32;
               }
             }
           }
           list interface {
             leaf interface-name {
               type string;
               description "Name of interface";
             }
             leaf interface-flags {
               type int32;
             }
           }
           list mesh-group-connection {
             leaf mesh-group-name {
               type string;
               description "Name of mesh-group";
             }
             list connection {
               leaf-list connection.heading {
                 type string;
               }
               leaf remote-pe {
                 type jt:ipaddr;
               }
               leaf l2vpn-local-site-id {
                 type int32;
                 description "Local site identifier";
               }
               leaf l2vpn-remote-site-id {
                 type int32;
                 description "Remote site identifier";
               }
               leaf connection-status {
                 type string;
               }
               leaf last-change {
                 type string;
               }
               leaf inbound-label {
                 type string;
               }
               leaf outbound-label {
                 type string;
               }
               container local-interface {
                 leaf interface-name {
                   type string;
                   description "Name of interface";
                 }
                 leaf interface-status {
                   type string;
                 }
                 leaf interface-encapsulation {
                   type string;
                 }
                 leaf working-status {
                   type string;
                 }
                 leaf profile-name {
                   type string;
                 }
                 leaf profile-varset-name {
                   type string;
                 }
                 leaf interface-description {
                   type string;
                 }
               }
               container connection-bandwidth {
                 leaf connection-bandwidth.heading {
                   type string;
                   description "Bandwidth of a layer 2 connection";
                 }
                 leaf bandwidth {
                   type int32;
                 }
                 leaf class-type {
                   type int32;
                 }
                 leaf class-bandwidth {
                   type int32;
                 }
               }
               container vpls-rsvp-te-p2mp-lsp-information {
                 leaf vpls-ingress-p2mp-branch-lsp-name {
                   type string;
                   description "Name of ingress point-to-multipoint branch LSP";
                 }
                 leaf vpls-ingress-p2mp-branch-lsp-state {
                   type string;
                   description "State of ingress point-to-multipoint branch LSP";
                 }
                 leaf vpls-egress-p2mp-branch-lsp-name {
                   type string;
                   description "Name of egress point-to-multipoint branch LSP";
                 }
                 leaf vpls-egress-p2mp-branch-lsp-state {
                   type string;
                   description "State of egress point-to-multipoint branch LSP";
                 }
               }
               container history {
                 leaf history.category-heading {
                   type string;
                 }
                 leaf history.heading {
                   type string;
                 }
                 container history-element {
                   leaf log-time-stamp {
                     type string;
                   }
                   leaf log-event {
                     type string;
                   }
                   leaf changed-entity {
                     type string;
                   }
                 }
               }
             }
             container connections-summary {
               leaf vc-up-count {
                 type int32;
               }
               leaf vc-down-count {
                 type int32;
               }
             }
           }
           list reference-site {
             leaf automatic-site-name {
               type string;
               description "VPLS automatic site name";
             }
             leaf automatic-site-id-status {
               type string;
               description "VPLS automatic site identifier status";
             }
             leaf automatic-site-claim-id {
               type int32;
               description "Claim site identifier";
             }
             leaf automatic-site-collisions {
               type int32;
               description "Number of collisions";
             }
             leaf automatic-site-timer-status {
               type string;
               description "VPLS automatic site timer status";
             }
             leaf vpls-signaling-protocol-identifier {
               type string;
             }
             leaf local-site-id {
               type string;
             }
             leaf source-attachment-id {
               type string;
               description "Local source attachment identifier";
             }
             leaf vpls-id {
               type int32;
               description "VPLS instance identifier";
             }
             leaf l2vpn-id {
               type string;
             }
             leaf local-id {
               type jt:ipaddr;
             }
             leaf num-local-interfaces {
               type int32;
             }
             leaf num-local-interfaces-up {
               type int32;
             }
             leaf irb-present {
               type string;
             }
             leaf mesh-group-count {
               type int32;
             }
             leaf mesh-group-up-count {
               type int32;
             }
             leaf remote-site-id {
               type string;
             }
             leaf target-attachment-id {
               type string;
               description "Remote target attachment identifier";
             }
             list mesh-group-interfaces {
               leaf mesh-group-name {
                 type string;
                 description "Name of mesh-group";
               }
               leaf mesh-group-state {
                 type string;
                 description "Mesh-group state";
               }
               leaf mesh-group-id {
                 type int32;
                 description "Mesh-group Identifier";
               }
               list interface {
                 leaf interface-name {
                   type string;
                   description "Name of interface";
                 }
                 leaf interface-description {
                   type string;
                 }
                 leaf interface-flags-description {
                   type string;
                 }
                 leaf interface-flags {
                   type int32;
                 }
               }
             }
             list interface {
               leaf interface-name {
                 type string;
                 description "Name of interface";
               }
               leaf interface-id {
                 type int32;
               }
               leaf interface-description {
                 type string;
               }
               leaf interface-flags-description {
                 type string;
               }
               leaf interface-flags {
                 type int32;
               }
             }
             list connection {
               container history {
               }
             }
             list mesh-group-connection {
               list connection {
                 container history {
                 }
               }
             }
           }
         }
         container vpls-rsvp-te-ingress-p2mp-lsp {
           leaf vpls-ingress-p2mp-lsp-name {
             type string;
             description "Name of ingress point-to-multipoint LSP";
           }
           leaf vpls-rsvp-te-p2mp-flood-nexthop-id {
             type int32;
             description "Identifier for VPLS RSVP traffic-engineering ingress flood next hop";
           }
         }
         container multihome {
           leaf multihome.heading {
             type string;
           }
           list multihome-site {
             leaf multihome-site-name {
               type string;
               description "Name of site";
             }
             leaf multihome-site-id {
               type int32;
               description "Site Identifier";
             }
             leaf multihome-site-preference {
               type int32;
               description "Site Preference";
             }
             leaf multihome-site-state {
               type string;
               description "Site state";
             }
             leaf multihome-num-interfaces {
               type int32;
             }
             leaf multihome-num-interfaces-up {
               type int32;
             }
             list interface {
               leaf interface-name {
                 type string;
                 description "Name of interface";
               }
               leaf interface-id {
                 type int32;
               }
               leaf interface-description {
                 type string;
               }
               leaf interface-flags-description {
                 type string;
               }
               leaf interface-flags {
                 type int32;
               }
             }
             container remote-advertisements {
               leaf remote-advertisements.heading {
                 type string;
               }
               list remote-adv {
                 leaf remote-adv-addr {
                   type string;
                 }
                 leaf remote-adv-preference {
                   type int32;
                   description "Remote PE preference";
                 }
                 leaf remote-adv-ctrl-flag {
                   type int32;
                   description "Remote PE Control flags";
                 }
                 leaf remote-adv-ctrl-flag-description {
                   type string;
                   description "Control flags description";
                 }
               }
             }
           }
         }
         container history {
           leaf history.category-heading {
             type string;
           }
           leaf history.heading {
             type string;
           }
           container history-element {
             leaf log-time-stamp {
               type string;
             }
             leaf log-event {
               type string;
             }
             leaf changed-entity {
               type string;
             }
           }
         }
       }
       list interface {
         leaf interface-name {
           type string;
           description "Name of interface";
         }
         leaf interface-flags {
           type int32;
         }
       }
       container next-hop-weight {
         leaf next-hop-weight-stat {
           type string;
           description "Nexthop weight statistics";
         }
         leaf next-hop-weight.heading {
           type string;
           description "Nexthop weight";
         }
         leaf equal-to {
           type uint32;
         }
         leaf greater-than {
           type uint32;
         }
         leaf greater-than-equal {
           type uint32;
         }
         leaf less-than {
           type uint32;
         }
         leaf less-than-equal {
           type uint32;
         }
         leaf all-nexthop {
           type empty;
         }
       }
       container next-hop-ecmp {
         leaf next-hop-ecmp-stat {
           type string;
           description "Nexthop ecmp statistics";
         }
         leaf next-hop-ecmp.heading {
           type string;
           description "Nexthop ecmp";
         }
         leaf equal-to {
           type uint32;
         }
         leaf greater-than {
           type uint32;
         }
         leaf greater-than-equal {
           type uint32;
         }
         leaf less-than {
           type uint32;
         }
         leaf less-than-equal {
           type uint32;
         }
         leaf all-nexthop {
           type empty;
         }
       }
       container route-filter-list {
         leaf route-filter-list-stat {
           type string;
           description "Route filter list statistics";
         }
         leaf route-filter-list.heading {
           type string;
         }
         leaf route-filter-list-name {
           type string;
           description "List of route-filter-lists of routes to match";
         }
         container policy-extended-information {
           leaf account {
             type empty;
             description "Account";
           }
           leaf accept {
             type empty;
             description "Accept a route";
           }
           leaf advertise-locator {
             type empty;
             description "Advertise SRv6 locator";
           }
           leaf advertise-locator-internal {
             type empty;
             description "Advertise SRv6 locator internal";
           }
           leaf aggregate-bandwidth {
             type int32;
             description "Aggregate bandwidth";
           }
           leaf auto-link-bandwidth {
             type empty;
             description "Auto link bandwidth";
           }
           leaf analyze {
             type empty;
             description "Send to registered controllers for analysis";
           }
           leaf as-path-prepend {
             type uint32;
             description "Prepend AS numbers to an AS path (BGP only)";
           }
           leaf cos-next-hop-map {
             type string;
             description "The CoS-based next-hop map in forwarding table";
           }
           leaf damping {
             type string;
             description "Define BGP route flap damping parameters";
           }
           leaf default-action {
             type string;
             description "The default policy action";
           }
           leaf destination-class {
             type string;
             description "The destination class in forwarding table";
           }
           leaf dynamic-tunnel-attributes {
             type string;
             description "The dynamic tunnel attributes used for forwarding";
           }
           leaf fib-install-priority {
             type string;
             description "FIB install priority";
           }
           leaf filter {
             type string;
             description "Next-hop firewall filter";
           }
           leaf get-route-range {
             type empty;
             description "Get route range";
           }
           leaf ignore-service-label {
             type string;
             description "Ignore service labels";
           }
           leaf install-to-fib {
             type string;
             description "Install to FIB";
           }
           leaf ipv4-source-router-id {
             type empty;
           }
           leaf ipv4-source-router-id-address {
             type string;
             description "IPV4 source router id address";
           }
           leaf ipv6-source-router-id {
             type empty;
           }
           leaf ipv6-source-router-id-address {
             type string;
             description "IPV6 source router id address";
           }
           leaf label-allocation {
             type string;
             description "Label allocation mode";
           }
           leaf label-allocation-fallback-reject {
             type string;
             description "Suppress prefix export when label allocation fails";
           }
           leaf limit-bandwidth {
             type uint64;
             description "Limit advertised aggregate outbound link bandwidth";
           }
           leaf load-balance {
             type string;
             description "Load-balancing algorithm chosen";
           }
           leaf mhop-bfd-port {
             type uint32;
             description "Use port number 4784 for MPLS-BFD as per RFC5884";
           }
           leaf multipath-resolve {
             type string;
             description "Use all paths for resolution over this prefix";
           }
           leaf next {
             type string;
             description "Skip to next policy or term";
           }
           leaf no-backup {
             type empty;
             description "This prefix should not have backup";
           }
           leaf no-entropy-label-capability {
             type empty;
             description "Don't advertise entropy label capability";
           }
           leaf no-route-localize {
             type empty;
             description "No route localize";
           }
           leaf origin {
             type string;
             description "BGP origin attribute";
           }
           leaf p2mp-lsp-root {
             type jt:ipaddr;
             description "P2mp lsp root address";
           }
           leaf policy-priority {
             type string;
           }
           leaf reject {
             type empty;
             description "Reject a route";
           }
           leaf request-long-lived-ack {
             type empty;
             description "Advertise route after forwarding is programmed";
           }
           leaf resolution-map {
             type string;
             description "Resolution map";
           }
           leaf resolution-map-mode {
             type string;
             description "Resolution map modes";
           }
           leaf selected-mldp-egress {
             type string;
             description "This node should act as egress node for MLDP inband signalling";
           }
           leaf send-withdrawal-on-route-change {
             type empty;
             description "Withdrawn route as change is not ack'd from forwarding";
           }
           leaf set-down-bit {
             type empty;
             description "Set down bit";
           }
           leaf slice {
             type string;
             description "Slice name";
           }
           leaf source-class {
             type string;
             description "The source class in forwarding table";
           }
           leaf sr-te-template {
             type string;
             description "SR TE template to apply";
           }
           leaf ssm-source {
             type jt:ipaddr;
             description "List of Sources for SSM mapping";
           }
           leaf trace {
             type empty;
             description "Log matches to a trace file";
           }
           leaf tunnel-end-point-address {
             type string;
             description "Set tunnel end-point address of tunnel";
           }
           leaf validation-state {
             type string;
             description "Validation-state of a route";
           }
           container install-nexthop {
             container except {
               leaf lsp {
                 type string;
                 description "Label switched path name";
               }
               leaf lsp-regex {
                 type string;
                 description "Label switched path name regular expression";
               }
               leaf non-labelled-nexthop {
                 type empty;
               }
               leaf non-lsp-nexthop {
                 type empty;
               }
               leaf static-lsp {
                 type string;
               }
               leaf static-lsp-regex {
                 type string;
               }
               leaf overlay-vxlan-interfaces {
                 type empty;
               }
             }
             container fallback {
               leaf lsp {
                 type string;
                 description "Label switched path name";
               }
               leaf lsp-regex {
                 type string;
                 description "Label switched path name regular expression";
               }
               leaf non-labelled-nexthop {
                 type empty;
               }
               leaf non-lsp-nexthop {
                 type empty;
               }
               leaf static-lsp {
                 type string;
               }
               leaf static-lsp-regex {
                 type string;
               }
               leaf overlay-vxlan-interfaces {
                 type empty;
               }
             }
           }
           container map-to-interface {
             list interface {
               leaf interface-name {
                 type string;
                 description "Name of interface";
               }
               leaf interface-flags {
                 type int32;
               }
             }
           }
           container then-metric {
           }
           container prefix-segment {
             leaf redistribute {
               type empty;
             }
             container algorithm {
               leaf prefix-segment-index-value {
                 type uint32;
               }
               leaf algorithm-name {
                 type uint32;
               }
               leaf node-segment {
                 type empty;
               }
               leaf redistribute {
                 type empty;
               }
             }
           }
           list tunnel-attribute {
             leaf tunnel-type {
               type string;
               description "Tunnel type";
             }
             leaf reference-count {
               type int32;
               description "Reference count";
             }
             leaf tunnel-data {
               type string;
               description "Tunnel Data";
             }
           }
           container source-based-forwarding {
             container sbf-attributes {
               leaf sbf-next-table {
                 type string;
               }
             }
           }
           container policy-label {
           }
         }
       }
       container source-routing-path {
         leaf source-routing-path-stat {
           type string;
           description "Source routing path statistics";
         }
         leaf source-routing-path.heading {
           type string;
         }
         leaf color-value {
           type uint32;
           description "Color";
         }
         leaf dest {
           type string;
           description "Spring-te lsp IPV4/IPV6 destination without color";
         }
         leaf name-regex {
           type string;
           description "Spring-te lsp name regex";
         }
         leaf origin-value {
           type string;
           description "Origin";
         }
         leaf route-distinguisher-value {
           type uint32;
           description "Route distinguisher";
         }
         leaf tunnel-source {
           type string;
           description "Source protocol";
         }
       }
       container ipv4-prefix {
         leaf ipv4-prefix.heading {
           type string;
         }
         leaf as {
           type uint32;
         }
         leaf router-id {
           type jt:ipaddr;
         }
         leaf prefix {
           type jt:ipaddr;
         }
         leaf sys-id {
           type string;
         }
         leaf any {
           type empty;
         }
       }
       container ipv6-prefix {
         leaf ipv6-prefix.heading {
           type string;
         }
         leaf as {
           type uint32;
         }
         leaf router-id {
           type jt:ipaddr;
         }
         leaf prefix {
           type jt:ipaddr;
         }
         leaf sys-id {
           type string;
         }
         leaf any {
           type empty;
         }
       }
       container srv6-sid {
         leaf srv6-sid.heading {
           type string;
         }
         leaf as {
           type uint32;
         }
         leaf router-id {
           type jt:ipaddr;
         }
         leaf end-sid {
           type string;
           description "SRv6 end sid";
         }
         leaf sys-id {
           type string;
         }
         leaf any {
           type empty;
         }
       }
       container link {
         container te-from {
           leaf te-from.heading {
             type string;
           }
           leaf as {
             type uint32;
           }
           leaf router-id {
             type jt:ipaddr;
           }
           leaf sys-id {
             type string;
           }
           leaf node-type {
             type string;
           }
           leaf any {
             type empty;
           }
           leaf link-address {
             type string;
           }
         }
         container te-to {
           leaf te-to.heading {
             type string;
           }
           leaf as {
             type uint32;
           }
           leaf router-id {
             type jt:ipaddr;
           }
           leaf sys-id {
             type string;
           }
           leaf node-type {
             type string;
           }
           leaf any {
             type empty;
           }
           leaf link-address {
             type string;
           }
         }
       }
       container te-node {
         leaf te-node.heading {
           type string;
         }
         leaf as {
           type uint32;
         }
         leaf router-id {
           type jt:ipaddr;
         }
         leaf sys-id {
           type string;
         }
         leaf node-type {
           type string;
         }
         leaf any {
           type empty;
         }
       }
       container te-springte {
         leaf te-springte.heading {
           type string;
         }
         leaf as {
           type uint32;
         }
         leaf router-id {
           type jt:ipaddr;
         }
         leaf color1 {
           type uint32;
           description "Color1";
         }
         leaf discriminator {
           type uint32;
           description "Spring-te discriminator";
         }
         leaf endpoint {
           type string;
           description "Spring-te endpoint";
         }
         leaf proto-origin {
           type string;
           description "Spring-te proto-origin";
         }
         leaf origin-as {
           type uint32;
         }
         leaf origin-addr {
           type string;
           description "Spring-te origin address";
         }
       }
       container validation-database-instance {
         leaf validation-database-instance-stat {
           type string;
           description "Validation database instance statistics";
         }
         leaf validation-database-instance.heading {
           type string;
           description "Validation database instance";
         }
         leaf validation-database-instance-database-name {
           type string;
           description "Name of the validation database";
         }
         leaf validation-database-instance-state-invalid {
           type empty;
           description "Invalid validation database instance state";
         }
         leaf validation-database-instance-state-unknown {
           type empty;
           description "Unknown validation database instance state";
         }
         leaf validation-database-instance-state-valid {
           type empty;
           description "Valid validation database instance state";
         }
       }
       container add-path {
         leaf add-path-stat {
           type string;
         }
         leaf add-path.heading {
           type string;
           description "BGP add-path attributes";
         }
         leaf sendcount {
           type uint32;
           description "Number of add-paths sent";
         }
       }
       container aigp-adjust {
         leaf aigp-adjust-stat {
           type string;
           description "AIGP adjust statistics";
         }
         leaf aigp-adjust.heading {
           type string;
           description "Adjust a BGP AIGP attribute";
         }
         leaf distance-to-protocol-nexthop {
           type empty;
         }
         leaf add {
           type empty;
         }
         leaf divide {
           type empty;
         }
         leaf multiply {
           type empty;
         }
         leaf subtract {
           type empty;
         }
         leaf user-value {
           type uint64;
         }
       }
       container aigp-originate {
         leaf aigp-originate-stat {
           type string;
           description "AIGP originate statistics";
         }
         leaf aigp-originate.heading {
           type string;
           description "Originate a BGP AIGP attribute";
         }
         leaf distance {
           type uint32;
           description "AIGP distance";
         }
       }
       container as-path-expand {
         leaf as-path-expand-stat {
           type string;
           description "AS path expand statistics";
         }
         leaf as-path-expand.heading {
           type string;
           description "Prepend AS numbers prior to adding local-as (BGP only)";
         }
         leaf as-path-sequence {
           type string;
         }
         leaf last-as-count {
           type uint32;
         }
       }
       container assisted-replication {
         leaf assisted-replication-stat {
           type string;
           description "Assisted replication";
         }
         leaf assisted-replication.heading {
           type string;
         }
         leaf replicator-ip {
           type string;
         }
         leaf strict-mode {
           type string;
         }
         leaf fallback-replicator-ip {
           type string;
         }
       }
       container bgp-output-queue-priority {
         leaf bgp-output-queue-priority-stat {
           type string;
           description "BGP output queue priority statistics";
         }
         leaf bgp-output-queue-priority.heading {
           type string;
           description "The BGP Update output queue priority";
         }
         leaf expedited {
           type empty;
         }
         leaf queue-priority {
           type uint32;
         }
       }
       container then-color {
         leaf color-stat {
           type string;
           description "Color statistics";
         }
         leaf then-color.heading {
           type string;
         }
         leaf add-metric {
           type uint32;
         }
         leaf subtract-metric {
           type uint32;
         }
         leaf metric1 {
           type uint32;
           description "Metric value";
         }
       }
       container then-color2 {
         leaf color2-stat {
           type string;
           description "Color2 statistics";
         }
         leaf then-color2.heading {
           type string;
         }
         leaf add-metric {
           type uint32;
         }
         leaf subtract-metric {
           type uint32;
         }
         leaf metric1 {
           type uint32;
           description "Metric value";
         }
       }
       container then-color3 {
         leaf color3-stat {
           type string;
           description "Color3 statistics";
         }
         leaf then-color3.heading {
           type string;
         }
         leaf add-metric {
           type uint32;
         }
         leaf subtract-metric {
           type uint32;
         }
         leaf metric1 {
           type uint32;
           description "Metric value";
         }
       }
       container then-color4 {
         leaf color4-stat {
           type string;
           description "Color4 statistics";
         }
         leaf then-color4.heading {
           type string;
         }
         leaf add-metric {
           type uint32;
         }
         leaf subtract-metric {
           type uint32;
         }
         leaf metric1 {
           type uint32;
           description "Metric value";
         }
       }
       container then-community {
         leaf community-stat {
           type string;
           description "Community statistics";
         }
         leaf then-community.heading {
           type string;
         }
         leaf add {
           type empty;
         }
         leaf set {
           type empty;
           description "Set BGP tunnel attribute in the route";
         }
         leaf community-delete {
           type empty;
         }
         leaf community-name {
           type string;
         }
       }
       container credibility {
         leaf credibility-stat {
           type string;
           description "Credibility statistics";
         }
         leaf credibility.heading {
           type string;
         }
         leaf add-metric {
           type uint32;
         }
         leaf subtract-metric {
           type uint32;
         }
         leaf metric1 {
           type uint32;
           description "Metric value";
         }
       }
       container install-nexthop {
         leaf install-nexthop-stat {
           type string;
           description "Install nexthop statistics";
         }
         leaf install-nexthop.heading {
           type string;
           description "The next hop to be used for forwarding";
         }
         leaf lsp {
           type string;
           description "Label switched path name";
         }
         leaf lsp-regex {
           type string;
           description "Label switched path name regular expression";
         }
         leaf non-labelled-nexthop {
           type empty;
         }
         leaf non-lsp-nexthop {
           type empty;
         }
         leaf static-lsp {
           type string;
         }
         leaf static-lsp-regex {
           type string;
         }
         leaf strict {
           type empty;
         }
         leaf strict-named-lsp {
           type empty;
         }
         leaf address {
           type jt:ipaddr;
         }
         leaf overlay-vxlan-interfaces {
           type empty;
         }
         leaf nh-select {
           type string;
         }
         leaf hash {
           type uint32;
         }
         container except {
           leaf lsp {
             type string;
             description "Label switched path name";
           }
           leaf lsp-regex {
             type string;
             description "Label switched path name regular expression";
           }
           leaf non-labelled-nexthop {
             type empty;
           }
           leaf non-lsp-nexthop {
             type empty;
           }
           leaf static-lsp {
             type string;
           }
           leaf static-lsp-regex {
             type string;
           }
           leaf overlay-vxlan-interfaces {
             type empty;
           }
         }
         container fallback {
           leaf lsp {
             type string;
             description "Label switched path name";
           }
           leaf lsp-regex {
             type string;
             description "Label switched path name regular expression";
           }
           leaf non-labelled-nexthop {
             type empty;
           }
           leaf non-lsp-nexthop {
             type empty;
           }
           leaf static-lsp {
             type string;
           }
           leaf static-lsp-regex {
             type string;
           }
           leaf overlay-vxlan-interfaces {
             type empty;
           }
         }
       }
       container localpreference {
         leaf policy-local-preference-stat {
           type string;
           description "Local preference statistics";
         }
         leaf localpreference.heading {
           type string;
         }
         leaf add-metric {
           type uint32;
         }
         leaf subtract-metric {
           type uint32;
         }
         leaf metric1 {
           type uint32;
           description "Metric value";
         }
       }
       container map-to-interface {
         leaf map-to-interface-stat {
           type string;
           description "Map to interface statistics";
         }
         leaf map-to-interface.heading {
           type string;
           description "Set output logical interface";
         }
         leaf-list interface {
           type string;
           description "Interface name or address";
         }
         leaf interface-name {
           type string;
           description "Name of interface";
         }
         leaf interface-flags {
           type int32;
         }
         leaf self {
           type empty;
         }
       }
       container source-based-forwarding {
         leaf source-based-forwarding-stat {
           type string;
           description "Source based forwarding statistics";
         }
         leaf source-based-forwarding.heading {
           type string;
         }
         container sbf-attributes {
           leaf sbf-next-table {
             type string;
           }
         }
       }
       container effective-aigp {
         leaf metric-offset {
           type uint32;
         }
       }
       container metric-expression {
         leaf metric-stat {
           type string;
           description "Metric statistics";
         }
         leaf metric-expression.heading {
           type string;
         }
         leaf expression-metric1-multiplier {
           type string;
         }
         leaf expression-metric1-offset {
           type int32;
         }
         leaf expression-metric2-multiplier {
           type string;
         }
         leaf expression-metric2-offset {
           type int32;
         }
       }
       container igp {
         leaf metric-offset {
           type uint32;
         }
       }
       container minimum-effective-aigp {
         leaf metric-offset {
           type uint32;
         }
       }
       container minimum-igp {
         leaf metric-offset {
           type uint32;
         }
       }
       container then-metric {
         leaf metric-stat {
           type string;
           description "Metric statistics";
         }
         leaf then-metric.heading {
           type string;
         }
         leaf metric1 {
           type uint32;
           description "Metric value";
         }
         leaf add-metric {
           type uint32;
         }
         leaf subtract-metric {
           type uint32;
         }
         leaf aigp-metric {
           type empty;
         }
       }
       container then-metric2 {
         leaf metric2-stat {
           type string;
           description "Metric2 statistics";
         }
         leaf then-metric2.heading {
           type string;
         }
         leaf metric1 {
           type uint32;
           description "Metric value";
         }
         leaf add-metric {
           type uint32;
         }
         leaf subtract-metric {
           type uint32;
         }
       }
       container then-metric3 {
         leaf metric3-stat {
           type string;
           description "Metric3 statistics";
         }
         leaf then-metric3.heading {
           type string;
         }
         leaf metric1 {
           type uint32;
           description "Metric value";
         }
         leaf add-metric {
           type uint32;
         }
         leaf subtract-metric {
           type uint32;
         }
       }
       container then-metric4 {
         leaf metric4-stat {
           type string;
           description "Metric4 statistics";
         }
         leaf then-metric4.heading {
           type string;
         }
         leaf metric1 {
           type uint32;
           description "Metric value";
         }
         leaf add-metric {
           type uint32;
         }
         leaf subtract-metric {
           type uint32;
         }
       }
       container then-metric5 {
         leaf metric5-stat {
           type string;
           description "Metric5 statistics";
         }
         leaf then-metric5.heading {
           type string;
         }
         leaf metric1 {
           type uint32;
           description "Metric value";
         }
         leaf add-metric {
           type uint32;
         }
         leaf subtract-metric {
           type uint32;
         }
       }
       container then-metric6 {
         leaf metric6-stat {
           type string;
           description "Metric6 statistics";
         }
         leaf then-metric6.heading {
           type string;
         }
         leaf metric1 {
           type uint32;
           description "Metric value";
         }
         leaf add-metric {
           type uint32;
         }
         leaf subtract-metric {
           type uint32;
         }
       }
       container then-metric7 {
         leaf metric7-stat {
           type string;
           description "Metric7 statistics";
         }
         leaf then-metric7.heading {
           type string;
         }
         leaf metric1 {
           type uint32;
           description "Metric value";
         }
         leaf add-metric {
           type uint32;
         }
         leaf subtract-metric {
           type uint32;
         }
       }
       container then-metric8 {
         leaf metric8-stat {
           type string;
           description "Metric8 statistics";
         }
         leaf then-metric8.heading {
           type string;
         }
         leaf metric1 {
           type uint32;
           description "Metric value";
         }
         leaf add-metric {
           type uint32;
         }
         leaf subtract-metric {
           type uint32;
         }
       }
       container then-metric9 {
         leaf metric9-stat {
           type string;
           description "Metric9 statistics";
         }
         leaf then-metric9.heading {
           type string;
         }
         leaf metric1 {
           type uint32;
           description "Metric value";
         }
         leaf add-metric {
           type uint32;
         }
         leaf subtract-metric {
           type uint32;
         }
       }
       container then-metric10 {
         leaf metric10-stat {
           type string;
           description "Metric10 statistics";
         }
         leaf then-metric10.heading {
           type string;
         }
         leaf metric1 {
           type uint32;
           description "Metric value";
         }
         leaf add-metric {
           type uint32;
         }
         leaf subtract-metric {
           type uint32;
         }
       }
       container then-metric11 {
         leaf metric11-stat {
           type string;
           description "Metric11 statistics";
         }
         leaf then-metric11.heading {
           type string;
         }
         leaf metric1 {
           type uint32;
           description "Metric value";
         }
         leaf add-metric {
           type uint32;
         }
         leaf subtract-metric {
           type uint32;
         }
       }
       container then-metric12 {
         leaf metric12-stat {
           type string;
           description "Metric12 statistics";
         }
         leaf then-metric12.heading {
           type string;
         }
         leaf metric1 {
           type uint32;
           description "Metric value";
         }
         leaf add-metric {
           type uint32;
         }
         leaf subtract-metric {
           type uint32;
         }
       }
       container then-nexthop {
         leaf next-hop-stat {
           type string;
           description "Nexthop statistics";
         }
         leaf then-nexthop.heading {
           type string;
         }
         leaf address {
           type jt:ipaddr;
         }
         leaf reject {
           type empty;
           description "Reject a route";
         }
         leaf discard {
           type empty;
         }
         leaf self {
           type empty;
         }
         leaf no-resolution {
           type empty;
         }
         leaf nexthop-peer-address {
           type empty;
         }
         leaf next-table {
           type string;
         }
       }
       container then-preference {
         leaf preference-stat {
           type string;
           description "Preference statistics";
         }
         leaf then-preference.heading {
           type string;
         }
         leaf metric1 {
           type uint32;
           description "Metric value";
         }
         leaf add-metric {
           type uint32;
         }
         leaf subtract-metric {
           type uint32;
         }
       }
       container then-preference2 {
         leaf preference2-stat {
           type string;
           description "Preference2 statistics";
         }
         leaf then-preference2.heading {
           type string;
         }
         leaf metric1 {
           type uint32;
           description "Metric value";
         }
         leaf add-metric {
           type uint32;
         }
         leaf subtract-metric {
           type uint32;
         }
       }
       container then-preference3 {
         leaf preference3-stat {
           type string;
           description "Preference3 statistics";
         }
         leaf then-preference3.heading {
           type string;
         }
         leaf metric1 {
           type uint32;
           description "Metric value";
         }
         leaf add-metric {
           type uint32;
         }
         leaf subtract-metric {
           type uint32;
         }
       }
       container then-preference4 {
         leaf preference4-stat {
           type string;
           description "Preference4 statistics";
         }
         leaf then-preference4.heading {
           type string;
         }
         leaf metric1 {
           type uint32;
           description "Metric value";
         }
         leaf add-metric {
           type uint32;
         }
         leaf subtract-metric {
           type uint32;
         }
       }
       container then-preference5 {
         leaf preference5-stat {
           type string;
           description "Preference5 statistics";
         }
         leaf then-preference5.heading {
           type string;
         }
         leaf metric1 {
           type uint32;
           description "Metric value";
         }
         leaf add-metric {
           type uint32;
         }
         leaf subtract-metric {
           type uint32;
         }
       }
       container then-preference6 {
         leaf preference6-stat {
           type string;
           description "Preference6 statistics";
         }
         leaf then-preference6.heading {
           type string;
         }
         leaf metric1 {
           type uint32;
           description "Metric value";
         }
         leaf add-metric {
           type uint32;
         }
         leaf subtract-metric {
           type uint32;
         }
       }
       container then-preference7 {
         leaf preference7-stat {
           type string;
           description "Preference7 statistics";
         }
         leaf then-preference7.heading {
           type string;
         }
         leaf metric1 {
           type uint32;
           description "Metric value";
         }
         leaf add-metric {
           type uint32;
         }
         leaf subtract-metric {
           type uint32;
         }
       }
       container then-preference8 {
         leaf preference8-stat {
           type string;
           description "Preference8 statistics";
         }
         leaf then-preference8.heading {
           type string;
         }
         leaf metric1 {
           type uint32;
           description "Metric value";
         }
         leaf add-metric {
           type uint32;
         }
         leaf subtract-metric {
           type uint32;
         }
       }
       container then-preference9 {
         leaf preference9-stat {
           type string;
           description "Preference9 statistics";
         }
         leaf then-preference9.heading {
           type string;
         }
         leaf metric1 {
           type uint32;
           description "Metric value";
         }
         leaf add-metric {
           type uint32;
         }
         leaf subtract-metric {
           type uint32;
         }
       }
       container then-preference10 {
         leaf preference10-stat {
           type string;
           description "Preference10 statistics";
         }
         leaf then-preference10.heading {
           type string;
         }
         leaf metric1 {
           type uint32;
           description "Metric value";
         }
         leaf add-metric {
           type uint32;
         }
         leaf subtract-metric {
           type uint32;
         }
       }
       container then-preference11 {
         leaf preference11-stat {
           type string;
           description "Preference11 statistics";
         }
         leaf then-preference11.heading {
           type string;
         }
         leaf metric1 {
           type uint32;
           description "Metric value";
         }
         leaf add-metric {
           type uint32;
         }
         leaf subtract-metric {
           type uint32;
         }
       }
       container then-preference12 {
         leaf preference12-stat {
           type string;
           description "Preference12 statistics";
         }
         leaf then-preference12.heading {
           type string;
         }
         leaf metric1 {
           type uint32;
           description "Metric value";
         }
         leaf add-metric {
           type uint32;
         }
         leaf subtract-metric {
           type uint32;
         }
       }
       container prefix-attribute-flags {
         leaf prefix-attribute-flags-stat {
           type string;
           description "Prefix attribute flag statistics";
         }
         leaf prefix-attribute-flags.heading {
           type string;
         }
         leaf node-segment-flag {
           type empty;
           description "Node segment flag";
         }
         leaf external-prefix-flag {
           type empty;
           description "External prefix flag";
         }
         leaf entropy-label-capability-flag {
           type empty;
           description "Entropy label capability flag";
         }
         leaf anycast-flag {
           type empty;
           description "Anycast flag";
         }
       }
       container prefix-segment {
         leaf prefix-segment-stat {
           type string;
           description "Prefix segment statistics";
         }
         leaf prefix-segment.heading {
           type string;
           description "The prefix segment attributes";
         }
         leaf prefix-segment-index-value {
           type uint32;
         }
         leaf node-segment {
           type empty;
         }
         leaf psid-extended-data {
           type int32;
           description "Prefix segment extendend information";
         }
         leaf redistribute {
           type empty;
         }
         container algorithm {
           leaf prefix-segment-index-value {
             type uint32;
           }
           leaf algorithm-name {
             type uint32;
           }
           leaf node-segment {
             type empty;
           }
           leaf redistribute {
             type empty;
           }
         }
       }
       container request-ack {
         leaf request-ack-stat {
           type string;
           description "Request acknowledgements statistics";
         }
         leaf request-ack.heading {
           type string;
           description "Request acknowledgements";
         }
         leaf route-ack {
           type empty;
           description "Route acknowledgements";
         }
         leaf nexthop-ack {
           type empty;
           description "Nexthop acknowledgements";
         }
       }
       container srv6 {
         leaf srv6-stat {
           type string;
           description "SRv6 SID";
         }
         leaf srv6.heading {
           type string;
         }
         leaf sid {
           type string;
         }
         leaf locator {
           type string;
           description "SRv6 locator";
         }
         leaf micro-dt4-sid {
           type empty;
         }
         leaf micro-dt6-sid {
           type empty;
         }
         leaf micro-dt46-sid {
           type empty;
         }
       }
       container then-tag {
         leaf tag-stat {
           type string;
           description "Policy tag statistics";
         }
         leaf then-tag.heading {
           type string;
         }
         leaf metric1 {
           type uint32;
           description "Metric value";
         }
         leaf add-metric {
           type uint32;
         }
         leaf subtract-metric {
           type uint32;
         }
       }
       container then-tag2 {
         leaf tag2-stat {
           type string;
           description "Policy tag2 statistics";
         }
         leaf then-tag2.heading {
           type string;
         }
         leaf metric1 {
           type uint32;
           description "Metric value";
         }
         leaf add-metric {
           type uint32;
         }
         leaf subtract-metric {
           type uint32;
         }
       }
       container then-tag3 {
         leaf tag3-stat {
           type string;
           description "Policy tag3 statistics";
         }
         leaf then-tag3.heading {
           type string;
         }
         leaf metric1 {
           type uint32;
           description "Metric value";
         }
         leaf add-metric {
           type uint32;
         }
         leaf subtract-metric {
           type uint32;
         }
       }
       container then-tag4 {
         leaf tag4-stat {
           type string;
           description "Policy tag4 statistics";
         }
         leaf then-tag4.heading {
           type string;
         }
         leaf metric1 {
           type uint32;
           description "Metric value";
         }
         leaf add-metric {
           type uint32;
         }
         leaf subtract-metric {
           type uint32;
         }
       }
       list tunnel-attribute {
         leaf tunnel-type {
           type string;
           description "Tunnel type";
         }
         leaf reference-count {
           type int32;
           description "Reference count";
         }
         leaf tunnel-data {
           type string;
           description "Tunnel Data";
         }
         leaf tunnel-attribute-stat {
           type string;
           description "Tunnel attribute statistics";
         }
         leaf-list tunnel-attribute.heading {
           type string;
           description "Tunnel attribute information";
         }
         leaf set {
           type empty;
           description "Set BGP tunnel attribute in the route";
         }
         leaf remove {
           type empty;
           description "Remove BGP tunnel attribute from the route";
         }
         leaf tunnel-attribute-name {
           type string;
           description "Name of a tunnel attribute , or 'all'";
         }
       }
       container policy-defaults {
         leaf route-filter-walk-up {
           type empty;
           description "Route filter walk up";
         }
         leaf route-filter-no-walk-up {
           type empty;
           description "Route filter no walk up";
         }
       }
       list term {
         leaf term-stat {
           type uint32;
         }
         leaf name {
           type string;
         }
         leaf get-route-range {
           type empty;
           description "Get route range";
         }
         container from {
           leaf aggregate-contributor-stat {
             type string;
             description "Aggregate contributor statistics";
           }
           leaf aggregate-contributor {
             type empty;
             description "Match more specifics of an aggregate";
           }
           leaf area-stat {
             type string;
             description "Area statistics";
           }
           leaf area {
             type uint32;
             description "OSPF area identifier";
           }
           leaf as-path-stat {
             type string;
             description "AS path statistics";
           }
           leaf as-path {
             type string;
             description "Name of AS path regular expression (BGP only)";
           }
           leaf as-path-group-stat {
             type string;
             description "AS path group statistics";
           }
           leaf as-path-group {
             type string;
             description "Name of AS path group (BGP only)";
           }
           leaf bgp-srte-discriminator-stat {
             type string;
             description "BGP SRTE discriminator statistics";
           }
           leaf bgp-srte-discriminator {
             type uint32;
             description "SRTE discriminator";
           }
           leaf bridge-domain-id-stat {
             type string;
             description "Bridge domain id statistics";
           }
           leaf bridge-domain-id {
             type uint32;
             description "Bridge Domain ID";
           }
           leaf color-stat {
             type string;
             description "Color statistics";
           }
           leaf color1 {
             type uint32;
             description "Color1";
           }
           leaf color2-stat {
             type string;
             description "Color2 statistics";
           }
           leaf color2 {
             type int32;
           }
           leaf color3-stat {
             type string;
             description "Color3 statistics";
           }
           leaf color3 {
             type uint32;
             description "Color 3";
           }
           leaf color4-stat {
             type string;
             description "Color4 statistics";
           }
           leaf color4 {
             type uint32;
             description "Color 4";
           }
           leaf community-stat {
             type string;
             description "Community statistics";
           }
           leaf-list community {
             type string;
             description "Basic community";
           }
           leaf condition-stat {
             type string;
             description "Condition statistics";
           }
           leaf condition {
             type string;
             description "Condition to match on";
           }
           leaf evpn-esi-stat {
             type string;
             description "EVPN esi statistics";
           }
           leaf-list evpn-esi {
             type string;
             description "ESI in EVPN Route";
           }
           leaf evpn-esi-value {
             type string;
           }
           leaf evpn-interconn-esi {
             type string;
           }
           leaf evpn-esi-status {
             type string;
           }
           leaf evpn-esi-state-bits {
             type int32;
           }
           leaf evpn-esi-min-isid {
             type int32;
           }
           leaf evpn-esi-mac-label {
             type int32;
           }
           leaf evpn-esi-aliasing-label {
             type int32;
           }
           leaf evpn-esi-split-horizon-label {
             type int32;
           }
           leaf evpn-esi-srv6-argument {
             type int32;
           }
           leaf evpn-esi-rt-label {
             type int32;
           }
           leaf evpn-esi-num-mac {
             type int32;
           }
           leaf evpn-esi-num-sgdb {
             type int32;
           }
           leaf evpn-esi-refcount {
             type int32;
           }
           leaf evpn-esi-nh-retry-count {
             type int32;
           }
           leaf evpn-esi-token-rt-nh {
             type int32;
           }
           leaf evpn-esi-srv6-token-rt-nh {
             type int32;
           }
           container evpn-esi-local-intf-information {
             leaf evpn-esi-num-local-intf {
               type int32;
             }
             leaf evpn-esi-local-intf-name {
               type string;
             }
             leaf evpn-esi-local-intf-status {
               type string;
             }
           }
           container evpn-esi-event-history-information {
             list evpn-esi-event-history-database {
               leaf evpn-esi-event-entry {
                 type string;
               }
             }
           }
           container evpn-esi-remote-pe-information {
             leaf evpn-esi-num-remote-pe {
               type int32;
             }
             list evpn-esi-remote-pe {
               leaf evpn-esi-remote-pe-ipaddr {
                 type jt:ipaddr;
               }
               leaf evpn-esi-remote-mac-label {
                 type int32;
               }
               leaf evpn-esi-remote-aliasing-label {
                 type int32;
               }
               leaf evpn-esi-remote-pe-mode {
                 type string;
               }
               container evpn-srv6-info {
                 leaf evpn-srv6-sid {
                   type jt:ipaddr;
                 }
                 leaf evpn-srv6-behavior {
                   type int32;
                 }
                 container evpn-srv6-ss {
                   leaf srv6-block-len {
                     type int32;
                   }
                   leaf srv6-node-len {
                     type int32;
                   }
                   leaf srv6-fn-len {
                     type int32;
                   }
                   leaf srv6-arg-len {
                     type int32;
                   }
                 }
               }
               leaf evpn-esi-remote-fp-label {
                 type int32;
               }
               leaf evpn-esi-remote-flags {
                 type int32;
               }
               leaf evpn-esi-num-remote-bd {
                 type int32;
               }
               leaf evpn-esi-remote-rd {
                 type string;
               }
               leaf evpn-esi-remote-nh {
                 type int32;
               }
               leaf evpn-esi-remote-srv6-nh {
                 type int32;
               }
               leaf evpn-esi-remote-mac-label-ts {
                 type string;
               }
               leaf evpn-esi-remote-token-rt-label {
                 type int32;
               }
               leaf evpn-esi-remote-token-rt-nh {
                 type int32;
               }
               leaf evpn-esi-remote-mac-count {
                 type int32;
               }
               leaf evpn-esi-remote-vlan-id {
                 type int32;
               }
               leaf evpn-esi-remote-flow-label-update-pending {
                 type string;
               }
             }
           }
           container evpn-esi-df-information {
             leaf esi-df-election-algorithm {
               type string;
             }
             leaf esi-granularity {
               type string;
             }
             leaf esi-lacp-oos-on-ndf {
               type string;
             }
             leaf esi-designated-forwarder {
               type string;
             }
             leaf esi-df-preference {
               type int32;
             }
             leaf esi-df-non-revertive {
               type string;
             }
             leaf-list esi-backup-forwarder {
               type string;
             }
             leaf-list esi-backup-df-preference {
               type int32;
             }
             leaf-list esi-backup-df-non-revertive {
               type string;
             }
             leaf esi-last-df-update-timestamp {
               type string;
             }
           }
           list evpn-esi-bd-remote-pe-information {
             leaf evpn-esi-bd-vlan {
               type int32;
             }
             leaf evpn-esi-bd-status {
               type string;
             }
             leaf evpn-esi-bd-state-bits {
               type int32;
             }
             leaf evpn-esi-bd-refcount {
               type int32;
             }
             leaf evpn-esi-bd-nh-retry-count {
               type int32;
             }
             leaf evpn-esi-bd-remote-prefix {
               type int32;
             }
             leaf evpn-esi-bd-token-rt-nh {
               type int32;
             }
             leaf evpn-esi-bd-num-remote-pe {
               type int32;
             }
             list evpn-esi-bd-remote-pe {
               leaf evpn-esi-bd-remote-pe-ipaddr {
                 type jt:ipaddr;
               }
               leaf evpn-esi-bd-remote-mac-label {
                 type int32;
               }
               leaf evpn-esi-bd-remote-aliasing-label {
                 type int32;
               }
               leaf evpn-esi-bd-remote-pe-mode {
                 type string;
               }
             }
           }
           leaf evpn-mac-route-stat {
             type string;
             description "EVPN mac route statistics";
           }
           leaf evpn-mac-route {
             type uint32;
             description "EVPN Mac Route type";
           }
           leaf evpn-tag-stat {
             type string;
             description "EVPN tag statistics";
           }
           leaf evpn-tag {
             type uint32;
             description "Tag in EVPN Route";
           }
           leaf family-stat {
             type string;
           }
           leaf family {
             type string;
           }
           leaf fib-complete-stat {
             type string;
             description "FIB complete Statistics";
           }
           leaf fib-complete {
             type empty;
             description "FIB complete";
           }
           leaf igp-instance-stat {
             type string;
             description "IGP instance statistics";
           }
           leaf igp-instance {
             type string;
             description "IGP instance";
           }
           leaf igp-instance-regex-stat {
             type string;
             description "IGP instance regex statistics";
           }
           leaf igp-instance-regex {
             type string;
             description "IGP instance regex";
           }
           leaf instance-stat {
             type string;
             description "Instance statistics";
           }
           leaf instance {
             type string;
             description "Routing protocol instance";
           }
           leaf-list instance-name {
             type string;
           }
           leaf instance-display-error {
             type string;
           }
           leaf edge-protection {
             type string;
           }
           leaf edge-protector {
             type string;
           }
           list reference-site {
             leaf automatic-site-name {
               type string;
               description "VPLS automatic site name";
             }
             leaf automatic-site-id-status {
               type string;
               description "VPLS automatic site identifier status";
             }
             leaf automatic-site-claim-id {
               type int32;
               description "Claim site identifier";
             }
             leaf automatic-site-collisions {
               type int32;
               description "Number of collisions";
             }
             leaf automatic-site-timer-status {
               type string;
               description "VPLS automatic site timer status";
             }
             leaf vpls-signaling-protocol-identifier {
               type string;
             }
             leaf local-site-id {
               type string;
             }
             leaf source-attachment-id {
               type string;
               description "Local source attachment identifier";
             }
             leaf vpls-id {
               type int32;
               description "VPLS instance identifier";
             }
             leaf l2vpn-id {
               type string;
             }
             leaf local-id {
               type jt:ipaddr;
             }
             leaf num-local-interfaces {
               type int32;
             }
             leaf num-local-interfaces-up {
               type int32;
             }
             leaf irb-present {
               type string;
             }
             leaf mesh-group-count {
               type int32;
             }
             leaf mesh-group-up-count {
               type int32;
             }
             leaf remote-site-id {
               type string;
             }
             leaf target-attachment-id {
               type string;
               description "Remote target attachment identifier";
             }
             list mesh-group-interfaces {
               leaf mesh-group-name {
                 type string;
                 description "Name of mesh-group";
               }
               leaf mesh-group-state {
                 type string;
                 description "Mesh-group state";
               }
               leaf mesh-group-id {
                 type int32;
                 description "Mesh-group Identifier";
               }
               list interface {
                 leaf interface-name {
                   type string;
                   description "Name of interface";
                 }
                 leaf interface-description {
                   type string;
                 }
                 leaf interface-flags-description {
                   type string;
                 }
                 leaf interface-flags {
                   type int32;
                 }
               }
             }
             list interface {
               leaf interface-name {
                 type string;
                 description "Name of interface";
               }
               leaf interface-id {
                 type int32;
               }
               leaf interface-description {
                 type string;
               }
               leaf interface-flags-description {
                 type string;
               }
               leaf interface-flags {
                 type int32;
               }
             }
             list label-block {
               leaf-list label-block.heading {
                 type string;
               }
               leaf label-block-base {
                 type int32;
               }
               leaf label-block-offset {
                 type int32;
               }
               leaf label-block-size {
                 type int32;
               }
               leaf label-block-range {
                 type int32;
               }
               leaf label-block-preference {
                 type int32;
               }
               leaf label-block-status-vector {
                 type string;
               }
             }
             list connection {
               leaf-list connection.heading {
                 type string;
               }
               leaf connection-id {
                 type string;
               }
               leaf connection-type {
                 type string;
               }
               leaf connection-status {
                 type string;
               }
               leaf last-change {
                 type string;
               }
               leaf up-transitions {
                 type int32;
               }
               leaf remote-pe {
                 type jt:ipaddr;
               }
               leaf control-word {
                 type string;
               }
               leaf control-word-type {
                 type string;
               }
               leaf interface-encapsulation {
                 type string;
               }
               leaf inbound-label {
                 type string;
               }
               leaf outbound-label {
                 type string;
               }
               leaf pw-status-tlv {
                 type string;
               }
               leaf local-pw-status-code {
                 type int32;
               }
               leaf remote-pw-status-code {
                 type int32;
               }
               leaf connection-protection {
                 type string;
               }
               leaf mesh-group-name {
                 type string;
                 description "Name of mesh-group";
               }
               leaf vc-flow-label-transmit {
                 type string;
               }
               leaf vc-flow-label-receive {
                 type string;
               }
               leaf auto-sensed {
                 type empty;
                 description "Auto-sensed";
               }
               container local-interface {
                 leaf interface-name {
                   type string;
                   description "Name of interface";
                 }
                 leaf interface-status {
                   type string;
                 }
                 leaf interface-encapsulation {
                   type string;
                 }
                 leaf working-status {
                   type string;
                 }
                 leaf profile-name {
                   type string;
                 }
                 leaf profile-varset-name {
                   type string;
                 }
                 leaf interface-description {
                   type string;
                 }
               }
               container remote-interface {
                 leaf interface-name {
                   type string;
                   description "Name of interface";
                 }
                 leaf interface-status {
                   type string;
                 }
                 leaf interface-encapsulation {
                   type string;
                 }
               }
               container connection-bandwidth {
                 leaf connection-bandwidth.heading {
                   type string;
                   description "Bandwidth of a layer 2 connection";
                 }
                 leaf bandwidth {
                   type int32;
                 }
                 leaf class-type {
                   type int32;
                 }
                 leaf class-bandwidth {
                   type int32;
                 }
               }
               container vpls-rsvp-te-p2mp-lsp-information {
                 leaf vpls-ingress-p2mp-branch-lsp-name {
                   type string;
                   description "Name of ingress point-to-multipoint branch LSP";
                 }
                 leaf vpls-ingress-p2mp-branch-lsp-state {
                   type string;
                   description "State of ingress point-to-multipoint branch LSP";
                 }
                 leaf vpls-egress-p2mp-branch-lsp-name {
                   type string;
                   description "Name of egress point-to-multipoint branch LSP";
                 }
                 leaf vpls-egress-p2mp-branch-lsp-state {
                   type string;
                   description "State of egress point-to-multipoint branch LSP";
                 }
               }
               container spe-info {
                 leaf spe-info.heading {
                   type string;
                 }
                 leaf local-ip-addr {
                   type jt:ipaddr;
                 }
                 leaf remote-ip-addr {
                   type jt:ipaddr;
                 }
                 leaf pw-status {
                   type string;
                 }
               }
               container history {
                 leaf history.category-heading {
                   type string;
                 }
                 leaf history.heading {
                   type string;
                 }
                 container history-element {
                   leaf log-time-stamp {
                     type string;
                   }
                   leaf log-event {
                     type string;
                   }
                   leaf changed-entity {
                     type string;
                   }
                 }
               }
             }
             list mesh-group-connection {
               leaf mesh-group-name {
                 type string;
                 description "Name of mesh-group";
               }
               list connection {
                 leaf-list connection.heading {
                   type string;
                 }
                 leaf connection-id {
                   type string;
                 }
                 leaf connection-type {
                   type string;
                 }
                 leaf connection-status {
                   type string;
                 }
                 leaf last-change {
                   type string;
                 }
                 leaf up-transitions {
                   type int32;
                 }
                 leaf remote-pe {
                   type jt:ipaddr;
                 }
                 leaf control-word {
                   type string;
                 }
                 leaf control-word-type {
                   type string;
                 }
                 leaf interface-encapsulation {
                   type string;
                 }
                 leaf inbound-label {
                   type string;
                 }
                 leaf outbound-label {
                   type string;
                 }
                 leaf pw-status-tlv {
                   type string;
                 }
                 leaf local-pw-status-code {
                   type int32;
                 }
                 leaf remote-pw-status-code {
                   type int32;
                 }
                 leaf connection-protection {
                   type string;
                 }
                 leaf mesh-group-name {
                   type string;
                   description "Name of mesh-group";
                 }
                 leaf vc-flow-label-transmit {
                   type string;
                 }
                 leaf vc-flow-label-receive {
                   type string;
                 }
                 leaf auto-sensed {
                   type empty;
                   description "Auto-sensed";
                 }
                 container local-interface {
                   leaf interface-name {
                     type string;
                     description "Name of interface";
                   }
                   leaf interface-status {
                     type string;
                   }
                   leaf interface-encapsulation {
                     type string;
                   }
                   leaf working-status {
                     type string;
                   }
                   leaf profile-name {
                     type string;
                   }
                   leaf profile-varset-name {
                     type string;
                   }
                   leaf interface-description {
                     type string;
                   }
                 }
                 container remote-interface {
                   leaf interface-name {
                     type string;
                     description "Name of interface";
                   }
                   leaf interface-status {
                     type string;
                   }
                   leaf interface-encapsulation {
                     type string;
                   }
                 }
                 container connection-bandwidth {
                   leaf connection-bandwidth.heading {
                     type string;
                     description "Bandwidth of a layer 2 connection";
                   }
                   leaf bandwidth {
                     type int32;
                   }
                   leaf class-type {
                     type int32;
                   }
                   leaf class-bandwidth {
                     type int32;
                   }
                 }
                 container vpls-rsvp-te-p2mp-lsp-information {
                   leaf vpls-ingress-p2mp-branch-lsp-name {
                     type string;
                     description "Name of ingress point-to-multipoint branch LSP";
                   }
                   leaf vpls-ingress-p2mp-branch-lsp-state {
                     type string;
                     description "State of ingress point-to-multipoint branch LSP";
                   }
                   leaf vpls-egress-p2mp-branch-lsp-name {
                     type string;
                     description "Name of egress point-to-multipoint branch LSP";
                   }
                   leaf vpls-egress-p2mp-branch-lsp-state {
                     type string;
                     description "State of egress point-to-multipoint branch LSP";
                   }
                 }
                 container history {
                   leaf history.category-heading {
                     type string;
                   }
                   leaf history.heading {
                     type string;
                   }
                   container history-element {
                     leaf log-time-stamp {
                       type string;
                     }
                     leaf log-event {
                       type string;
                     }
                     leaf changed-entity {
                       type string;
                     }
                   }
                 }
               }
             }
             container automatic-site-timers {
               leaf automatic-site-timers.heading {
                 type string;
               }
               leaf automatic-site-startup-wait-time {
                 type string;
               }
               leaf automatic-site-new-site-wait-time {
                 type string;
               }
               leaf automatic-site-collision-detect-time {
                 type string;
               }
               leaf automatic-site-reclaim-wait-time {
                 type string;
               }
             }
             container connections-summary {
               leaf vc-up-count {
                 type int32;
               }
               leaf vc-down-count {
                 type int32;
               }
             }
           }
           list ldp-vpls-reference-site {
             leaf vpls-signaling-protocol-identifier {
               type string;
             }
             leaf local-site-id {
               type string;
             }
             leaf vpls-id {
               type int32;
               description "VPLS instance identifier";
             }
             leaf l2vpn-id {
               type string;
             }
             leaf local-id {
               type jt:ipaddr;
             }
             leaf num-local-interfaces {
               type int32;
             }
             leaf num-local-interfaces-up {
               type int32;
             }
             leaf irb-present {
               type string;
             }
             leaf mesh-group-count {
               type int32;
             }
             leaf mesh-group-up-count {
               type int32;
             }
             leaf remote-site-id {
               type string;
             }
             list mesh-group-interfaces {
               leaf mesh-group-name {
                 type string;
                 description "Name of mesh-group";
               }
               leaf mesh-group-state {
                 type string;
                 description "Mesh-group state";
               }
               leaf mesh-group-id {
                 type int32;
                 description "Mesh-group Identifier";
               }
               list interface {
                 leaf interface-name {
                   type string;
                   description "Name of interface";
                 }
                 leaf interface-description {
                   type string;
                 }
                 leaf interface-flags-description {
                   type string;
                 }
                 leaf interface-flags {
                   type int32;
                 }
               }
             }
             list interface {
               leaf interface-name {
                 type string;
                 description "Name of interface";
               }
               leaf interface-id {
                 type int32;
               }
               leaf interface-description {
                 type string;
               }
               leaf interface-flags-description {
                 type string;
               }
               leaf interface-flags {
                 type int32;
               }
             }
             list connection {
               leaf-list connection.heading {
                 type string;
               }
               leaf connection-id {
                 type string;
               }
               leaf connection-type {
                 type string;
               }
               leaf connection-status {
                 type string;
               }
               leaf last-change {
                 type string;
               }
               leaf up-transitions {
                 type int32;
               }
               leaf remote-pe {
                 type jt:ipaddr;
               }
               leaf control-word {
                 type string;
               }
               leaf control-word-type {
                 type string;
               }
               leaf interface-encapsulation {
                 type string;
               }
               leaf inbound-label {
                 type string;
               }
               leaf outbound-label {
                 type string;
               }
               leaf pw-status-tlv {
                 type string;
               }
               leaf local-pw-status-code {
                 type int32;
               }
               leaf remote-pw-status-code {
                 type int32;
               }
               leaf connection-protection {
                 type string;
               }
               leaf mesh-group-name {
                 type string;
                 description "Name of mesh-group";
               }
               leaf vc-flow-label-transmit {
                 type string;
               }
               leaf vc-flow-label-receive {
                 type string;
               }
               leaf auto-sensed {
                 type empty;
                 description "Auto-sensed";
               }
               container local-interface {
                 leaf interface-name {
                   type string;
                   description "Name of interface";
                 }
                 leaf interface-status {
                   type string;
                 }
                 leaf interface-encapsulation {
                   type string;
                 }
                 leaf working-status {
                   type string;
                 }
                 leaf profile-name {
                   type string;
                 }
                 leaf profile-varset-name {
                   type string;
                 }
                 leaf interface-description {
                   type string;
                 }
               }
               container remote-interface {
                 leaf interface-name {
                   type string;
                   description "Name of interface";
                 }
                 leaf interface-status {
                   type string;
                 }
                 leaf interface-encapsulation {
                   type string;
                 }
               }
               container connection-bandwidth {
                 leaf connection-bandwidth.heading {
                   type string;
                   description "Bandwidth of a layer 2 connection";
                 }
                 leaf bandwidth {
                   type int32;
                 }
                 leaf class-type {
                   type int32;
                 }
                 leaf class-bandwidth {
                   type int32;
                 }
               }
               container vpls-rsvp-te-p2mp-lsp-information {
                 leaf vpls-ingress-p2mp-branch-lsp-name {
                   type string;
                   description "Name of ingress point-to-multipoint branch LSP";
                 }
                 leaf vpls-ingress-p2mp-branch-lsp-state {
                   type string;
                   description "State of ingress point-to-multipoint branch LSP";
                 }
                 leaf vpls-egress-p2mp-branch-lsp-name {
                   type string;
                   description "Name of egress point-to-multipoint branch LSP";
                 }
                 leaf vpls-egress-p2mp-branch-lsp-state {
                   type string;
                   description "State of egress point-to-multipoint branch LSP";
                 }
               }
               container history {
                 leaf history.category-heading {
                   type string;
                 }
                 leaf history.heading {
                   type string;
                 }
                 container history-element {
                   leaf log-time-stamp {
                     type string;
                   }
                   leaf log-event {
                     type string;
                   }
                   leaf changed-entity {
                     type string;
                   }
                 }
               }
             }
             list mesh-group-connection {
               leaf mesh-group-name {
                 type string;
                 description "Name of mesh-group";
               }
               list connection {
                 leaf-list connection.heading {
                   type string;
                 }
                 leaf connection-id {
                   type string;
                 }
                 leaf connection-type {
                   type string;
                 }
                 leaf connection-status {
                   type string;
                 }
                 leaf last-change {
                   type string;
                 }
                 leaf up-transitions {
                   type int32;
                 }
                 leaf remote-pe {
                   type jt:ipaddr;
                 }
                 leaf control-word {
                   type string;
                 }
                 leaf control-word-type {
                   type string;
                 }
                 leaf interface-encapsulation {
                   type string;
                 }
                 leaf inbound-label {
                   type string;
                 }
                 leaf outbound-label {
                   type string;
                 }
                 leaf pw-status-tlv {
                   type string;
                 }
                 leaf local-pw-status-code {
                   type int32;
                 }
                 leaf remote-pw-status-code {
                   type int32;
                 }
                 leaf connection-protection {
                   type string;
                 }
                 leaf mesh-group-name {
                   type string;
                   description "Name of mesh-group";
                 }
                 leaf vc-flow-label-transmit {
                   type string;
                 }
                 leaf vc-flow-label-receive {
                   type string;
                 }
                 leaf auto-sensed {
                   type empty;
                   description "Auto-sensed";
                 }
                 container local-interface {
                   leaf interface-name {
                     type string;
                     description "Name of interface";
                   }
                   leaf interface-status {
                     type string;
                   }
                   leaf interface-encapsulation {
                     type string;
                   }
                   leaf working-status {
                     type string;
                   }
                   leaf profile-name {
                     type string;
                   }
                   leaf profile-varset-name {
                     type string;
                   }
                   leaf interface-description {
                     type string;
                   }
                 }
                 container remote-interface {
                   leaf interface-name {
                     type string;
                     description "Name of interface";
                   }
                   leaf interface-status {
                     type string;
                   }
                   leaf interface-encapsulation {
                     type string;
                   }
                 }
                 container connection-bandwidth {
                   leaf connection-bandwidth.heading {
                     type string;
                     description "Bandwidth of a layer 2 connection";
                   }
                   leaf bandwidth {
                     type int32;
                   }
                   leaf class-type {
                     type int32;
                   }
                   leaf class-bandwidth {
                     type int32;
                   }
                 }
                 container vpls-rsvp-te-p2mp-lsp-information {
                   leaf vpls-ingress-p2mp-branch-lsp-name {
                     type string;
                     description "Name of ingress point-to-multipoint branch LSP";
                   }
                   leaf vpls-ingress-p2mp-branch-lsp-state {
                     type string;
                     description "State of ingress point-to-multipoint branch LSP";
                   }
                   leaf vpls-egress-p2mp-branch-lsp-name {
                     type string;
                     description "Name of egress point-to-multipoint branch LSP";
                   }
                   leaf vpls-egress-p2mp-branch-lsp-state {
                     type string;
                     description "State of egress point-to-multipoint branch LSP";
                   }
                 }
                 container history {
                   leaf history.category-heading {
                     type string;
                   }
                   leaf history.heading {
                     type string;
                   }
                   container history-element {
                     leaf log-time-stamp {
                       type string;
                     }
                     leaf log-event {
                       type string;
                     }
                     leaf changed-entity {
                       type string;
                     }
                   }
                 }
               }
             }
             container connections-summary {
               leaf vc-up-count {
                 type int32;
               }
               leaf vc-down-count {
                 type int32;
               }
             }
           }
           container vpls-protocol-state {
             leaf vpls-signaling-protocol-identifier {
               type string;
             }
             leaf num-local-interfaces {
               type int32;
             }
             leaf num-local-interfaces-up {
               type int32;
             }
             leaf irb-present {
               type string;
             }
             leaf mesh-group-count {
               type int32;
             }
             leaf mesh-group-up-count {
               type int32;
             }
             list mesh-group-interfaces {
               list interface {
                 leaf interface-name {
                   type string;
                   description "Name of interface";
                 }
                 leaf interface-flags {
                   type int32;
                 }
               }
             }
             list interface {
               leaf interface-name {
                 type string;
                 description "Name of interface";
               }
               leaf interface-flags {
                 type int32;
               }
             }
             list mesh-group-connection {
               leaf mesh-group-name {
                 type string;
                 description "Name of mesh-group";
               }
               list connection {
                 leaf-list connection.heading {
                   type string;
                 }
                 leaf remote-pe {
                   type jt:ipaddr;
                 }
                 leaf l2vpn-local-site-id {
                   type int32;
                   description "Local site identifier";
                 }
                 leaf l2vpn-remote-site-id {
                   type int32;
                   description "Remote site identifier";
                 }
                 leaf connection-status {
                   type string;
                 }
                 leaf last-change {
                   type string;
                 }
                 leaf inbound-label {
                   type string;
                 }
                 leaf outbound-label {
                   type string;
                 }
                 container local-interface {
                   leaf interface-name {
                     type string;
                     description "Name of interface";
                   }
                   leaf interface-status {
                     type string;
                   }
                   leaf interface-encapsulation {
                     type string;
                   }
                   leaf working-status {
                     type string;
                   }
                   leaf profile-name {
                     type string;
                   }
                   leaf profile-varset-name {
                     type string;
                   }
                   leaf interface-description {
                     type string;
                   }
                 }
                 container connection-bandwidth {
                   leaf connection-bandwidth.heading {
                     type string;
                     description "Bandwidth of a layer 2 connection";
                   }
                   leaf bandwidth {
                     type int32;
                   }
                   leaf class-type {
                     type int32;
                   }
                   leaf class-bandwidth {
                     type int32;
                   }
                 }
                 container vpls-rsvp-te-p2mp-lsp-information {
                   leaf vpls-ingress-p2mp-branch-lsp-name {
                     type string;
                     description "Name of ingress point-to-multipoint branch LSP";
                   }
                   leaf vpls-ingress-p2mp-branch-lsp-state {
                     type string;
                     description "State of ingress point-to-multipoint branch LSP";
                   }
                   leaf vpls-egress-p2mp-branch-lsp-name {
                     type string;
                     description "Name of egress point-to-multipoint branch LSP";
                   }
                   leaf vpls-egress-p2mp-branch-lsp-state {
                     type string;
                     description "State of egress point-to-multipoint branch LSP";
                   }
                 }
                 container history {
                   leaf history.category-heading {
                     type string;
                   }
                   leaf history.heading {
                     type string;
                   }
                   container history-element {
                     leaf log-time-stamp {
                       type string;
                     }
                     leaf log-event {
                       type string;
                     }
                     leaf changed-entity {
                       type string;
                     }
                   }
                 }
               }
               container connections-summary {
                 leaf vc-up-count {
                   type int32;
                 }
                 leaf vc-down-count {
                   type int32;
                 }
               }
             }
             list reference-site {
               leaf automatic-site-name {
                 type string;
                 description "VPLS automatic site name";
               }
               leaf automatic-site-id-status {
                 type string;
                 description "VPLS automatic site identifier status";
               }
               leaf automatic-site-claim-id {
                 type int32;
                 description "Claim site identifier";
               }
               leaf automatic-site-collisions {
                 type int32;
                 description "Number of collisions";
               }
               leaf automatic-site-timer-status {
                 type string;
                 description "VPLS automatic site timer status";
               }
               leaf vpls-signaling-protocol-identifier {
                 type string;
               }
               leaf local-site-id {
                 type string;
               }
               leaf source-attachment-id {
                 type string;
                 description "Local source attachment identifier";
               }
               leaf vpls-id {
                 type int32;
                 description "VPLS instance identifier";
               }
               leaf l2vpn-id {
                 type string;
               }
               leaf local-id {
                 type jt:ipaddr;
               }
               leaf num-local-interfaces {
                 type int32;
               }
               leaf num-local-interfaces-up {
                 type int32;
               }
               leaf irb-present {
                 type string;
               }
               leaf mesh-group-count {
                 type int32;
               }
               leaf mesh-group-up-count {
                 type int32;
               }
               leaf remote-site-id {
                 type string;
               }
               leaf target-attachment-id {
                 type string;
                 description "Remote target attachment identifier";
               }
               list mesh-group-interfaces {
                 leaf mesh-group-name {
                   type string;
                   description "Name of mesh-group";
                 }
                 leaf mesh-group-state {
                   type string;
                   description "Mesh-group state";
                 }
                 leaf mesh-group-id {
                   type int32;
                   description "Mesh-group Identifier";
                 }
                 list interface {
                   leaf interface-name {
                     type string;
                     description "Name of interface";
                   }
                   leaf interface-description {
                     type string;
                   }
                   leaf interface-flags-description {
                     type string;
                   }
                   leaf interface-flags {
                     type int32;
                   }
                 }
               }
               list interface {
                 leaf interface-name {
                   type string;
                   description "Name of interface";
                 }
                 leaf interface-id {
                   type int32;
                 }
                 leaf interface-description {
                   type string;
                 }
                 leaf interface-flags-description {
                   type string;
                 }
                 leaf interface-flags {
                   type int32;
                 }
               }
               list connection {
                 container history {
                 }
               }
               list mesh-group-connection {
                 list connection {
                   container history {
                   }
                 }
               }
             }
           }
           container vpls-rsvp-te-ingress-p2mp-lsp {
             leaf vpls-ingress-p2mp-lsp-name {
               type string;
               description "Name of ingress point-to-multipoint LSP";
             }
             leaf vpls-rsvp-te-p2mp-flood-nexthop-id {
               type int32;
               description "Identifier for VPLS RSVP traffic-engineering ingress flood next hop";
             }
           }
           container multihome {
             leaf multihome.heading {
               type string;
             }
             list multihome-site {
               leaf multihome-site-name {
                 type string;
                 description "Name of site";
               }
               leaf multihome-site-id {
                 type int32;
                 description "Site Identifier";
               }
               leaf multihome-site-preference {
                 type int32;
                 description "Site Preference";
               }
               leaf multihome-site-state {
                 type string;
                 description "Site state";
               }
               leaf multihome-num-interfaces {
                 type int32;
               }
               leaf multihome-num-interfaces-up {
                 type int32;
               }
               list interface {
                 leaf interface-name {
                   type string;
                   description "Name of interface";
                 }
                 leaf interface-id {
                   type int32;
                 }
                 leaf interface-description {
                   type string;
                 }
                 leaf interface-flags-description {
                   type string;
                 }
                 leaf interface-flags {
                   type int32;
                 }
               }
               container remote-advertisements {
                 leaf remote-advertisements.heading {
                   type string;
                 }
                 list remote-adv {
                   leaf remote-adv-addr {
                     type string;
                   }
                   leaf remote-adv-preference {
                     type int32;
                     description "Remote PE preference";
                   }
                   leaf remote-adv-ctrl-flag {
                     type int32;
                     description "Remote PE Control flags";
                   }
                   leaf remote-adv-ctrl-flag-description {
                     type string;
                     description "Control flags description";
                   }
                 }
               }
             }
           }
           container history {
             leaf history.category-heading {
               type string;
             }
             leaf history.heading {
               type string;
             }
             container history-element {
               leaf log-time-stamp {
                 type string;
               }
               leaf log-event {
                 type string;
               }
               leaf changed-entity {
                 type string;
               }
             }
           }
           leaf instance-any-stat {
             type string;
             description "Instance any statistics";
           }
           leaf instance-any {
             type empty;
             description "Any routing protocol instance";
           }
           leaf instance-list-stat {
             type string;
             description "Instance list statistics";
           }
           leaf instance-list {
             type string;
             description "A list of routing protocol instances";
           }
           leaf interface-stat {
             type string;
             description "Interface statistics";
           }
           leaf-list interface {
             type string;
             description "Interface name or address";
           }
           leaf interface-name {
             type string;
             description "Name of interface";
           }
           leaf interface-flags {
             type int32;
           }
           leaf policy-level-stat {
             type string;
             description "Level statistics";
           }
           leaf policy-level {
             type uint32;
           }
           leaf policy-local-preference-stat {
             type string;
             description "Local preference statistics";
           }
           leaf policy-local-preference {
             type uint32;
             description "Local preference associated with a route";
           }
           leaf lsp-stat {
             type string;
             description "LSP statistics";
           }
           leaf lsp {
             type string;
             description "Label switched path name";
           }
           leaf lsp-regex-stat {
             type string;
             description "LSP regex statistics";
           }
           leaf lsp-regex {
             type string;
             description "Label switched path name regular expression";
           }
           leaf metric-stat {
             type string;
             description "Metric statistics";
           }
           leaf metric1 {
             type uint32;
             description "Metric value";
           }
           leaf metric2-stat {
             type string;
             description "Metric2 statistics";
           }
           leaf metric-2 {
             type uint32;
             description "Metric value 2";
           }
           leaf metric3-stat {
             type string;
             description "Metric3 statistics";
           }
           leaf metric3 {
             type uint32;
             description "Metric value 3";
           }
           leaf metric4-stat {
             type string;
             description "Metric4 statistics";
           }
           leaf metric4 {
             type uint32;
             description "Metric value 4";
           }
           leaf metric5-stat {
             type string;
             description "Metric5 statistics";
           }
           leaf metric5 {
             type uint32;
             description "Metric value 5";
           }
           leaf metric6-stat {
             type string;
             description "Metric6 statistics";
           }
           leaf metric6 {
             type uint32;
             description "Metric value 6";
           }
           leaf metric7-stat {
             type string;
             description "Metric7 statistics";
           }
           leaf metric7 {
             type uint32;
             description "Metric value 7";
           }
           leaf metric8-stat {
             type string;
             description "Metric8 statistics";
           }
           leaf metric8 {
             type uint32;
             description "Metric value 8";
           }
           leaf metric9-stat {
             type string;
             description "Metric9 statistics";
           }
           leaf metric9 {
             type uint32;
             description "Metric value 9";
           }
           leaf metric10-stat {
             type string;
             description "Metric10 statistics";
           }
           leaf metric10 {
             type uint32;
             description "Metric value 10";
           }
           leaf metric11-stat {
             type string;
             description "Metric11 statistics";
           }
           leaf metric11 {
             type uint32;
             description "Metric value 11";
           }
           leaf metric12-stat {
             type string;
             description "Metric12 statistics";
           }
           leaf metric12 {
             type uint32;
             description "Metric value 12";
           }
           leaf policy-neighbor-stat {
             type string;
             description "Policy neighbor statistics";
           }
           leaf policy-neighbor {
             type string;
             description "Neighboring router";
           }
           leaf next-hop-stat {
             type string;
             description "Nexthop statistics";
           }
           leaf next-hop {
             type jt:ipaddr;
             description "Next-hop address";
           }
           leaf next-hop-type-stat {
             type string;
             description "Nexthop type statistics";
           }
           leaf next-hop-type {
             type string;
             description "Next-hop type";
           }
           leaf nlri-route-type-stat {
             type string;
             description "NLRI route type statistics";
           }
           leaf nlri-route-type {
             type uint32;
             description "Route type from NLRI (1..10)";
           }
           leaf origin-stat {
             type string;
             description "Origin statistics";
           }
           leaf origin {
             type string;
             description "BGP origin attribute";
           }
           leaf policy-name-stat {
             type string;
             description "Policy statistics";
           }
           leaf policy-name {
             type string;
             description "Name of the policy";
           }
           leaf preference-stat {
             type string;
             description "Preference statistics";
           }
           leaf preference1 {
             type uint32;
           }
           leaf preference2-stat {
             type string;
             description "Preference2 statistics";
           }
           leaf preference-2 {
             type uint32;
             description "Preference value 2";
           }
           leaf preference3-stat {
             type string;
             description "Preference3 statistics";
           }
           leaf preference3 {
             type uint32;
             description "Preference value 3";
           }
           leaf preference4-stat {
             type string;
             description "Preference4 statistics";
           }
           leaf preference4 {
             type uint32;
             description "Preference value 4";
           }
           leaf preference5-stat {
             type string;
             description "Preference5 statistics";
           }
           leaf preference5 {
             type uint32;
             description "Preference value 5";
           }
           leaf preference6-stat {
             type string;
             description "Preference6 statistics";
           }
           leaf preference6 {
             type uint32;
             description "Preference value 6";
           }
           leaf preference7-stat {
             type string;
             description "Preference7 statistics";
           }
           leaf preference7 {
             type uint32;
             description "Preference value 7";
           }
           leaf preference8-stat {
             type string;
             description "Preference8 statistics";
           }
           leaf preference8 {
             type uint32;
             description "Preference value 8";
           }
           leaf preference9-stat {
             type string;
             description "Preference9 statistics";
           }
           leaf preference9 {
             type uint32;
             description "Preference value 9";
           }
           leaf preference10-stat {
             type string;
             description "Preference10 statistics";
           }
           leaf preference10 {
             type uint32;
             description "Preference value 10";
           }
           leaf preference11-stat {
             type string;
             description "Preference11 statistics";
           }
           leaf preference11 {
             type uint32;
             description "Preference value 11";
           }
           leaf preference12-stat {
             type string;
             description "Preference12 statistics";
           }
           leaf preference12 {
             type uint32;
             description "Preference value 12";
           }
           leaf prefix-list-stat {
             type string;
             description "Prefix list statistics";
           }
           leaf prefix-list {
             type string;
             description "List of prefix-lists of routes to match";
           }
           leaf prefix-string-stat {
             type string;
             description "Prefix segment statistics";
           }
           leaf prefix-string {
             type string;
             description "Prefix string";
           }
           leaf programmed-stat {
             type string;
             description "Programmed statistics";
           }
           leaf programmed {
             type empty;
             description "API-programmed route";
           }
           leaf protocol-stat {
             type string;
             description "Protocol statistics";
           }
           leaf-list protocol {
             type string;
             description "Protocol from which route was learned";
           }
           leaf rib-stat {
             type string;
             description "RIB statistics";
           }
           leaf rib {
             type string;
             description "Routing table";
           }
           leaf rib-list-stat {
             type string;
             description "RIB list statistics";
           }
           leaf rib-list {
             type string;
             description "RIB list";
           }
           leaf route-distinguisher-stat {
             type string;
             description "Route distinguisher statistics";
           }
           leaf route-distinguisher {
             type string;
             description "Name of the route-distinguisher";
           }
           leaf route-type-stat {
             type string;
             description "Route type statistics";
           }
           leaf route-type {
             type string;
             description "Route type";
           }
           leaf rtf-prefix-list-stat {
             type string;
             description "RTF prefix list statistics";
           }
           leaf rtf-prefix-list {
             type string;
             description "List of rtf-prefix-lists of routes to match";
           }
           leaf source-address-filter-list-stat {
             type string;
             description "Source address filter list statistics";
           }
           leaf source-address-filter-list {
             type string;
             description "List of source-address-filter-lists of routes to match";
           }
           leaf srte-color-stat {
             type string;
             description "SRTE color statistics";
           }
           leaf srte-color {
             type uint32;
             description "SRTE color";
           }
           leaf state-stat {
             type string;
             description "State statistics";
           }
           leaf state {
             type string;
             description "HFRR profile Current state";
           }
           leaf tag-stat {
             type string;
             description "Policy tag statistics";
           }
           leaf policy-tag {
             type uint32;
             description "Tag string";
           }
           leaf tag2-stat {
             type string;
             description "Policy tag2 statistics";
           }
           leaf policy-tag2 {
             type uint32;
             description "Tag string 2";
           }
           leaf tag3-stat {
             type string;
             description "Policy tag3 statistics";
           }
           leaf policy-tag3 {
             type uint32;
             description "Tag string 3";
           }
           leaf tag4-stat {
             type string;
             description "Policy tag4 statistics";
           }
           leaf policy-tag4 {
             type uint32;
             description "Tag string 4";
           }
           leaf tunnel-type-stat {
             type string;
             description "Tunnel type statistics";
           }
           leaf tunnel-type {
             type string;
             description "Tunnel type";
           }
           leaf validation-state-stat {
             type string;
             description "Validation database statistics";
           }
           leaf validation-database {
             type string;
             description "Name to identify a validation-state";
           }
           leaf mac-filter-list-stat {
             type string;
             description "MAC filter list statistics";
           }
           leaf mac-filter-list {
             type string;
             description "List of mac-filter-list macs to match";
           }
           leaf mac-filter {
             type string;
             description "Information on mac filter";
           }
           leaf global {
             type empty;
           }
           leaf as-path-calc-length-stat {
             type string;
             description "AS path calculation length statistics";
           }
           leaf as-path-neighbors-stat {
             type string;
             description "AS path neighbors statistics";
           }
           leaf as-path-origins-stat {
             type string;
             description "AS path origins statistics";
           }
           leaf as-path-transits-stat {
             type string;
             description "AS path transits statistics";
           }
           leaf as-path-unique-count-stat {
             type string;
             description "AS path unique count statistics";
           }
           leaf community-count-stat {
             type string;
             description "Community count statistics";
           }
           leaf large-community-count-stat {
             type string;
             description "Large community count statistics";
           }
           leaf external-stat {
             type string;
             description "External statistics";
           }
           leaf multicast-scope-stat {
             type string;
             description "Multicast scope statistics";
           }
           leaf next-hop-weight-stat {
             type string;
             description "Nexthop weight statistics";
           }
           leaf next-hop-ecmp-stat {
             type string;
             description "Nexthop ecmp statistics";
           }
           leaf prefix-list-filter-stat {
             type string;
             description "Prefix list filter statistics";
           }
           leaf prefix-segment-stat {
             type string;
             description "Prefix segment statistics";
           }
           leaf route-filter-stat {
             type string;
             description "Route filter statistics";
           }
           leaf route-filter-list-stat {
             type string;
             description "Route filter list statistics";
           }
           leaf source-routing-path-stat {
             type string;
             description "Source routing path statistics";
           }
           leaf traffic-engineering-stat {
             type string;
             description "Traffic engineering statistics";
           }
           leaf validation-database-instance-stat {
             type string;
             description "Validation database instance statistics";
           }
           container as-path-calc-length {
             leaf as-path-calc-length-stat {
               type string;
               description "AS path calculation length statistics";
             }
             leaf as-path-calc-length.heading {
               type string;
               description "Number of BGP ASes excluding confederations";
             }
             leaf equal {
               type empty;
             }
             leaf orhigher {
               type empty;
             }
             leaf orlower {
               type empty;
             }
             leaf as-path-calc-length-value {
               type uint32;
             }
           }
           container as-path-neighbors {
             leaf as-path-neighbors-stat {
               type string;
               description "AS path neighbors statistics";
             }
             leaf as-path-neighbors.heading {
               type string;
             }
             leaf as-list {
               type string;
               description "AS list name";
             }
             leaf as-list-group {
               type string;
               description "AS list group name";
             }
           }
           container as-path-origins {
             leaf as-path-origins-stat {
               type string;
               description "AS path origins statistics";
             }
             leaf as-path-origins.heading {
               type string;
             }
             leaf as-list {
               type string;
               description "AS list name";
             }
             leaf as-list-group {
               type string;
               description "AS list group name";
             }
           }
           container as-path-transits {
             leaf as-path-transits-stat {
               type string;
               description "AS path transits statistics";
             }
             leaf as-path-transits.heading {
               type string;
             }
             leaf as-list {
               type string;
               description "AS list name";
             }
             leaf as-list-group {
               type string;
               description "AS list group name";
             }
           }
           container as-path-unique-count {
             leaf as-path-unique-count-stat {
               type string;
               description "AS path unique count statistics";
             }
             leaf as-path-unique-count.heading {
               type string;
               description "Number of unique BGP ASes excluding confederations";
             }
             leaf equal {
               type empty;
             }
             leaf orhigher {
               type empty;
             }
             leaf orlower {
               type empty;
             }
             leaf policy-value {
               type uint32;
             }
           }
           container external {
             leaf external-stat {
               type string;
               description "External statistics";
             }
             leaf external.heading {
               type string;
               description "External route";
             }
             leaf external-type {
               type uint32;
             }
             leaf nssa-only {
               type empty;
             }
           }
           list multicast-scope {
             leaf multicast-scope-stat {
               type string;
               description "Multicast scope statistics";
             }
             leaf-list multicast-scope.heading {
               type string;
               description "Multicast scope to match";
             }
             leaf orlower {
               type empty;
             }
             leaf orhigher {
               type empty;
             }
             leaf equal {
               type empty;
             }
             leaf multicast-scope-value {
               type uint32;
               description "Multicast scope value";
             }
             leaf interface-name {
               type string;
               description "Name of interface";
             }
             leaf scope-rejects {
               type uint32;
               description "Number of rejects in multicast scope";
             }
             leaf link-local {
               type empty;
             }
             leaf node-local {
               type empty;
             }
             leaf organization-local {
               type empty;
             }
             leaf site-local {
               type empty;
             }
             leaf global {
               type empty;
             }
           }
           container next-hop-ecmp {
             leaf all-nexthop {
               type empty;
             }
             leaf next-hop-ecmp-stat {
               type string;
               description "Nexthop ecmp statistics";
             }
             leaf next-hop-ecmp.heading {
               type string;
               description "Nexthop ecmp";
             }
             leaf equal-to {
               type uint32;
             }
             leaf greater-than {
               type uint32;
             }
             leaf greater-than-equal {
               type uint32;
             }
             leaf less-than {
               type uint32;
             }
             leaf less-than-equal {
               type uint32;
             }
           }
           container policy-path-type {
             leaf path-type-stat {
               type string;
               description "Path type statistics";
             }
             leaf policy-path-type.heading {
               type string;
             }
             leaf protect {
               type empty;
               description "Path type protect";
             }
             leaf working {
               type empty;
               description "Path type working";
             }
           }
           list prefix-list-filter {
             leaf prefix-list-filter-stat {
               type string;
               description "Prefix list filter statistics";
             }
             leaf-list prefix-list-filter.heading {
               type string;
             }
             leaf prefix-list-filter-name {
               type string;
             }
             container policy-extended-information {
               leaf account {
                 type empty;
                 description "Account";
               }
               leaf accept {
                 type empty;
                 description "Accept a route";
               }
               leaf advertise-locator {
                 type empty;
                 description "Advertise SRv6 locator";
               }
               leaf advertise-locator-internal {
                 type empty;
                 description "Advertise SRv6 locator internal";
               }
               leaf aggregate-bandwidth {
                 type int32;
                 description "Aggregate bandwidth";
               }
               leaf auto-link-bandwidth {
                 type empty;
                 description "Auto link bandwidth";
               }
               leaf analyze {
                 type empty;
                 description "Send to registered controllers for analysis";
               }
               leaf as-path-prepend {
                 type uint32;
                 description "Prepend AS numbers to an AS path (BGP only)";
               }
               leaf cos-next-hop-map {
                 type string;
                 description "The CoS-based next-hop map in forwarding table";
               }
               leaf damping {
                 type string;
                 description "Define BGP route flap damping parameters";
               }
               leaf default-action {
                 type string;
                 description "The default policy action";
               }
               leaf destination-class {
                 type string;
                 description "The destination class in forwarding table";
               }
               leaf dynamic-tunnel-attributes {
                 type string;
                 description "The dynamic tunnel attributes used for forwarding";
               }
               leaf fib-install-priority {
                 type string;
                 description "FIB install priority";
               }
               leaf filter {
                 type string;
                 description "Next-hop firewall filter";
               }
               leaf get-route-range {
                 type empty;
                 description "Get route range";
               }
               leaf ignore-service-label {
                 type string;
                 description "Ignore service labels";
               }
               leaf install-to-fib {
                 type string;
                 description "Install to FIB";
               }
               leaf ipv4-source-router-id {
                 type empty;
               }
               leaf ipv4-source-router-id-address {
                 type string;
                 description "IPV4 source router id address";
               }
               leaf ipv6-source-router-id {
                 type empty;
               }
               leaf ipv6-source-router-id-address {
                 type string;
                 description "IPV6 source router id address";
               }
               leaf label-allocation {
                 type string;
                 description "Label allocation mode";
               }
               leaf label-allocation-fallback-reject {
                 type string;
                 description "Suppress prefix export when label allocation fails";
               }
               leaf limit-bandwidth {
                 type uint64;
                 description "Limit advertised aggregate outbound link bandwidth";
               }
               leaf load-balance {
                 type string;
                 description "Load-balancing algorithm chosen";
               }
               leaf mhop-bfd-port {
                 type uint32;
                 description "Use port number 4784 for MPLS-BFD as per RFC5884";
               }
               leaf multipath-resolve {
                 type string;
                 description "Use all paths for resolution over this prefix";
               }
               leaf next {
                 type string;
                 description "Skip to next policy or term";
               }
               leaf no-backup {
                 type empty;
                 description "This prefix should not have backup";
               }
               leaf no-entropy-label-capability {
                 type empty;
                 description "Don't advertise entropy label capability";
               }
               leaf no-route-localize {
                 type empty;
                 description "No route localize";
               }
               leaf origin {
                 type string;
                 description "BGP origin attribute";
               }
               leaf p2mp-lsp-root {
                 type jt:ipaddr;
                 description "P2mp lsp root address";
               }
               leaf policy-priority {
                 type string;
               }
               leaf reject {
                 type empty;
                 description "Reject a route";
               }
               leaf request-long-lived-ack {
                 type empty;
                 description "Advertise route after forwarding is programmed";
               }
               leaf resolution-map {
                 type string;
                 description "Resolution map";
               }
               leaf resolution-map-mode {
                 type string;
                 description "Resolution map modes";
               }
               leaf selected-mldp-egress {
                 type string;
                 description "This node should act as egress node for MLDP inband signalling";
               }
               leaf send-withdrawal-on-route-change {
                 type empty;
                 description "Withdrawn route as change is not ack'd from forwarding";
               }
               leaf set-down-bit {
                 type empty;
                 description "Set down bit";
               }
               leaf slice {
                 type string;
                 description "Slice name";
               }
               leaf source-class {
                 type string;
                 description "The source class in forwarding table";
               }
               leaf sr-te-template {
                 type string;
                 description "SR TE template to apply";
               }
               leaf ssm-source {
                 type jt:ipaddr;
                 description "List of Sources for SSM mapping";
               }
               leaf trace {
                 type empty;
                 description "Log matches to a trace file";
               }
               leaf tunnel-end-point-address {
                 type string;
                 description "Set tunnel end-point address of tunnel";
               }
               leaf validation-state {
                 type string;
                 description "Validation-state of a route";
               }
               container install-nexthop {
                 container except {
                   leaf lsp {
                     type string;
                     description "Label switched path name";
                   }
                   leaf lsp-regex {
                     type string;
                     description "Label switched path name regular expression";
                   }
                   leaf non-labelled-nexthop {
                     type empty;
                   }
                   leaf non-lsp-nexthop {
                     type empty;
                   }
                   leaf static-lsp {
                     type string;
                   }
                   leaf static-lsp-regex {
                     type string;
                   }
                   leaf overlay-vxlan-interfaces {
                     type empty;
                   }
                 }
                 container fallback {
                   leaf lsp {
                     type string;
                     description "Label switched path name";
                   }
                   leaf lsp-regex {
                     type string;
                     description "Label switched path name regular expression";
                   }
                   leaf non-labelled-nexthop {
                     type empty;
                   }
                   leaf non-lsp-nexthop {
                     type empty;
                   }
                   leaf static-lsp {
                     type string;
                   }
                   leaf static-lsp-regex {
                     type string;
                   }
                   leaf overlay-vxlan-interfaces {
                     type empty;
                   }
                 }
                 leaf install-nexthop-stat {
                   type string;
                   description "Install nexthop statistics";
                 }
                 leaf install-nexthop.heading {
                   type string;
                   description "The next hop to be used for forwarding";
                 }
                 leaf lsp {
                   type string;
                   description "Label switched path name";
                 }
                 leaf lsp-regex {
                   type string;
                   description "Label switched path name regular expression";
                 }
                 leaf non-labelled-nexthop {
                   type empty;
                 }
                 leaf non-lsp-nexthop {
                   type empty;
                 }
                 leaf static-lsp {
                   type string;
                 }
                 leaf static-lsp-regex {
                   type string;
                 }
                 leaf strict {
                   type empty;
                 }
                 leaf strict-named-lsp {
                   type empty;
                 }
                 leaf address {
                   type jt:ipaddr;
                 }
                 leaf overlay-vxlan-interfaces {
                   type empty;
                 }
                 leaf nh-select {
                   type string;
                 }
                 leaf hash {
                   type uint32;
                 }
               }
               container map-to-interface {
                 list interface {
                   leaf interface-name {
                     type string;
                     description "Name of interface";
                   }
                   leaf interface-flags {
                     type int32;
                   }
                 }
                 leaf map-to-interface-stat {
                   type string;
                   description "Map to interface statistics";
                 }
                 leaf map-to-interface.heading {
                   type string;
                   description "Set output logical interface";
                 }
                 leaf self {
                   type empty;
                 }
               }
               container then-metric {
                 leaf metric-stat {
                   type string;
                   description "Metric statistics";
                 }
                 leaf then-metric.heading {
                   type string;
                 }
                 leaf metric1 {
                   type uint32;
                   description "Metric value";
                 }
                 leaf add-metric {
                   type uint32;
                 }
                 leaf subtract-metric {
                   type uint32;
                 }
                 leaf aigp-metric {
                   type empty;
                 }
                 container effective-aigp {
                   leaf metric-offset {
                     type uint32;
                   }
                 }
                 container igp {
                   leaf metric-offset {
                     type uint32;
                   }
                 }
                 container minimum-effective-aigp {
                   leaf metric-offset {
                     type uint32;
                   }
                 }
                 container minimum-igp {
                   leaf metric-offset {
                     type uint32;
                   }
                 }
               }
               container prefix-segment {
                 leaf redistribute {
                   type empty;
                 }
                 container algorithm {
                   leaf prefix-segment-index-value {
                     type uint32;
                   }
                   leaf algorithm-name {
                     type uint32;
                   }
                   leaf node-segment {
                     type empty;
                   }
                   leaf redistribute {
                     type empty;
                   }
                 }
                 leaf prefix-segment-stat {
                   type string;
                   description "Prefix segment statistics";
                 }
                 leaf prefix-segment.heading {
                   type string;
                   description "The prefix segment attributes";
                 }
                 leaf prefix-segment-index-value {
                   type uint32;
                 }
                 leaf node-segment {
                   type empty;
                 }
                 leaf psid-extended-data {
                   type int32;
                   description "Prefix segment extendend information";
                 }
               }
               list tunnel-attribute {
                 leaf tunnel-type {
                   type string;
                   description "Tunnel type";
                 }
                 leaf reference-count {
                   type int32;
                   description "Reference count";
                 }
                 leaf tunnel-data {
                   type string;
                   description "Tunnel Data";
                 }
                 leaf tunnel-attribute-stat {
                   type string;
                   description "Tunnel attribute statistics";
                 }
                 leaf-list tunnel-attribute.heading {
                   type string;
                   description "Tunnel attribute information";
                 }
                 leaf set {
                   type empty;
                   description "Set BGP tunnel attribute in the route";
                 }
                 leaf remove {
                   type empty;
                   description "Remove BGP tunnel attribute from the route";
                 }
                 leaf tunnel-attribute-name {
                   type string;
                   description "Name of a tunnel attribute , or 'all'";
                 }
               }
               container source-based-forwarding {
                 container sbf-attributes {
                   leaf sbf-next-table {
                     type string;
                   }
                 }
                 leaf source-based-forwarding-stat {
                   type string;
                   description "Source based forwarding statistics";
                 }
                 leaf source-based-forwarding.heading {
                   type string;
                 }
               }
               container policy-label {
                 leaf-list label-value {
                   type uint32;
                   description "Label value";
                 }
                 leaf label-range {
                   type int32;
                   description "Label range for l2vpn";
                 }
               }
               leaf-list class {
                 type string;
                 description "An instance of BGP output queue statistics";
               }
               container add-path {
                 leaf add-path-stat {
                   type string;
                 }
                 leaf add-path.heading {
                   type string;
                   description "BGP add-path attributes";
                 }
                 leaf sendcount {
                   type uint32;
                   description "Number of add-paths sent";
                 }
               }
               container aigp-adjust {
                 leaf aigp-adjust-stat {
                   type string;
                   description "AIGP adjust statistics";
                 }
                 leaf aigp-adjust.heading {
                   type string;
                   description "Adjust a BGP AIGP attribute";
                 }
                 leaf distance-to-protocol-nexthop {
                   type empty;
                 }
                 leaf add {
                   type empty;
                 }
                 leaf divide {
                   type empty;
                 }
                 leaf multiply {
                   type empty;
                 }
                 leaf subtract {
                   type empty;
                 }
                 leaf user-value {
                   type uint64;
                 }
               }
               container aigp-originate {
                 leaf aigp-originate-stat {
                   type string;
                   description "AIGP originate statistics";
                 }
                 leaf aigp-originate.heading {
                   type string;
                   description "Originate a BGP AIGP attribute";
                 }
                 leaf distance {
                   type uint32;
                   description "AIGP distance";
                 }
               }
               container as-path-expand {
                 leaf as-path-expand-stat {
                   type string;
                   description "AS path expand statistics";
                 }
                 leaf as-path-expand.heading {
                   type string;
                   description "Prepend AS numbers prior to adding local-as (BGP only)";
                 }
                 leaf as-path-sequence {
                   type string;
                 }
                 leaf last-as-count {
                   type uint32;
                 }
               }
               container assisted-replication {
                 leaf assisted-replication-stat {
                   type string;
                   description "Assisted replication";
                 }
                 leaf assisted-replication.heading {
                   type string;
                 }
                 leaf replicator-ip {
                   type string;
                 }
                 leaf strict-mode {
                   type string;
                 }
                 leaf fallback-replicator-ip {
                   type string;
                 }
               }
               container bgp-output-queue-priority {
                 leaf bgp-output-queue-priority-stat {
                   type string;
                   description "BGP output queue priority statistics";
                 }
                 leaf bgp-output-queue-priority.heading {
                   type string;
                   description "The BGP Update output queue priority";
                 }
                 leaf expedited {
                   type empty;
                 }
                 leaf queue-priority {
                   type uint32;
                 }
               }
               container then-color {
                 leaf color-stat {
                   type string;
                   description "Color statistics";
                 }
                 leaf then-color.heading {
                   type string;
                 }
                 leaf add-metric {
                   type uint32;
                 }
                 leaf subtract-metric {
                   type uint32;
                 }
                 leaf metric1 {
                   type uint32;
                   description "Metric value";
                 }
               }
               container then-color2 {
                 leaf color2-stat {
                   type string;
                   description "Color2 statistics";
                 }
                 leaf then-color2.heading {
                   type string;
                 }
                 leaf add-metric {
                   type uint32;
                 }
                 leaf subtract-metric {
                   type uint32;
                 }
                 leaf metric1 {
                   type uint32;
                   description "Metric value";
                 }
               }
               container then-color3 {
                 leaf color3-stat {
                   type string;
                   description "Color3 statistics";
                 }
                 leaf then-color3.heading {
                   type string;
                 }
                 leaf add-metric {
                   type uint32;
                 }
                 leaf subtract-metric {
                   type uint32;
                 }
                 leaf metric1 {
                   type uint32;
                   description "Metric value";
                 }
               }
               container then-color4 {
                 leaf color4-stat {
                   type string;
                   description "Color4 statistics";
                 }
                 leaf then-color4.heading {
                   type string;
                 }
                 leaf add-metric {
                   type uint32;
                 }
                 leaf subtract-metric {
                   type uint32;
                 }
                 leaf metric1 {
                   type uint32;
                   description "Metric value";
                 }
               }
               container then-community {
                 leaf community-stat {
                   type string;
                   description "Community statistics";
                 }
                 leaf then-community.heading {
                   type string;
                 }
                 leaf add {
                   type empty;
                 }
                 leaf set {
                   type empty;
                   description "Set BGP tunnel attribute in the route";
                 }
                 leaf community-delete {
                   type empty;
                 }
                 leaf community-name {
                   type string;
                 }
               }
               container credibility {
                 leaf credibility-stat {
                   type string;
                   description "Credibility statistics";
                 }
                 leaf credibility.heading {
                   type string;
                 }
                 leaf add-metric {
                   type uint32;
                 }
                 leaf subtract-metric {
                   type uint32;
                 }
                 leaf metric1 {
                   type uint32;
                   description "Metric value";
                 }
               }
               container external {
                 leaf external-stat {
                   type string;
                   description "External statistics";
                 }
                 leaf external.heading {
                   type string;
                   description "External route";
                 }
                 leaf external-type {
                   type uint32;
                 }
                 leaf nssa-only {
                   type empty;
                 }
               }
               container localpreference {
                 leaf policy-local-preference-stat {
                   type string;
                   description "Local preference statistics";
                 }
                 leaf localpreference.heading {
                   type string;
                 }
                 leaf add-metric {
                   type uint32;
                 }
                 leaf subtract-metric {
                   type uint32;
                 }
                 leaf metric1 {
                   type uint32;
                   description "Metric value";
                 }
               }
               container then-metric2 {
                 leaf metric2-stat {
                   type string;
                   description "Metric2 statistics";
                 }
                 leaf then-metric2.heading {
                   type string;
                 }
                 leaf metric1 {
                   type uint32;
                   description "Metric value";
                 }
                 leaf add-metric {
                   type uint32;
                 }
                 leaf subtract-metric {
                   type uint32;
                 }
               }
               container then-metric3 {
                 leaf metric3-stat {
                   type string;
                   description "Metric3 statistics";
                 }
                 leaf then-metric3.heading {
                   type string;
                 }
                 leaf metric1 {
                   type uint32;
                   description "Metric value";
                 }
                 leaf add-metric {
                   type uint32;
                 }
                 leaf subtract-metric {
                   type uint32;
                 }
               }
               container then-metric4 {
                 leaf metric4-stat {
                   type string;
                   description "Metric4 statistics";
                 }
                 leaf then-metric4.heading {
                   type string;
                 }
                 leaf metric1 {
                   type uint32;
                   description "Metric value";
                 }
                 leaf add-metric {
                   type uint32;
                 }
                 leaf subtract-metric {
                   type uint32;
                 }
               }
               container then-metric5 {
                 leaf metric5-stat {
                   type string;
                   description "Metric5 statistics";
                 }
                 leaf then-metric5.heading {
                   type string;
                 }
                 leaf metric1 {
                   type uint32;
                   description "Metric value";
                 }
                 leaf add-metric {
                   type uint32;
                 }
                 leaf subtract-metric {
                   type uint32;
                 }
               }
               container then-metric6 {
                 leaf metric6-stat {
                   type string;
                   description "Metric6 statistics";
                 }
                 leaf then-metric6.heading {
                   type string;
                 }
                 leaf metric1 {
                   type uint32;
                   description "Metric value";
                 }
                 leaf add-metric {
                   type uint32;
                 }
                 leaf subtract-metric {
                   type uint32;
                 }
               }
               container then-metric7 {
                 leaf metric7-stat {
                   type string;
                   description "Metric7 statistics";
                 }
                 leaf then-metric7.heading {
                   type string;
                 }
                 leaf metric1 {
                   type uint32;
                   description "Metric value";
                 }
                 leaf add-metric {
                   type uint32;
                 }
                 leaf subtract-metric {
                   type uint32;
                 }
               }
               container then-metric8 {
                 leaf metric8-stat {
                   type string;
                   description "Metric8 statistics";
                 }
                 leaf then-metric8.heading {
                   type string;
                 }
                 leaf metric1 {
                   type uint32;
                   description "Metric value";
                 }
                 leaf add-metric {
                   type uint32;
                 }
                 leaf subtract-metric {
                   type uint32;
                 }
               }
               container then-metric9 {
                 leaf metric9-stat {
                   type string;
                   description "Metric9 statistics";
                 }
                 leaf then-metric9.heading {
                   type string;
                 }
                 leaf metric1 {
                   type uint32;
                   description "Metric value";
                 }
                 leaf add-metric {
                   type uint32;
                 }
                 leaf subtract-metric {
                   type uint32;
                 }
               }
               container then-metric10 {
                 leaf metric10-stat {
                   type string;
                   description "Metric10 statistics";
                 }
                 leaf then-metric10.heading {
                   type string;
                 }
                 leaf metric1 {
                   type uint32;
                   description "Metric value";
                 }
                 leaf add-metric {
                   type uint32;
                 }
                 leaf subtract-metric {
                   type uint32;
                 }
               }
               container then-metric11 {
                 leaf metric11-stat {
                   type string;
                   description "Metric11 statistics";
                 }
                 leaf then-metric11.heading {
                   type string;
                 }
                 leaf metric1 {
                   type uint32;
                   description "Metric value";
                 }
                 leaf add-metric {
                   type uint32;
                 }
                 leaf subtract-metric {
                   type uint32;
                 }
               }
               container then-metric12 {
                 leaf metric12-stat {
                   type string;
                   description "Metric12 statistics";
                 }
                 leaf then-metric12.heading {
                   type string;
                 }
                 leaf metric1 {
                   type uint32;
                   description "Metric value";
                 }
                 leaf add-metric {
                   type uint32;
                 }
                 leaf subtract-metric {
                   type uint32;
                 }
               }
               container then-nexthop {
                 leaf next-hop-stat {
                   type string;
                   description "Nexthop statistics";
                 }
                 leaf then-nexthop.heading {
                   type string;
                 }
                 leaf address {
                   type jt:ipaddr;
                 }
                 leaf reject {
                   type empty;
                   description "Reject a route";
                 }
                 leaf discard {
                   type empty;
                 }
                 leaf self {
                   type empty;
                 }
                 leaf no-resolution {
                   type empty;
                 }
                 leaf nexthop-peer-address {
                   type empty;
                 }
                 leaf next-table {
                   type string;
                 }
               }
               container then-preference {
                 leaf preference-stat {
                   type string;
                   description "Preference statistics";
                 }
                 leaf then-preference.heading {
                   type string;
                 }
                 leaf metric1 {
                   type uint32;
                   description "Metric value";
                 }
                 leaf add-metric {
                   type uint32;
                 }
                 leaf subtract-metric {
                   type uint32;
                 }
               }
               container then-preference2 {
                 leaf preference2-stat {
                   type string;
                   description "Preference2 statistics";
                 }
                 leaf then-preference2.heading {
                   type string;
                 }
                 leaf metric1 {
                   type uint32;
                   description "Metric value";
                 }
                 leaf add-metric {
                   type uint32;
                 }
                 leaf subtract-metric {
                   type uint32;
                 }
               }
               container then-preference3 {
                 leaf preference3-stat {
                   type string;
                   description "Preference3 statistics";
                 }
                 leaf then-preference3.heading {
                   type string;
                 }
                 leaf metric1 {
                   type uint32;
                   description "Metric value";
                 }
                 leaf add-metric {
                   type uint32;
                 }
                 leaf subtract-metric {
                   type uint32;
                 }
               }
               container then-preference4 {
                 leaf preference4-stat {
                   type string;
                   description "Preference4 statistics";
                 }
                 leaf then-preference4.heading {
                   type string;
                 }
                 leaf metric1 {
                   type uint32;
                   description "Metric value";
                 }
                 leaf add-metric {
                   type uint32;
                 }
                 leaf subtract-metric {
                   type uint32;
                 }
               }
               container then-preference5 {
                 leaf preference5-stat {
                   type string;
                   description "Preference5 statistics";
                 }
                 leaf then-preference5.heading {
                   type string;
                 }
                 leaf metric1 {
                   type uint32;
                   description "Metric value";
                 }
                 leaf add-metric {
                   type uint32;
                 }
                 leaf subtract-metric {
                   type uint32;
                 }
               }
               container then-preference6 {
                 leaf preference6-stat {
                   type string;
                   description "Preference6 statistics";
                 }
                 leaf then-preference6.heading {
                   type string;
                 }
                 leaf metric1 {
                   type uint32;
                   description "Metric value";
                 }
                 leaf add-metric {
                   type uint32;
                 }
                 leaf subtract-metric {
                   type uint32;
                 }
               }
               container then-preference7 {
                 leaf preference7-stat {
                   type string;
                   description "Preference7 statistics";
                 }
                 leaf then-preference7.heading {
                   type string;
                 }
                 leaf metric1 {
                   type uint32;
                   description "Metric value";
                 }
                 leaf add-metric {
                   type uint32;
                 }
                 leaf subtract-metric {
                   type uint32;
                 }
               }
               container then-preference8 {
                 leaf preference8-stat {
                   type string;
                   description "Preference8 statistics";
                 }
                 leaf then-preference8.heading {
                   type string;
                 }
                 leaf metric1 {
                   type uint32;
                   description "Metric value";
                 }
                 leaf add-metric {
                   type uint32;
                 }
                 leaf subtract-metric {
                   type uint32;
                 }
               }
               container then-preference9 {
                 leaf preference9-stat {
                   type string;
                   description "Preference9 statistics";
                 }
                 leaf then-preference9.heading {
                   type string;
                 }
                 leaf metric1 {
                   type uint32;
                   description "Metric value";
                 }
                 leaf add-metric {
                   type uint32;
                 }
                 leaf subtract-metric {
                   type uint32;
                 }
               }
               container then-preference10 {
                 leaf preference10-stat {
                   type string;
                   description "Preference10 statistics";
                 }
                 leaf then-preference10.heading {
                   type string;
                 }
                 leaf metric1 {
                   type uint32;
                   description "Metric value";
                 }
                 leaf add-metric {
                   type uint32;
                 }
                 leaf subtract-metric {
                   type uint32;
                 }
               }
               container then-preference11 {
                 leaf preference11-stat {
                   type string;
                   description "Preference11 statistics";
                 }
                 leaf then-preference11.heading {
                   type string;
                 }
                 leaf metric1 {
                   type uint32;
                   description "Metric value";
                 }
                 leaf add-metric {
                   type uint32;
                 }
                 leaf subtract-metric {
                   type uint32;
                 }
               }
               container then-preference12 {
                 leaf preference12-stat {
                   type string;
                   description "Preference12 statistics";
                 }
                 leaf then-preference12.heading {
                   type string;
                 }
                 leaf metric1 {
                   type uint32;
                   description "Metric value";
                 }
                 leaf add-metric {
                   type uint32;
                 }
                 leaf subtract-metric {
                   type uint32;
                 }
               }
               container prefix-attribute-flags {
                 leaf prefix-attribute-flags-stat {
                   type string;
                   description "Prefix attribute flag statistics";
                 }
                 leaf prefix-attribute-flags.heading {
                   type string;
                 }
                 leaf node-segment-flag {
                   type empty;
                   description "Node segment flag";
                 }
                 leaf external-prefix-flag {
                   type empty;
                   description "External prefix flag";
                 }
                 leaf entropy-label-capability-flag {
                   type empty;
                   description "Entropy label capability flag";
                 }
                 leaf anycast-flag {
                   type empty;
                   description "Anycast flag";
                 }
               }
               container request-ack {
                 leaf request-ack-stat {
                   type string;
                   description "Request acknowledgements statistics";
                 }
                 leaf request-ack.heading {
                   type string;
                   description "Request acknowledgements";
                 }
                 leaf route-ack {
                   type empty;
                   description "Route acknowledgements";
                 }
                 leaf nexthop-ack {
                   type empty;
                   description "Nexthop acknowledgements";
                 }
               }
               container srv6 {
                 leaf srv6-stat {
                   type string;
                   description "SRv6 SID";
                 }
                 leaf srv6.heading {
                   type string;
                 }
                 leaf sid {
                   type string;
                 }
                 leaf locator {
                   type string;
                   description "SRv6 locator";
                 }
                 leaf micro-dt4-sid {
                   type empty;
                 }
                 leaf micro-dt6-sid {
                   type empty;
                 }
                 leaf micro-dt46-sid {
                   type empty;
                 }
               }
               container then-tag {
                 leaf tag-stat {
                   type string;
                   description "Policy tag statistics";
                 }
                 leaf then-tag.heading {
                   type string;
                 }
                 leaf metric1 {
                   type uint32;
                   description "Metric value";
                 }
                 leaf add-metric {
                   type uint32;
                 }
                 leaf subtract-metric {
                   type uint32;
                 }
               }
               container then-tag2 {
                 leaf tag2-stat {
                   type string;
                   description "Policy tag2 statistics";
                 }
                 leaf then-tag2.heading {
                   type string;
                 }
                 leaf metric1 {
                   type uint32;
                   description "Metric value";
                 }
                 leaf add-metric {
                   type uint32;
                 }
                 leaf subtract-metric {
                   type uint32;
                 }
               }
               container then-tag3 {
                 leaf tag3-stat {
                   type string;
                   description "Policy tag3 statistics";
                 }
                 leaf then-tag3.heading {
                   type string;
                 }
                 leaf metric1 {
                   type uint32;
                   description "Metric value";
                 }
                 leaf add-metric {
                   type uint32;
                 }
                 leaf subtract-metric {
                   type uint32;
                 }
               }
               container then-tag4 {
                 leaf tag4-stat {
                   type string;
                   description "Policy tag4 statistics";
                 }
                 leaf then-tag4.heading {
                   type string;
                 }
                 leaf metric1 {
                   type uint32;
                   description "Metric value";
                 }
                 leaf add-metric {
                   type uint32;
                 }
                 leaf subtract-metric {
                   type uint32;
                 }
               }
               container metric-expression {
                 leaf metric-stat {
                   type string;
                   description "Metric statistics";
                 }
                 leaf metric-expression.heading {
                   type string;
                 }
                 leaf expression-metric1-multiplier {
                   type string;
                 }
                 leaf expression-metric1-offset {
                   type int32;
                 }
                 leaf expression-metric2-multiplier {
                   type string;
                 }
                 leaf expression-metric2-offset {
                   type int32;
                 }
               }
             }
           }
           container prefix-segment {
             leaf redistribute {
               type empty;
             }
             container algorithm {
               leaf prefix-segment-index-value {
                 type uint32;
               }
               leaf algorithm-name {
                 type uint32;
               }
               leaf node-segment {
                 type empty;
               }
               leaf redistribute {
                 type empty;
               }
             }
             leaf prefix-segment-stat {
               type string;
               description "Prefix segment statistics";
             }
             leaf prefix-segment.heading {
               type string;
               description "The prefix segment attributes";
             }
             leaf prefix-segment-index-value {
               type uint32;
             }
             leaf node-segment {
               type empty;
             }
             leaf psid-extended-data {
               type int32;
               description "Prefix segment extendend information";
             }
           }
           list route-filter {
             leaf route-filter-stat {
               type string;
               description "Route filter statistics";
             }
             leaf-list route-filter.heading {
               type string;
               description "Entries in martian table";
             }
             leaf address {
               type jt:ipaddr;
             }
             leaf flags {
               type string;
               description "Enabled trace flags";
             }
             leaf match-count {
               type uint64;
             }
             container policy-extended-information {
               leaf account {
                 type empty;
                 description "Account";
               }
               leaf accept {
                 type empty;
                 description "Accept a route";
               }
               leaf advertise-locator {
                 type empty;
                 description "Advertise SRv6 locator";
               }
               leaf advertise-locator-internal {
                 type empty;
                 description "Advertise SRv6 locator internal";
               }
               leaf aggregate-bandwidth {
                 type int32;
                 description "Aggregate bandwidth";
               }
               leaf auto-link-bandwidth {
                 type empty;
                 description "Auto link bandwidth";
               }
               leaf analyze {
                 type empty;
                 description "Send to registered controllers for analysis";
               }
               leaf as-path-prepend {
                 type uint32;
                 description "Prepend AS numbers to an AS path (BGP only)";
               }
               leaf cos-next-hop-map {
                 type string;
                 description "The CoS-based next-hop map in forwarding table";
               }
               leaf damping {
                 type string;
                 description "Define BGP route flap damping parameters";
               }
               leaf default-action {
                 type string;
                 description "The default policy action";
               }
               leaf destination-class {
                 type string;
                 description "The destination class in forwarding table";
               }
               leaf dynamic-tunnel-attributes {
                 type string;
                 description "The dynamic tunnel attributes used for forwarding";
               }
               leaf fib-install-priority {
                 type string;
                 description "FIB install priority";
               }
               leaf filter {
                 type string;
                 description "Next-hop firewall filter";
               }
               leaf get-route-range {
                 type empty;
                 description "Get route range";
               }
               leaf ignore-service-label {
                 type string;
                 description "Ignore service labels";
               }
               leaf install-to-fib {
                 type string;
                 description "Install to FIB";
               }
               leaf ipv4-source-router-id {
                 type empty;
               }
               leaf ipv4-source-router-id-address {
                 type string;
                 description "IPV4 source router id address";
               }
               leaf ipv6-source-router-id {
                 type empty;
               }
               leaf ipv6-source-router-id-address {
                 type string;
                 description "IPV6 source router id address";
               }
               leaf label-allocation {
                 type string;
                 description "Label allocation mode";
               }
               leaf label-allocation-fallback-reject {
                 type string;
                 description "Suppress prefix export when label allocation fails";
               }
               leaf limit-bandwidth {
                 type uint64;
                 description "Limit advertised aggregate outbound link bandwidth";
               }
               leaf load-balance {
                 type string;
                 description "Load-balancing algorithm chosen";
               }
               leaf mhop-bfd-port {
                 type uint32;
                 description "Use port number 4784 for MPLS-BFD as per RFC5884";
               }
               leaf multipath-resolve {
                 type string;
                 description "Use all paths for resolution over this prefix";
               }
               leaf next {
                 type string;
                 description "Skip to next policy or term";
               }
               leaf no-backup {
                 type empty;
                 description "This prefix should not have backup";
               }
               leaf no-entropy-label-capability {
                 type empty;
                 description "Don't advertise entropy label capability";
               }
               leaf no-route-localize {
                 type empty;
                 description "No route localize";
               }
               leaf origin {
                 type string;
                 description "BGP origin attribute";
               }
               leaf p2mp-lsp-root {
                 type jt:ipaddr;
                 description "P2mp lsp root address";
               }
               leaf policy-priority {
                 type string;
               }
               leaf reject {
                 type empty;
                 description "Reject a route";
               }
               leaf request-long-lived-ack {
                 type empty;
                 description "Advertise route after forwarding is programmed";
               }
               leaf resolution-map {
                 type string;
                 description "Resolution map";
               }
               leaf resolution-map-mode {
                 type string;
                 description "Resolution map modes";
               }
               leaf selected-mldp-egress {
                 type string;
                 description "This node should act as egress node for MLDP inband signalling";
               }
               leaf send-withdrawal-on-route-change {
                 type empty;
                 description "Withdrawn route as change is not ack'd from forwarding";
               }
               leaf set-down-bit {
                 type empty;
                 description "Set down bit";
               }
               leaf slice {
                 type string;
                 description "Slice name";
               }
               leaf source-class {
                 type string;
                 description "The source class in forwarding table";
               }
               leaf sr-te-template {
                 type string;
                 description "SR TE template to apply";
               }
               leaf ssm-source {
                 type jt:ipaddr;
                 description "List of Sources for SSM mapping";
               }
               leaf trace {
                 type empty;
                 description "Log matches to a trace file";
               }
               leaf tunnel-end-point-address {
                 type string;
                 description "Set tunnel end-point address of tunnel";
               }
               leaf validation-state {
                 type string;
                 description "Validation-state of a route";
               }
               container install-nexthop {
                 container except {
                   leaf lsp {
                     type string;
                     description "Label switched path name";
                   }
                   leaf lsp-regex {
                     type string;
                     description "Label switched path name regular expression";
                   }
                   leaf non-labelled-nexthop {
                     type empty;
                   }
                   leaf non-lsp-nexthop {
                     type empty;
                   }
                   leaf static-lsp {
                     type string;
                   }
                   leaf static-lsp-regex {
                     type string;
                   }
                   leaf overlay-vxlan-interfaces {
                     type empty;
                   }
                 }
                 container fallback {
                   leaf lsp {
                     type string;
                     description "Label switched path name";
                   }
                   leaf lsp-regex {
                     type string;
                     description "Label switched path name regular expression";
                   }
                   leaf non-labelled-nexthop {
                     type empty;
                   }
                   leaf non-lsp-nexthop {
                     type empty;
                   }
                   leaf static-lsp {
                     type string;
                   }
                   leaf static-lsp-regex {
                     type string;
                   }
                   leaf overlay-vxlan-interfaces {
                     type empty;
                   }
                 }
                 leaf install-nexthop-stat {
                   type string;
                   description "Install nexthop statistics";
                 }
                 leaf install-nexthop.heading {
                   type string;
                   description "The next hop to be used for forwarding";
                 }
                 leaf lsp {
                   type string;
                   description "Label switched path name";
                 }
                 leaf lsp-regex {
                   type string;
                   description "Label switched path name regular expression";
                 }
                 leaf non-labelled-nexthop {
                   type empty;
                 }
                 leaf non-lsp-nexthop {
                   type empty;
                 }
                 leaf static-lsp {
                   type string;
                 }
                 leaf static-lsp-regex {
                   type string;
                 }
                 leaf strict {
                   type empty;
                 }
                 leaf strict-named-lsp {
                   type empty;
                 }
                 leaf address {
                   type jt:ipaddr;
                 }
                 leaf overlay-vxlan-interfaces {
                   type empty;
                 }
                 leaf nh-select {
                   type string;
                 }
                 leaf hash {
                   type uint32;
                 }
               }
               container map-to-interface {
                 list interface {
                   leaf interface-name {
                     type string;
                     description "Name of interface";
                   }
                   leaf interface-flags {
                     type int32;
                   }
                 }
                 leaf map-to-interface-stat {
                   type string;
                   description "Map to interface statistics";
                 }
                 leaf map-to-interface.heading {
                   type string;
                   description "Set output logical interface";
                 }
                 leaf self {
                   type empty;
                 }
               }
               container then-metric {
                 leaf metric-stat {
                   type string;
                   description "Metric statistics";
                 }
                 leaf then-metric.heading {
                   type string;
                 }
                 leaf metric1 {
                   type uint32;
                   description "Metric value";
                 }
                 leaf add-metric {
                   type uint32;
                 }
                 leaf subtract-metric {
                   type uint32;
                 }
                 leaf aigp-metric {
                   type empty;
                 }
                 container effective-aigp {
                   leaf metric-offset {
                     type uint32;
                   }
                 }
                 container igp {
                   leaf metric-offset {
                     type uint32;
                   }
                 }
                 container minimum-effective-aigp {
                   leaf metric-offset {
                     type uint32;
                   }
                 }
                 container minimum-igp {
                   leaf metric-offset {
                     type uint32;
                   }
                 }
               }
               container prefix-segment {
                 leaf redistribute {
                   type empty;
                 }
                 container algorithm {
                   leaf prefix-segment-index-value {
                     type uint32;
                   }
                   leaf algorithm-name {
                     type uint32;
                   }
                   leaf node-segment {
                     type empty;
                   }
                   leaf redistribute {
                     type empty;
                   }
                 }
                 leaf prefix-segment-stat {
                   type string;
                   description "Prefix segment statistics";
                 }
                 leaf prefix-segment.heading {
                   type string;
                   description "The prefix segment attributes";
                 }
                 leaf prefix-segment-index-value {
                   type uint32;
                 }
                 leaf node-segment {
                   type empty;
                 }
                 leaf psid-extended-data {
                   type int32;
                   description "Prefix segment extendend information";
                 }
               }
               list tunnel-attribute {
                 leaf tunnel-type {
                   type string;
                   description "Tunnel type";
                 }
                 leaf reference-count {
                   type int32;
                   description "Reference count";
                 }
                 leaf tunnel-data {
                   type string;
                   description "Tunnel Data";
                 }
                 leaf tunnel-attribute-stat {
                   type string;
                   description "Tunnel attribute statistics";
                 }
                 leaf-list tunnel-attribute.heading {
                   type string;
                   description "Tunnel attribute information";
                 }
                 leaf set {
                   type empty;
                   description "Set BGP tunnel attribute in the route";
                 }
                 leaf remove {
                   type empty;
                   description "Remove BGP tunnel attribute from the route";
                 }
                 leaf tunnel-attribute-name {
                   type string;
                   description "Name of a tunnel attribute , or 'all'";
                 }
               }
               container source-based-forwarding {
                 container sbf-attributes {
                   leaf sbf-next-table {
                     type string;
                   }
                 }
                 leaf source-based-forwarding-stat {
                   type string;
                   description "Source based forwarding statistics";
                 }
                 leaf source-based-forwarding.heading {
                   type string;
                 }
               }
               container policy-label {
                 leaf-list label-value {
                   type uint32;
                   description "Label value";
                 }
                 leaf label-range {
                   type int32;
                   description "Label range for l2vpn";
                 }
               }
               leaf-list class {
                 type string;
                 description "An instance of BGP output queue statistics";
               }
               container add-path {
                 leaf add-path-stat {
                   type string;
                 }
                 leaf add-path.heading {
                   type string;
                   description "BGP add-path attributes";
                 }
                 leaf sendcount {
                   type uint32;
                   description "Number of add-paths sent";
                 }
               }
               container aigp-adjust {
                 leaf aigp-adjust-stat {
                   type string;
                   description "AIGP adjust statistics";
                 }
                 leaf aigp-adjust.heading {
                   type string;
                   description "Adjust a BGP AIGP attribute";
                 }
                 leaf distance-to-protocol-nexthop {
                   type empty;
                 }
                 leaf add {
                   type empty;
                 }
                 leaf divide {
                   type empty;
                 }
                 leaf multiply {
                   type empty;
                 }
                 leaf subtract {
                   type empty;
                 }
                 leaf user-value {
                   type uint64;
                 }
               }
               container aigp-originate {
                 leaf aigp-originate-stat {
                   type string;
                   description "AIGP originate statistics";
                 }
                 leaf aigp-originate.heading {
                   type string;
                   description "Originate a BGP AIGP attribute";
                 }
                 leaf distance {
                   type uint32;
                   description "AIGP distance";
                 }
               }
               container as-path-expand {
                 leaf as-path-expand-stat {
                   type string;
                   description "AS path expand statistics";
                 }
                 leaf as-path-expand.heading {
                   type string;
                   description "Prepend AS numbers prior to adding local-as (BGP only)";
                 }
                 leaf as-path-sequence {
                   type string;
                 }
                 leaf last-as-count {
                   type uint32;
                 }
               }
               container assisted-replication {
                 leaf assisted-replication-stat {
                   type string;
                   description "Assisted replication";
                 }
                 leaf assisted-replication.heading {
                   type string;
                 }
                 leaf replicator-ip {
                   type string;
                 }
                 leaf strict-mode {
                   type string;
                 }
                 leaf fallback-replicator-ip {
                   type string;
                 }
               }
               container bgp-output-queue-priority {
                 leaf bgp-output-queue-priority-stat {
                   type string;
                   description "BGP output queue priority statistics";
                 }
                 leaf bgp-output-queue-priority.heading {
                   type string;
                   description "The BGP Update output queue priority";
                 }
                 leaf expedited {
                   type empty;
                 }
                 leaf queue-priority {
                   type uint32;
                 }
               }
               container then-color {
                 leaf color-stat {
                   type string;
                   description "Color statistics";
                 }
                 leaf then-color.heading {
                   type string;
                 }
                 leaf add-metric {
                   type uint32;
                 }
                 leaf subtract-metric {
                   type uint32;
                 }
                 leaf metric1 {
                   type uint32;
                   description "Metric value";
                 }
               }
               container then-color2 {
                 leaf color2-stat {
                   type string;
                   description "Color2 statistics";
                 }
                 leaf then-color2.heading {
                   type string;
                 }
                 leaf add-metric {
                   type uint32;
                 }
                 leaf subtract-metric {
                   type uint32;
                 }
                 leaf metric1 {
                   type uint32;
                   description "Metric value";
                 }
               }
               container then-color3 {
                 leaf color3-stat {
                   type string;
                   description "Color3 statistics";
                 }
                 leaf then-color3.heading {
                   type string;
                 }
                 leaf add-metric {
                   type uint32;
                 }
                 leaf subtract-metric {
                   type uint32;
                 }
                 leaf metric1 {
                   type uint32;
                   description "Metric value";
                 }
               }
               container then-color4 {
                 leaf color4-stat {
                   type string;
                   description "Color4 statistics";
                 }
                 leaf then-color4.heading {
                   type string;
                 }
                 leaf add-metric {
                   type uint32;
                 }
                 leaf subtract-metric {
                   type uint32;
                 }
                 leaf metric1 {
                   type uint32;
                   description "Metric value";
                 }
               }
               container then-community {
                 leaf community-stat {
                   type string;
                   description "Community statistics";
                 }
                 leaf then-community.heading {
                   type string;
                 }
                 leaf add {
                   type empty;
                 }
                 leaf set {
                   type empty;
                   description "Set BGP tunnel attribute in the route";
                 }
                 leaf community-delete {
                   type empty;
                 }
                 leaf community-name {
                   type string;
                 }
               }
               container credibility {
                 leaf credibility-stat {
                   type string;
                   description "Credibility statistics";
                 }
                 leaf credibility.heading {
                   type string;
                 }
                 leaf add-metric {
                   type uint32;
                 }
                 leaf subtract-metric {
                   type uint32;
                 }
                 leaf metric1 {
                   type uint32;
                   description "Metric value";
                 }
               }
               container external {
                 leaf external-stat {
                   type string;
                   description "External statistics";
                 }
                 leaf external.heading {
                   type string;
                   description "External route";
                 }
                 leaf external-type {
                   type uint32;
                 }
                 leaf nssa-only {
                   type empty;
                 }
               }
               container localpreference {
                 leaf policy-local-preference-stat {
                   type string;
                   description "Local preference statistics";
                 }
                 leaf localpreference.heading {
                   type string;
                 }
                 leaf add-metric {
                   type uint32;
                 }
                 leaf subtract-metric {
                   type uint32;
                 }
                 leaf metric1 {
                   type uint32;
                   description "Metric value";
                 }
               }
               container then-metric2 {
                 leaf metric2-stat {
                   type string;
                   description "Metric2 statistics";
                 }
                 leaf then-metric2.heading {
                   type string;
                 }
                 leaf metric1 {
                   type uint32;
                   description "Metric value";
                 }
                 leaf add-metric {
                   type uint32;
                 }
                 leaf subtract-metric {
                   type uint32;
                 }
               }
               container then-metric3 {
                 leaf metric3-stat {
                   type string;
                   description "Metric3 statistics";
                 }
                 leaf then-metric3.heading {
                   type string;
                 }
                 leaf metric1 {
                   type uint32;
                   description "Metric value";
                 }
                 leaf add-metric {
                   type uint32;
                 }
                 leaf subtract-metric {
                   type uint32;
                 }
               }
               container then-metric4 {
                 leaf metric4-stat {
                   type string;
                   description "Metric4 statistics";
                 }
                 leaf then-metric4.heading {
                   type string;
                 }
                 leaf metric1 {
                   type uint32;
                   description "Metric value";
                 }
                 leaf add-metric {
                   type uint32;
                 }
                 leaf subtract-metric {
                   type uint32;
                 }
               }
               container then-metric5 {
                 leaf metric5-stat {
                   type string;
                   description "Metric5 statistics";
                 }
                 leaf then-metric5.heading {
                   type string;
                 }
                 leaf metric1 {
                   type uint32;
                   description "Metric value";
                 }
                 leaf add-metric {
                   type uint32;
                 }
                 leaf subtract-metric {
                   type uint32;
                 }
               }
               container then-metric6 {
                 leaf metric6-stat {
                   type string;
                   description "Metric6 statistics";
                 }
                 leaf then-metric6.heading {
                   type string;
                 }
                 leaf metric1 {
                   type uint32;
                   description "Metric value";
                 }
                 leaf add-metric {
                   type uint32;
                 }
                 leaf subtract-metric {
                   type uint32;
                 }
               }
               container then-metric7 {
                 leaf metric7-stat {
                   type string;
                   description "Metric7 statistics";
                 }
                 leaf then-metric7.heading {
                   type string;
                 }
                 leaf metric1 {
                   type uint32;
                   description "Metric value";
                 }
                 leaf add-metric {
                   type uint32;
                 }
                 leaf subtract-metric {
                   type uint32;
                 }
               }
               container then-metric8 {
                 leaf metric8-stat {
                   type string;
                   description "Metric8 statistics";
                 }
                 leaf then-metric8.heading {
                   type string;
                 }
                 leaf metric1 {
                   type uint32;
                   description "Metric value";
                 }
                 leaf add-metric {
                   type uint32;
                 }
                 leaf subtract-metric {
                   type uint32;
                 }
               }
               container then-metric9 {
                 leaf metric9-stat {
                   type string;
                   description "Metric9 statistics";
                 }
                 leaf then-metric9.heading {
                   type string;
                 }
                 leaf metric1 {
                   type uint32;
                   description "Metric value";
                 }
                 leaf add-metric {
                   type uint32;
                 }
                 leaf subtract-metric {
                   type uint32;
                 }
               }
               container then-metric10 {
                 leaf metric10-stat {
                   type string;
                   description "Metric10 statistics";
                 }
                 leaf then-metric10.heading {
                   type string;
                 }
                 leaf metric1 {
                   type uint32;
                   description "Metric value";
                 }
                 leaf add-metric {
                   type uint32;
                 }
                 leaf subtract-metric {
                   type uint32;
                 }
               }
               container then-metric11 {
                 leaf metric11-stat {
                   type string;
                   description "Metric11 statistics";
                 }
                 leaf then-metric11.heading {
                   type string;
                 }
                 leaf metric1 {
                   type uint32;
                   description "Metric value";
                 }
                 leaf add-metric {
                   type uint32;
                 }
                 leaf subtract-metric {
                   type uint32;
                 }
               }
               container then-metric12 {
                 leaf metric12-stat {
                   type string;
                   description "Metric12 statistics";
                 }
                 leaf then-metric12.heading {
                   type string;
                 }
                 leaf metric1 {
                   type uint32;
                   description "Metric value";
                 }
                 leaf add-metric {
                   type uint32;
                 }
                 leaf subtract-metric {
                   type uint32;
                 }
               }
               container then-nexthop {
                 leaf next-hop-stat {
                   type string;
                   description "Nexthop statistics";
                 }
                 leaf then-nexthop.heading {
                   type string;
                 }
                 leaf address {
                   type jt:ipaddr;
                 }
                 leaf reject {
                   type empty;
                   description "Reject a route";
                 }
                 leaf discard {
                   type empty;
                 }
                 leaf self {
                   type empty;
                 }
                 leaf no-resolution {
                   type empty;
                 }
                 leaf nexthop-peer-address {
                   type empty;
                 }
                 leaf next-table {
                   type string;
                 }
               }
               container then-preference {
                 leaf preference-stat {
                   type string;
                   description "Preference statistics";
                 }
                 leaf then-preference.heading {
                   type string;
                 }
                 leaf metric1 {
                   type uint32;
                   description "Metric value";
                 }
                 leaf add-metric {
                   type uint32;
                 }
                 leaf subtract-metric {
                   type uint32;
                 }
               }
               container then-preference2 {
                 leaf preference2-stat {
                   type string;
                   description "Preference2 statistics";
                 }
                 leaf then-preference2.heading {
                   type string;
                 }
                 leaf metric1 {
                   type uint32;
                   description "Metric value";
                 }
                 leaf add-metric {
                   type uint32;
                 }
                 leaf subtract-metric {
                   type uint32;
                 }
               }
               container then-preference3 {
                 leaf preference3-stat {
                   type string;
                   description "Preference3 statistics";
                 }
                 leaf then-preference3.heading {
                   type string;
                 }
                 leaf metric1 {
                   type uint32;
                   description "Metric value";
                 }
                 leaf add-metric {
                   type uint32;
                 }
                 leaf subtract-metric {
                   type uint32;
                 }
               }
               container then-preference4 {
                 leaf preference4-stat {
                   type string;
                   description "Preference4 statistics";
                 }
                 leaf then-preference4.heading {
                   type string;
                 }
                 leaf metric1 {
                   type uint32;
                   description "Metric value";
                 }
                 leaf add-metric {
                   type uint32;
                 }
                 leaf subtract-metric {
                   type uint32;
                 }
               }
               container then-preference5 {
                 leaf preference5-stat {
                   type string;
                   description "Preference5 statistics";
                 }
                 leaf then-preference5.heading {
                   type string;
                 }
                 leaf metric1 {
                   type uint32;
                   description "Metric value";
                 }
                 leaf add-metric {
                   type uint32;
                 }
                 leaf subtract-metric {
                   type uint32;
                 }
               }
               container then-preference6 {
                 leaf preference6-stat {
                   type string;
                   description "Preference6 statistics";
                 }
                 leaf then-preference6.heading {
                   type string;
                 }
                 leaf metric1 {
                   type uint32;
                   description "Metric value";
                 }
                 leaf add-metric {
                   type uint32;
                 }
                 leaf subtract-metric {
                   type uint32;
                 }
               }
               container then-preference7 {
                 leaf preference7-stat {
                   type string;
                   description "Preference7 statistics";
                 }
                 leaf then-preference7.heading {
                   type string;
                 }
                 leaf metric1 {
                   type uint32;
                   description "Metric value";
                 }
                 leaf add-metric {
                   type uint32;
                 }
                 leaf subtract-metric {
                   type uint32;
                 }
               }
               container then-preference8 {
                 leaf preference8-stat {
                   type string;
                   description "Preference8 statistics";
                 }
                 leaf then-preference8.heading {
                   type string;
                 }
                 leaf metric1 {
                   type uint32;
                   description "Metric value";
                 }
                 leaf add-metric {
                   type uint32;
                 }
                 leaf subtract-metric {
                   type uint32;
                 }
               }
               container then-preference9 {
                 leaf preference9-stat {
                   type string;
                   description "Preference9 statistics";
                 }
                 leaf then-preference9.heading {
                   type string;
                 }
                 leaf metric1 {
                   type uint32;
                   description "Metric value";
                 }
                 leaf add-metric {
                   type uint32;
                 }
                 leaf subtract-metric {
                   type uint32;
                 }
               }
               container then-preference10 {
                 leaf preference10-stat {
                   type string;
                   description "Preference10 statistics";
                 }
                 leaf then-preference10.heading {
                   type string;
                 }
                 leaf metric1 {
                   type uint32;
                   description "Metric value";
                 }
                 leaf add-metric {
                   type uint32;
                 }
                 leaf subtract-metric {
                   type uint32;
                 }
               }
               container then-preference11 {
                 leaf preference11-stat {
                   type string;
                   description "Preference11 statistics";
                 }
                 leaf then-preference11.heading {
                   type string;
                 }
                 leaf metric1 {
                   type uint32;
                   description "Metric value";
                 }
                 leaf add-metric {
                   type uint32;
                 }
                 leaf subtract-metric {
                   type uint32;
                 }
               }
               container then-preference12 {
                 leaf preference12-stat {
                   type string;
                   description "Preference12 statistics";
                 }
                 leaf then-preference12.heading {
                   type string;
                 }
                 leaf metric1 {
                   type uint32;
                   description "Metric value";
                 }
                 leaf add-metric {
                   type uint32;
                 }
                 leaf subtract-metric {
                   type uint32;
                 }
               }
               container prefix-attribute-flags {
                 leaf prefix-attribute-flags-stat {
                   type string;
                   description "Prefix attribute flag statistics";
                 }
                 leaf prefix-attribute-flags.heading {
                   type string;
                 }
                 leaf node-segment-flag {
                   type empty;
                   description "Node segment flag";
                 }
                 leaf external-prefix-flag {
                   type empty;
                   description "External prefix flag";
                 }
                 leaf entropy-label-capability-flag {
                   type empty;
                   description "Entropy label capability flag";
                 }
                 leaf anycast-flag {
                   type empty;
                   description "Anycast flag";
                 }
               }
               container request-ack {
                 leaf request-ack-stat {
                   type string;
                   description "Request acknowledgements statistics";
                 }
                 leaf request-ack.heading {
                   type string;
                   description "Request acknowledgements";
                 }
                 leaf route-ack {
                   type empty;
                   description "Route acknowledgements";
                 }
                 leaf nexthop-ack {
                   type empty;
                   description "Nexthop acknowledgements";
                 }
               }
               container srv6 {
                 leaf srv6-stat {
                   type string;
                   description "SRv6 SID";
                 }
                 leaf srv6.heading {
                   type string;
                 }
                 leaf sid {
                   type string;
                 }
                 leaf locator {
                   type string;
                   description "SRv6 locator";
                 }
                 leaf micro-dt4-sid {
                   type empty;
                 }
                 leaf micro-dt6-sid {
                   type empty;
                 }
                 leaf micro-dt46-sid {
                   type empty;
                 }
               }
               container then-tag {
                 leaf tag-stat {
                   type string;
                   description "Policy tag statistics";
                 }
                 leaf then-tag.heading {
                   type string;
                 }
                 leaf metric1 {
                   type uint32;
                   description "Metric value";
                 }
                 leaf add-metric {
                   type uint32;
                 }
                 leaf subtract-metric {
                   type uint32;
                 }
               }
               container then-tag2 {
                 leaf tag2-stat {
                   type string;
                   description "Policy tag2 statistics";
                 }
                 leaf then-tag2.heading {
                   type string;
                 }
                 leaf metric1 {
                   type uint32;
                   description "Metric value";
                 }
                 leaf add-metric {
                   type uint32;
                 }
                 leaf subtract-metric {
                   type uint32;
                 }
               }
               container then-tag3 {
                 leaf tag3-stat {
                   type string;
                   description "Policy tag3 statistics";
                 }
                 leaf then-tag3.heading {
                   type string;
                 }
                 leaf metric1 {
                   type uint32;
                   description "Metric value";
                 }
                 leaf add-metric {
                   type uint32;
                 }
                 leaf subtract-metric {
                   type uint32;
                 }
               }
               container then-tag4 {
                 leaf tag4-stat {
                   type string;
                   description "Policy tag4 statistics";
                 }
                 leaf then-tag4.heading {
                   type string;
                 }
                 leaf metric1 {
                   type uint32;
                   description "Metric value";
                 }
                 leaf add-metric {
                   type uint32;
                 }
                 leaf subtract-metric {
                   type uint32;
                 }
               }
               container metric-expression {
                 leaf metric-stat {
                   type string;
                   description "Metric statistics";
                 }
                 leaf metric-expression.heading {
                   type string;
                 }
                 leaf expression-metric1-multiplier {
                   type string;
                 }
                 leaf expression-metric1-offset {
                   type int32;
                 }
                 leaf expression-metric2-multiplier {
                   type string;
                 }
                 leaf expression-metric2-offset {
                   type int32;
                 }
               }
             }
           }
           container route-filter-list {
             container policy-extended-information {
               leaf account {
                 type empty;
                 description "Account";
               }
               leaf accept {
                 type empty;
                 description "Accept a route";
               }
               leaf advertise-locator {
                 type empty;
                 description "Advertise SRv6 locator";
               }
               leaf advertise-locator-internal {
                 type empty;
                 description "Advertise SRv6 locator internal";
               }
               leaf aggregate-bandwidth {
                 type int32;
                 description "Aggregate bandwidth";
               }
               leaf auto-link-bandwidth {
                 type empty;
                 description "Auto link bandwidth";
               }
               leaf analyze {
                 type empty;
                 description "Send to registered controllers for analysis";
               }
               leaf as-path-prepend {
                 type uint32;
                 description "Prepend AS numbers to an AS path (BGP only)";
               }
               leaf cos-next-hop-map {
                 type string;
                 description "The CoS-based next-hop map in forwarding table";
               }
               leaf damping {
                 type string;
                 description "Define BGP route flap damping parameters";
               }
               leaf default-action {
                 type string;
                 description "The default policy action";
               }
               leaf destination-class {
                 type string;
                 description "The destination class in forwarding table";
               }
               leaf dynamic-tunnel-attributes {
                 type string;
                 description "The dynamic tunnel attributes used for forwarding";
               }
               leaf fib-install-priority {
                 type string;
                 description "FIB install priority";
               }
               leaf filter {
                 type string;
                 description "Next-hop firewall filter";
               }
               leaf get-route-range {
                 type empty;
                 description "Get route range";
               }
               leaf ignore-service-label {
                 type string;
                 description "Ignore service labels";
               }
               leaf install-to-fib {
                 type string;
                 description "Install to FIB";
               }
               leaf ipv4-source-router-id {
                 type empty;
               }
               leaf ipv4-source-router-id-address {
                 type string;
                 description "IPV4 source router id address";
               }
               leaf ipv6-source-router-id {
                 type empty;
               }
               leaf ipv6-source-router-id-address {
                 type string;
                 description "IPV6 source router id address";
               }
               leaf label-allocation {
                 type string;
                 description "Label allocation mode";
               }
               leaf label-allocation-fallback-reject {
                 type string;
                 description "Suppress prefix export when label allocation fails";
               }
               leaf limit-bandwidth {
                 type uint64;
                 description "Limit advertised aggregate outbound link bandwidth";
               }
               leaf load-balance {
                 type string;
                 description "Load-balancing algorithm chosen";
               }
               leaf mhop-bfd-port {
                 type uint32;
                 description "Use port number 4784 for MPLS-BFD as per RFC5884";
               }
               leaf multipath-resolve {
                 type string;
                 description "Use all paths for resolution over this prefix";
               }
               leaf next {
                 type string;
                 description "Skip to next policy or term";
               }
               leaf no-backup {
                 type empty;
                 description "This prefix should not have backup";
               }
               leaf no-entropy-label-capability {
                 type empty;
                 description "Don't advertise entropy label capability";
               }
               leaf no-route-localize {
                 type empty;
                 description "No route localize";
               }
               leaf origin {
                 type string;
                 description "BGP origin attribute";
               }
               leaf p2mp-lsp-root {
                 type jt:ipaddr;
                 description "P2mp lsp root address";
               }
               leaf policy-priority {
                 type string;
               }
               leaf reject {
                 type empty;
                 description "Reject a route";
               }
               leaf request-long-lived-ack {
                 type empty;
                 description "Advertise route after forwarding is programmed";
               }
               leaf resolution-map {
                 type string;
                 description "Resolution map";
               }
               leaf resolution-map-mode {
                 type string;
                 description "Resolution map modes";
               }
               leaf selected-mldp-egress {
                 type string;
                 description "This node should act as egress node for MLDP inband signalling";
               }
               leaf send-withdrawal-on-route-change {
                 type empty;
                 description "Withdrawn route as change is not ack'd from forwarding";
               }
               leaf set-down-bit {
                 type empty;
                 description "Set down bit";
               }
               leaf slice {
                 type string;
                 description "Slice name";
               }
               leaf source-class {
                 type string;
                 description "The source class in forwarding table";
               }
               leaf sr-te-template {
                 type string;
                 description "SR TE template to apply";
               }
               leaf ssm-source {
                 type jt:ipaddr;
                 description "List of Sources for SSM mapping";
               }
               leaf trace {
                 type empty;
                 description "Log matches to a trace file";
               }
               leaf tunnel-end-point-address {
                 type string;
                 description "Set tunnel end-point address of tunnel";
               }
               leaf validation-state {
                 type string;
                 description "Validation-state of a route";
               }
               container install-nexthop {
                 container except {
                   leaf lsp {
                     type string;
                     description "Label switched path name";
                   }
                   leaf lsp-regex {
                     type string;
                     description "Label switched path name regular expression";
                   }
                   leaf non-labelled-nexthop {
                     type empty;
                   }
                   leaf non-lsp-nexthop {
                     type empty;
                   }
                   leaf static-lsp {
                     type string;
                   }
                   leaf static-lsp-regex {
                     type string;
                   }
                   leaf overlay-vxlan-interfaces {
                     type empty;
                   }
                 }
                 container fallback {
                   leaf lsp {
                     type string;
                     description "Label switched path name";
                   }
                   leaf lsp-regex {
                     type string;
                     description "Label switched path name regular expression";
                   }
                   leaf non-labelled-nexthop {
                     type empty;
                   }
                   leaf non-lsp-nexthop {
                     type empty;
                   }
                   leaf static-lsp {
                     type string;
                   }
                   leaf static-lsp-regex {
                     type string;
                   }
                   leaf overlay-vxlan-interfaces {
                     type empty;
                   }
                 }
                 leaf install-nexthop-stat {
                   type string;
                   description "Install nexthop statistics";
                 }
                 leaf install-nexthop.heading {
                   type string;
                   description "The next hop to be used for forwarding";
                 }
                 leaf lsp {
                   type string;
                   description "Label switched path name";
                 }
                 leaf lsp-regex {
                   type string;
                   description "Label switched path name regular expression";
                 }
                 leaf non-labelled-nexthop {
                   type empty;
                 }
                 leaf non-lsp-nexthop {
                   type empty;
                 }
                 leaf static-lsp {
                   type string;
                 }
                 leaf static-lsp-regex {
                   type string;
                 }
                 leaf strict {
                   type empty;
                 }
                 leaf strict-named-lsp {
                   type empty;
                 }
                 leaf address {
                   type jt:ipaddr;
                 }
                 leaf overlay-vxlan-interfaces {
                   type empty;
                 }
                 leaf nh-select {
                   type string;
                 }
                 leaf hash {
                   type uint32;
                 }
               }
               container map-to-interface {
                 list interface {
                   leaf interface-name {
                     type string;
                     description "Name of interface";
                   }
                   leaf interface-flags {
                     type int32;
                   }
                 }
                 leaf map-to-interface-stat {
                   type string;
                   description "Map to interface statistics";
                 }
                 leaf map-to-interface.heading {
                   type string;
                   description "Set output logical interface";
                 }
                 leaf self {
                   type empty;
                 }
               }
               container then-metric {
                 leaf metric-stat {
                   type string;
                   description "Metric statistics";
                 }
                 leaf then-metric.heading {
                   type string;
                 }
                 leaf metric1 {
                   type uint32;
                   description "Metric value";
                 }
                 leaf add-metric {
                   type uint32;
                 }
                 leaf subtract-metric {
                   type uint32;
                 }
                 leaf aigp-metric {
                   type empty;
                 }
                 container effective-aigp {
                   leaf metric-offset {
                     type uint32;
                   }
                 }
                 container igp {
                   leaf metric-offset {
                     type uint32;
                   }
                 }
                 container minimum-effective-aigp {
                   leaf metric-offset {
                     type uint32;
                   }
                 }
                 container minimum-igp {
                   leaf metric-offset {
                     type uint32;
                   }
                 }
               }
               container prefix-segment {
                 leaf redistribute {
                   type empty;
                 }
                 container algorithm {
                   leaf prefix-segment-index-value {
                     type uint32;
                   }
                   leaf algorithm-name {
                     type uint32;
                   }
                   leaf node-segment {
                     type empty;
                   }
                   leaf redistribute {
                     type empty;
                   }
                 }
                 leaf prefix-segment-stat {
                   type string;
                   description "Prefix segment statistics";
                 }
                 leaf prefix-segment.heading {
                   type string;
                   description "The prefix segment attributes";
                 }
                 leaf prefix-segment-index-value {
                   type uint32;
                 }
                 leaf node-segment {
                   type empty;
                 }
                 leaf psid-extended-data {
                   type int32;
                   description "Prefix segment extendend information";
                 }
               }
               list tunnel-attribute {
                 leaf tunnel-type {
                   type string;
                   description "Tunnel type";
                 }
                 leaf reference-count {
                   type int32;
                   description "Reference count";
                 }
                 leaf tunnel-data {
                   type string;
                   description "Tunnel Data";
                 }
                 leaf tunnel-attribute-stat {
                   type string;
                   description "Tunnel attribute statistics";
                 }
                 leaf-list tunnel-attribute.heading {
                   type string;
                   description "Tunnel attribute information";
                 }
                 leaf set {
                   type empty;
                   description "Set BGP tunnel attribute in the route";
                 }
                 leaf remove {
                   type empty;
                   description "Remove BGP tunnel attribute from the route";
                 }
                 leaf tunnel-attribute-name {
                   type string;
                   description "Name of a tunnel attribute , or 'all'";
                 }
               }
               container source-based-forwarding {
                 container sbf-attributes {
                   leaf sbf-next-table {
                     type string;
                   }
                 }
                 leaf source-based-forwarding-stat {
                   type string;
                   description "Source based forwarding statistics";
                 }
                 leaf source-based-forwarding.heading {
                   type string;
                 }
               }
               container policy-label {
                 leaf-list label-value {
                   type uint32;
                   description "Label value";
                 }
                 leaf label-range {
                   type int32;
                   description "Label range for l2vpn";
                 }
               }
               leaf-list class {
                 type string;
                 description "An instance of BGP output queue statistics";
               }
               container add-path {
                 leaf add-path-stat {
                   type string;
                 }
                 leaf add-path.heading {
                   type string;
                   description "BGP add-path attributes";
                 }
                 leaf sendcount {
                   type uint32;
                   description "Number of add-paths sent";
                 }
               }
               container aigp-adjust {
                 leaf aigp-adjust-stat {
                   type string;
                   description "AIGP adjust statistics";
                 }
                 leaf aigp-adjust.heading {
                   type string;
                   description "Adjust a BGP AIGP attribute";
                 }
                 leaf distance-to-protocol-nexthop {
                   type empty;
                 }
                 leaf add {
                   type empty;
                 }
                 leaf divide {
                   type empty;
                 }
                 leaf multiply {
                   type empty;
                 }
                 leaf subtract {
                   type empty;
                 }
                 leaf user-value {
                   type uint64;
                 }
               }
               container aigp-originate {
                 leaf aigp-originate-stat {
                   type string;
                   description "AIGP originate statistics";
                 }
                 leaf aigp-originate.heading {
                   type string;
                   description "Originate a BGP AIGP attribute";
                 }
                 leaf distance {
                   type uint32;
                   description "AIGP distance";
                 }
               }
               container as-path-expand {
                 leaf as-path-expand-stat {
                   type string;
                   description "AS path expand statistics";
                 }
                 leaf as-path-expand.heading {
                   type string;
                   description "Prepend AS numbers prior to adding local-as (BGP only)";
                 }
                 leaf as-path-sequence {
                   type string;
                 }
                 leaf last-as-count {
                   type uint32;
                 }
               }
               container assisted-replication {
                 leaf assisted-replication-stat {
                   type string;
                   description "Assisted replication";
                 }
                 leaf assisted-replication.heading {
                   type string;
                 }
                 leaf replicator-ip {
                   type string;
                 }
                 leaf strict-mode {
                   type string;
                 }
                 leaf fallback-replicator-ip {
                   type string;
                 }
               }
               container bgp-output-queue-priority {
                 leaf bgp-output-queue-priority-stat {
                   type string;
                   description "BGP output queue priority statistics";
                 }
                 leaf bgp-output-queue-priority.heading {
                   type string;
                   description "The BGP Update output queue priority";
                 }
                 leaf expedited {
                   type empty;
                 }
                 leaf queue-priority {
                   type uint32;
                 }
               }
               container then-color {
                 leaf color-stat {
                   type string;
                   description "Color statistics";
                 }
                 leaf then-color.heading {
                   type string;
                 }
                 leaf add-metric {
                   type uint32;
                 }
                 leaf subtract-metric {
                   type uint32;
                 }
                 leaf metric1 {
                   type uint32;
                   description "Metric value";
                 }
               }
               container then-color2 {
                 leaf color2-stat {
                   type string;
                   description "Color2 statistics";
                 }
                 leaf then-color2.heading {
                   type string;
                 }
                 leaf add-metric {
                   type uint32;
                 }
                 leaf subtract-metric {
                   type uint32;
                 }
                 leaf metric1 {
                   type uint32;
                   description "Metric value";
                 }
               }
               container then-color3 {
                 leaf color3-stat {
                   type string;
                   description "Color3 statistics";
                 }
                 leaf then-color3.heading {
                   type string;
                 }
                 leaf add-metric {
                   type uint32;
                 }
                 leaf subtract-metric {
                   type uint32;
                 }
                 leaf metric1 {
                   type uint32;
                   description "Metric value";
                 }
               }
               container then-color4 {
                 leaf color4-stat {
                   type string;
                   description "Color4 statistics";
                 }
                 leaf then-color4.heading {
                   type string;
                 }
                 leaf add-metric {
                   type uint32;
                 }
                 leaf subtract-metric {
                   type uint32;
                 }
                 leaf metric1 {
                   type uint32;
                   description "Metric value";
                 }
               }
               container then-community {
                 leaf community-stat {
                   type string;
                   description "Community statistics";
                 }
                 leaf then-community.heading {
                   type string;
                 }
                 leaf add {
                   type empty;
                 }
                 leaf set {
                   type empty;
                   description "Set BGP tunnel attribute in the route";
                 }
                 leaf community-delete {
                   type empty;
                 }
                 leaf community-name {
                   type string;
                 }
               }
               container credibility {
                 leaf credibility-stat {
                   type string;
                   description "Credibility statistics";
                 }
                 leaf credibility.heading {
                   type string;
                 }
                 leaf add-metric {
                   type uint32;
                 }
                 leaf subtract-metric {
                   type uint32;
                 }
                 leaf metric1 {
                   type uint32;
                   description "Metric value";
                 }
               }
               container external {
                 leaf external-stat {
                   type string;
                   description "External statistics";
                 }
                 leaf external.heading {
                   type string;
                   description "External route";
                 }
                 leaf external-type {
                   type uint32;
                 }
                 leaf nssa-only {
                   type empty;
                 }
               }
               container localpreference {
                 leaf policy-local-preference-stat {
                   type string;
                   description "Local preference statistics";
                 }
                 leaf localpreference.heading {
                   type string;
                 }
                 leaf add-metric {
                   type uint32;
                 }
                 leaf subtract-metric {
                   type uint32;
                 }
                 leaf metric1 {
                   type uint32;
                   description "Metric value";
                 }
               }
               container then-metric2 {
                 leaf metric2-stat {
                   type string;
                   description "Metric2 statistics";
                 }
                 leaf then-metric2.heading {
                   type string;
                 }
                 leaf metric1 {
                   type uint32;
                   description "Metric value";
                 }
                 leaf add-metric {
                   type uint32;
                 }
                 leaf subtract-metric {
                   type uint32;
                 }
               }
               container then-metric3 {
                 leaf metric3-stat {
                   type string;
                   description "Metric3 statistics";
                 }
                 leaf then-metric3.heading {
                   type string;
                 }
                 leaf metric1 {
                   type uint32;
                   description "Metric value";
                 }
                 leaf add-metric {
                   type uint32;
                 }
                 leaf subtract-metric {
                   type uint32;
                 }
               }
               container then-metric4 {
                 leaf metric4-stat {
                   type string;
                   description "Metric4 statistics";
                 }
                 leaf then-metric4.heading {
                   type string;
                 }
                 leaf metric1 {
                   type uint32;
                   description "Metric value";
                 }
                 leaf add-metric {
                   type uint32;
                 }
                 leaf subtract-metric {
                   type uint32;
                 }
               }
               container then-metric5 {
                 leaf metric5-stat {
                   type string;
                   description "Metric5 statistics";
                 }
                 leaf then-metric5.heading {
                   type string;
                 }
                 leaf metric1 {
                   type uint32;
                   description "Metric value";
                 }
                 leaf add-metric {
                   type uint32;
                 }
                 leaf subtract-metric {
                   type uint32;
                 }
               }
               container then-metric6 {
                 leaf metric6-stat {
                   type string;
                   description "Metric6 statistics";
                 }
                 leaf then-metric6.heading {
                   type string;
                 }
                 leaf metric1 {
                   type uint32;
                   description "Metric value";
                 }
                 leaf add-metric {
                   type uint32;
                 }
                 leaf subtract-metric {
                   type uint32;
                 }
               }
               container then-metric7 {
                 leaf metric7-stat {
                   type string;
                   description "Metric7 statistics";
                 }
                 leaf then-metric7.heading {
                   type string;
                 }
                 leaf metric1 {
                   type uint32;
                   description "Metric value";
                 }
                 leaf add-metric {
                   type uint32;
                 }
                 leaf subtract-metric {
                   type uint32;
                 }
               }
               container then-metric8 {
                 leaf metric8-stat {
                   type string;
                   description "Metric8 statistics";
                 }
                 leaf then-metric8.heading {
                   type string;
                 }
                 leaf metric1 {
                   type uint32;
                   description "Metric value";
                 }
                 leaf add-metric {
                   type uint32;
                 }
                 leaf subtract-metric {
                   type uint32;
                 }
               }
               container then-metric9 {
                 leaf metric9-stat {
                   type string;
                   description "Metric9 statistics";
                 }
                 leaf then-metric9.heading {
                   type string;
                 }
                 leaf metric1 {
                   type uint32;
                   description "Metric value";
                 }
                 leaf add-metric {
                   type uint32;
                 }
                 leaf subtract-metric {
                   type uint32;
                 }
               }
               container then-metric10 {
                 leaf metric10-stat {
                   type string;
                   description "Metric10 statistics";
                 }
                 leaf then-metric10.heading {
                   type string;
                 }
                 leaf metric1 {
                   type uint32;
                   description "Metric value";
                 }
                 leaf add-metric {
                   type uint32;
                 }
                 leaf subtract-metric {
                   type uint32;
                 }
               }
               container then-metric11 {
                 leaf metric11-stat {
                   type string;
                   description "Metric11 statistics";
                 }
                 leaf then-metric11.heading {
                   type string;
                 }
                 leaf metric1 {
                   type uint32;
                   description "Metric value";
                 }
                 leaf add-metric {
                   type uint32;
                 }
                 leaf subtract-metric {
                   type uint32;
                 }
               }
               container then-metric12 {
                 leaf metric12-stat {
                   type string;
                   description "Metric12 statistics";
                 }
                 leaf then-metric12.heading {
                   type string;
                 }
                 leaf metric1 {
                   type uint32;
                   description "Metric value";
                 }
                 leaf add-metric {
                   type uint32;
                 }
                 leaf subtract-metric {
                   type uint32;
                 }
               }
               container then-nexthop {
                 leaf next-hop-stat {
                   type string;
                   description "Nexthop statistics";
                 }
                 leaf then-nexthop.heading {
                   type string;
                 }
                 leaf address {
                   type jt:ipaddr;
                 }
                 leaf reject {
                   type empty;
                   description "Reject a route";
                 }
                 leaf discard {
                   type empty;
                 }
                 leaf self {
                   type empty;
                 }
                 leaf no-resolution {
                   type empty;
                 }
                 leaf nexthop-peer-address {
                   type empty;
                 }
                 leaf next-table {
                   type string;
                 }
               }
               container then-preference {
                 leaf preference-stat {
                   type string;
                   description "Preference statistics";
                 }
                 leaf then-preference.heading {
                   type string;
                 }
                 leaf metric1 {
                   type uint32;
                   description "Metric value";
                 }
                 leaf add-metric {
                   type uint32;
                 }
                 leaf subtract-metric {
                   type uint32;
                 }
               }
               container then-preference2 {
                 leaf preference2-stat {
                   type string;
                   description "Preference2 statistics";
                 }
                 leaf then-preference2.heading {
                   type string;
                 }
                 leaf metric1 {
                   type uint32;
                   description "Metric value";
                 }
                 leaf add-metric {
                   type uint32;
                 }
                 leaf subtract-metric {
                   type uint32;
                 }
               }
               container then-preference3 {
                 leaf preference3-stat {
                   type string;
                   description "Preference3 statistics";
                 }
                 leaf then-preference3.heading {
                   type string;
                 }
                 leaf metric1 {
                   type uint32;
                   description "Metric value";
                 }
                 leaf add-metric {
                   type uint32;
                 }
                 leaf subtract-metric {
                   type uint32;
                 }
               }
               container then-preference4 {
                 leaf preference4-stat {
                   type string;
                   description "Preference4 statistics";
                 }
                 leaf then-preference4.heading {
                   type string;
                 }
                 leaf metric1 {
                   type uint32;
                   description "Metric value";
                 }
                 leaf add-metric {
                   type uint32;
                 }
                 leaf subtract-metric {
                   type uint32;
                 }
               }
               container then-preference5 {
                 leaf preference5-stat {
                   type string;
                   description "Preference5 statistics";
                 }
                 leaf then-preference5.heading {
                   type string;
                 }
                 leaf metric1 {
                   type uint32;
                   description "Metric value";
                 }
                 leaf add-metric {
                   type uint32;
                 }
                 leaf subtract-metric {
                   type uint32;
                 }
               }
               container then-preference6 {
                 leaf preference6-stat {
                   type string;
                   description "Preference6 statistics";
                 }
                 leaf then-preference6.heading {
                   type string;
                 }
                 leaf metric1 {
                   type uint32;
                   description "Metric value";
                 }
                 leaf add-metric {
                   type uint32;
                 }
                 leaf subtract-metric {
                   type uint32;
                 }
               }
               container then-preference7 {
                 leaf preference7-stat {
                   type string;
                   description "Preference7 statistics";
                 }
                 leaf then-preference7.heading {
                   type string;
                 }
                 leaf metric1 {
                   type uint32;
                   description "Metric value";
                 }
                 leaf add-metric {
                   type uint32;
                 }
                 leaf subtract-metric {
                   type uint32;
                 }
               }
               container then-preference8 {
                 leaf preference8-stat {
                   type string;
                   description "Preference8 statistics";
                 }
                 leaf then-preference8.heading {
                   type string;
                 }
                 leaf metric1 {
                   type uint32;
                   description "Metric value";
                 }
                 leaf add-metric {
                   type uint32;
                 }
                 leaf subtract-metric {
                   type uint32;
                 }
               }
               container then-preference9 {
                 leaf preference9-stat {
                   type string;
                   description "Preference9 statistics";
                 }
                 leaf then-preference9.heading {
                   type string;
                 }
                 leaf metric1 {
                   type uint32;
                   description "Metric value";
                 }
                 leaf add-metric {
                   type uint32;
                 }
                 leaf subtract-metric {
                   type uint32;
                 }
               }
               container then-preference10 {
                 leaf preference10-stat {
                   type string;
                   description "Preference10 statistics";
                 }
                 leaf then-preference10.heading {
                   type string;
                 }
                 leaf metric1 {
                   type uint32;
                   description "Metric value";
                 }
                 leaf add-metric {
                   type uint32;
                 }
                 leaf subtract-metric {
                   type uint32;
                 }
               }
               container then-preference11 {
                 leaf preference11-stat {
                   type string;
                   description "Preference11 statistics";
                 }
                 leaf then-preference11.heading {
                   type string;
                 }
                 leaf metric1 {
                   type uint32;
                   description "Metric value";
                 }
                 leaf add-metric {
                   type uint32;
                 }
                 leaf subtract-metric {
                   type uint32;
                 }
               }
               container then-preference12 {
                 leaf preference12-stat {
                   type string;
                   description "Preference12 statistics";
                 }
                 leaf then-preference12.heading {
                   type string;
                 }
                 leaf metric1 {
                   type uint32;
                   description "Metric value";
                 }
                 leaf add-metric {
                   type uint32;
                 }
                 leaf subtract-metric {
                   type uint32;
                 }
               }
               container prefix-attribute-flags {
                 leaf prefix-attribute-flags-stat {
                   type string;
                   description "Prefix attribute flag statistics";
                 }
                 leaf prefix-attribute-flags.heading {
                   type string;
                 }
                 leaf node-segment-flag {
                   type empty;
                   description "Node segment flag";
                 }
                 leaf external-prefix-flag {
                   type empty;
                   description "External prefix flag";
                 }
                 leaf entropy-label-capability-flag {
                   type empty;
                   description "Entropy label capability flag";
                 }
                 leaf anycast-flag {
                   type empty;
                   description "Anycast flag";
                 }
               }
               container request-ack {
                 leaf request-ack-stat {
                   type string;
                   description "Request acknowledgements statistics";
                 }
                 leaf request-ack.heading {
                   type string;
                   description "Request acknowledgements";
                 }
                 leaf route-ack {
                   type empty;
                   description "Route acknowledgements";
                 }
                 leaf nexthop-ack {
                   type empty;
                   description "Nexthop acknowledgements";
                 }
               }
               container srv6 {
                 leaf srv6-stat {
                   type string;
                   description "SRv6 SID";
                 }
                 leaf srv6.heading {
                   type string;
                 }
                 leaf sid {
                   type string;
                 }
                 leaf locator {
                   type string;
                   description "SRv6 locator";
                 }
                 leaf micro-dt4-sid {
                   type empty;
                 }
                 leaf micro-dt6-sid {
                   type empty;
                 }
                 leaf micro-dt46-sid {
                   type empty;
                 }
               }
               container then-tag {
                 leaf tag-stat {
                   type string;
                   description "Policy tag statistics";
                 }
                 leaf then-tag.heading {
                   type string;
                 }
                 leaf metric1 {
                   type uint32;
                   description "Metric value";
                 }
                 leaf add-metric {
                   type uint32;
                 }
                 leaf subtract-metric {
                   type uint32;
                 }
               }
               container then-tag2 {
                 leaf tag2-stat {
                   type string;
                   description "Policy tag2 statistics";
                 }
                 leaf then-tag2.heading {
                   type string;
                 }
                 leaf metric1 {
                   type uint32;
                   description "Metric value";
                 }
                 leaf add-metric {
                   type uint32;
                 }
                 leaf subtract-metric {
                   type uint32;
                 }
               }
               container then-tag3 {
                 leaf tag3-stat {
                   type string;
                   description "Policy tag3 statistics";
                 }
                 leaf then-tag3.heading {
                   type string;
                 }
                 leaf metric1 {
                   type uint32;
                   description "Metric value";
                 }
                 leaf add-metric {
                   type uint32;
                 }
                 leaf subtract-metric {
                   type uint32;
                 }
               }
               container then-tag4 {
                 leaf tag4-stat {
                   type string;
                   description "Policy tag4 statistics";
                 }
                 leaf then-tag4.heading {
                   type string;
                 }
                 leaf metric1 {
                   type uint32;
                   description "Metric value";
                 }
                 leaf add-metric {
                   type uint32;
                 }
                 leaf subtract-metric {
                   type uint32;
                 }
               }
               container metric-expression {
                 leaf metric-stat {
                   type string;
                   description "Metric statistics";
                 }
                 leaf metric-expression.heading {
                   type string;
                 }
                 leaf expression-metric1-multiplier {
                   type string;
                 }
                 leaf expression-metric1-offset {
                   type int32;
                 }
                 leaf expression-metric2-multiplier {
                   type string;
                 }
                 leaf expression-metric2-offset {
                   type int32;
                 }
               }
             }
             leaf route-filter-list-stat {
               type string;
               description "Route filter list statistics";
             }
             leaf route-filter-list.heading {
               type string;
             }
             leaf route-filter-list-name {
               type string;
               description "List of route-filter-lists of routes to match";
             }
           }
           list source-address-filter {
             leaf source-address-filter-stat {
               type string;
               description "Source address filter statistics";
             }
             leaf-list source-address-filter.heading {
               type string;
             }
             leaf address {
               type jt:ipaddr;
             }
             leaf flags {
               type string;
               description "Enabled trace flags";
             }
             leaf match-count {
               type uint64;
             }
             container policy-extended-information {
               leaf account {
                 type empty;
                 description "Account";
               }
               leaf accept {
                 type empty;
                 description "Accept a route";
               }
               leaf advertise-locator {
                 type empty;
                 description "Advertise SRv6 locator";
               }
               leaf advertise-locator-internal {
                 type empty;
                 description "Advertise SRv6 locator internal";
               }
               leaf aggregate-bandwidth {
                 type int32;
                 description "Aggregate bandwidth";
               }
               leaf auto-link-bandwidth {
                 type empty;
                 description "Auto link bandwidth";
               }
               leaf analyze {
                 type empty;
                 description "Send to registered controllers for analysis";
               }
               leaf as-path-prepend {
                 type uint32;
                 description "Prepend AS numbers to an AS path (BGP only)";
               }
               leaf cos-next-hop-map {
                 type string;
                 description "The CoS-based next-hop map in forwarding table";
               }
               leaf damping {
                 type string;
                 description "Define BGP route flap damping parameters";
               }
               leaf default-action {
                 type string;
                 description "The default policy action";
               }
               leaf destination-class {
                 type string;
                 description "The destination class in forwarding table";
               }
               leaf dynamic-tunnel-attributes {
                 type string;
                 description "The dynamic tunnel attributes used for forwarding";
               }
               leaf fib-install-priority {
                 type string;
                 description "FIB install priority";
               }
               leaf filter {
                 type string;
                 description "Next-hop firewall filter";
               }
               leaf get-route-range {
                 type empty;
                 description "Get route range";
               }
               leaf ignore-service-label {
                 type string;
                 description "Ignore service labels";
               }
               leaf install-to-fib {
                 type string;
                 description "Install to FIB";
               }
               leaf ipv4-source-router-id {
                 type empty;
               }
               leaf ipv4-source-router-id-address {
                 type string;
                 description "IPV4 source router id address";
               }
               leaf ipv6-source-router-id {
                 type empty;
               }
               leaf ipv6-source-router-id-address {
                 type string;
                 description "IPV6 source router id address";
               }
               leaf label-allocation {
                 type string;
                 description "Label allocation mode";
               }
               leaf label-allocation-fallback-reject {
                 type string;
                 description "Suppress prefix export when label allocation fails";
               }
               leaf limit-bandwidth {
                 type uint64;
                 description "Limit advertised aggregate outbound link bandwidth";
               }
               leaf load-balance {
                 type string;
                 description "Load-balancing algorithm chosen";
               }
               leaf mhop-bfd-port {
                 type uint32;
                 description "Use port number 4784 for MPLS-BFD as per RFC5884";
               }
               leaf multipath-resolve {
                 type string;
                 description "Use all paths for resolution over this prefix";
               }
               leaf next {
                 type string;
                 description "Skip to next policy or term";
               }
               leaf no-backup {
                 type empty;
                 description "This prefix should not have backup";
               }
               leaf no-entropy-label-capability {
                 type empty;
                 description "Don't advertise entropy label capability";
               }
               leaf no-route-localize {
                 type empty;
                 description "No route localize";
               }
               leaf origin {
                 type string;
                 description "BGP origin attribute";
               }
               leaf p2mp-lsp-root {
                 type jt:ipaddr;
                 description "P2mp lsp root address";
               }
               leaf policy-priority {
                 type string;
               }
               leaf reject {
                 type empty;
                 description "Reject a route";
               }
               leaf request-long-lived-ack {
                 type empty;
                 description "Advertise route after forwarding is programmed";
               }
               leaf resolution-map {
                 type string;
                 description "Resolution map";
               }
               leaf resolution-map-mode {
                 type string;
                 description "Resolution map modes";
               }
               leaf selected-mldp-egress {
                 type string;
                 description "This node should act as egress node for MLDP inband signalling";
               }
               leaf send-withdrawal-on-route-change {
                 type empty;
                 description "Withdrawn route as change is not ack'd from forwarding";
               }
               leaf set-down-bit {
                 type empty;
                 description "Set down bit";
               }
               leaf slice {
                 type string;
                 description "Slice name";
               }
               leaf source-class {
                 type string;
                 description "The source class in forwarding table";
               }
               leaf sr-te-template {
                 type string;
                 description "SR TE template to apply";
               }
               leaf ssm-source {
                 type jt:ipaddr;
                 description "List of Sources for SSM mapping";
               }
               leaf trace {
                 type empty;
                 description "Log matches to a trace file";
               }
               leaf tunnel-end-point-address {
                 type string;
                 description "Set tunnel end-point address of tunnel";
               }
               leaf validation-state {
                 type string;
                 description "Validation-state of a route";
               }
               container install-nexthop {
                 container except {
                   leaf lsp {
                     type string;
                     description "Label switched path name";
                   }
                   leaf lsp-regex {
                     type string;
                     description "Label switched path name regular expression";
                   }
                   leaf non-labelled-nexthop {
                     type empty;
                   }
                   leaf non-lsp-nexthop {
                     type empty;
                   }
                   leaf static-lsp {
                     type string;
                   }
                   leaf static-lsp-regex {
                     type string;
                   }
                   leaf overlay-vxlan-interfaces {
                     type empty;
                   }
                 }
                 container fallback {
                   leaf lsp {
                     type string;
                     description "Label switched path name";
                   }
                   leaf lsp-regex {
                     type string;
                     description "Label switched path name regular expression";
                   }
                   leaf non-labelled-nexthop {
                     type empty;
                   }
                   leaf non-lsp-nexthop {
                     type empty;
                   }
                   leaf static-lsp {
                     type string;
                   }
                   leaf static-lsp-regex {
                     type string;
                   }
                   leaf overlay-vxlan-interfaces {
                     type empty;
                   }
                 }
                 leaf install-nexthop-stat {
                   type string;
                   description "Install nexthop statistics";
                 }
                 leaf install-nexthop.heading {
                   type string;
                   description "The next hop to be used for forwarding";
                 }
                 leaf lsp {
                   type string;
                   description "Label switched path name";
                 }
                 leaf lsp-regex {
                   type string;
                   description "Label switched path name regular expression";
                 }
                 leaf non-labelled-nexthop {
                   type empty;
                 }
                 leaf non-lsp-nexthop {
                   type empty;
                 }
                 leaf static-lsp {
                   type string;
                 }
                 leaf static-lsp-regex {
                   type string;
                 }
                 leaf strict {
                   type empty;
                 }
                 leaf strict-named-lsp {
                   type empty;
                 }
                 leaf address {
                   type jt:ipaddr;
                 }
                 leaf overlay-vxlan-interfaces {
                   type empty;
                 }
                 leaf nh-select {
                   type string;
                 }
                 leaf hash {
                   type uint32;
                 }
               }
               container map-to-interface {
                 list interface {
                   leaf interface-name {
                     type string;
                     description "Name of interface";
                   }
                   leaf interface-flags {
                     type int32;
                   }
                 }
                 leaf map-to-interface-stat {
                   type string;
                   description "Map to interface statistics";
                 }
                 leaf map-to-interface.heading {
                   type string;
                   description "Set output logical interface";
                 }
                 leaf self {
                   type empty;
                 }
               }
               container then-metric {
                 leaf metric-stat {
                   type string;
                   description "Metric statistics";
                 }
                 leaf then-metric.heading {
                   type string;
                 }
                 leaf metric1 {
                   type uint32;
                   description "Metric value";
                 }
                 leaf add-metric {
                   type uint32;
                 }
                 leaf subtract-metric {
                   type uint32;
                 }
                 leaf aigp-metric {
                   type empty;
                 }
                 container effective-aigp {
                   leaf metric-offset {
                     type uint32;
                   }
                 }
                 container igp {
                   leaf metric-offset {
                     type uint32;
                   }
                 }
                 container minimum-effective-aigp {
                   leaf metric-offset {
                     type uint32;
                   }
                 }
                 container minimum-igp {
                   leaf metric-offset {
                     type uint32;
                   }
                 }
               }
               container prefix-segment {
                 leaf redistribute {
                   type empty;
                 }
                 container algorithm {
                   leaf prefix-segment-index-value {
                     type uint32;
                   }
                   leaf algorithm-name {
                     type uint32;
                   }
                   leaf node-segment {
                     type empty;
                   }
                   leaf redistribute {
                     type empty;
                   }
                 }
                 leaf prefix-segment-stat {
                   type string;
                   description "Prefix segment statistics";
                 }
                 leaf prefix-segment.heading {
                   type string;
                   description "The prefix segment attributes";
                 }
                 leaf prefix-segment-index-value {
                   type uint32;
                 }
                 leaf node-segment {
                   type empty;
                 }
                 leaf psid-extended-data {
                   type int32;
                   description "Prefix segment extendend information";
                 }
               }
               list tunnel-attribute {
                 leaf tunnel-type {
                   type string;
                   description "Tunnel type";
                 }
                 leaf reference-count {
                   type int32;
                   description "Reference count";
                 }
                 leaf tunnel-data {
                   type string;
                   description "Tunnel Data";
                 }
                 leaf tunnel-attribute-stat {
                   type string;
                   description "Tunnel attribute statistics";
                 }
                 leaf-list tunnel-attribute.heading {
                   type string;
                   description "Tunnel attribute information";
                 }
                 leaf set {
                   type empty;
                   description "Set BGP tunnel attribute in the route";
                 }
                 leaf remove {
                   type empty;
                   description "Remove BGP tunnel attribute from the route";
                 }
                 leaf tunnel-attribute-name {
                   type string;
                   description "Name of a tunnel attribute , or 'all'";
                 }
               }
               container source-based-forwarding {
                 container sbf-attributes {
                   leaf sbf-next-table {
                     type string;
                   }
                 }
                 leaf source-based-forwarding-stat {
                   type string;
                   description "Source based forwarding statistics";
                 }
                 leaf source-based-forwarding.heading {
                   type string;
                 }
               }
               container policy-label {
                 leaf-list label-value {
                   type uint32;
                   description "Label value";
                 }
                 leaf label-range {
                   type int32;
                   description "Label range for l2vpn";
                 }
               }
               leaf-list class {
                 type string;
                 description "An instance of BGP output queue statistics";
               }
               container add-path {
                 leaf add-path-stat {
                   type string;
                 }
                 leaf add-path.heading {
                   type string;
                   description "BGP add-path attributes";
                 }
                 leaf sendcount {
                   type uint32;
                   description "Number of add-paths sent";
                 }
               }
               container aigp-adjust {
                 leaf aigp-adjust-stat {
                   type string;
                   description "AIGP adjust statistics";
                 }
                 leaf aigp-adjust.heading {
                   type string;
                   description "Adjust a BGP AIGP attribute";
                 }
                 leaf distance-to-protocol-nexthop {
                   type empty;
                 }
                 leaf add {
                   type empty;
                 }
                 leaf divide {
                   type empty;
                 }
                 leaf multiply {
                   type empty;
                 }
                 leaf subtract {
                   type empty;
                 }
                 leaf user-value {
                   type uint64;
                 }
               }
               container aigp-originate {
                 leaf aigp-originate-stat {
                   type string;
                   description "AIGP originate statistics";
                 }
                 leaf aigp-originate.heading {
                   type string;
                   description "Originate a BGP AIGP attribute";
                 }
                 leaf distance {
                   type uint32;
                   description "AIGP distance";
                 }
               }
               container as-path-expand {
                 leaf as-path-expand-stat {
                   type string;
                   description "AS path expand statistics";
                 }
                 leaf as-path-expand.heading {
                   type string;
                   description "Prepend AS numbers prior to adding local-as (BGP only)";
                 }
                 leaf as-path-sequence {
                   type string;
                 }
                 leaf last-as-count {
                   type uint32;
                 }
               }
               container assisted-replication {
                 leaf assisted-replication-stat {
                   type string;
                   description "Assisted replication";
                 }
                 leaf assisted-replication.heading {
                   type string;
                 }
                 leaf replicator-ip {
                   type string;
                 }
                 leaf strict-mode {
                   type string;
                 }
                 leaf fallback-replicator-ip {
                   type string;
                 }
               }
               container bgp-output-queue-priority {
                 leaf bgp-output-queue-priority-stat {
                   type string;
                   description "BGP output queue priority statistics";
                 }
                 leaf bgp-output-queue-priority.heading {
                   type string;
                   description "The BGP Update output queue priority";
                 }
                 leaf expedited {
                   type empty;
                 }
                 leaf queue-priority {
                   type uint32;
                 }
               }
               container then-color {
                 leaf color-stat {
                   type string;
                   description "Color statistics";
                 }
                 leaf then-color.heading {
                   type string;
                 }
                 leaf add-metric {
                   type uint32;
                 }
                 leaf subtract-metric {
                   type uint32;
                 }
                 leaf metric1 {
                   type uint32;
                   description "Metric value";
                 }
               }
               container then-color2 {
                 leaf color2-stat {
                   type string;
                   description "Color2 statistics";
                 }
                 leaf then-color2.heading {
                   type string;
                 }
                 leaf add-metric {
                   type uint32;
                 }
                 leaf subtract-metric {
                   type uint32;
                 }
                 leaf metric1 {
                   type uint32;
                   description "Metric value";
                 }
               }
               container then-color3 {
                 leaf color3-stat {
                   type string;
                   description "Color3 statistics";
                 }
                 leaf then-color3.heading {
                   type string;
                 }
                 leaf add-metric {
                   type uint32;
                 }
                 leaf subtract-metric {
                   type uint32;
                 }
                 leaf metric1 {
                   type uint32;
                   description "Metric value";
                 }
               }
               container then-color4 {
                 leaf color4-stat {
                   type string;
                   description "Color4 statistics";
                 }
                 leaf then-color4.heading {
                   type string;
                 }
                 leaf add-metric {
                   type uint32;
                 }
                 leaf subtract-metric {
                   type uint32;
                 }
                 leaf metric1 {
                   type uint32;
                   description "Metric value";
                 }
               }
               container then-community {
                 leaf community-stat {
                   type string;
                   description "Community statistics";
                 }
                 leaf then-community.heading {
                   type string;
                 }
                 leaf add {
                   type empty;
                 }
                 leaf set {
                   type empty;
                   description "Set BGP tunnel attribute in the route";
                 }
                 leaf community-delete {
                   type empty;
                 }
                 leaf community-name {
                   type string;
                 }
               }
               container credibility {
                 leaf credibility-stat {
                   type string;
                   description "Credibility statistics";
                 }
                 leaf credibility.heading {
                   type string;
                 }
                 leaf add-metric {
                   type uint32;
                 }
                 leaf subtract-metric {
                   type uint32;
                 }
                 leaf metric1 {
                   type uint32;
                   description "Metric value";
                 }
               }
               container external {
                 leaf external-stat {
                   type string;
                   description "External statistics";
                 }
                 leaf external.heading {
                   type string;
                   description "External route";
                 }
                 leaf external-type {
                   type uint32;
                 }
                 leaf nssa-only {
                   type empty;
                 }
               }
               container localpreference {
                 leaf policy-local-preference-stat {
                   type string;
                   description "Local preference statistics";
                 }
                 leaf localpreference.heading {
                   type string;
                 }
                 leaf add-metric {
                   type uint32;
                 }
                 leaf subtract-metric {
                   type uint32;
                 }
                 leaf metric1 {
                   type uint32;
                   description "Metric value";
                 }
               }
               container then-metric2 {
                 leaf metric2-stat {
                   type string;
                   description "Metric2 statistics";
                 }
                 leaf then-metric2.heading {
                   type string;
                 }
                 leaf metric1 {
                   type uint32;
                   description "Metric value";
                 }
                 leaf add-metric {
                   type uint32;
                 }
                 leaf subtract-metric {
                   type uint32;
                 }
               }
               container then-metric3 {
                 leaf metric3-stat {
                   type string;
                   description "Metric3 statistics";
                 }
                 leaf then-metric3.heading {
                   type string;
                 }
                 leaf metric1 {
                   type uint32;
                   description "Metric value";
                 }
                 leaf add-metric {
                   type uint32;
                 }
                 leaf subtract-metric {
                   type uint32;
                 }
               }
               container then-metric4 {
                 leaf metric4-stat {
                   type string;
                   description "Metric4 statistics";
                 }
                 leaf then-metric4.heading {
                   type string;
                 }
                 leaf metric1 {
                   type uint32;
                   description "Metric value";
                 }
                 leaf add-metric {
                   type uint32;
                 }
                 leaf subtract-metric {
                   type uint32;
                 }
               }
               container then-metric5 {
                 leaf metric5-stat {
                   type string;
                   description "Metric5 statistics";
                 }
                 leaf then-metric5.heading {
                   type string;
                 }
                 leaf metric1 {
                   type uint32;
                   description "Metric value";
                 }
                 leaf add-metric {
                   type uint32;
                 }
                 leaf subtract-metric {
                   type uint32;
                 }
               }
               container then-metric6 {
                 leaf metric6-stat {
                   type string;
                   description "Metric6 statistics";
                 }
                 leaf then-metric6.heading {
                   type string;
                 }
                 leaf metric1 {
                   type uint32;
                   description "Metric value";
                 }
                 leaf add-metric {
                   type uint32;
                 }
                 leaf subtract-metric {
                   type uint32;
                 }
               }
               container then-metric7 {
                 leaf metric7-stat {
                   type string;
                   description "Metric7 statistics";
                 }
                 leaf then-metric7.heading {
                   type string;
                 }
                 leaf metric1 {
                   type uint32;
                   description "Metric value";
                 }
                 leaf add-metric {
                   type uint32;
                 }
                 leaf subtract-metric {
                   type uint32;
                 }
               }
               container then-metric8 {
                 leaf metric8-stat {
                   type string;
                   description "Metric8 statistics";
                 }
                 leaf then-metric8.heading {
                   type string;
                 }
                 leaf metric1 {
                   type uint32;
                   description "Metric value";
                 }
                 leaf add-metric {
                   type uint32;
                 }
                 leaf subtract-metric {
                   type uint32;
                 }
               }
               container then-metric9 {
                 leaf metric9-stat {
                   type string;
                   description "Metric9 statistics";
                 }
                 leaf then-metric9.heading {
                   type string;
                 }
                 leaf metric1 {
                   type uint32;
                   description "Metric value";
                 }
                 leaf add-metric {
                   type uint32;
                 }
                 leaf subtract-metric {
                   type uint32;
                 }
               }
               container then-metric10 {
                 leaf metric10-stat {
                   type string;
                   description "Metric10 statistics";
                 }
                 leaf then-metric10.heading {
                   type string;
                 }
                 leaf metric1 {
                   type uint32;
                   description "Metric value";
                 }
                 leaf add-metric {
                   type uint32;
                 }
                 leaf subtract-metric {
                   type uint32;
                 }
               }
               container then-metric11 {
                 leaf metric11-stat {
                   type string;
                   description "Metric11 statistics";
                 }
                 leaf then-metric11.heading {
                   type string;
                 }
                 leaf metric1 {
                   type uint32;
                   description "Metric value";
                 }
                 leaf add-metric {
                   type uint32;
                 }
                 leaf subtract-metric {
                   type uint32;
                 }
               }
               container then-metric12 {
                 leaf metric12-stat {
                   type string;
                   description "Metric12 statistics";
                 }
                 leaf then-metric12.heading {
                   type string;
                 }
                 leaf metric1 {
                   type uint32;
                   description "Metric value";
                 }
                 leaf add-metric {
                   type uint32;
                 }
                 leaf subtract-metric {
                   type uint32;
                 }
               }
               container then-nexthop {
                 leaf next-hop-stat {
                   type string;
                   description "Nexthop statistics";
                 }
                 leaf then-nexthop.heading {
                   type string;
                 }
                 leaf address {
                   type jt:ipaddr;
                 }
                 leaf reject {
                   type empty;
                   description "Reject a route";
                 }
                 leaf discard {
                   type empty;
                 }
                 leaf self {
                   type empty;
                 }
                 leaf no-resolution {
                   type empty;
                 }
                 leaf nexthop-peer-address {
                   type empty;
                 }
                 leaf next-table {
                   type string;
                 }
               }
               container then-preference {
                 leaf preference-stat {
                   type string;
                   description "Preference statistics";
                 }
                 leaf then-preference.heading {
                   type string;
                 }
                 leaf metric1 {
                   type uint32;
                   description "Metric value";
                 }
                 leaf add-metric {
                   type uint32;
                 }
                 leaf subtract-metric {
                   type uint32;
                 }
               }
               container then-preference2 {
                 leaf preference2-stat {
                   type string;
                   description "Preference2 statistics";
                 }
                 leaf then-preference2.heading {
                   type string;
                 }
                 leaf metric1 {
                   type uint32;
                   description "Metric value";
                 }
                 leaf add-metric {
                   type uint32;
                 }
                 leaf subtract-metric {
                   type uint32;
                 }
               }
               container then-preference3 {
                 leaf preference3-stat {
                   type string;
                   description "Preference3 statistics";
                 }
                 leaf then-preference3.heading {
                   type string;
                 }
                 leaf metric1 {
                   type uint32;
                   description "Metric value";
                 }
                 leaf add-metric {
                   type uint32;
                 }
                 leaf subtract-metric {
                   type uint32;
                 }
               }
               container then-preference4 {
                 leaf preference4-stat {
                   type string;
                   description "Preference4 statistics";
                 }
                 leaf then-preference4.heading {
                   type string;
                 }
                 leaf metric1 {
                   type uint32;
                   description "Metric value";
                 }
                 leaf add-metric {
                   type uint32;
                 }
                 leaf subtract-metric {
                   type uint32;
                 }
               }
               container then-preference5 {
                 leaf preference5-stat {
                   type string;
                   description "Preference5 statistics";
                 }
                 leaf then-preference5.heading {
                   type string;
                 }
                 leaf metric1 {
                   type uint32;
                   description "Metric value";
                 }
                 leaf add-metric {
                   type uint32;
                 }
                 leaf subtract-metric {
                   type uint32;
                 }
               }
               container then-preference6 {
                 leaf preference6-stat {
                   type string;
                   description "Preference6 statistics";
                 }
                 leaf then-preference6.heading {
                   type string;
                 }
                 leaf metric1 {
                   type uint32;
                   description "Metric value";
                 }
                 leaf add-metric {
                   type uint32;
                 }
                 leaf subtract-metric {
                   type uint32;
                 }
               }
               container then-preference7 {
                 leaf preference7-stat {
                   type string;
                   description "Preference7 statistics";
                 }
                 leaf then-preference7.heading {
                   type string;
                 }
                 leaf metric1 {
                   type uint32;
                   description "Metric value";
                 }
                 leaf add-metric {
                   type uint32;
                 }
                 leaf subtract-metric {
                   type uint32;
                 }
               }
               container then-preference8 {
                 leaf preference8-stat {
                   type string;
                   description "Preference8 statistics";
                 }
                 leaf then-preference8.heading {
                   type string;
                 }
                 leaf metric1 {
                   type uint32;
                   description "Metric value";
                 }
                 leaf add-metric {
                   type uint32;
                 }
                 leaf subtract-metric {
                   type uint32;
                 }
               }
               container then-preference9 {
                 leaf preference9-stat {
                   type string;
                   description "Preference9 statistics";
                 }
                 leaf then-preference9.heading {
                   type string;
                 }
                 leaf metric1 {
                   type uint32;
                   description "Metric value";
                 }
                 leaf add-metric {
                   type uint32;
                 }
                 leaf subtract-metric {
                   type uint32;
                 }
               }
               container then-preference10 {
                 leaf preference10-stat {
                   type string;
                   description "Preference10 statistics";
                 }
                 leaf then-preference10.heading {
                   type string;
                 }
                 leaf metric1 {
                   type uint32;
                   description "Metric value";
                 }
                 leaf add-metric {
                   type uint32;
                 }
                 leaf subtract-metric {
                   type uint32;
                 }
               }
               container then-preference11 {
                 leaf preference11-stat {
                   type string;
                   description "Preference11 statistics";
                 }
                 leaf then-preference11.heading {
                   type string;
                 }
                 leaf metric1 {
                   type uint32;
                   description "Metric value";
                 }
                 leaf add-metric {
                   type uint32;
                 }
                 leaf subtract-metric {
                   type uint32;
                 }
               }
               container then-preference12 {
                 leaf preference12-stat {
                   type string;
                   description "Preference12 statistics";
                 }
                 leaf then-preference12.heading {
                   type string;
                 }
                 leaf metric1 {
                   type uint32;
                   description "Metric value";
                 }
                 leaf add-metric {
                   type uint32;
                 }
                 leaf subtract-metric {
                   type uint32;
                 }
               }
               container prefix-attribute-flags {
                 leaf prefix-attribute-flags-stat {
                   type string;
                   description "Prefix attribute flag statistics";
                 }
                 leaf prefix-attribute-flags.heading {
                   type string;
                 }
                 leaf node-segment-flag {
                   type empty;
                   description "Node segment flag";
                 }
                 leaf external-prefix-flag {
                   type empty;
                   description "External prefix flag";
                 }
                 leaf entropy-label-capability-flag {
                   type empty;
                   description "Entropy label capability flag";
                 }
                 leaf anycast-flag {
                   type empty;
                   description "Anycast flag";
                 }
               }
               container request-ack {
                 leaf request-ack-stat {
                   type string;
                   description "Request acknowledgements statistics";
                 }
                 leaf request-ack.heading {
                   type string;
                   description "Request acknowledgements";
                 }
                 leaf route-ack {
                   type empty;
                   description "Route acknowledgements";
                 }
                 leaf nexthop-ack {
                   type empty;
                   description "Nexthop acknowledgements";
                 }
               }
               container srv6 {
                 leaf srv6-stat {
                   type string;
                   description "SRv6 SID";
                 }
                 leaf srv6.heading {
                   type string;
                 }
                 leaf sid {
                   type string;
                 }
                 leaf locator {
                   type string;
                   description "SRv6 locator";
                 }
                 leaf micro-dt4-sid {
                   type empty;
                 }
                 leaf micro-dt6-sid {
                   type empty;
                 }
                 leaf micro-dt46-sid {
                   type empty;
                 }
               }
               container then-tag {
                 leaf tag-stat {
                   type string;
                   description "Policy tag statistics";
                 }
                 leaf then-tag.heading {
                   type string;
                 }
                 leaf metric1 {
                   type uint32;
                   description "Metric value";
                 }
                 leaf add-metric {
                   type uint32;
                 }
                 leaf subtract-metric {
                   type uint32;
                 }
               }
               container then-tag2 {
                 leaf tag2-stat {
                   type string;
                   description "Policy tag2 statistics";
                 }
                 leaf then-tag2.heading {
                   type string;
                 }
                 leaf metric1 {
                   type uint32;
                   description "Metric value";
                 }
                 leaf add-metric {
                   type uint32;
                 }
                 leaf subtract-metric {
                   type uint32;
                 }
               }
               container then-tag3 {
                 leaf tag3-stat {
                   type string;
                   description "Policy tag3 statistics";
                 }
                 leaf then-tag3.heading {
                   type string;
                 }
                 leaf metric1 {
                   type uint32;
                   description "Metric value";
                 }
                 leaf add-metric {
                   type uint32;
                 }
                 leaf subtract-metric {
                   type uint32;
                 }
               }
               container then-tag4 {
                 leaf tag4-stat {
                   type string;
                   description "Policy tag4 statistics";
                 }
                 leaf then-tag4.heading {
                   type string;
                 }
                 leaf metric1 {
                   type uint32;
                   description "Metric value";
                 }
                 leaf add-metric {
                   type uint32;
                 }
                 leaf subtract-metric {
                   type uint32;
                 }
               }
               container metric-expression {
                 leaf metric-stat {
                   type string;
                   description "Metric statistics";
                 }
                 leaf metric-expression.heading {
                   type string;
                 }
                 leaf expression-metric1-multiplier {
                   type string;
                 }
                 leaf expression-metric1-offset {
                   type int32;
                 }
                 leaf expression-metric2-multiplier {
                   type string;
                 }
                 leaf expression-metric2-offset {
                   type int32;
                 }
               }
             }
           }
           container traffic-engineering {
             leaf traffic-engineering-stat {
               type string;
               description "Traffic engineering statistics";
             }
             leaf traffic-engineering.heading {
               type string;
               description "Traffic-Engineering related parameters";
             }
             leaf te-identifier {
               type uint64;
               description "BGP-TE identifier";
             }
             leaf te-protocol {
               type string;
             }
             container link {
               container te-from {
                 leaf te-from.heading {
                   type string;
                 }
                 leaf as {
                   type uint32;
                 }
                 leaf router-id {
                   type jt:ipaddr;
                 }
                 leaf sys-id {
                   type string;
                 }
                 leaf node-type {
                   type string;
                 }
                 leaf any {
                   type empty;
                 }
                 leaf link-address {
                   type string;
                 }
               }
               container te-to {
                 leaf te-to.heading {
                   type string;
                 }
                 leaf as {
                   type uint32;
                 }
                 leaf router-id {
                   type jt:ipaddr;
                 }
                 leaf sys-id {
                   type string;
                 }
                 leaf node-type {
                   type string;
                 }
                 leaf any {
                   type empty;
                 }
                 leaf link-address {
                   type string;
                 }
               }
             }
             container ipv4-prefix {
               leaf ipv4-prefix.heading {
                 type string;
               }
               leaf as {
                 type uint32;
               }
               leaf router-id {
                 type jt:ipaddr;
               }
               leaf prefix {
                 type jt:ipaddr;
               }
               leaf sys-id {
                 type string;
               }
               leaf any {
                 type empty;
               }
             }
             container ipv6-prefix {
               leaf ipv6-prefix.heading {
                 type string;
               }
               leaf as {
                 type uint32;
               }
               leaf router-id {
                 type jt:ipaddr;
               }
               leaf prefix {
                 type jt:ipaddr;
               }
               leaf sys-id {
                 type string;
               }
               leaf any {
                 type empty;
               }
             }
             container srv6-sid {
               leaf srv6-sid.heading {
                 type string;
               }
               leaf as {
                 type uint32;
               }
               leaf router-id {
                 type jt:ipaddr;
               }
               leaf end-sid {
                 type string;
                 description "SRv6 end sid";
               }
               leaf sys-id {
                 type string;
               }
               leaf any {
                 type empty;
               }
             }
             container te-node {
               leaf te-node.heading {
                 type string;
               }
               leaf as {
                 type uint32;
               }
               leaf router-id {
                 type jt:ipaddr;
               }
               leaf sys-id {
                 type string;
               }
               leaf node-type {
                 type string;
               }
               leaf any {
                 type empty;
               }
             }
             container te-springte {
               leaf te-springte.heading {
                 type string;
               }
               leaf as {
                 type uint32;
               }
               leaf router-id {
                 type jt:ipaddr;
               }
               leaf color1 {
                 type uint32;
                 description "Color1";
               }
               leaf discriminator {
                 type uint32;
                 description "Spring-te discriminator";
               }
               leaf endpoint {
                 type string;
                 description "Spring-te endpoint";
               }
               leaf proto-origin {
                 type string;
                 description "Spring-te proto-origin";
               }
               leaf origin-as {
                 type uint32;
               }
               leaf origin-addr {
                 type string;
                 description "Spring-te origin address";
               }
             }
           }
           container route-distinguisher-info {
             leaf rd-filter-flag {
               type string;
               description "Route distinguisher filter flag";
             }
             leaf rd-details {
               type string;
               description "Route distingusher details";
             }
           }
           leaf from.heading {
             type string;
           }
           container route-target-prefix-count {
             leaf route-target-prefix-count-stat {
               type string;
               description "'Route Target' extended community prefix count statistics";
             }
             leaf route-target-prefix-count.heading {
               type string;
               description "Number of BGP prefixes with a 'Route Target' set";
             }
             leaf orhigher {
               type empty;
             }
             leaf policy-value {
               type uint32;
             }
           }
           container community-count {
             leaf community-count-stat {
               type string;
               description "Community count statistics";
             }
             leaf community-count.heading {
               type string;
               description "Number of BGP communities";
             }
             leaf equal {
               type empty;
             }
             leaf orhigher {
               type empty;
             }
             leaf orlower {
               type empty;
             }
             leaf policy-value {
               type uint32;
             }
           }
           container large-community-count {
             leaf large-community-count-stat {
               type string;
               description "Large community count statistics";
             }
             leaf large-community-count.heading {
               type string;
               description "Large community count";
             }
             leaf equal {
               type empty;
             }
             leaf orhigher {
               type empty;
             }
             leaf orlower {
               type empty;
             }
             leaf policy-value {
               type uint32;
             }
           }
           container next-hop-weight {
             leaf next-hop-weight-stat {
               type string;
               description "Nexthop weight statistics";
             }
             leaf next-hop-weight.heading {
               type string;
               description "Nexthop weight";
             }
             leaf equal-to {
               type uint32;
             }
             leaf greater-than {
               type uint32;
             }
             leaf greater-than-equal {
               type uint32;
             }
             leaf less-than {
               type uint32;
             }
             leaf less-than-equal {
               type uint32;
             }
             leaf all-nexthop {
               type empty;
             }
           }
           container source-routing-path {
             leaf source-routing-path-stat {
               type string;
               description "Source routing path statistics";
             }
             leaf source-routing-path.heading {
               type string;
             }
             leaf color-value {
               type uint32;
               description "Color";
             }
             leaf dest {
               type string;
               description "Spring-te lsp IPV4/IPV6 destination without color";
             }
             leaf name-regex {
               type string;
               description "Spring-te lsp name regex";
             }
             leaf origin-value {
               type string;
               description "Origin";
             }
             leaf route-distinguisher-value {
               type uint32;
               description "Route distinguisher";
             }
             leaf tunnel-source {
               type string;
               description "Source protocol";
             }
           }
           container validation-database-instance {
             leaf validation-database-instance-stat {
               type string;
               description "Validation database instance statistics";
             }
             leaf validation-database-instance.heading {
               type string;
               description "Validation database instance";
             }
             leaf validation-database-instance-database-name {
               type string;
               description "Name of the validation database";
             }
             leaf validation-database-instance-state-invalid {
               type empty;
               description "Invalid validation database instance state";
             }
             leaf validation-database-instance-state-unknown {
               type empty;
               description "Unknown validation database instance state";
             }
             leaf validation-database-instance-state-valid {
               type empty;
               description "Valid validation database instance state";
             }
           }
         }
         container policy-to {
           leaf family-stat {
             type string;
           }
           leaf family {
             type string;
           }
           leaf area-stat {
             type string;
             description "Area statistics";
           }
           leaf area {
             type uint32;
             description "OSPF area identifier";
           }
           leaf as-path-stat {
             type string;
             description "AS path statistics";
           }
           leaf as-path {
             type string;
             description "Name of AS path regular expression (BGP only)";
           }
           leaf as-path-group-stat {
             type string;
             description "AS path group statistics";
           }
           leaf as-path-group {
             type string;
             description "Name of AS path group (BGP only)";
           }
           leaf bgp-srte-discriminator-stat {
             type string;
             description "BGP SRTE discriminator statistics";
           }
           leaf bgp-srte-discriminator {
             type uint32;
             description "SRTE discriminator";
           }
           leaf color-stat {
             type string;
             description "Color statistics";
           }
           leaf color1 {
             type uint32;
             description "Color1";
           }
           leaf color2-stat {
             type string;
             description "Color2 statistics";
           }
           leaf color2 {
             type int32;
           }
           leaf color3-stat {
             type string;
             description "Color3 statistics";
           }
           leaf color3 {
             type uint32;
             description "Color 3";
           }
           leaf color4-stat {
             type string;
             description "Color4 statistics";
           }
           leaf color4 {
             type uint32;
             description "Color 4";
           }
           leaf community-stat {
             type string;
             description "Community statistics";
           }
           leaf-list community {
             type string;
             description "Basic community";
           }
           leaf igp-instance-stat {
             type string;
             description "IGP instance statistics";
           }
           leaf igp-instance {
             type string;
             description "IGP instance";
           }
           leaf igp-instance-regex-stat {
             type string;
             description "IGP instance regex statistics";
           }
           leaf igp-instance-regex {
             type string;
             description "IGP instance regex";
           }
           leaf instance-stat {
             type string;
             description "Instance statistics";
           }
           leaf instance {
             type string;
             description "Routing protocol instance";
           }
           leaf-list instance-name {
             type string;
           }
           leaf instance-display-error {
             type string;
           }
           leaf edge-protection {
             type string;
           }
           leaf edge-protector {
             type string;
           }
           list reference-site {
             leaf automatic-site-name {
               type string;
               description "VPLS automatic site name";
             }
             leaf automatic-site-id-status {
               type string;
               description "VPLS automatic site identifier status";
             }
             leaf automatic-site-claim-id {
               type int32;
               description "Claim site identifier";
             }
             leaf automatic-site-collisions {
               type int32;
               description "Number of collisions";
             }
             leaf automatic-site-timer-status {
               type string;
               description "VPLS automatic site timer status";
             }
             leaf vpls-signaling-protocol-identifier {
               type string;
             }
             leaf local-site-id {
               type string;
             }
             leaf source-attachment-id {
               type string;
               description "Local source attachment identifier";
             }
             leaf vpls-id {
               type int32;
               description "VPLS instance identifier";
             }
             leaf l2vpn-id {
               type string;
             }
             leaf local-id {
               type jt:ipaddr;
             }
             leaf num-local-interfaces {
               type int32;
             }
             leaf num-local-interfaces-up {
               type int32;
             }
             leaf irb-present {
               type string;
             }
             leaf mesh-group-count {
               type int32;
             }
             leaf mesh-group-up-count {
               type int32;
             }
             leaf remote-site-id {
               type string;
             }
             leaf target-attachment-id {
               type string;
               description "Remote target attachment identifier";
             }
             list mesh-group-interfaces {
               leaf mesh-group-name {
                 type string;
                 description "Name of mesh-group";
               }
               leaf mesh-group-state {
                 type string;
                 description "Mesh-group state";
               }
               leaf mesh-group-id {
                 type int32;
                 description "Mesh-group Identifier";
               }
               list interface {
                 leaf interface-name {
                   type string;
                   description "Name of interface";
                 }
                 leaf interface-description {
                   type string;
                 }
                 leaf interface-flags-description {
                   type string;
                 }
                 leaf interface-flags {
                   type int32;
                 }
               }
             }
             list interface {
               leaf interface-name {
                 type string;
                 description "Name of interface";
               }
               leaf interface-id {
                 type int32;
               }
               leaf interface-description {
                 type string;
               }
               leaf interface-flags-description {
                 type string;
               }
               leaf interface-flags {
                 type int32;
               }
             }
             list label-block {
               leaf-list label-block.heading {
                 type string;
               }
               leaf label-block-base {
                 type int32;
               }
               leaf label-block-offset {
                 type int32;
               }
               leaf label-block-size {
                 type int32;
               }
               leaf label-block-range {
                 type int32;
               }
               leaf label-block-preference {
                 type int32;
               }
               leaf label-block-status-vector {
                 type string;
               }
             }
             list connection {
               leaf-list connection.heading {
                 type string;
               }
               leaf connection-id {
                 type string;
               }
               leaf connection-type {
                 type string;
               }
               leaf connection-status {
                 type string;
               }
               leaf last-change {
                 type string;
               }
               leaf up-transitions {
                 type int32;
               }
               leaf remote-pe {
                 type jt:ipaddr;
               }
               leaf control-word {
                 type string;
               }
               leaf control-word-type {
                 type string;
               }
               leaf interface-encapsulation {
                 type string;
               }
               leaf inbound-label {
                 type string;
               }
               leaf outbound-label {
                 type string;
               }
               leaf pw-status-tlv {
                 type string;
               }
               leaf local-pw-status-code {
                 type int32;
               }
               leaf remote-pw-status-code {
                 type int32;
               }
               leaf connection-protection {
                 type string;
               }
               leaf mesh-group-name {
                 type string;
                 description "Name of mesh-group";
               }
               leaf vc-flow-label-transmit {
                 type string;
               }
               leaf vc-flow-label-receive {
                 type string;
               }
               leaf auto-sensed {
                 type empty;
                 description "Auto-sensed";
               }
               container local-interface {
                 leaf interface-name {
                   type string;
                   description "Name of interface";
                 }
                 leaf interface-status {
                   type string;
                 }
                 leaf interface-encapsulation {
                   type string;
                 }
                 leaf working-status {
                   type string;
                 }
                 leaf profile-name {
                   type string;
                 }
                 leaf profile-varset-name {
                   type string;
                 }
                 leaf interface-description {
                   type string;
                 }
               }
               container remote-interface {
                 leaf interface-name {
                   type string;
                   description "Name of interface";
                 }
                 leaf interface-status {
                   type string;
                 }
                 leaf interface-encapsulation {
                   type string;
                 }
               }
               container connection-bandwidth {
                 leaf connection-bandwidth.heading {
                   type string;
                   description "Bandwidth of a layer 2 connection";
                 }
                 leaf bandwidth {
                   type int32;
                 }
                 leaf class-type {
                   type int32;
                 }
                 leaf class-bandwidth {
                   type int32;
                 }
               }
               container vpls-rsvp-te-p2mp-lsp-information {
                 leaf vpls-ingress-p2mp-branch-lsp-name {
                   type string;
                   description "Name of ingress point-to-multipoint branch LSP";
                 }
                 leaf vpls-ingress-p2mp-branch-lsp-state {
                   type string;
                   description "State of ingress point-to-multipoint branch LSP";
                 }
                 leaf vpls-egress-p2mp-branch-lsp-name {
                   type string;
                   description "Name of egress point-to-multipoint branch LSP";
                 }
                 leaf vpls-egress-p2mp-branch-lsp-state {
                   type string;
                   description "State of egress point-to-multipoint branch LSP";
                 }
               }
               container spe-info {
                 leaf spe-info.heading {
                   type string;
                 }
                 leaf local-ip-addr {
                   type jt:ipaddr;
                 }
                 leaf remote-ip-addr {
                   type jt:ipaddr;
                 }
                 leaf pw-status {
                   type string;
                 }
               }
               container history {
                 leaf history.category-heading {
                   type string;
                 }
                 leaf history.heading {
                   type string;
                 }
                 container history-element {
                   leaf log-time-stamp {
                     type string;
                   }
                   leaf log-event {
                     type string;
                   }
                   leaf changed-entity {
                     type string;
                   }
                 }
               }
             }
             list mesh-group-connection {
               leaf mesh-group-name {
                 type string;
                 description "Name of mesh-group";
               }
               list connection {
                 leaf-list connection.heading {
                   type string;
                 }
                 leaf connection-id {
                   type string;
                 }
                 leaf connection-type {
                   type string;
                 }
                 leaf connection-status {
                   type string;
                 }
                 leaf last-change {
                   type string;
                 }
                 leaf up-transitions {
                   type int32;
                 }
                 leaf remote-pe {
                   type jt:ipaddr;
                 }
                 leaf control-word {
                   type string;
                 }
                 leaf control-word-type {
                   type string;
                 }
                 leaf interface-encapsulation {
                   type string;
                 }
                 leaf inbound-label {
                   type string;
                 }
                 leaf outbound-label {
                   type string;
                 }
                 leaf pw-status-tlv {
                   type string;
                 }
                 leaf local-pw-status-code {
                   type int32;
                 }
                 leaf remote-pw-status-code {
                   type int32;
                 }
                 leaf connection-protection {
                   type string;
                 }
                 leaf mesh-group-name {
                   type string;
                   description "Name of mesh-group";
                 }
                 leaf vc-flow-label-transmit {
                   type string;
                 }
                 leaf vc-flow-label-receive {
                   type string;
                 }
                 leaf auto-sensed {
                   type empty;
                   description "Auto-sensed";
                 }
                 container local-interface {
                   leaf interface-name {
                     type string;
                     description "Name of interface";
                   }
                   leaf interface-status {
                     type string;
                   }
                   leaf interface-encapsulation {
                     type string;
                   }
                   leaf working-status {
                     type string;
                   }
                   leaf profile-name {
                     type string;
                   }
                   leaf profile-varset-name {
                     type string;
                   }
                   leaf interface-description {
                     type string;
                   }
                 }
                 container remote-interface {
                   leaf interface-name {
                     type string;
                     description "Name of interface";
                   }
                   leaf interface-status {
                     type string;
                   }
                   leaf interface-encapsulation {
                     type string;
                   }
                 }
                 container connection-bandwidth {
                   leaf connection-bandwidth.heading {
                     type string;
                     description "Bandwidth of a layer 2 connection";
                   }
                   leaf bandwidth {
                     type int32;
                   }
                   leaf class-type {
                     type int32;
                   }
                   leaf class-bandwidth {
                     type int32;
                   }
                 }
                 container vpls-rsvp-te-p2mp-lsp-information {
                   leaf vpls-ingress-p2mp-branch-lsp-name {
                     type string;
                     description "Name of ingress point-to-multipoint branch LSP";
                   }
                   leaf vpls-ingress-p2mp-branch-lsp-state {
                     type string;
                     description "State of ingress point-to-multipoint branch LSP";
                   }
                   leaf vpls-egress-p2mp-branch-lsp-name {
                     type string;
                     description "Name of egress point-to-multipoint branch LSP";
                   }
                   leaf vpls-egress-p2mp-branch-lsp-state {
                     type string;
                     description "State of egress point-to-multipoint branch LSP";
                   }
                 }
                 container history {
                   leaf history.category-heading {
                     type string;
                   }
                   leaf history.heading {
                     type string;
                   }
                   container history-element {
                     leaf log-time-stamp {
                       type string;
                     }
                     leaf log-event {
                       type string;
                     }
                     leaf changed-entity {
                       type string;
                     }
                   }
                 }
               }
             }
             container automatic-site-timers {
               leaf automatic-site-timers.heading {
                 type string;
               }
               leaf automatic-site-startup-wait-time {
                 type string;
               }
               leaf automatic-site-new-site-wait-time {
                 type string;
               }
               leaf automatic-site-collision-detect-time {
                 type string;
               }
               leaf automatic-site-reclaim-wait-time {
                 type string;
               }
             }
             container connections-summary {
               leaf vc-up-count {
                 type int32;
               }
               leaf vc-down-count {
                 type int32;
               }
             }
           }
           list ldp-vpls-reference-site {
             leaf vpls-signaling-protocol-identifier {
               type string;
             }
             leaf local-site-id {
               type string;
             }
             leaf vpls-id {
               type int32;
               description "VPLS instance identifier";
             }
             leaf l2vpn-id {
               type string;
             }
             leaf local-id {
               type jt:ipaddr;
             }
             leaf num-local-interfaces {
               type int32;
             }
             leaf num-local-interfaces-up {
               type int32;
             }
             leaf irb-present {
               type string;
             }
             leaf mesh-group-count {
               type int32;
             }
             leaf mesh-group-up-count {
               type int32;
             }
             leaf remote-site-id {
               type string;
             }
             list mesh-group-interfaces {
               leaf mesh-group-name {
                 type string;
                 description "Name of mesh-group";
               }
               leaf mesh-group-state {
                 type string;
                 description "Mesh-group state";
               }
               leaf mesh-group-id {
                 type int32;
                 description "Mesh-group Identifier";
               }
               list interface {
                 leaf interface-name {
                   type string;
                   description "Name of interface";
                 }
                 leaf interface-description {
                   type string;
                 }
                 leaf interface-flags-description {
                   type string;
                 }
                 leaf interface-flags {
                   type int32;
                 }
               }
             }
             list interface {
               leaf interface-name {
                 type string;
                 description "Name of interface";
               }
               leaf interface-id {
                 type int32;
               }
               leaf interface-description {
                 type string;
               }
               leaf interface-flags-description {
                 type string;
               }
               leaf interface-flags {
                 type int32;
               }
             }
             list connection {
               leaf-list connection.heading {
                 type string;
               }
               leaf connection-id {
                 type string;
               }
               leaf connection-type {
                 type string;
               }
               leaf connection-status {
                 type string;
               }
               leaf last-change {
                 type string;
               }
               leaf up-transitions {
                 type int32;
               }
               leaf remote-pe {
                 type jt:ipaddr;
               }
               leaf control-word {
                 type string;
               }
               leaf control-word-type {
                 type string;
               }
               leaf interface-encapsulation {
                 type string;
               }
               leaf inbound-label {
                 type string;
               }
               leaf outbound-label {
                 type string;
               }
               leaf pw-status-tlv {
                 type string;
               }
               leaf local-pw-status-code {
                 type int32;
               }
               leaf remote-pw-status-code {
                 type int32;
               }
               leaf connection-protection {
                 type string;
               }
               leaf mesh-group-name {
                 type string;
                 description "Name of mesh-group";
               }
               leaf vc-flow-label-transmit {
                 type string;
               }
               leaf vc-flow-label-receive {
                 type string;
               }
               leaf auto-sensed {
                 type empty;
                 description "Auto-sensed";
               }
               container local-interface {
                 leaf interface-name {
                   type string;
                   description "Name of interface";
                 }
                 leaf interface-status {
                   type string;
                 }
                 leaf interface-encapsulation {
                   type string;
                 }
                 leaf working-status {
                   type string;
                 }
                 leaf profile-name {
                   type string;
                 }
                 leaf profile-varset-name {
                   type string;
                 }
                 leaf interface-description {
                   type string;
                 }
               }
               container remote-interface {
                 leaf interface-name {
                   type string;
                   description "Name of interface";
                 }
                 leaf interface-status {
                   type string;
                 }
                 leaf interface-encapsulation {
                   type string;
                 }
               }
               container connection-bandwidth {
                 leaf connection-bandwidth.heading {
                   type string;
                   description "Bandwidth of a layer 2 connection";
                 }
                 leaf bandwidth {
                   type int32;
                 }
                 leaf class-type {
                   type int32;
                 }
                 leaf class-bandwidth {
                   type int32;
                 }
               }
               container vpls-rsvp-te-p2mp-lsp-information {
                 leaf vpls-ingress-p2mp-branch-lsp-name {
                   type string;
                   description "Name of ingress point-to-multipoint branch LSP";
                 }
                 leaf vpls-ingress-p2mp-branch-lsp-state {
                   type string;
                   description "State of ingress point-to-multipoint branch LSP";
                 }
                 leaf vpls-egress-p2mp-branch-lsp-name {
                   type string;
                   description "Name of egress point-to-multipoint branch LSP";
                 }
                 leaf vpls-egress-p2mp-branch-lsp-state {
                   type string;
                   description "State of egress point-to-multipoint branch LSP";
                 }
               }
               container history {
                 leaf history.category-heading {
                   type string;
                 }
                 leaf history.heading {
                   type string;
                 }
                 container history-element {
                   leaf log-time-stamp {
                     type string;
                   }
                   leaf log-event {
                     type string;
                   }
                   leaf changed-entity {
                     type string;
                   }
                 }
               }
             }
             list mesh-group-connection {
               leaf mesh-group-name {
                 type string;
                 description "Name of mesh-group";
               }
               list connection {
                 leaf-list connection.heading {
                   type string;
                 }
                 leaf connection-id {
                   type string;
                 }
                 leaf connection-type {
                   type string;
                 }
                 leaf connection-status {
                   type string;
                 }
                 leaf last-change {
                   type string;
                 }
                 leaf up-transitions {
                   type int32;
                 }
                 leaf remote-pe {
                   type jt:ipaddr;
                 }
                 leaf control-word {
                   type string;
                 }
                 leaf control-word-type {
                   type string;
                 }
                 leaf interface-encapsulation {
                   type string;
                 }
                 leaf inbound-label {
                   type string;
                 }
                 leaf outbound-label {
                   type string;
                 }
                 leaf pw-status-tlv {
                   type string;
                 }
                 leaf local-pw-status-code {
                   type int32;
                 }
                 leaf remote-pw-status-code {
                   type int32;
                 }
                 leaf connection-protection {
                   type string;
                 }
                 leaf mesh-group-name {
                   type string;
                   description "Name of mesh-group";
                 }
                 leaf vc-flow-label-transmit {
                   type string;
                 }
                 leaf vc-flow-label-receive {
                   type string;
                 }
                 leaf auto-sensed {
                   type empty;
                   description "Auto-sensed";
                 }
                 container local-interface {
                   leaf interface-name {
                     type string;
                     description "Name of interface";
                   }
                   leaf interface-status {
                     type string;
                   }
                   leaf interface-encapsulation {
                     type string;
                   }
                   leaf working-status {
                     type string;
                   }
                   leaf profile-name {
                     type string;
                   }
                   leaf profile-varset-name {
                     type string;
                   }
                   leaf interface-description {
                     type string;
                   }
                 }
                 container remote-interface {
                   leaf interface-name {
                     type string;
                     description "Name of interface";
                   }
                   leaf interface-status {
                     type string;
                   }
                   leaf interface-encapsulation {
                     type string;
                   }
                 }
                 container connection-bandwidth {
                   leaf connection-bandwidth.heading {
                     type string;
                     description "Bandwidth of a layer 2 connection";
                   }
                   leaf bandwidth {
                     type int32;
                   }
                   leaf class-type {
                     type int32;
                   }
                   leaf class-bandwidth {
                     type int32;
                   }
                 }
                 container vpls-rsvp-te-p2mp-lsp-information {
                   leaf vpls-ingress-p2mp-branch-lsp-name {
                     type string;
                     description "Name of ingress point-to-multipoint branch LSP";
                   }
                   leaf vpls-ingress-p2mp-branch-lsp-state {
                     type string;
                     description "State of ingress point-to-multipoint branch LSP";
                   }
                   leaf vpls-egress-p2mp-branch-lsp-name {
                     type string;
                     description "Name of egress point-to-multipoint branch LSP";
                   }
                   leaf vpls-egress-p2mp-branch-lsp-state {
                     type string;
                     description "State of egress point-to-multipoint branch LSP";
                   }
                 }
                 container history {
                   leaf history.category-heading {
                     type string;
                   }
                   leaf history.heading {
                     type string;
                   }
                   container history-element {
                     leaf log-time-stamp {
                       type string;
                     }
                     leaf log-event {
                       type string;
                     }
                     leaf changed-entity {
                       type string;
                     }
                   }
                 }
               }
             }
             container connections-summary {
               leaf vc-up-count {
                 type int32;
               }
               leaf vc-down-count {
                 type int32;
               }
             }
           }
           container vpls-protocol-state {
             leaf vpls-signaling-protocol-identifier {
               type string;
             }
             leaf num-local-interfaces {
               type int32;
             }
             leaf num-local-interfaces-up {
               type int32;
             }
             leaf irb-present {
               type string;
             }
             leaf mesh-group-count {
               type int32;
             }
             leaf mesh-group-up-count {
               type int32;
             }
             list mesh-group-interfaces {
               list interface {
                 leaf interface-name {
                   type string;
                   description "Name of interface";
                 }
                 leaf interface-flags {
                   type int32;
                 }
               }
             }
             list interface {
               leaf interface-name {
                 type string;
                 description "Name of interface";
               }
               leaf interface-flags {
                 type int32;
               }
             }
             list mesh-group-connection {
               leaf mesh-group-name {
                 type string;
                 description "Name of mesh-group";
               }
               list connection {
                 leaf-list connection.heading {
                   type string;
                 }
                 leaf remote-pe {
                   type jt:ipaddr;
                 }
                 leaf l2vpn-local-site-id {
                   type int32;
                   description "Local site identifier";
                 }
                 leaf l2vpn-remote-site-id {
                   type int32;
                   description "Remote site identifier";
                 }
                 leaf connection-status {
                   type string;
                 }
                 leaf last-change {
                   type string;
                 }
                 leaf inbound-label {
                   type string;
                 }
                 leaf outbound-label {
                   type string;
                 }
                 container local-interface {
                   leaf interface-name {
                     type string;
                     description "Name of interface";
                   }
                   leaf interface-status {
                     type string;
                   }
                   leaf interface-encapsulation {
                     type string;
                   }
                   leaf working-status {
                     type string;
                   }
                   leaf profile-name {
                     type string;
                   }
                   leaf profile-varset-name {
                     type string;
                   }
                   leaf interface-description {
                     type string;
                   }
                 }
                 container connection-bandwidth {
                   leaf connection-bandwidth.heading {
                     type string;
                     description "Bandwidth of a layer 2 connection";
                   }
                   leaf bandwidth {
                     type int32;
                   }
                   leaf class-type {
                     type int32;
                   }
                   leaf class-bandwidth {
                     type int32;
                   }
                 }
                 container vpls-rsvp-te-p2mp-lsp-information {
                   leaf vpls-ingress-p2mp-branch-lsp-name {
                     type string;
                     description "Name of ingress point-to-multipoint branch LSP";
                   }
                   leaf vpls-ingress-p2mp-branch-lsp-state {
                     type string;
                     description "State of ingress point-to-multipoint branch LSP";
                   }
                   leaf vpls-egress-p2mp-branch-lsp-name {
                     type string;
                     description "Name of egress point-to-multipoint branch LSP";
                   }
                   leaf vpls-egress-p2mp-branch-lsp-state {
                     type string;
                     description "State of egress point-to-multipoint branch LSP";
                   }
                 }
                 container history {
                   leaf history.category-heading {
                     type string;
                   }
                   leaf history.heading {
                     type string;
                   }
                   container history-element {
                     leaf log-time-stamp {
                       type string;
                     }
                     leaf log-event {
                       type string;
                     }
                     leaf changed-entity {
                       type string;
                     }
                   }
                 }
               }
               container connections-summary {
                 leaf vc-up-count {
                   type int32;
                 }
                 leaf vc-down-count {
                   type int32;
                 }
               }
             }
             list reference-site {
               leaf automatic-site-name {
                 type string;
                 description "VPLS automatic site name";
               }
               leaf automatic-site-id-status {
                 type string;
                 description "VPLS automatic site identifier status";
               }
               leaf automatic-site-claim-id {
                 type int32;
                 description "Claim site identifier";
               }
               leaf automatic-site-collisions {
                 type int32;
                 description "Number of collisions";
               }
               leaf automatic-site-timer-status {
                 type string;
                 description "VPLS automatic site timer status";
               }
               leaf vpls-signaling-protocol-identifier {
                 type string;
               }
               leaf local-site-id {
                 type string;
               }
               leaf source-attachment-id {
                 type string;
                 description "Local source attachment identifier";
               }
               leaf vpls-id {
                 type int32;
                 description "VPLS instance identifier";
               }
               leaf l2vpn-id {
                 type string;
               }
               leaf local-id {
                 type jt:ipaddr;
               }
               leaf num-local-interfaces {
                 type int32;
               }
               leaf num-local-interfaces-up {
                 type int32;
               }
               leaf irb-present {
                 type string;
               }
               leaf mesh-group-count {
                 type int32;
               }
               leaf mesh-group-up-count {
                 type int32;
               }
               leaf remote-site-id {
                 type string;
               }
               leaf target-attachment-id {
                 type string;
                 description "Remote target attachment identifier";
               }
               list mesh-group-interfaces {
                 leaf mesh-group-name {
                   type string;
                   description "Name of mesh-group";
                 }
                 leaf mesh-group-state {
                   type string;
                   description "Mesh-group state";
                 }
                 leaf mesh-group-id {
                   type int32;
                   description "Mesh-group Identifier";
                 }
                 list interface {
                   leaf interface-name {
                     type string;
                     description "Name of interface";
                   }
                   leaf interface-description {
                     type string;
                   }
                   leaf interface-flags-description {
                     type string;
                   }
                   leaf interface-flags {
                     type int32;
                   }
                 }
               }
               list interface {
                 leaf interface-name {
                   type string;
                   description "Name of interface";
                 }
                 leaf interface-id {
                   type int32;
                 }
                 leaf interface-description {
                   type string;
                 }
                 leaf interface-flags-description {
                   type string;
                 }
                 leaf interface-flags {
                   type int32;
                 }
               }
               list connection {
                 container history {
                 }
               }
               list mesh-group-connection {
                 list connection {
                   container history {
                   }
                 }
               }
             }
           }
           container vpls-rsvp-te-ingress-p2mp-lsp {
             leaf vpls-ingress-p2mp-lsp-name {
               type string;
               description "Name of ingress point-to-multipoint LSP";
             }
             leaf vpls-rsvp-te-p2mp-flood-nexthop-id {
               type int32;
               description "Identifier for VPLS RSVP traffic-engineering ingress flood next hop";
             }
           }
           container multihome {
             leaf multihome.heading {
               type string;
             }
             list multihome-site {
               leaf multihome-site-name {
                 type string;
                 description "Name of site";
               }
               leaf multihome-site-id {
                 type int32;
                 description "Site Identifier";
               }
               leaf multihome-site-preference {
                 type int32;
                 description "Site Preference";
               }
               leaf multihome-site-state {
                 type string;
                 description "Site state";
               }
               leaf multihome-num-interfaces {
                 type int32;
               }
               leaf multihome-num-interfaces-up {
                 type int32;
               }
               list interface {
                 leaf interface-name {
                   type string;
                   description "Name of interface";
                 }
                 leaf interface-id {
                   type int32;
                 }
                 leaf interface-description {
                   type string;
                 }
                 leaf interface-flags-description {
                   type string;
                 }
                 leaf interface-flags {
                   type int32;
                 }
               }
               container remote-advertisements {
                 leaf remote-advertisements.heading {
                   type string;
                 }
                 list remote-adv {
                   leaf remote-adv-addr {
                     type string;
                   }
                   leaf remote-adv-preference {
                     type int32;
                     description "Remote PE preference";
                   }
                   leaf remote-adv-ctrl-flag {
                     type int32;
                     description "Remote PE Control flags";
                   }
                   leaf remote-adv-ctrl-flag-description {
                     type string;
                     description "Control flags description";
                   }
                 }
               }
             }
           }
           container history {
             leaf history.category-heading {
               type string;
             }
             leaf history.heading {
               type string;
             }
             container history-element {
               leaf log-time-stamp {
                 type string;
               }
               leaf log-event {
                 type string;
               }
               leaf changed-entity {
                 type string;
               }
             }
           }
           leaf instance-any-stat {
             type string;
             description "Instance any statistics";
           }
           leaf instance-any {
             type empty;
             description "Any routing protocol instance";
           }
           leaf instance-list-stat {
             type string;
             description "Instance list statistics";
           }
           leaf instance-list {
             type string;
             description "A list of routing protocol instances";
           }
           leaf interface-stat {
             type string;
             description "Interface statistics";
           }
           leaf-list interface {
             type string;
             description "Interface name or address";
           }
           leaf interface-name {
             type string;
             description "Name of interface";
           }
           leaf interface-flags {
             type int32;
           }
           leaf policy-level-stat {
             type string;
             description "Level statistics";
           }
           leaf policy-level {
             type uint32;
           }
           leaf policy-local-preference-stat {
             type string;
             description "Local preference statistics";
           }
           leaf policy-local-preference {
             type uint32;
             description "Local preference associated with a route";
           }
           leaf lsp-stat {
             type string;
             description "LSP statistics";
           }
           leaf lsp {
             type string;
             description "Label switched path name";
           }
           leaf lsp-regex-stat {
             type string;
             description "LSP regex statistics";
           }
           leaf lsp-regex {
             type string;
             description "Label switched path name regular expression";
           }
           leaf metric-stat {
             type string;
             description "Metric statistics";
           }
           leaf metric1 {
             type uint32;
             description "Metric value";
           }
           leaf metric2-stat {
             type string;
             description "Metric2 statistics";
           }
           leaf metric-2 {
             type uint32;
             description "Metric value 2";
           }
           leaf metric3-stat {
             type string;
             description "Metric3 statistics";
           }
           leaf metric3 {
             type uint32;
             description "Metric value 3";
           }
           leaf metric4-stat {
             type string;
             description "Metric4 statistics";
           }
           leaf metric4 {
             type uint32;
             description "Metric value 4";
           }
           leaf metric5-stat {
             type string;
             description "Metric5 statistics";
           }
           leaf metric5 {
             type uint32;
             description "Metric value 5";
           }
           leaf metric6-stat {
             type string;
             description "Metric6 statistics";
           }
           leaf metric6 {
             type uint32;
             description "Metric value 6";
           }
           leaf metric7-stat {
             type string;
             description "Metric7 statistics";
           }
           leaf metric7 {
             type uint32;
             description "Metric value 7";
           }
           leaf metric8-stat {
             type string;
             description "Metric8 statistics";
           }
           leaf metric8 {
             type uint32;
             description "Metric value 8";
           }
           leaf metric9-stat {
             type string;
             description "Metric9 statistics";
           }
           leaf metric9 {
             type uint32;
             description "Metric value 9";
           }
           leaf metric10-stat {
             type string;
             description "Metric10 statistics";
           }
           leaf metric10 {
             type uint32;
             description "Metric value 10";
           }
           leaf metric11-stat {
             type string;
             description "Metric11 statistics";
           }
           leaf metric11 {
             type uint32;
             description "Metric value 11";
           }
           leaf metric12-stat {
             type string;
             description "Metric12 statistics";
           }
           leaf metric12 {
             type uint32;
             description "Metric value 12";
           }
           leaf policy-neighbor-stat {
             type string;
             description "Policy neighbor statistics";
           }
           leaf policy-neighbor {
             type string;
             description "Neighboring router";
           }
           leaf next-hop-stat {
             type string;
             description "Nexthop statistics";
           }
           leaf next-hop {
             type jt:ipaddr;
             description "Next-hop address";
           }
           leaf origin-stat {
             type string;
             description "Origin statistics";
           }
           leaf origin {
             type string;
             description "BGP origin attribute";
           }
           leaf preference-stat {
             type string;
             description "Preference statistics";
           }
           leaf preference1 {
             type uint32;
           }
           leaf preference2-stat {
             type string;
             description "Preference2 statistics";
           }
           leaf preference-2 {
             type uint32;
             description "Preference value 2";
           }
           leaf preference3-stat {
             type string;
             description "Preference3 statistics";
           }
           leaf preference3 {
             type uint32;
             description "Preference value 3";
           }
           leaf preference4-stat {
             type string;
             description "Preference4 statistics";
           }
           leaf preference4 {
             type uint32;
             description "Preference value 4";
           }
           leaf preference5-stat {
             type string;
             description "Preference5 statistics";
           }
           leaf preference5 {
             type uint32;
             description "Preference value 5";
           }
           leaf preference6-stat {
             type string;
             description "Preference6 statistics";
           }
           leaf preference6 {
             type uint32;
             description "Preference value 6";
           }
           leaf preference7-stat {
             type string;
             description "Preference7 statistics";
           }
           leaf preference7 {
             type uint32;
             description "Preference value 7";
           }
           leaf preference8-stat {
             type string;
             description "Preference8 statistics";
           }
           leaf preference8 {
             type uint32;
             description "Preference value 8";
           }
           leaf preference9-stat {
             type string;
             description "Preference9 statistics";
           }
           leaf preference9 {
             type uint32;
             description "Preference value 9";
           }
           leaf preference10-stat {
             type string;
             description "Preference10 statistics";
           }
           leaf preference10 {
             type uint32;
             description "Preference value 10";
           }
           leaf preference11-stat {
             type string;
             description "Preference11 statistics";
           }
           leaf preference11 {
             type uint32;
             description "Preference value 11";
           }
           leaf preference12-stat {
             type string;
             description "Preference12 statistics";
           }
           leaf preference12 {
             type uint32;
             description "Preference value 12";
           }
           leaf programmed-stat {
             type string;
             description "Programmed statistics";
           }
           leaf programmed {
             type empty;
             description "API-programmed route";
           }
           leaf protocol-stat {
             type string;
             description "Protocol statistics";
           }
           leaf-list protocol {
             type string;
             description "Protocol from which route was learned";
           }
           leaf rib-stat {
             type string;
             description "RIB statistics";
           }
           leaf rib {
             type string;
             description "Routing table";
           }
           leaf srte-color-stat {
             type string;
             description "SRTE color statistics";
           }
           leaf srte-color {
             type uint32;
             description "SRTE color";
           }
           leaf tag-stat {
             type string;
             description "Policy tag statistics";
           }
           leaf policy-tag {
             type uint32;
             description "Tag string";
           }
           leaf tag2-stat {
             type string;
             description "Policy tag2 statistics";
           }
           leaf policy-tag2 {
             type uint32;
             description "Tag string 2";
           }
           leaf tag3-stat {
             type string;
             description "Policy tag3 statistics";
           }
           leaf policy-tag3 {
             type uint32;
             description "Tag string 3";
           }
           leaf tag4-stat {
             type string;
             description "Policy tag4 statistics";
           }
           leaf policy-tag4 {
             type uint32;
             description "Tag string 4";
           }
           leaf validation-state-stat {
             type string;
             description "Validation database statistics";
           }
           leaf validation-database {
             type string;
             description "Name to identify a validation-state";
           }
           leaf external-stat {
             type string;
             description "External statistics";
           }
           leaf next-hop-weight-stat {
             type string;
             description "Nexthop weight statistics";
           }
           leaf next-hop-ecmp-stat {
             type string;
             description "Nexthop ecmp statistics";
           }
           leaf source-routing-path-stat {
             type string;
             description "Source routing path statistics";
           }
           container next-hop-ecmp {
             leaf all-nexthop {
               type empty;
             }
             leaf next-hop-ecmp-stat {
               type string;
               description "Nexthop ecmp statistics";
             }
             leaf next-hop-ecmp.heading {
               type string;
               description "Nexthop ecmp";
             }
             leaf equal-to {
               type uint32;
             }
             leaf greater-than {
               type uint32;
             }
             leaf greater-than-equal {
               type uint32;
             }
             leaf less-than {
               type uint32;
             }
             leaf less-than-equal {
               type uint32;
             }
           }
           leaf policy-to.heading {
             type string;
           }
           container external {
             leaf external-stat {
               type string;
               description "External statistics";
             }
             leaf external.heading {
               type string;
               description "External route";
             }
             leaf external-type {
               type uint32;
             }
             leaf nssa-only {
               type empty;
             }
           }
           container next-hop-weight {
             leaf next-hop-weight-stat {
               type string;
               description "Nexthop weight statistics";
             }
             leaf next-hop-weight.heading {
               type string;
               description "Nexthop weight";
             }
             leaf equal-to {
               type uint32;
             }
             leaf greater-than {
               type uint32;
             }
             leaf greater-than-equal {
               type uint32;
             }
             leaf less-than {
               type uint32;
             }
             leaf less-than-equal {
               type uint32;
             }
             leaf all-nexthop {
               type empty;
             }
           }
           container source-routing-path {
             leaf source-routing-path-stat {
               type string;
               description "Source routing path statistics";
             }
             leaf source-routing-path.heading {
               type string;
             }
             leaf color-value {
               type uint32;
               description "Color";
             }
             leaf dest {
               type string;
               description "Spring-te lsp IPV4/IPV6 destination without color";
             }
             leaf name-regex {
               type string;
               description "Spring-te lsp name regex";
             }
             leaf origin-value {
               type string;
               description "Origin";
             }
             leaf route-distinguisher-value {
               type uint32;
               description "Route distinguisher";
             }
             leaf tunnel-source {
               type string;
               description "Source protocol";
             }
           }
         }
         container then {
           leaf account-stat {
             type string;
           }
           leaf account {
             type empty;
             description "Account";
           }
           leaf accept-stat {
             type string;
           }
           leaf accept {
             type empty;
             description "Accept a route";
           }
           leaf advertise-locator-stat {
             type string;
             description "Advertise locator statistics";
           }
           leaf advertise-locator {
             type empty;
             description "Advertise SRv6 locator";
           }
           leaf advertise-locator-internal {
             type empty;
             description "Advertise SRv6 locator internal";
           }
           leaf aggregate-bandwidth-stat {
             type string;
             description "Aggregate bandwidth statistics";
           }
           leaf aggregate-bandwidth {
             type int32;
             description "Aggregate bandwidth";
           }
           leaf auto-link-bandwidth-stat {
             type string;
             description "Auto link bandwidth statistics";
           }
           leaf auto-link-bandwidth {
             type empty;
             description "Auto link bandwidth";
           }
           leaf analyze-stat {
             type string;
             description "Analyze statistics";
           }
           leaf analyze {
             type empty;
             description "Send to registered controllers for analysis";
           }
           leaf as-path-prepend-stat {
             type string;
             description "AS path prepend statistics";
           }
           leaf as-path-prepend {
             type uint32;
             description "Prepend AS numbers to an AS path (BGP only)";
           }
           leaf class-stat {
             type string;
             description "Class statistics";
           }
           leaf-list class {
             type string;
             description "An instance of BGP output queue statistics";
           }
           leaf cos-next-hop-map-stat {
             type string;
             description "COS next hop map statistics";
           }
           leaf cos-next-hop-map {
             type string;
             description "The CoS-based next-hop map in forwarding table";
           }
           leaf damping-stat {
             type string;
             description "Damping statistics";
           }
           leaf damping {
             type string;
             description "Define BGP route flap damping parameters";
           }
           leaf default-action-stat {
             type string;
             description "Default action statistics";
           }
           leaf default-action {
             type string;
             description "The default policy action";
           }
           leaf destination-class-stat {
             type string;
             description "Destination class statistics";
           }
           leaf destination-class {
             type string;
             description "The destination class in forwarding table";
           }
           leaf dynamic-tunnel-attributes-stat {
             type string;
             description "Dynamic tunnel attribute statistics";
           }
           leaf dynamic-tunnel-attributes {
             type string;
             description "The dynamic tunnel attributes used for forwarding";
           }
           leaf fib-install-priority-stat {
             type string;
             description "FIB install priority statistics";
           }
           leaf fib-install-priority {
             type string;
             description "FIB install priority";
           }
           leaf filter-stat {
             type string;
             description "Filter statistics";
           }
           leaf filter {
             type string;
             description "Next-hop firewall filter";
           }
           leaf get-route-range {
             type empty;
             description "Get route range";
           }
           leaf ignore-service-label-stat {
             type string;
             description "Ignore service label statistics";
           }
           leaf ignore-service-label {
             type string;
             description "Ignore service labels";
           }
           leaf install-to-fib-stat {
             type string;
             description "Install to FIB statistics";
           }
           leaf install-to-fib {
             type string;
             description "Install to FIB";
           }
           leaf ipv4-source-router-id-stat {
             type string;
             description "IPV4 source router id statistics";
           }
           leaf ipv4-source-router-id {
             type empty;
           }
           leaf ipv4-source-router-id-address {
             type string;
             description "IPV4 source router id address";
           }
           leaf ipv6-source-router-id-stat {
             type string;
             description "IPV6 source router id statistics";
           }
           leaf ipv6-source-router-id {
             type empty;
           }
           leaf ipv6-source-router-id-address {
             type string;
             description "IPV6 source router id address";
           }
           leaf label-allocation-stat {
             type string;
             description "Label allocation statistics";
           }
           leaf label-allocation {
             type string;
             description "Label allocation mode";
           }
           leaf label-allocation-fallback-reject-stat {
             type string;
             description "Label allocation fallback reject statistics";
           }
           leaf label-allocation-fallback-reject {
             type string;
             description "Suppress prefix export when label allocation fails";
           }
           leaf limit-bandwidth-stat {
             type string;
             description "Limit bandwidth statistics";
           }
           leaf limit-bandwidth {
             type uint64;
             description "Limit advertised aggregate outbound link bandwidth";
           }
           leaf load-balance-stat {
             type string;
             description "Load balance statistics";
           }
           leaf load-balance {
             type string;
             description "Load-balancing algorithm chosen";
           }
           leaf mhop-bfd-port-stat {
             type string;
             description "Mhop bfd port statistics";
           }
           leaf mhop-bfd-port {
             type uint32;
             description "Use port number 4784 for MPLS-BFD as per RFC5884";
           }
           leaf multipath-resolve-stat {
             type string;
             description "Multipath resolve statistics";
           }
           leaf multipath-resolve {
             type string;
             description "Use all paths for resolution over this prefix";
           }
           leaf next-stat {
             type string;
             description "Next policy statistics";
           }
           leaf next {
             type string;
             description "Skip to next policy or term";
           }
           leaf no-backup-stat {
             type string;
             description "No backup statistics";
           }
           leaf no-backup {
             type empty;
             description "This prefix should not have backup";
           }
           leaf no-entropy-label-capability-stat {
             type string;
             description "No entropy label capability statistics";
           }
           leaf no-entropy-label-capability {
             type empty;
             description "Don't advertise entropy label capability";
           }
           leaf no-route-localize-stat {
             type string;
             description "No route localize statistics";
           }
           leaf no-route-localize {
             type empty;
             description "No route localize";
           }
           leaf origin-stat {
             type string;
             description "Origin statistics";
           }
           leaf origin {
             type string;
             description "BGP origin attribute";
           }
           leaf p2mp-lsp-root-stat {
             type string;
             description "P2mp lsp root statistics";
           }
           leaf p2mp-lsp-root {
             type jt:ipaddr;
             description "P2mp lsp root address";
           }
           leaf policy-priority-stat {
             type string;
             description "Policy priority statistics";
           }
           leaf policy-priority {
             type string;
           }
           leaf reject-stat {
             type string;
             description "Reject statistics";
           }
           leaf reject {
             type empty;
             description "Reject a route";
           }
           leaf request-long-lived-ack-stat {
             type string;
             description "Request long lived ack statistics";
           }
           leaf request-long-lived-ack {
             type empty;
             description "Advertise route after forwarding is programmed";
           }
           leaf resolution-map-stat {
             type string;
             description "Resolution map stat";
           }
           leaf resolution-map {
             type string;
             description "Resolution map";
           }
           leaf resolution-map-mode {
             type string;
             description "Resolution map modes";
           }
           leaf selected-mldp-egress-stat {
             type string;
             description "Selected mldp egress statistics";
           }
           leaf selected-mldp-egress {
             type string;
             description "This node should act as egress node for MLDP inband signalling";
           }
           leaf send-withdrawal-on-route-change-stat {
             type string;
             description "Send withdrawal on route change statistics";
           }
           leaf send-withdrawal-on-route-change {
             type empty;
             description "Withdrawn route as change is not ack'd from forwarding";
           }
           leaf set-down-bit-stat {
             type string;
             description "Set down bit statistics";
           }
           leaf set-down-bit {
             type empty;
             description "Set down bit";
           }
           leaf slice-stat {
             type string;
             description "Slice statistics";
           }
           leaf slice {
             type string;
             description "Slice name";
           }
           leaf source-class-stat {
             type string;
             description "Source class statistics";
           }
           leaf source-class {
             type string;
             description "The source class in forwarding table";
           }
           leaf sr-te-template-stat {
             type string;
             description "SRTE template statistics";
           }
           leaf sr-te-template {
             type string;
             description "SR TE template to apply";
           }
           leaf ssm-source-stat {
             type string;
             description "SSM source statistics";
           }
           leaf ssm-source {
             type jt:ipaddr;
             description "List of Sources for SSM mapping";
           }
           leaf strip-as-path-stat {
             type string;
             description "Strip Aspath statistics";
           }
           leaf strip-as-path {
             type empty;
             description "Atrip As path";
           }
           leaf trace-stat {
             type string;
             description "Tunnel statistics";
           }
           leaf trace {
             type empty;
             description "Log matches to a trace file";
           }
           leaf tunnel-end-point-address-stat {
             type string;
             description "Tunnel end point address statistics";
           }
           leaf tunnel-end-point-address {
             type string;
             description "Set tunnel end-point address of tunnel";
           }
           leaf validation-state-stat {
             type string;
             description "Validation database statistics";
           }
           leaf validation-state {
             type string;
             description "Validation-state of a route";
           }
           leaf aigp-adjust-stat {
             type string;
             description "AIGP adjust statistics";
           }
           leaf aigp-originate-stat {
             type string;
             description "AIGP originate statistics";
           }
           leaf as-path-expand-stat {
             type string;
             description "AS path expand statistics";
           }
           leaf bgp-output-queue-priority-stat {
             type string;
             description "BGP output queue priority statistics";
           }
           leaf color-stat {
             type string;
             description "Color statistics";
           }
           leaf color2-stat {
             type string;
             description "Color2 statistics";
           }
           leaf color3-stat {
             type string;
             description "Color3 statistics";
           }
           leaf color4-stat {
             type string;
             description "Color4 statistics";
           }
           leaf credibility-stat {
             type string;
             description "Credibility statistics";
           }
           leaf external-stat {
             type string;
             description "External statistics";
           }
           leaf install-nexthop-stat {
             type string;
             description "Install nexthop statistics";
           }
           leaf map-to-interface-stat {
             type string;
             description "Map to interface statistics";
           }
           leaf metric-stat {
             type string;
             description "Metric statistics";
           }
           leaf metric2-stat {
             type string;
             description "Metric2 statistics";
           }
           leaf metric3-stat {
             type string;
             description "Metric3 statistics";
           }
           leaf metric4-stat {
             type string;
             description "Metric4 statistics";
           }
           leaf metric5-stat {
             type string;
             description "Metric5 statistics";
           }
           leaf metric6-stat {
             type string;
             description "Metric6 statistics";
           }
           leaf metric7-stat {
             type string;
             description "Metric7 statistics";
           }
           leaf metric8-stat {
             type string;
             description "Metric8 statistics";
           }
           leaf metric9-stat {
             type string;
             description "Metric9 statistics";
           }
           leaf metric10-stat {
             type string;
             description "Metric10 statistics";
           }
           leaf metric11-stat {
             type string;
             description "Metric11 statistics";
           }
           leaf metric12-stat {
             type string;
             description "Metric12 statistics";
           }
           leaf next-hop-stat {
             type string;
             description "Nexthop statistics";
           }
           leaf preference-stat {
             type string;
             description "Preference statistics";
           }
           leaf preference2-stat {
             type string;
             description "Preference2 statistics";
           }
           leaf preference3-stat {
             type string;
             description "Preference3 statistics";
           }
           leaf preference4-stat {
             type string;
             description "Preference4 statistics";
           }
           leaf preference5-stat {
             type string;
             description "Preference5 statistics";
           }
           leaf preference6-stat {
             type string;
             description "Preference6 statistics";
           }
           leaf preference7-stat {
             type string;
             description "Preference7 statistics";
           }
           leaf preference8-stat {
             type string;
             description "Preference8 statistics";
           }
           leaf preference9-stat {
             type string;
             description "Preference9 statistics";
           }
           leaf preference10-stat {
             type string;
             description "Preference10 statistics";
           }
           leaf preference11-stat {
             type string;
             description "Preference11 statistics";
           }
           leaf preference12-stat {
             type string;
             description "Preference12 statistics";
           }
           leaf prefix-attribute-flags-stat {
             type string;
             description "Prefix attribute flag statistics";
           }
           leaf prefix-segment-stat {
             type string;
             description "Prefix segment statistics";
           }
           leaf resolution-map-mode-stat {
             type string;
             description "Resolution map mode statistics";
           }
           leaf tag-stat {
             type string;
             description "Policy tag statistics";
           }
           leaf tag2-stat {
             type string;
             description "Policy tag2 statistics";
           }
           leaf tag3-stat {
             type string;
             description "Policy tag3 statistics";
           }
           leaf tag4-stat {
             type string;
             description "Policy tag4 statistics";
           }
           leaf tunnel-attribute-stat {
             type string;
             description "Tunnel attribute statistics";
           }
           leaf source-based-forwarding-stat {
             type string;
             description "Source based forwarding statistics";
           }
           container install-nexthop {
             container except {
               leaf lsp {
                 type string;
                 description "Label switched path name";
               }
               leaf lsp-regex {
                 type string;
                 description "Label switched path name regular expression";
               }
               leaf non-labelled-nexthop {
                 type empty;
               }
               leaf non-lsp-nexthop {
                 type empty;
               }
               leaf static-lsp {
                 type string;
               }
               leaf static-lsp-regex {
                 type string;
               }
               leaf overlay-vxlan-interfaces {
                 type empty;
               }
             }
             container fallback {
               leaf lsp {
                 type string;
                 description "Label switched path name";
               }
               leaf lsp-regex {
                 type string;
                 description "Label switched path name regular expression";
               }
               leaf non-labelled-nexthop {
                 type empty;
               }
               leaf non-lsp-nexthop {
                 type empty;
               }
               leaf static-lsp {
                 type string;
               }
               leaf static-lsp-regex {
                 type string;
               }
               leaf overlay-vxlan-interfaces {
                 type empty;
               }
             }
             leaf install-nexthop-stat {
               type string;
               description "Install nexthop statistics";
             }
             leaf install-nexthop.heading {
               type string;
               description "The next hop to be used for forwarding";
             }
             leaf lsp {
               type string;
               description "Label switched path name";
             }
             leaf lsp-regex {
               type string;
               description "Label switched path name regular expression";
             }
             leaf non-labelled-nexthop {
               type empty;
             }
             leaf non-lsp-nexthop {
               type empty;
             }
             leaf static-lsp {
               type string;
             }
             leaf static-lsp-regex {
               type string;
             }
             leaf strict {
               type empty;
             }
             leaf strict-named-lsp {
               type empty;
             }
             leaf address {
               type jt:ipaddr;
             }
             leaf overlay-vxlan-interfaces {
               type empty;
             }
             leaf nh-select {
               type string;
             }
             leaf hash {
               type uint32;
             }
           }
           container map-to-interface {
             list interface {
               leaf interface-name {
                 type string;
                 description "Name of interface";
               }
               leaf interface-flags {
                 type int32;
               }
             }
             leaf map-to-interface-stat {
               type string;
               description "Map to interface statistics";
             }
             leaf map-to-interface.heading {
               type string;
               description "Set output logical interface";
             }
             leaf self {
               type empty;
             }
           }
           container then-metric {
             leaf metric-stat {
               type string;
               description "Metric statistics";
             }
             leaf then-metric.heading {
               type string;
             }
             leaf metric1 {
               type uint32;
               description "Metric value";
             }
             leaf add-metric {
               type uint32;
             }
             leaf subtract-metric {
               type uint32;
             }
             leaf aigp-metric {
               type empty;
             }
             container effective-aigp {
               leaf metric-offset {
                 type uint32;
               }
             }
             container igp {
               leaf metric-offset {
                 type uint32;
               }
             }
             container minimum-effective-aigp {
               leaf metric-offset {
                 type uint32;
               }
             }
             container minimum-igp {
               leaf metric-offset {
                 type uint32;
               }
             }
           }
           container prefix-segment {
             leaf redistribute {
               type empty;
             }
             container algorithm {
               leaf prefix-segment-index-value {
                 type uint32;
               }
               leaf algorithm-name {
                 type uint32;
               }
               leaf node-segment {
                 type empty;
               }
               leaf redistribute {
                 type empty;
               }
             }
             leaf prefix-segment-stat {
               type string;
               description "Prefix segment statistics";
             }
             leaf prefix-segment.heading {
               type string;
               description "The prefix segment attributes";
             }
             leaf prefix-segment-index-value {
               type uint32;
             }
             leaf node-segment {
               type empty;
             }
             leaf psid-extended-data {
               type int32;
               description "Prefix segment extendend information";
             }
           }
           list tunnel-attribute {
             leaf tunnel-type {
               type string;
               description "Tunnel type";
             }
             leaf reference-count {
               type int32;
               description "Reference count";
             }
             leaf tunnel-data {
               type string;
               description "Tunnel Data";
             }
             leaf tunnel-attribute-stat {
               type string;
               description "Tunnel attribute statistics";
             }
             leaf-list tunnel-attribute.heading {
               type string;
               description "Tunnel attribute information";
             }
             leaf set {
               type empty;
               description "Set BGP tunnel attribute in the route";
             }
             leaf remove {
               type empty;
               description "Remove BGP tunnel attribute from the route";
             }
             leaf tunnel-attribute-name {
               type string;
               description "Name of a tunnel attribute , or 'all'";
             }
           }
           container source-based-forwarding {
             container sbf-attributes {
               leaf sbf-next-table {
                 type string;
               }
             }
             leaf source-based-forwarding-stat {
               type string;
               description "Source based forwarding statistics";
             }
             leaf source-based-forwarding.heading {
               type string;
             }
           }
           leaf then.heading {
             type string;
           }
           container add-path {
             leaf add-path-stat {
               type string;
             }
             leaf add-path.heading {
               type string;
               description "BGP add-path attributes";
             }
             leaf sendcount {
               type uint32;
               description "Number of add-paths sent";
             }
           }
           container aigp-adjust {
             leaf aigp-adjust-stat {
               type string;
               description "AIGP adjust statistics";
             }
             leaf aigp-adjust.heading {
               type string;
               description "Adjust a BGP AIGP attribute";
             }
             leaf distance-to-protocol-nexthop {
               type empty;
             }
             leaf add {
               type empty;
             }
             leaf divide {
               type empty;
             }
             leaf multiply {
               type empty;
             }
             leaf subtract {
               type empty;
             }
             leaf user-value {
               type uint64;
             }
           }
           container aigp-originate {
             leaf aigp-originate-stat {
               type string;
               description "AIGP originate statistics";
             }
             leaf aigp-originate.heading {
               type string;
               description "Originate a BGP AIGP attribute";
             }
             leaf distance {
               type uint32;
               description "AIGP distance";
             }
           }
           container as-path-expand {
             leaf as-path-expand-stat {
               type string;
               description "AS path expand statistics";
             }
             leaf as-path-expand.heading {
               type string;
               description "Prepend AS numbers prior to adding local-as (BGP only)";
             }
             leaf as-path-sequence {
               type string;
             }
             leaf last-as-count {
               type uint32;
             }
           }
           container assisted-replication {
             leaf assisted-replication-stat {
               type string;
               description "Assisted replication";
             }
             leaf assisted-replication.heading {
               type string;
             }
             leaf replicator-ip {
               type string;
             }
             leaf strict-mode {
               type string;
             }
             leaf fallback-replicator-ip {
               type string;
             }
           }
           container bgp-output-queue-priority {
             leaf bgp-output-queue-priority-stat {
               type string;
               description "BGP output queue priority statistics";
             }
             leaf bgp-output-queue-priority.heading {
               type string;
               description "The BGP Update output queue priority";
             }
             leaf expedited {
               type empty;
             }
             leaf queue-priority {
               type uint32;
             }
           }
           container then-color {
             leaf color-stat {
               type string;
               description "Color statistics";
             }
             leaf then-color.heading {
               type string;
             }
             leaf add-metric {
               type uint32;
             }
             leaf subtract-metric {
               type uint32;
             }
             leaf metric1 {
               type uint32;
               description "Metric value";
             }
           }
           container then-color2 {
             leaf color2-stat {
               type string;
               description "Color2 statistics";
             }
             leaf then-color2.heading {
               type string;
             }
             leaf add-metric {
               type uint32;
             }
             leaf subtract-metric {
               type uint32;
             }
             leaf metric1 {
               type uint32;
               description "Metric value";
             }
           }
           container then-color3 {
             leaf color3-stat {
               type string;
               description "Color3 statistics";
             }
             leaf then-color3.heading {
               type string;
             }
             leaf add-metric {
               type uint32;
             }
             leaf subtract-metric {
               type uint32;
             }
             leaf metric1 {
               type uint32;
               description "Metric value";
             }
           }
           container then-color4 {
             leaf color4-stat {
               type string;
               description "Color4 statistics";
             }
             leaf then-color4.heading {
               type string;
             }
             leaf add-metric {
               type uint32;
             }
             leaf subtract-metric {
               type uint32;
             }
             leaf metric1 {
               type uint32;
               description "Metric value";
             }
           }
           container then-community {
             leaf community-stat {
               type string;
               description "Community statistics";
             }
             leaf then-community.heading {
               type string;
             }
             leaf add {
               type empty;
             }
             leaf set {
               type empty;
               description "Set BGP tunnel attribute in the route";
             }
             leaf community-delete {
               type empty;
             }
             leaf community-name {
               type string;
             }
           }
           container credibility {
             leaf credibility-stat {
               type string;
               description "Credibility statistics";
             }
             leaf credibility.heading {
               type string;
             }
             leaf add-metric {
               type uint32;
             }
             leaf subtract-metric {
               type uint32;
             }
             leaf metric1 {
               type uint32;
               description "Metric value";
             }
           }
           container external {
             leaf external-stat {
               type string;
               description "External statistics";
             }
             leaf external.heading {
               type string;
               description "External route";
             }
             leaf external-type {
               type uint32;
             }
             leaf nssa-only {
               type empty;
             }
           }
           container localpreference {
             leaf policy-local-preference-stat {
               type string;
               description "Local preference statistics";
             }
             leaf localpreference.heading {
               type string;
             }
             leaf add-metric {
               type uint32;
             }
             leaf subtract-metric {
               type uint32;
             }
             leaf metric1 {
               type uint32;
               description "Metric value";
             }
           }
           container then-metric2 {
             leaf metric2-stat {
               type string;
               description "Metric2 statistics";
             }
             leaf then-metric2.heading {
               type string;
             }
             leaf metric1 {
               type uint32;
               description "Metric value";
             }
             leaf add-metric {
               type uint32;
             }
             leaf subtract-metric {
               type uint32;
             }
           }
           container then-metric3 {
             leaf metric3-stat {
               type string;
               description "Metric3 statistics";
             }
             leaf then-metric3.heading {
               type string;
             }
             leaf metric1 {
               type uint32;
               description "Metric value";
             }
             leaf add-metric {
               type uint32;
             }
             leaf subtract-metric {
               type uint32;
             }
           }
           container then-metric4 {
             leaf metric4-stat {
               type string;
               description "Metric4 statistics";
             }
             leaf then-metric4.heading {
               type string;
             }
             leaf metric1 {
               type uint32;
               description "Metric value";
             }
             leaf add-metric {
               type uint32;
             }
             leaf subtract-metric {
               type uint32;
             }
           }
           container then-metric5 {
             leaf metric5-stat {
               type string;
               description "Metric5 statistics";
             }
             leaf then-metric5.heading {
               type string;
             }
             leaf metric1 {
               type uint32;
               description "Metric value";
             }
             leaf add-metric {
               type uint32;
             }
             leaf subtract-metric {
               type uint32;
             }
           }
           container then-metric6 {
             leaf metric6-stat {
               type string;
               description "Metric6 statistics";
             }
             leaf then-metric6.heading {
               type string;
             }
             leaf metric1 {
               type uint32;
               description "Metric value";
             }
             leaf add-metric {
               type uint32;
             }
             leaf subtract-metric {
               type uint32;
             }
           }
           container then-metric7 {
             leaf metric7-stat {
               type string;
               description "Metric7 statistics";
             }
             leaf then-metric7.heading {
               type string;
             }
             leaf metric1 {
               type uint32;
               description "Metric value";
             }
             leaf add-metric {
               type uint32;
             }
             leaf subtract-metric {
               type uint32;
             }
           }
           container then-metric8 {
             leaf metric8-stat {
               type string;
               description "Metric8 statistics";
             }
             leaf then-metric8.heading {
               type string;
             }
             leaf metric1 {
               type uint32;
               description "Metric value";
             }
             leaf add-metric {
               type uint32;
             }
             leaf subtract-metric {
               type uint32;
             }
           }
           container then-metric9 {
             leaf metric9-stat {
               type string;
               description "Metric9 statistics";
             }
             leaf then-metric9.heading {
               type string;
             }
             leaf metric1 {
               type uint32;
               description "Metric value";
             }
             leaf add-metric {
               type uint32;
             }
             leaf subtract-metric {
               type uint32;
             }
           }
           container then-metric10 {
             leaf metric10-stat {
               type string;
               description "Metric10 statistics";
             }
             leaf then-metric10.heading {
               type string;
             }
             leaf metric1 {
               type uint32;
               description "Metric value";
             }
             leaf add-metric {
               type uint32;
             }
             leaf subtract-metric {
               type uint32;
             }
           }
           container then-metric11 {
             leaf metric11-stat {
               type string;
               description "Metric11 statistics";
             }
             leaf then-metric11.heading {
               type string;
             }
             leaf metric1 {
               type uint32;
               description "Metric value";
             }
             leaf add-metric {
               type uint32;
             }
             leaf subtract-metric {
               type uint32;
             }
           }
           container then-metric12 {
             leaf metric12-stat {
               type string;
               description "Metric12 statistics";
             }
             leaf then-metric12.heading {
               type string;
             }
             leaf metric1 {
               type uint32;
               description "Metric value";
             }
             leaf add-metric {
               type uint32;
             }
             leaf subtract-metric {
               type uint32;
             }
           }
           container then-nexthop {
             leaf next-hop-stat {
               type string;
               description "Nexthop statistics";
             }
             leaf then-nexthop.heading {
               type string;
             }
             leaf address {
               type jt:ipaddr;
             }
             leaf reject {
               type empty;
               description "Reject a route";
             }
             leaf discard {
               type empty;
             }
             leaf self {
               type empty;
             }
             leaf no-resolution {
               type empty;
             }
             leaf nexthop-peer-address {
               type empty;
             }
             leaf next-table {
               type string;
             }
           }
           container then-preference {
             leaf preference-stat {
               type string;
               description "Preference statistics";
             }
             leaf then-preference.heading {
               type string;
             }
             leaf metric1 {
               type uint32;
               description "Metric value";
             }
             leaf add-metric {
               type uint32;
             }
             leaf subtract-metric {
               type uint32;
             }
           }
           container then-preference2 {
             leaf preference2-stat {
               type string;
               description "Preference2 statistics";
             }
             leaf then-preference2.heading {
               type string;
             }
             leaf metric1 {
               type uint32;
               description "Metric value";
             }
             leaf add-metric {
               type uint32;
             }
             leaf subtract-metric {
               type uint32;
             }
           }
           container then-preference3 {
             leaf preference3-stat {
               type string;
               description "Preference3 statistics";
             }
             leaf then-preference3.heading {
               type string;
             }
             leaf metric1 {
               type uint32;
               description "Metric value";
             }
             leaf add-metric {
               type uint32;
             }
             leaf subtract-metric {
               type uint32;
             }
           }
           container then-preference4 {
             leaf preference4-stat {
               type string;
               description "Preference4 statistics";
             }
             leaf then-preference4.heading {
               type string;
             }
             leaf metric1 {
               type uint32;
               description "Metric value";
             }
             leaf add-metric {
               type uint32;
             }
             leaf subtract-metric {
               type uint32;
             }
           }
           container then-preference5 {
             leaf preference5-stat {
               type string;
               description "Preference5 statistics";
             }
             leaf then-preference5.heading {
               type string;
             }
             leaf metric1 {
               type uint32;
               description "Metric value";
             }
             leaf add-metric {
               type uint32;
             }
             leaf subtract-metric {
               type uint32;
             }
           }
           container then-preference6 {
             leaf preference6-stat {
               type string;
               description "Preference6 statistics";
             }
             leaf then-preference6.heading {
               type string;
             }
             leaf metric1 {
               type uint32;
               description "Metric value";
             }
             leaf add-metric {
               type uint32;
             }
             leaf subtract-metric {
               type uint32;
             }
           }
           container then-preference7 {
             leaf preference7-stat {
               type string;
               description "Preference7 statistics";
             }
             leaf then-preference7.heading {
               type string;
             }
             leaf metric1 {
               type uint32;
               description "Metric value";
             }
             leaf add-metric {
               type uint32;
             }
             leaf subtract-metric {
               type uint32;
             }
           }
           container then-preference8 {
             leaf preference8-stat {
               type string;
               description "Preference8 statistics";
             }
             leaf then-preference8.heading {
               type string;
             }
             leaf metric1 {
               type uint32;
               description "Metric value";
             }
             leaf add-metric {
               type uint32;
             }
             leaf subtract-metric {
               type uint32;
             }
           }
           container then-preference9 {
             leaf preference9-stat {
               type string;
               description "Preference9 statistics";
             }
             leaf then-preference9.heading {
               type string;
             }
             leaf metric1 {
               type uint32;
               description "Metric value";
             }
             leaf add-metric {
               type uint32;
             }
             leaf subtract-metric {
               type uint32;
             }
           }
           container then-preference10 {
             leaf preference10-stat {
               type string;
               description "Preference10 statistics";
             }
             leaf then-preference10.heading {
               type string;
             }
             leaf metric1 {
               type uint32;
               description "Metric value";
             }
             leaf add-metric {
               type uint32;
             }
             leaf subtract-metric {
               type uint32;
             }
           }
           container then-preference11 {
             leaf preference11-stat {
               type string;
               description "Preference11 statistics";
             }
             leaf then-preference11.heading {
               type string;
             }
             leaf metric1 {
               type uint32;
               description "Metric value";
             }
             leaf add-metric {
               type uint32;
             }
             leaf subtract-metric {
               type uint32;
             }
           }
           container then-preference12 {
             leaf preference12-stat {
               type string;
               description "Preference12 statistics";
             }
             leaf then-preference12.heading {
               type string;
             }
             leaf metric1 {
               type uint32;
               description "Metric value";
             }
             leaf add-metric {
               type uint32;
             }
             leaf subtract-metric {
               type uint32;
             }
           }
           container prefix-attribute-flags {
             leaf prefix-attribute-flags-stat {
               type string;
               description "Prefix attribute flag statistics";
             }
             leaf prefix-attribute-flags.heading {
               type string;
             }
             leaf node-segment-flag {
               type empty;
               description "Node segment flag";
             }
             leaf external-prefix-flag {
               type empty;
               description "External prefix flag";
             }
             leaf entropy-label-capability-flag {
               type empty;
               description "Entropy label capability flag";
             }
             leaf anycast-flag {
               type empty;
               description "Anycast flag";
             }
           }
           container request-ack {
             leaf request-ack-stat {
               type string;
               description "Request acknowledgements statistics";
             }
             leaf request-ack.heading {
               type string;
               description "Request acknowledgements";
             }
             leaf route-ack {
               type empty;
               description "Route acknowledgements";
             }
             leaf nexthop-ack {
               type empty;
               description "Nexthop acknowledgements";
             }
           }
           container srv6 {
             leaf srv6-stat {
               type string;
               description "SRv6 SID";
             }
             leaf srv6.heading {
               type string;
             }
             leaf sid {
               type string;
             }
             leaf locator {
               type string;
               description "SRv6 locator";
             }
             leaf micro-dt4-sid {
               type empty;
             }
             leaf micro-dt6-sid {
               type empty;
             }
             leaf micro-dt46-sid {
               type empty;
             }
           }
           container then-tag {
             leaf tag-stat {
               type string;
               description "Policy tag statistics";
             }
             leaf then-tag.heading {
               type string;
             }
             leaf metric1 {
               type uint32;
               description "Metric value";
             }
             leaf add-metric {
               type uint32;
             }
             leaf subtract-metric {
               type uint32;
             }
           }
           container then-tag2 {
             leaf tag2-stat {
               type string;
               description "Policy tag2 statistics";
             }
             leaf then-tag2.heading {
               type string;
             }
             leaf metric1 {
               type uint32;
               description "Metric value";
             }
             leaf add-metric {
               type uint32;
             }
             leaf subtract-metric {
               type uint32;
             }
           }
           container then-tag3 {
             leaf tag3-stat {
               type string;
               description "Policy tag3 statistics";
             }
             leaf then-tag3.heading {
               type string;
             }
             leaf metric1 {
               type uint32;
               description "Metric value";
             }
             leaf add-metric {
               type uint32;
             }
             leaf subtract-metric {
               type uint32;
             }
           }
           container then-tag4 {
             leaf tag4-stat {
               type string;
               description "Policy tag4 statistics";
             }
             leaf then-tag4.heading {
               type string;
             }
             leaf metric1 {
               type uint32;
               description "Metric value";
             }
             leaf add-metric {
               type uint32;
             }
             leaf subtract-metric {
               type uint32;
             }
           }
           container metric-expression {
             leaf metric-stat {
               type string;
               description "Metric statistics";
             }
             leaf metric-expression.heading {
               type string;
             }
             leaf expression-metric1-multiplier {
               type string;
             }
             leaf expression-metric1-offset {
               type int32;
             }
             leaf expression-metric2-multiplier {
               type string;
             }
             leaf expression-metric2-offset {
               type int32;
             }
           }
         }
       }
       leaf policy-flags {
         type string;
         description "Policy flags";
       }
     }
     container policy-label {
       leaf-list label-value {
         type uint32;
         description "Label value";
       }
       leaf label-range {
         type int32;
         description "Label range for l2vpn";
       }
     }
     container policy-extended-information {
       leaf account {
         type empty;
         description "Account";
       }
       leaf accept {
         type empty;
         description "Accept a route";
       }
       leaf advertise-locator {
         type empty;
         description "Advertise SRv6 locator";
       }
       leaf advertise-locator-internal {
         type empty;
         description "Advertise SRv6 locator internal";
       }
       leaf aggregate-bandwidth {
         type int32;
         description "Aggregate bandwidth";
       }
       leaf auto-link-bandwidth {
         type empty;
         description "Auto link bandwidth";
       }
       leaf analyze {
         type empty;
         description "Send to registered controllers for analysis";
       }
       leaf as-path-prepend {
         type uint32;
         description "Prepend AS numbers to an AS path (BGP only)";
       }
       leaf-list class {
         type string;
         description "An instance of BGP output queue statistics";
       }
       leaf cos-next-hop-map {
         type string;
         description "The CoS-based next-hop map in forwarding table";
       }
       leaf damping {
         type string;
         description "Define BGP route flap damping parameters";
       }
       leaf default-action {
         type string;
         description "The default policy action";
       }
       leaf destination-class {
         type string;
         description "The destination class in forwarding table";
       }
       leaf dynamic-tunnel-attributes {
         type string;
         description "The dynamic tunnel attributes used for forwarding";
       }
       leaf fib-install-priority {
         type string;
         description "FIB install priority";
       }
       leaf filter {
         type string;
         description "Next-hop firewall filter";
       }
       leaf get-route-range {
         type empty;
         description "Get route range";
       }
       leaf ignore-service-label {
         type string;
         description "Ignore service labels";
       }
       leaf install-to-fib {
         type string;
         description "Install to FIB";
       }
       leaf ipv4-source-router-id {
         type empty;
       }
       leaf ipv4-source-router-id-address {
         type string;
         description "IPV4 source router id address";
       }
       leaf ipv6-source-router-id {
         type empty;
       }
       leaf ipv6-source-router-id-address {
         type string;
         description "IPV6 source router id address";
       }
       leaf label-allocation {
         type string;
         description "Label allocation mode";
       }
       leaf label-allocation-fallback-reject {
         type string;
         description "Suppress prefix export when label allocation fails";
       }
       leaf limit-bandwidth {
         type uint64;
         description "Limit advertised aggregate outbound link bandwidth";
       }
       leaf load-balance {
         type string;
         description "Load-balancing algorithm chosen";
       }
       leaf mhop-bfd-port {
         type uint32;
         description "Use port number 4784 for MPLS-BFD as per RFC5884";
       }
       leaf multipath-resolve {
         type string;
         description "Use all paths for resolution over this prefix";
       }
       leaf next {
         type string;
         description "Skip to next policy or term";
       }
       leaf no-backup {
         type empty;
         description "This prefix should not have backup";
       }
       leaf no-entropy-label-capability {
         type empty;
         description "Don't advertise entropy label capability";
       }
       leaf no-route-localize {
         type empty;
         description "No route localize";
       }
       leaf origin {
         type string;
         description "BGP origin attribute";
       }
       leaf p2mp-lsp-root {
         type jt:ipaddr;
         description "P2mp lsp root address";
       }
       leaf policy-priority {
         type string;
       }
       leaf reject {
         type empty;
         description "Reject a route";
       }
       leaf request-long-lived-ack {
         type empty;
         description "Advertise route after forwarding is programmed";
       }
       leaf resolution-map {
         type string;
         description "Resolution map";
       }
       leaf resolution-map-mode {
         type string;
         description "Resolution map modes";
       }
       leaf selected-mldp-egress {
         type string;
         description "This node should act as egress node for MLDP inband signalling";
       }
       leaf send-withdrawal-on-route-change {
         type empty;
         description "Withdrawn route as change is not ack'd from forwarding";
       }
       leaf set-down-bit {
         type empty;
         description "Set down bit";
       }
       leaf slice {
         type string;
         description "Slice name";
       }
       leaf source-class {
         type string;
         description "The source class in forwarding table";
       }
       leaf sr-te-template {
         type string;
         description "SR TE template to apply";
       }
       leaf ssm-source {
         type jt:ipaddr;
         description "List of Sources for SSM mapping";
       }
       leaf trace {
         type empty;
         description "Log matches to a trace file";
       }
       leaf tunnel-end-point-address {
         type string;
         description "Set tunnel end-point address of tunnel";
       }
       leaf validation-state {
         type string;
         description "Validation-state of a route";
       }
       container install-nexthop {
         container except {
           leaf lsp {
             type string;
             description "Label switched path name";
           }
           leaf lsp-regex {
             type string;
             description "Label switched path name regular expression";
           }
           leaf non-labelled-nexthop {
             type empty;
           }
           leaf non-lsp-nexthop {
             type empty;
           }
           leaf static-lsp {
             type string;
           }
           leaf static-lsp-regex {
             type string;
           }
           leaf overlay-vxlan-interfaces {
             type empty;
           }
         }
         container fallback {
           leaf lsp {
             type string;
             description "Label switched path name";
           }
           leaf lsp-regex {
             type string;
             description "Label switched path name regular expression";
           }
           leaf non-labelled-nexthop {
             type empty;
           }
           leaf non-lsp-nexthop {
             type empty;
           }
           leaf static-lsp {
             type string;
           }
           leaf static-lsp-regex {
             type string;
           }
           leaf overlay-vxlan-interfaces {
             type empty;
           }
         }
       }
       container map-to-interface {
         list interface {
           leaf interface-name {
             type string;
             description "Name of interface";
           }
           leaf interface-flags {
             type int32;
           }
         }
       }
       container then-metric {
       }
       container prefix-segment {
         leaf redistribute {
           type empty;
         }
         container algorithm {
           leaf prefix-segment-index-value {
             type uint32;
           }
           leaf algorithm-name {
             type uint32;
           }
           leaf node-segment {
             type empty;
           }
           leaf redistribute {
             type empty;
           }
         }
       }
       list tunnel-attribute {
         leaf tunnel-type {
           type string;
           description "Tunnel type";
         }
         leaf reference-count {
           type int32;
           description "Reference count";
         }
         leaf tunnel-data {
           type string;
           description "Tunnel Data";
         }
       }
       container source-based-forwarding {
         container sbf-attributes {
           leaf sbf-next-table {
             type string;
           }
         }
       }
       container policy-label {
       }
     }
     leaf evpn-default-vs-rt-detail {
       type string;
       description "EVPN Deafult virtual switch route detail";
     }
   }
 }
