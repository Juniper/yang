/*
 * Copyright (c) 2025 Juniper Networks, Inc.
 * All rights reserved.
 */
 module junos-ex-rpc-virtual-chassis {
   namespace "http://yang.juniper.net/junos-ex/rpc/virtual-chassis";

   prefix virtual-chassis;

   import junos-common-ddl-extensions {
     prefix junos;
     revision-date 2024-01-01;
   }

   import junos-common-types {
     prefix jt;
     revision-date 2024-01-01;
   }

   organization "Juniper Networks, Inc.";

   contact "yang-support@juniper.net";

   description "Junos RPC YANG module for virtual-chassis command(s)";

   revision 2024-01-01 {
     description "Junos: 24.4R2.25";
   }

   rpc get-virtual-chassis-information {
     description "Show virtual chassis information";
     junos:command "show virtual-chassis";
     output {
       container virtual-chassis-information {
         uses virtual-chassis-information-block;
       }
     }
   }
   rpc get-virtual-chassis-status-information {
     description "Virtual chassis information";
     junos:command "show virtual-chassis status";
     input {
       leaf fabric {
         description "Internal fabric state";
         type empty;
       }
       leaf verbosity_level {
         junos:cli-feature "nokeyword";
         default "brief";
         type enumeration {
           enum "brief" {
             description "Display brief output (default)";
           }
           enum "detail" {
             description "Display detailed output";
           }
         }
       }
     }
     output {
       container virtual-chassis-information {
         uses virtual-chassis-information-block;
       }
     }
   }
   rpc get-virtual-chassis-device-topology {
     description "PFE device topology";
     junos:command "show virtual-chassis device-topology";
     input {
       uses command-forwarding;
     }
     output {
       container virtual-chassis-device-information {
         uses virtual-chassis-device-information-block;
       }
     }
   }
   rpc get-virtual-chassis-packet-path {
     description "Show virtual-chassis packet path";
     junos:command "show virtual-chassis vc-path";
     input {
       leaf source-interface {
         description "Source interface name";
         type string;
         mandatory true;
       }
       leaf destination-interface {
         description "Destination interface name";
         type string;
         mandatory true;
       }
     }
     output {
       container virtual-chassis-packet-path {
         uses virtual-chassis-packet-path-block;
       }
     }
   }
   rpc get-virtual-chassis-active-topology {
     description "Virtual chassis active topology";
     junos:command "show virtual-chassis active-topology";
     input {
       uses command-forwarding;
       leaf fabric {
         description "Internal fabric state";
         type empty;
       }
     }
     output {
       container virtual-chassis-active-topology {
         uses virtual-chassis-active-topology-block;
       }
     }
   }
   rpc get-virtual-chassis-port-information {
     description "Virtual chassis port information";
     junos:command "show virtual-chassis vc-port";
     input {
       uses command-forwarding;
     }
     output {
       container virtual-chassis-port-information {
         uses virtual-chassis-port-information-block;
       }
     }
   }
   rpc get-virtual-chassis-port-lag-hash-information {
     description "VC ports lag hashing information";
     junos:command "show virtual-chassis vc-port lag-hash";
     input {
       uses command-forwarding;
     }
     output {
       container virtual-chassis-port-lag-hash-information {
         uses virtual-chassis-port-lag-hash-information-block;
       }
     }
   }
   rpc get-virtual-chassis-port-statistics {
     description "Show virtual chassis port statistics";
     junos:command "show virtual-chassis vc-port statistics";
     input {
       uses command-forwarding;
       leaf verbosity_level {
         junos:cli-feature "nokeyword";
         default "brief";
         type enumeration {
           enum "brief" {
             description "Display brief output (default)";
           }
           enum "detail" {
             description "Display detailed output";
           }
           enum "extensive" {
             description "Display extensive output";
           }
         }
       }
       leaf interface-name {
         description "Name of virtual chassis port";
         junos:cli-feature "nokeyword";
         type string;
       }
     }
   }
   rpc get-virtual-chassis-optics-diagnostics {
     description "Show virtual chassis port diagnostics optics";
     junos:command "show virtual-chassis vc-port diagnostics optics";
     input {
       uses command-forwarding;
       leaf interface-name {
         description "Name of virtual chassis port";
         junos:cli-feature "nokeyword";
         type string;
       }
     }
     output {
       container virtual-chassis-port-optics-diagnostics-information {
         uses virtual-chassis-port-optics-diagnostics-information-block;
       }
     }
   }
   rpc get-virtual-chassis-adjacency-information {
     description "Show virtual chassis adjacency database";
     junos:command "show virtual-chassis protocol adjacency";
     input {
       uses command-forwarding;
       leaf fabric {
         description "Internal fabric state";
         type empty;
       }
       leaf verbosity_level {
         junos:cli-feature "nokeyword";
         default "brief";
         type enumeration {
           enum "brief" {
             description "Display brief output (default)";
           }
           enum "detail" {
             description "Display detailed output";
           }
           enum "extensive" {
             description "Display extensive output";
           }
         }
       }
       leaf system-id {
         description "System ID of neighbor";
         junos:cli-feature "nokeyword";
         type string;
       }
     }
     output {
       container virtual-chassis-adjacency-information {
         uses virtual-chassis-adjacency-information-block;
       }
     }
   }
   rpc get-virtual-chassis-database-information {
     description "Show virtual chassis link-state database";
     junos:command "show virtual-chassis protocol database";
     input {
       uses command-forwarding;
       leaf fabric {
         description "Internal fabric state";
         type empty;
       }
       leaf verbosity_level {
         junos:cli-feature "nokeyword";
         default "brief";
         type enumeration {
           enum "brief" {
             description "Display brief output (default)";
           }
           enum "detail" {
             description "Display detailed output";
           }
           enum "extensive" {
             description "Display extensive output";
           }
         }
       }
       leaf system-id {
         description "System ID of neighbor";
         junos:cli-feature "nokeyword";
         type string;
       }
     }
     output {
       container virtual-chassis-database-information {
         uses virtual-chassis-database-information-block;
       }
     }
   }
   rpc get-virtual-chassis-interface-information {
     description "Show virtual chassis protocol interface information";
     junos:command "show virtual-chassis protocol interface";
     input {
       uses command-forwarding;
       leaf fabric {
         description "Internal fabric state";
         type empty;
       }
       leaf verbosity_level {
         junos:cli-feature "nokeyword";
         default "brief";
         type enumeration {
           enum "brief" {
             description "Display brief output (default)";
           }
           enum "detail" {
             description "Display detailed output";
           }
         }
       }
       leaf interface-name {
         description "Name of interface";
         junos:cli-feature "nokeyword";
         type string;
       }
     }
     output {
       container virtual-chassis-interface-information {
         uses virtual-chassis-interface-information-block;
       }
     }
   }
   rpc get-virtual-chassis-route-information {
     description "Show virtual chassis routing table";
     junos:command "show virtual-chassis protocol route";
     input {
       uses command-forwarding;
       leaf destination {
         description "System ID of destination";
         junos:cli-feature "nokeyword";
         type string;
       }
     }
     output {
       container virtual-chassis-route-information {
         uses virtual-chassis-route-information-block;
       }
     }
   }
   rpc get-virtual-chassis-statistics-information {
     description "Show virtual chassis performance statistics";
     junos:command "show virtual-chassis protocol statistics";
     input {
       uses command-forwarding;
       leaf fabric {
         description "Internal fabric state";
         type empty;
       }
       leaf interface-name {
         description "Name of logical interface";
         junos:cli-feature "nokeyword";
         type string;
       }
     }
     output {
       container virtual-chassis-statistics-information {
         uses virtual-chassis-statistics-information-block;
       }
     }
   }
   rpc get-virtual-chassis-fast-failover {
     description "Fast failover status";
     junos:command "show virtual-chassis fast-failover";
     output {
       container virtual-chassis-fast-failover {
         uses virtual-chassis-fast-failover-block;
       }
     }
   }
   rpc get-virtual-chassis-mode-information {
     description "Virtual chassis mode information";
     junos:command "show virtual-chassis mode";
     input {
       uses command-forwarding;
     }
     output {
       container virtual-chassis-mode-information {
         uses virtual-chassis-mode-information-block;
       }
     }
   }
   grouping command-forwarding {
     leaf no-forwarding {
       description "No forwarding";
       type empty;
     }
     choice chassis-selector {
       case case_1 {
         leaf all-chassis {
           description "All chassis";
           type empty;
         }
       }
       case case_2 {
         leaf all-lcc {
           description "All LCC chassis";
           type empty;
         }
       }
       case case_3 {
         leaf scc {
           description "SCC";
           type empty;
         }
       }
       case case_4 {
         leaf sfc {
           description "SFC";
           type union {
             type string {
               pattern "<.*>|$.*";
             }
             type uint32;
           }
         }
       }
       case case_5 {
         leaf lcc {
           description "Specific LCC";
           type union {
             type string {
               pattern "<.*>|$.*";
             }
             type uint32;
           }
         }
       }
       case case_6 {
         leaf node {
           description "Specific node";
           type string;
         }
       }
       case case_7 {
         leaf bsys {
           description "Base system";
           type empty;
         }
       }
       case case_8 {
         leaf gnf {
           description "Specific guest network function";
           type union {
             type string {
               pattern "<.*>|$.*";
             }
             type uint32 {
               range "1 .. 10";
             }
           }
         }
       }
       case case_9 {
         leaf all-gnfs {
           description "All guest network functions";
           type empty;
         }
       }
       case case_10 {
         leaf all-system {
           description "All system (BSYS and GNFs)";
           type empty;
         }
       }
       case case_11 {
         leaf server {
           description "Specific server slot";
           type union {
             type string {
               pattern "<.*>|$.*";
             }
             type uint32 {
               range "0 .. 1";
             }
           }
         }
       }
       case case_12 {
         leaf all-servers {
           description "All servers";
           type empty;
         }
       }
       case case_13 {
         leaf vnf {
           description "Specific virtual-network-function";
           type string;
         }
       }
       case case_14 {
         leaf all-vnfs {
           description "All virtual-network-functions";
           type empty;
         }
       }
     }
     choice re-selector {
       case case_1 {
         leaf re0 {
           description "RE0";
           type empty;
         }
       }
       case case_2 {
         leaf re1 {
           description "RE1";
           type empty;
         }
       }
       case case_3 {
         leaf routing-engine {
           description "Specific routing engine";
           type enumeration {
             enum "local" {
               description "Local routing engine";
             }
             enum "other" {
               description "Other routing engine";
             }
             enum "master" {
               description "Master routing engine";
             }
             enum "backup" {
               description "Backup routing engine";
             }
             enum "both" {
               description "Both routing engines";
             }
           }
         }
       }
     }
     choice lr-selector {
       case case_1 {
         leaf logical-system {
           description "Name of logical system, or 'all'";
           type string;
         }
       }
     }
     choice tenant-selector {
       case case_1 {
         leaf tenant {
           description "Name of tenant, or 'all'";
           type string;
         }
       }
     }
     choice vc-selector {
       case case_1 {
         leaf local {
           description "Local virtual chassis member";
           type empty;
         }
       }
       case case_2 {
         leaf all-members {
           description "All virtual chassis members";
           type empty;
         }
       }
       case case_3 {
         leaf member {
           description "Specific virtual chassis member which is master";
           type union {
             type string {
               pattern "<.*>|$.*";
             }
             type uint32;
           }
         }
       }
     }
   }
   grouping virtual-chassis-information-block {
     leaf virtual-chassis-id {
       type string;
       description "Virtual Chassis identifier";
     }
     container preprovisioned-virtual-chassis-information {
       leaf virtual-chassis-id {
         type string;
         description "Virtual Chassis identifier";
       }
       leaf virtual-chassis-mode {
         type string;
         description "Virtual Chassis Mode";
       }
     }
     container virtual-chassis-id-information {
       leaf virtual-chassis-id {
         type string;
         description "Virtual Chassis identifier";
       }
       leaf virtual-chassis-mode {
         type string;
         description "Virtual Chassis Mode";
       }
     }
     list member-list {
       container member {
         leaf member-id {
           type int32;
           description "Member identifier";
         }
         leaf fpc-slot {
           type int32;
           description "FPC Slot Number";
         }
         leaf member-status {
           type string;
           description "Member's status";
         }
         leaf member-model {
           type string;
           description "Member's model";
         }
         leaf member-priority {
           type int32;
           description "Member's mastership priority";
         }
         leaf member-role {
           type string;
           description "Member's role";
         }
         leaf member-serial-number {
           type string;
           description "Member's serial number";
         }
         list neighbor-list {
           container neighbor {
             leaf neighbor-id {
               type int32;
               description "Neighbor identifier";
             }
             leaf neighbor-interface {
               type string;
               description "Neighbor interface";
             }
           }
         }
         leaf member-alias-name {
           type string;
           description "Member's alias name";
         }
         leaf member-mixed-mode {
           type string;
           description "Member's mixed mode value";
         }
         leaf member-route-mode {
           type string;
           description "Member's route mode value";
         }
         leaf fpc-slot-range {
           type string;
           description "FPC Slot Range";
         }
         leaf member-location {
           type string;
           description "Member's location";
         }
       }
     }
     container next-member-information {
       leaf next-member-id {
         type int32;
         description "Next member ID";
       }
       leaf next-fpc-slot {
         type int32;
         description "Next FPC Slot";
       }
     }
   }
   grouping virtual-chassis-device-information-block {
     list device-list {
       list device {
         leaf member-id {
           type int32;
           description "Member identifier";
         }
         leaf device-id {
           type uint32;
         }
         leaf device-status {
           type string;
         }
         leaf system-id {
           type string;
         }
         list neighbor-list {
           container neighbor {
             leaf neighbor-id {
               type int32;
               description "Neighbor identifier";
             }
             leaf neighbor-device-id {
               type int32;
             }
             leaf neighbor-interface {
               type string;
               description "Neighbor interface";
             }
           }
         }
       }
     }
   }
   grouping virtual-chassis-packet-path-block {
     container packet-path-information {
       leaf source-interface {
         type string;
       }
       leaf destination-interface {
         type string;
       }
     }
     list device {
       leaf hop {
         type int32;
       }
       leaf member-id {
         type int32;
         description "Member identifier";
       }
       leaf device-id {
         type uint32;
       }
       leaf interface-name {
         type string;
       }
       list neighbor-list {
       }
     }
   }
   grouping virtual-chassis-active-topology-block {
     container destination-reachability {
       leaf destination-member {
         type int32;
       }
       leaf nexthop-list {
         type string;
       }
     }
   }
   grouping virtual-chassis-port-information-block {
     list port-list {
       container port-information {
         leaf port-name {
           type string;
         }
         leaf port-type {
           type string;
         }
         leaf port-trunk-id {
           type int32;
         }
         leaf port-status {
           type string;
         }
         leaf port-speed {
           type uint64;
         }
         leaf neighbor-id {
           type int32;
           description "Neighbor identifier";
         }
         leaf neighbor-interface {
           type string;
           description "Neighbor interface";
         }
       }
     }
   }
   grouping virtual-chassis-port-lag-hash-information-block {
     leaf virtual-chassis-port-lag-hash {
       type string;
       description "Virtual Chassis Ports lag hash Mode";
     }
   }
   grouping virtual-chassis-port-optics-diagnostics-information-block {
     list optics-diagnostics-port-list {
       container port-optics-diagnostics {
         leaf port-name {
           type string;
         }
         container optics-diagnostics {
           leaf optic-diagnostics-not-available {
             type string;
             description "Optical diagnostics not supported by this transceiver";
           }
           leaf laser-bias-current-not-available {
             type string;
             description "Laser bias current measurement not available";
           }
           leaf soa-bias-current-not-available {
             type string;
             description "SOA bias current measurement not available";
           }
           leaf laser-tx-power-not-available {
             type string;
             description "Laser output power measurement not available";
           }
           leaf module-temperature-not-available {
             type string;
             description "Module temperature measurement not available";
           }
           leaf laser-rx-power-not-available {
             type string;
             description "Laser receiver optical power measurement not available";
           }
           leaf laser-bias-current {
             type string;
             description "Laser bias current (milliamperes)";
           }
           leaf soa-bias-current {
             type string;
             description "SOA bias current (milliamperes)";
           }
           leaf laser-output-power {
             type string;
             description "Laser output power (milliwatts)";
           }
           leaf laser-output-power-dbm {
             type string;
             description "Laser output power (dBm)";
           }
           leaf module-temperature {
             type string;
             description "Module temperature";
           }
           leaf module-voltage {
             type string;
             description "Module voltage";
           }
           leaf rx-signal-avg-optical-power {
             type string;
             description "Receiver signal average power (milliwatts)";
           }
           leaf rx-signal-avg-optical-power-dbm {
             type string;
             description "Receiver signal average power (dBm)";
           }
           leaf laser-rx-optical-power {
             type string;
             description "Laser receiver optical power (milliwatts)";
           }
           leaf laser-rx-optical-power-dbm {
             type string;
             description "Laser receiver optical power (dBm)";
           }
           leaf laser-bias-current-high-alarm {
             type string;
             description "Laser bias current high alarm";
           }
           leaf laser-bias-current-low-alarm {
             type string;
             description "Laser bias current low alarm";
           }
           leaf laser-bias-current-high-warn {
             type string;
             description "Laser bias current high warning";
           }
           leaf laser-bias-current-low-warn {
             type string;
             description "Laser bias current low warning";
           }
           leaf soa-bias-current-high-alarm {
             type string;
             description "SOA bias current high alarm";
           }
           leaf soa-bias-current-low-alarm {
             type string;
             description "SOA bias current low alarm";
           }
           leaf soa-bias-current-high-warn {
             type string;
             description "SOA bias current high warning";
           }
           leaf soa-bias-current-low-warn {
             type string;
             description "SOA bias current low warning";
           }
           leaf laser-tx-power-high-alarm {
             type string;
             description "Laser output power high alarm";
           }
           leaf laser-tx-power-low-alarm {
             type string;
             description "Laser output power low alarm";
           }
           leaf laser-tx-power-high-warn {
             type string;
             description "Laser output power high warning";
           }
           leaf laser-tx-power-low-warn {
             type string;
             description "Laser output power low warning";
           }
           leaf module-temperature-high-alarm {
             type string;
             description "Module temperature high alarm";
           }
           leaf module-temperature-low-alarm {
             type string;
             description "Module temperature low alarm";
           }
           leaf module-temperature-high-warn {
             type string;
             description "Module temperature high warning";
           }
           leaf module-temperature-low-warn {
             type string;
             description "Module temperature low warning";
           }
           leaf module-voltage-high-alarm {
             type string;
             description "Module voltage high alarm";
           }
           leaf module-voltage-low-alarm {
             type string;
             description "Module voltage low alarm";
           }
           leaf module-voltage-high-warn {
             type string;
             description "Module voltage high warning";
           }
           leaf module-voltage-low-warn {
             type string;
             description "Module voltage low warning";
           }
           leaf laser-rx-power-high-alarm {
             type string;
             description "Laser receiver power high alarm";
           }
           leaf laser-rx-power-low-alarm {
             type string;
             description "Laser receiver power low alarm";
           }
           leaf laser-rx-power-high-warn {
             type string;
             description "Laser receiver power high warning";
           }
           leaf laser-rx-power-low-warn {
             type string;
             description "Laser receiver power low warning";
           }
           leaf laser-end-of-life-alarm {
             type string;
             description "Laser end-of-life alarm";
           }
           leaf laser-wavelength-alarm {
             type string;
             description "Laser wavelength alarm";
           }
           leaf laser-bias-current-alarm {
             type string;
             description "Laser bias current alarm";
           }
           leaf module-temperature-alarm {
             type string;
             description "Module temperature alarm";
           }
           leaf laser-power-alarm {
             type string;
             description "Laser power alarm";
           }
           leaf modulator-temperature-alarm {
             type string;
             description "Modulator temperature alarm";
           }
           leaf modulator-bias-alarm {
             type string;
             description "Modulator bias alarm";
           }
           leaf module-not-ready-alarm {
             type string;
             description "Module not ready alarm";
           }
           leaf module-power-down-alarm {
             type string;
             description "Module power down alarm";
           }
           leaf module-not-init-done-alarm {
             type string;
             description "Module initialization not done alarm";
           }
           leaf module-not-high-power-on-alarm {
             type string;
             description "Module not high powered on alarm";
           }
           leaf module-fault-alarm {
             type string;
             description "Module in fault state alarm";
           }
           leaf pld-flash-init-fault-alarm {
             type string;
             description "PLD or Flash initialization fault alarm";
           }
           leaf power-supply-fault-alarm {
             type string;
             description "Power supply fault alarm";
           }
           leaf checksum-fault-alarm {
             type string;
             description "Checksum fault alarm";
           }
           leaf apd-supply-fault-alarm {
             type string;
             description "APD supply fault alarm";
           }
           leaf tec-fault-alarm {
             type string;
             description "TEC fault alarm";
           }
           leaf wavelength-unlocked-alarm {
             type string;
             description "Wavelength unlocked alarm";
           }
           leaf tx-mux-fifo-error-alarm {
             type string;
             description "Tx multiplexer fifo error alarm";
           }
           leaf tx-loss-of-pll-alarm {
             type string;
             description "Tx loss of PLL alarm";
           }
           leaf tx-data-not-ready-alarm {
             type string;
             description "Tx data not ready alarm";
           }
           leaf tx-not-ready-alarm {
             type string;
             description "Tx not ready alarm";
           }
           leaf tx-laser-fault-alarm {
             type string;
             description "Tx laser fault alarm";
           }
           leaf tx-laser-disabled-alarm {
             type string;
             description "Tx laser disabled alarm";
           }
           leaf tx-loss-of-signal-functionality-alarm {
             type string;
             description "Tx loss of signal functionality alarm";
           }
           leaf tx-cdr-loss-of-lock-alarm {
             type string;
             description "Tx CDR loss of lock alarm";
           }
           leaf rx-loss-avg-opt-power-alarm {
             type string;
             description "Receiver loss of average optical power alarm";
           }
           leaf rx-loss-ac-power-alarm {
             type string;
             description "Receiver loss of AC power alarm";
           }
           leaf rx-loss-of-pll-alarm {
             type string;
             description "Receiver loss of PLL alarm";
           }
           leaf rx-not-ready-alarm {
             type string;
             description "Receiver not ready alarm";
           }
           leaf rx-loss-of-signal-alarm {
             type string;
             description "Receiver loss of signal alarm";
           }
           leaf rx-cdr-loss-of-lock-alarm {
             type string;
             description "Receiver CDR loss of lock alarm";
           }
           leaf laser-bias-current-high-alarm-threshold {
             type string;
             description "Laser bias current high alarm threshold (milliamperes)";
           }
           leaf laser-bias-current-low-alarm-threshold {
             type string;
             description "Laser bias current low alarm threshold (milliamperes)";
           }
           leaf laser-bias-current-high-warn-threshold {
             type string;
             description "Laser bias current high warning threshold (milliamperes)";
           }
           leaf laser-bias-current-low-warn-threshold {
             type string;
             description "Laser bias current low warning threshold (milliamperes)";
           }
           leaf soa-bias-current-high-alarm-threshold {
             type string;
             description "SOA bias current high alarm threshold (milliamperes)";
           }
           leaf soa-bias-current-low-alarm-threshold {
             type string;
             description "SOA bias current low alarm threshold (milliamperes)";
           }
           leaf soa-bias-current-high-warn-threshold {
             type string;
             description "SOA bias current high warning threshold (milliamperes)";
           }
           leaf soa-bias-current-low-warn-threshold {
             type string;
             description "SOA bias current low warning threshold (milliamperes)";
           }
           leaf laser-tx-power-high-alarm-threshold {
             type string;
             description "Laser transmitter power high alarm threshold (milliwatts)";
           }
           leaf laser-tx-power-high-alarm-threshold-dbm {
             type string;
             description "Laser transmitter power high alarm threshold (dBm)";
           }
           leaf laser-tx-power-low-alarm-threshold {
             type string;
             description "Laser transmitter power low alarm threshold (milliwatts)";
           }
           leaf laser-tx-power-low-alarm-threshold-dbm {
             type string;
             description "Laser transmitter power low alarm threshold (dBm)";
           }
           leaf laser-tx-power-high-warn-threshold {
             type string;
             description "Laser transmitter power high warning threshold (milliwatts)";
           }
           leaf laser-tx-power-high-warn-threshold-dbm {
             type string;
             description "Laser transmitter power high warning threshold (dBm)";
           }
           leaf laser-tx-power-low-warn-threshold {
             type string;
             description "Laser transmitter power low warning threshold (milliwatts)";
           }
           leaf laser-tx-power-low-warn-threshold-dbm {
             type string;
             description "Laser transmitter power low warning threshold (dBm)";
           }
           leaf module-temperature-high-alarm-threshold {
             type string;
             description "Module temperature high alarm threshold";
           }
           leaf module-temperature-low-alarm-threshold {
             type string;
             description "Module temperature low alarm threshold";
           }
           leaf module-temperature-high-warn-threshold {
             type string;
             description "Module temperature high warning threshold";
           }
           leaf module-temperature-low-warn-threshold {
             type string;
             description "Module temperature low warning threshold";
           }
           leaf laser-temperature-high-alarm-threshold {
             type string;
             description "Laser temperature high alarm threshold";
           }
           leaf laser-temperature-low-alarm-threshold {
             type string;
             description "Laser temperature low alarm threshold";
           }
           leaf laser-temperature-high-warn-threshold {
             type string;
             description "Laser temperature high warning threshold";
           }
           leaf laser-temperature-low-warn-threshold {
             type string;
             description "Laser temperature low warning threshold";
           }
           leaf module-voltage-high-alarm-threshold {
             type string;
             description "Module voltage high alarm threshold (volts)";
           }
           leaf module-voltage-low-alarm-threshold {
             type string;
             description "Module voltage low alarm threshold (volts)";
           }
           leaf module-voltage-high-warn-threshold {
             type string;
             description "Module voltage high warning threshold (volts)";
           }
           leaf module-voltage-low-warn-threshold {
             type string;
             description "Module voltage low warning threshold (volts)";
           }
           leaf laser-rx-power-high-alarm-threshold {
             type string;
             description "Laser receiver power high alarm (milliwatts)";
           }
           leaf laser-rx-power-high-alarm-threshold-dbm {
             type string;
             description "Laser receiver power high alarm (dBm)";
           }
           leaf laser-rx-power-low-alarm-threshold {
             type string;
             description "Laser receiver power low alarm (milliwatts)";
           }
           leaf laser-rx-power-low-alarm-threshold-dbm {
             type string;
             description "Laser receiver power low alarm (dBm)";
           }
           leaf laser-rx-power-high-warn-threshold {
             type string;
             description "Laser receiver power high warning (milliwatts)";
           }
           leaf laser-rx-power-high-warn-threshold-dbm {
             type string;
             description "Laser receiver power high warning (dBm)";
           }
           leaf laser-rx-power-low-warn-threshold {
             type string;
             description "Laser receiver power low warning (milliwatts)";
           }
           leaf laser-rx-power-low-warn-threshold-dbm {
             type string;
             description "Laser receiver power low warning (dBm)";
           }
           list optics-diagnostics-lane-values {
             leaf lane-index {
               type int32;
             }
             leaf laser-bias-current {
               type string;
               description "Laser bias current (milliamperes)";
             }
             leaf laser-output-power {
               type string;
               description "Laser output power (milliwatts)";
             }
             leaf laser-output-power-dbm {
               type string;
               description "Laser output power (dBm)";
             }
             leaf laser-temperature {
               type string;
               description "Laser temperature";
             }
             leaf laser-rx-optical-power {
               type string;
               description "Laser receiver optical power (milliwatts)";
             }
             leaf laser-rx-optical-power-dbm {
               type string;
               description "Laser receiver optical power (dBm)";
             }
             leaf laser-bias-current-high-alarm {
               type string;
               description "Laser bias current high alarm";
             }
             leaf laser-bias-current-low-alarm {
               type string;
               description "Laser bias current low alarm";
             }
             leaf laser-bias-current-high-warn {
               type string;
               description "Laser bias current high warning";
             }
             leaf laser-bias-current-low-warn {
               type string;
               description "Laser bias current low warning";
             }
             leaf laser-tx-power-high-alarm {
               type string;
               description "Laser output power high alarm";
             }
             leaf laser-tx-power-low-alarm {
               type string;
               description "Laser output power low alarm";
             }
             leaf laser-tx-power-high-warn {
               type string;
               description "Laser output power high warning";
             }
             leaf laser-tx-power-low-warn {
               type string;
               description "Laser output power low warning";
             }
             leaf laser-temp-high-alarm {
               type string;
               description "Laser temperature high alarm";
             }
             leaf laser-temp-low-alarm {
               type string;
               description "Laser temperature low alarm";
             }
             leaf laser-temp-high-warn {
               type string;
               description "Laser temperature high warning";
             }
             leaf laser-temp-low-warn {
               type string;
               description "Laser temperature low warning";
             }
             leaf laser-rx-power-high-alarm {
               type string;
               description "Laser receiver power high alarm";
             }
             leaf laser-rx-power-low-alarm {
               type string;
               description "Laser receiver power low alarm";
             }
             leaf laser-rx-power-high-warn {
               type string;
               description "Laser receiver power high warning";
             }
             leaf laser-rx-power-low-warn {
               type string;
               description "Laser receiver power low warning";
             }
             leaf tx-loss-of-signal-functionality-alarm {
               type string;
               description "Tx loss of signal functionality alarm";
             }
             leaf tx-cdr-loss-of-lock-alarm {
               type string;
               description "Tx CDR loss of lock alarm";
             }
             leaf rx-loss-of-signal-alarm {
               type string;
               description "Receiver loss of signal alarm";
             }
             leaf rx-cdr-loss-of-lock-alarm {
               type string;
               description "Receiver CDR loss of lock alarm";
             }
             leaf tec-fault-alarm {
               type string;
               description "TEC fault alarm";
             }
             leaf wavelength-unlocked-alarm {
               type string;
               description "Wavelength unlocked alarm";
             }
             leaf apd-supply-fault-alarm {
               type string;
               description "APD supply fault alarm";
             }
           }
         }
       }
     }
   }
   grouping virtual-chassis-adjacency-information-block {
     container vccp-adjacency {
       leaf interface-name {
         type string;
       }
       leaf system-name {
         type string;
         description "Hostname of a system";
       }
       leaf adjacency-state {
         type string;
         description "State of the adjacency";
       }
       leaf holdtime {
         type int32;
       }
       leaf adjacency-flag {
         type string;
       }
       leaf interface-priority {
         type int32;
       }
       leaf transition-count {
         type int32;
       }
       leaf last-transition-time {
         type string;
       }
       list vccp-adjacency-log {
         leaf adjacency-when {
           type string;
           description "Time at which the transition occurred";
         }
         leaf adjacency-state {
           type string;
           description "State of the adjacency";
         }
         leaf adjacency-event {
           type string;
           description "Event that triggered the transition";
         }
         leaf adjacency-down-reason {
           type string;
           description "Reason for the down transition event";
         }
       }
     }
   }
   grouping virtual-chassis-database-information-block {
     container vccp-database {
       leaf lsp-count {
         type int32;
       }
       container vccp-database-entry {
         leaf lsp-id {
           type string;
         }
         leaf sequence-number {
           type int32;
         }
         leaf checksum {
           type int32;
         }
         leaf remaining-lifetime {
           type int32;
         }
         container vccp-tlv {
           container vccp-tlv-overhead {
             leaf tlv-type {
               type int32;
             }
             leaf tlv-length {
               type int32;
             }
             leaf bytes-left {
               type int32;
             }
           }
           container reachability-tlv {
             leaf reachability-tlv.heading {
               type string;
             }
             leaf system-name {
               type string;
               description "Hostname of a system";
             }
             leaf interface-name {
               type string;
             }
             leaf metric {
               type int32;
             }
             leaf tlv-length {
               type int32;
             }
           }
           container node-info-tlv {
             leaf node-info-tlv.heading {
               type string;
             }
             leaf member-id {
               type int32;
               description "Member identifier";
             }
             leaf vc-id {
               type string;
             }
             leaf ni-flags {
               type int32;
             }
             leaf mastership-priority {
               type int32;
             }
             container device-info {
               leaf system-name {
                 type string;
                 description "Hostname of a system";
               }
               leaf device-id {
                 type uint32;
               }
             }
             container dcp-device-information {
               leaf vc-mode {
                 type string;
               }
               leaf vc-size {
                 type uint32;
               }
               leaf my-master-id {
                 type string;
               }
               leaf device-physical-id {
                 type string;
                 description "Chassis serial number and optioal slot for the device";
               }
               leaf dcp-system-id {
                 type string;
               }
               leaf dcp-device-id {
                 type uint32;
               }
               leaf device-physical-type {
                 type string;
               }
               leaf dcp-vdcf-id {
                 type uint32;
               }
               leaf dcp-device-start-ppfe-id {
                 type uint32;
               }
               leaf dcp-device-ppfe-count {
                 type uint32;
               }
               leaf logical-function-bitmap {
                 type uint32;
               }
               leaf dcp-device-flags {
                 type string;
               }
               leaf dcp-device-name {
                 type string;
               }
             }
           }
           container dynamic-hostname-tlv {
             leaf hostname {
               type string;
             }
           }
           container dcp-atomicity-tlv {
             leaf dcp-atomicity-tlv.heading {
               type string;
             }
             leaf fragment-offset {
               type uint32;
             }
             leaf fragment-count {
               type uint32;
             }
             container fragment-sequence-number-list {
               leaf fragment-id {
                 type uint32;
               }
               leaf sequence-number {
                 type int32;
               }
             }
           }
           container dcp-vdcf-information-tlv {
             leaf dcp-vdcf-information-tlv.heading {
               type string;
             }
             leaf dcp-vdcf-id {
               type uint32;
             }
             leaf dcp-vdcf-name {
               type string;
             }
             leaf vdcf-flags {
               type uint32;
             }
           }
           container dcp-dynamic-device-tlv {
             leaf dcp-dynamic-device-tlv.heading {
               type string;
             }
             leaf dynamic-device-id {
               type uint32;
             }
             leaf dynamic-device-name {
               type string;
             }
             leaf dynamic-device-type {
               type uint32;
             }
             leaf dynamic-device-physical-type {
               type uint32;
             }
             leaf dynamic-flags {
               type uint32;
             }
           }
           container dcp-device-information-tlv {
             leaf dcp-device-information-tlv.heading {
               type string;
             }
             leaf device-system-id {
               type string;
             }
             leaf device-vdcf-id {
               type uint32;
             }
             leaf dcp-device-id {
               type uint32;
             }
             leaf dcp-device-start-ppfe-id {
               type uint32;
             }
             leaf dcp-device-ppfe-count {
               type uint32;
             }
             leaf device-name {
               type string;
             }
             leaf device-flags {
               type uint32;
             }
             leaf device-physical-id {
               type string;
               description "Chassis serial number and optioal slot for the device";
             }
           }
           container dcp-ine-information-tlv {
             leaf dcp-ine-information-tlv.heading {
               type string;
             }
             leaf vdcf-id {
               type uint32;
             }
             leaf ine-id {
               type uint32;
             }
             leaf ine-name {
               type string;
             }
             leaf logical-function-bitmap {
               type uint32;
             }
             leaf ine-flags {
               type uint32;
             }
           }
           container dcp-ine-membership-information-tlv {
             leaf dcp-ine-membership-information-tlv.heading {
               type string;
             }
             leaf ine-system-id {
               type string;
             }
             leaf ine-id {
               type uint32;
             }
             leaf ine-slot {
               type uint32;
             }
             leaf ine-member-flags {
               type uint32;
             }
           }
           container dcp-product-category-tlv {
             leaf dcp-product-category-tlv.heading {
               type string;
             }
             leaf product-category {
               type string;
             }
           }
           container dcp-node-ic-connectivity-map-tlv {
             leaf dcp-node-ic-connectivity-map-tlv.heading {
               type string;
             }
             leaf chip-id {
               type uint32;
             }
             leaf node-ic-connectivity-map {
               type string;
             }
           }
           container master-info-tlv {
             leaf master-info-tlv.heading {
               type string;
             }
             leaf system-name {
               type string;
               description "Hostname of a system";
             }
           }
           container backup-info-tlv {
             leaf backup-info-tlv.heading {
               type string;
             }
             leaf system-name {
               type string;
               description "Hostname of a system";
             }
           }
           container stable-state-tlv {
             leaf stable-state-tlv.heading {
               type string;
             }
             leaf stable-master {
               type string;
             }
             leaf stable-backup {
               type string;
             }
           }
           container route-tlv {
             leaf route-tlv.heading {
               type string;
             }
             leaf unicast {
               type string;
             }
             leaf multicast {
               type string;
             }
             leaf vcf-route-mode {
               type int32;
             }
             leaf vcf-provision-mode {
               type int32;
             }
             leaf vcf-route-preference {
               type int32;
             }
           }
           container me-sync-tlv {
             leaf me-sync-tlv.heading {
               type string;
             }
             leaf state {
               type int32;
             }
             leaf duration {
               type int32;
             }
           }
           container topology-hash-tlv {
             leaf topology-hash-tlv.heading {
               type string;
             }
             leaf vcf-topology-hash {
               type int32;
             }
           }
           container member-info-tlv {
             leaf member-info-tlv.heading {
               type string;
             }
             leaf system-name {
               type string;
               description "Hostname of a system";
             }
             leaf member-id {
               type int32;
               description "Member identifier";
             }
             leaf member-role {
               type string;
               description "Member's role";
             }
             container device-info {
               leaf system-name {
                 type string;
                 description "Hostname of a system";
               }
               leaf device-id {
                 type uint32;
               }
             }
           }
           container topology-tlv {
             leaf topology-tlv.heading {
               type string;
             }
             leaf system-name {
               type string;
               description "Hostname of a system";
             }
           }
           container provision-tlv {
             leaf provision-tlv.heading {
               type string;
             }
             leaf member-id {
               type int32;
               description "Member identifier";
             }
             leaf serial-number {
               type string;
               description "Serial number of a system";
             }
           }
           container dcf-fabric-device-information-tlv {
             leaf system-name {
               type string;
               description "Hostname of a system";
             }
             leaf device-id {
               type uint32;
             }
           }
           container iri-tlv {
             leaf iri-tlv.heading {
               type string;
             }
             leaf ip-address {
               type jt:ipaddr;
               description "IRI IP address";
             }
           }
           container me-link-status-tlv {
             leaf me-link-status-tlv.heading {
               type string;
             }
             leaf link-state {
               type int32;
             }
           }
           container port-info-tlv {
             leaf port-info-tlv.heading {
               type string;
             }
             leaf port-interface {
               type string;
             }
             leaf port-state {
               type int32;
             }
           }
           container version-information-tlv {
             leaf version-information-tlv.heading {
               type string;
             }
             leaf software-major {
               type int32;
             }
             leaf software-minor {
               type int32;
             }
             leaf software-category {
               type string;
             }
             leaf software-build {
               type string;
             }
             leaf software-spin {
               type int32;
             }
           }
           container member-fpc-slots-tlv {
             leaf member-fpc-slots-tlv.heading {
               type string;
             }
             leaf member-fpc-slots {
               type int32;
             }
           }
           container unknown-tlv {
             leaf tlv-type {
               type int32;
             }
             leaf tlv-length {
               type int32;
             }
           }
           container tlv-stragglers {
             leaf bytes-left {
               type int32;
             }
           }
           leaf vccp-tlv.heading {
             type string;
           }
         }
         leaf lsp-stub {
           type empty;
         }
         container vccp-isis-neighbor {
           leaf is-neighbor-id {
             type string;
           }
           leaf interface-name {
             type string;
           }
           leaf metric {
             type int32;
           }
         }
         container vccp-header {
           leaf lsp-id {
             type string;
           }
           leaf pdu-length {
             type int32;
           }
           leaf allocated-length {
             type int32;
           }
           leaf remaining-lifetime {
             type int32;
           }
           leaf interface-index {
             type int32;
           }
           leaf estimated-free-bytes {
             type int32;
           }
           leaf actual-free-bytes {
             type int32;
           }
           leaf lsdb-timer-type {
             type string;
           }
           leaf lsdb-expiration-time {
             type int32;
           }
           leaf needs-rebuild {
             type empty;
           }
         }
         container vccp-packet {
           leaf lsp-id {
             type string;
           }
           leaf pdu-length {
             type int32;
           }
           leaf pdu-lifetime {
             type int32;
           }
           leaf checksum {
             type int32;
           }
           leaf sequence-number {
             type int32;
           }
           leaf lsp-length {
             type int32;
           }
           leaf pdu-version {
             type int32;
           }
           leaf system-id-length {
             type int32;
           }
           leaf vccp-packet-type {
             type int32;
           }
           leaf software-major-version {
             type int32;
           }
           leaf software-minor-version {
             type int32;
           }
         }
         container transmission-status {
           leaf transmit-count {
             type int32;
           }
           leaf message {
             type string;
           }
           leaf interface-name {
             type string;
           }
           leaf transmit-time {
             type string;
             description "Time to queue this message for transmission";
           }
         }
       }
     }
   }
   grouping virtual-chassis-interface-information-block {
     container vccp-interface {
       leaf interface-name {
         type string;
       }
       leaf vccp-interface-state {
         type string;
       }
       leaf metric {
         type int32;
       }
       leaf vccp-interface.heading {
         type string;
       }
       leaf interface-index {
         type int32;
       }
       leaf interface-state-value {
         type int32;
       }
       leaf interface-disabled-flag {
         type empty;
       }
       leaf lsp-interval {
         type int32;
       }
       leaf hello-padding {
         type string;
       }
       leaf system-name {
         type string;
         description "Hostname of a system";
       }
       container interface-level-data {
         leaf adjacency-count {
           type int32;
         }
         leaf metric {
           type int32;
         }
         leaf hello-time {
           type int32;
         }
         leaf holdtime {
           type int32;
         }
       }
     }
   }
   grouping virtual-chassis-route-information-block {
     container vccp-routing-table {
       leaf system-name {
         type string;
         description "Hostname of a system";
       }
       leaf vccp-rtttype {
         type int32;
       }
       leaf table-version {
         type int32;
       }
       container vccp-route {
         leaf system-name {
           type string;
           description "Hostname of a system";
         }
         leaf route-version {
           type int32;
         }
         leaf metric {
           type int32;
         }
         leaf interface-name {
           type string;
         }
         leaf vccp-next-hop {
           type string;
         }
       }
     }
   }
   grouping virtual-chassis-statistics-information-block {
     container vccp-statistics {
       leaf system-name {
         type string;
         description "Hostname of a system";
       }
       leaf lsp-queue-length {
         type int32;
       }
       leaf lsp-queue-drops {
         type int32;
       }
       leaf spf-runs {
         type int32;
       }
       leaf fragments-rebuilt {
         type int32;
       }
       leaf lsps-regenerated {
         type int32;
       }
       leaf purges-initiated {
         type int32;
       }
       list vccp-pdu-statistics {
         leaf vccp-pdu-type {
           type string;
         }
         leaf packets-received {
           type uint64;
         }
         leaf packets-processed {
           type uint64;
         }
         leaf packets-dropped {
           type uint64;
         }
         leaf packets-sent {
           type uint64;
         }
         leaf packets-retransmitted {
           type uint64;
         }
       }
       container totals-information {
         leaf packets-received {
           type uint64;
         }
         leaf packets-sent {
           type uint64;
         }
       }
     }
   }
   grouping virtual-chassis-fast-failover-block {
     leaf virtual-chassis-fast-failover-vcp {
       type string;
       description "Fast failover status on dedicated VCP ports";
     }
     leaf virtual-chassis-fast-failover-et {
       type string;
       description "Fast failover status on ET uplink VCP ports";
     }
     leaf virtual-chassis-fast-failover-xe {
       type string;
       description "Fast failover status on XE uplink VCP ports";
     }
     leaf virtual-chassis-fast-failover-ge {
       type string;
       description "Fast failover status on GE uplink VCP ports";
     }
   }
   grouping virtual-chassis-mode-information-block {
     leaf vc-mode-current {
       type string;
     }
     leaf vc-mode-after-reboot {
       type string;
     }
   }
 }
