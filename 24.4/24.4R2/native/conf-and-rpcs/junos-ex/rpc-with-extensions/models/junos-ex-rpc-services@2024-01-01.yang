/*
 * Copyright (c) 2025 Juniper Networks, Inc.
 * All rights reserved.
 */
 module junos-ex-rpc-services {
   namespace "http://yang.juniper.net/junos-ex/rpc/services";

   prefix services;

   import junos-common-ddl-extensions {
     prefix junos;
     revision-date 2024-01-01;
   }

   import junos-common-types {
     prefix jt;
     revision-date 2024-01-01;
   }

   organization "Juniper Networks, Inc.";

   contact "yang-support@juniper.net";

   description "Junos RPC YANG module for services command(s)";

   revision 2024-01-01 {
     description "Junos: 24.4R2.25";
   }

   rpc get-pcef-subscribers {
     description "Show subscriber information";
     junos:command "show services pcef subscribers";
     input {
       leaf address {
         description "IPv4 or IPv6 address of subscriber";
         type string;
       }
       leaf interface {
         description "Interface name, or with wildcards (e.g. fe-0/0/*, fe-0/*/*)";
         type union {
           type jt:interface-wildcard;
           type string {
             pattern "<.*>|$.*";
           }
         }
       }
       leaf physical-interface {
         description "Physical Interface name";
         type union {
           type jt:interface-wildcard;
           type string {
             pattern "<.*>|$.*";
           }
         }
       }
       leaf user-name {
         description "Username of subscriber";
         type string;
       }
       leaf logical-system {
         description "Logical system where subscriber resides";
         type string;
       }
       leaf routing-instance {
         description "Routing instance where subscriber resides";
         type string;
       }
       leaf profile-name {
         description "Profile with which subscriber has been activated";
         type string {
           length "1 .. 80";
         }
       }
       leaf agent-circuit-identifier {
         description "Display summary for specified agent circuit identifier";
         type string;
       }
       leaf aci-interface-set-name {
         description "Display summary for specified ACI interface set";
         type string;
       }
       leaf stacked-vlan-id {
         description "Stacked VLAN identifier of subscriber";
         type union {
           type string {
             pattern "<.*>|$.*";
           }
           type uint16 {
             range "0 .. 4094";
           }
         }
       }
       leaf vlan-id {
         description "VLAN identifier of subscriber";
         type union {
           type string {
             pattern "<.*>|$.*";
           }
           type uint16 {
             range "0 .. 4094";
           }
         }
       }
       leaf vpi {
         description "ATM VPI of subscriber";
         type union {
           type string {
             pattern "<.*>|$.*";
           }
           type uint16 {
             range "0 .. 255";
           }
         }
       }
       leaf vci {
         description "ATM VCI of subscriber";
         type union {
           type string {
             pattern "<.*>|$.*";
           }
           type uint16 {
             range "0 .. 65535";
           }
         }
       }
       leaf id {
         description "Identifier of subscriber";
         type string;
       }
       leaf mac-address {
         description "MAC address of subscriber";
         type jt:mac-addr;
       }
       leaf client-type {
         description "Client type of subscriber";
         type enumeration {
           enum "dhcp" {
             description "DHCP clients only";
           }
           enum "vlan" {
             description "VLAN clients only";
           }
           enum "ppp" {
             description "PPP clients only";
           }
           enum "pppoe" {
             description "PPPoE clients only";
           }
           enum "l2tp" {
             description "L2TP clients only";
           }
           enum "static" {
             description "Static clients only";
           }
           enum "vpls-pw" {
             description "VPLS-PW clients only";
           }
           enum "mlppp" {
             description "MLPPP clients only";
           }
           enum "xauth" {
             description "XAuth clients only";
           }
           enum "fwauth" {
             description "FwAuth clients only";
           }
           enum "dot1x" {
             description "Dot1x clients only";
           }
           enum "essm" {
             description "ESSM clients only";
           }
           enum "fwa" {
             description "FWA clients only";
           }
           enum "agf" {
             description "AGF clients only";
           }
         }
       }
       leaf subscriber-state {
         description "State of subscriber";
         type enumeration {
           enum "init" {
             description "INIT state only";
           }
           enum "configured" {
             description "CONFIGURED state only";
           }
           enum "active" {
             description "ACTIVE state only";
           }
           enum "terminating" {
             description "TERMINATING state only";
           }
         }
       }
       leaf display {
         junos:cli-feature "nokeyword";
         default "terse";
         type enumeration {
           enum "terse" {
             description "Display terse output";
           }
           enum "detail" {
             description "Display detailed output";
           }
           enum "extensive" {
             description "Display extensive output";
           }
           enum "count" {
             description "Display number of subscribers";
           }
         }
       }
     }
   }
   rpc get-pcef-subscribers-summary {
     description "Display pcef subscriber summary";
     junos:command "show services pcef subscribers summary";
     input {
       leaf logical-system {
         description "Display summary for specified logical system";
         type string;
       }
       leaf routing-instance {
         description "Display summary for specified routing instance";
         type string;
       }
       leaf physical-interface {
         description "Physical Interface name";
         type union {
           type jt:interface-wildcard;
           type string {
             pattern "<.*>|$.*";
           }
         }
       }
       leaf port {
         description "Display full subscriber port summary";
         type empty;
       }
       leaf pic {
         description "Display full subscriber pic summary";
         type empty;
       }
       leaf slot {
         description "Display full subscriber slot summary";
         type empty;
       }
       leaf all {
         description "Display full subscriber summary";
         type empty;
       }
     }
   }
   rpc get-pcef-pic {
     description "Show physical interface card information";
     junos:command "show services pcef pic";
     input {
       leaf fpc-slot {
         description "FPC slot number";
         type union {
           type string {
             pattern "<.*>|$.*";
           }
           type uint32;
         }
       }
       leaf pic-slot {
         description "PIC slot number";
         type union {
           type string {
             pattern "<.*>|$.*";
           }
           type uint32;
         }
       }
       leaf display {
         junos:cli-feature "nokeyword";
         default "terse";
         type enumeration {
           enum "terse" {
             description "Display terse output";
           }
         }
       }
     }
   }
   rpc get-uac-debug-counters {
     description "Show uac debug counters";
     junos:command "show services unified-access-control debug-counters";
     input {
       uses command-forwarding;
     }
     output {
       container uac-debug-counters {
         uses uac-debug-counters-block;
       }
     }
   }
   rpc get-uac-policies {
     description "Access policies from infranet controller";
     junos:command "show services unified-access-control policies";
     input {
       uses command-forwarding;
       leaf detail {
         description "Display detail output";
         type empty;
       }
       leaf identifier {
         description "Show specified policy information";
         type string;
       }
     }
   }
   rpc get-uac-auth-table {
     description "Show authentication table configured from infranet controller";
     junos:command "show services unified-access-control authentication-table";
     input {
       uses command-forwarding;
       leaf detail {
         description "Display detail output";
         type empty;
       }
       leaf identifier {
         description "Show specified authentication entry";
         type string;
       }
       leaf extended {
         description "Show authentication entries with all roles";
         type empty;
       }
       leaf role {
         description "Show authentication entries matching the role";
         type string;
       }
       leaf ip {
         description "Show authentication entries matching the ip";
         type string;
       }
       leaf user {
         description "Show authentication entries matching the user";
         type string;
       }
     }
   }
   rpc get-uac-status {
     description "Show connection status with infranet controller";
     junos:command "show services unified-access-control status";
     input {
       uses command-forwarding;
     }
   }
   rpc get-uac-counters {
     description "Show unified access control(uac) service related counters";
     junos:command "show services unified-access-control counters";
     input {
       uses command-forwarding;
     }
     output {
       container uac-counters {
         uses uac-counters-block;
       }
     }
   }
   rpc get-ift-global-information {
     description "Show inband telemetry information";
     junos:command "show services inband-flow-telemetry global";
     output {
       container ift-global-information {
         uses ift-global-information-block;
       }
     }
   }
   rpc get-ift-profile-information {
     description "Show inband telemetry profile details";
     junos:command "show services inband-flow-telemetry profile";
     input {
       leaf profile-name {
         description "Name of the profile";
         junos:cli-feature "nokeyword";
         type string;
       }
     }
     output {
       container ift-profile-information {
         uses ift-profile-information-block;
       }
     }
   }
   rpc get-ift-stats-information {
     description "Show inband telemetry stats information";
     junos:command "show services inband-flow-telemetry stats";
     output {
       container ift-stats-information {
         uses ift-stats-information-block;
       }
     }
   }
   rpc get-services-security-associations-information {
     description "Show IPSec security association information";
     junos:command "show services ipsec-vpn ipsec security-associations";
     input {
       leaf level {
         junos:cli-feature "nokeyword";
         default "brief";
         type enumeration {
           enum "brief" {
             description "Display brief output (default)";
           }
           enum "detail" {
             description "Display detailed output";
           }
           enum "extensive" {
             description "Display extensive output";
           }
         }
       }
       leaf service-set {
         description "Restrict output to one service set";
         junos:cli-feature "nokeyword";
         type string {
           junos:posix-pattern "^[A-Za-z0-9][_0-9A-Za-z-]{0,62}$";
           junos:pattern-message "Must be a string beginning with a number or letter and consisting of no more than 63 total letters, numbers, dashes and underscores.";
         }
       }
       leaf hex {
         description "Display SPI in hexadecimal format";
         type empty;
       }
     }
     output {
       container services-security-associations-information {
         uses services-security-associations-information-block;
       }
     }
   }
   rpc get-services-ipsec-statistics-information {
     description "Show IPSec statistics";
     junos:command "show services ipsec-vpn ipsec statistics";
     input {
       leaf remote-gw {
         description "Peer address to use as filter";
         type string;
       }
       leaf display {
         junos:cli-feature "nokeyword";
         default "brief";
         type enumeration {
           enum "detail" {
             description "Display all tunnels";
           }
           enum "brief" {
             description "Display accumulated statistics (default)";
           }
         }
       }
       leaf service-set {
         description "Name of service set";
         type string;
       }
     }
     output {
       container ipsec-total-statistics-information {
         uses ipsec-total-statistics-information-block;
       }
     }
   }
   rpc get-ike-services-security-associations-information {
     description "Show services IKE security association information";
     junos:command "show services ipsec-vpn ike security-associations";
     input {
       leaf level {
         junos:cli-feature "nokeyword";
         default "brief";
         type enumeration {
           enum "brief" {
             description "Show brief output (default)";
           }
           enum "detail" {
             description "Show detailed output";
           }
         }
       }
       leaf peer-address {
         description "Name of security association";
         junos:cli-feature "nokeyword";
         type jt:ipaddr;
       }
       leaf routing-instance {
         description "Name of the local-gateway routing-instance";
         type string;
       }
     }
     output {
       container ike-security-associations-information {
         uses ike-security-associations-information-block;
       }
     }
   }
   rpc get-ike-services-statistics {
     description "Show services IKE security association statistics";
     junos:command "show services ipsec-vpn ike statistics";
     input {
       leaf peer-address {
         description "Name of security association";
         junos:cli-feature "nokeyword";
         type jt:ipaddr;
       }
       leaf routing-instance {
         description "Name of the local-gateway routing-instance";
         type string;
       }
     }
     output {
       container ike-security-associations-statistics {
         uses ike-security-associations-statistics-block;
       }
     }
   }
   rpc get-fips-pic-status-information {
     description "Show FIPS PIC authorization status";
     junos:command "show services fips pic status";
     output {
       container fips-pic-status-information {
         uses fips-pic-status-information-block;
       }
     }
   }
   rpc get-lrf-statistics {
     description "Show lrf statistics";
     junos:command "show services lrf statistics";
     output {
       container lrf-statistics-summary {
         uses lrf-statistics-summary-block;
       }
     }
   }
   rpc get-lrf-collector-statistics {
     description "Show lrf collector statistics";
     junos:command "show services lrf collector statistics";
     input {
       leaf collector-name {
         description "Name of collector";
         junos:cli-feature "nokeyword";
         type string;
       }
     }
     output {
       container lrf-collector-statistics-summary {
         uses lrf-collector-statistics-summary-block;
       }
     }
   }
   rpc get-lrf-rule-statistics {
     description "Show lrf rule statistics";
     junos:command "show services lrf rule statistics";
     input {
       leaf rule-name {
         description "Name of rule";
         junos:cli-feature "nokeyword";
         type string;
       }
     }
     output {
       container lrf-rule-statistics-summary {
         uses lrf-rule-statistics-summary-block;
       }
     }
   }
   rpc get-lrf-template {
     description "Show lrf template";
     junos:command "show services lrf template";
     input {
       leaf template-type {
         description "Template type";
         junos:cli-feature "nokeyword";
         type enumeration {
           enum "ipv4" {
             description "Ipv4 template type";
           }
           enum "ipv4-extended" {
             description "Ipv4 extended template type";
           }
           enum "ipv6" {
             description "Ipv6 template type";
           }
           enum "ipv6-extended" {
             description "Ipv6 extended template type";
           }
           enum "transport-layer" {
             description "Transport layer template type";
           }
           enum "flow-id" {
             description "Flow id template type";
           }
           enum "ipflow" {
             description "IPFlow type";
           }
           enum "ipflow-ts" {
             description "IPFlow TS type";
           }
           enum "ipflow-extended" {
             description "IPFlow extended type";
           }
           enum "device-data" {
             description "Device data template type";
           }
           enum "l7-app" {
             description "L7 APP template type";
           }
           enum "http" {
             description "HTTP type";
           }
           enum "mobile-subscriber" {
             description "Mobile subscriber type";
           }
           enum "subscriber-data" {
             description "Subscriber data type";
           }
           enum "ifl-subscriber" {
             description "IFL based subscriber type";
           }
           enum "wireline-subscriber" {
             description "Wireline subscriber type";
           }
           enum "ipflow-tcp-ts" {
             description "IPFLOW TCP timestamp type (IBM specific)";
           }
           enum "ipflow-tcp" {
             description "IPFLOW TCP type";
           }
           enum "video" {
             description "Video type";
           }
           enum "dns" {
             description "DNS type";
           }
           enum "status-code-distribution" {
             description "Status code distribution for HTTP and DNS";
           }
           enum "pcc" {
             description "PCC type";
           }
         }
         mandatory true;
       }
     }
     output {
       container lrf-template {
         uses lrf-template-block;
       }
     }
   }
   rpc get-analytics-agent-information {
     description "Show analytics service agent information";
     junos:command "show services analytics agent";
     input {
       leaf level {
         junos:cli-feature "nokeyword";
         default "brief";
         type enumeration {
           enum "detail" {
             description "Display detailed data";
           }
           enum "brief" {
             description "Display brief data (default)";
           }
         }
       }
     }
     output {
       container analytics-agent-information {
         uses analytics-agent-information-block;
       }
     }
   }
   rpc get-probe-results {
     description "Show probe results";
     junos:command "show services rpm probe-results";
     input {
       leaf owner {
         description "Name of owner";
         type string {
           length "1 .. 32";
         }
       }
       leaf test {
         description "Name of test";
         type string {
           length "1 .. 32";
         }
       }
       leaf source-address {
         description "Filter results based on ipv4 or ipv6 source-address";
         type jt:ipaddr;
       }
       leaf target-address {
         description "Filter results based on ipv4 or ipv6 target-address";
         type jt:ipaddr;
       }
       leaf dst-interface {
         description "Filter results based on destination-interface";
         type union {
           type jt:interface-unit;
           type string {
             pattern "<.*>|$.*";
           }
         }
       }
       leaf status {
         description "Filter based on test status PASS or FAIL";
         type enumeration {
           enum "PASS" {
             description "Dump successful tests";
           }
           enum "FAIL" {
             description "Dump failed tests";
           }
         }
       }
       leaf terse {
         description "Terse output";
         type empty;
       }
       leaf limit {
         description "Dump specified number of results (default is 100)";
         default "100";
         type union {
           type string {
             pattern "<.*>|$.*";
           }
           type uint32 {
             range "1 .. 4294967295";
           }
         }
       }
     }
     output {
       container probe-results {
         uses probe-results-block;
       }
     }
   }
   rpc get-history-results {
     description "Show history results";
     junos:command "show services rpm history-results";
     input {
       leaf verbosity_level {
         junos:cli-feature "nokeyword";
         default "brief";
         type enumeration {
           enum "brief" {
             description "Display brief output (default)";
           }
           enum "detail" {
             description "Display detailed output";
           }
         }
       }
       leaf owner {
         description "Name of owner";
         type string {
           length "1 .. 32";
         }
         mandatory true;
       }
       leaf test {
         description "Name of test";
         type string {
           length "1 .. 32";
         }
       }
       leaf since {
         description "Show history since YYYY-MM-DD.HH:MM:SS";
         type jt:time;
       }
       leaf source-address {
         description "Filter history based on ipv4 or ipv6 source-address";
         type jt:ipaddr;
       }
       leaf target-address {
         description "Filter history based on ipv4 or ipv6 target-address";
         type jt:ipaddr;
       }
       leaf dst-interface {
         description "Filter based on destination-interface";
         type union {
           type jt:interface-unit;
           type string {
             pattern "<.*>|$.*";
           }
         }
       }
       leaf limit {
         description "Dump specified number of results (default is 100)";
         default "100";
         type union {
           type string {
             pattern "<.*>|$.*";
           }
           type uint32 {
             range "1 .. 4294967295";
           }
         }
       }
     }
     output {
       container history-results {
         uses history-results-block;
       }
     }
   }
   rpc get-active-servers {
     description "Show configured servers";
     junos:command "show services rpm active-servers";
     output {
       container active-servers {
         uses active-servers-block;
       }
     }
   }
   rpc get-service-mss-sessions-information {
     description "Show mobile subscriber data sessions";
     junos:command "show services mobile sessions";
     input {
       leaf imsi {
         description "IMSI of subscriber";
         type string {
           length "5 .. 15";
         }
       }
     }
   }
   rpc get-service-hcm-sessions-stats {
     description "Show hcm session statistics";
     junos:command "show services mobile hcm statistics";
     input {
       leaf imsi {
         description "IMSI of subscriber";
         type string {
           length "5 .. 15";
         }
         mandatory true;
       }
     }
   }
   rpc get-service-tdf-sessions-information {
     description "Show traffic-detection-function subscriber data sessions";
     junos:command "show services traffic-detection-function sessions";
     input {
       leaf routing-instance {
         description "Name of routing instance";
         type string;
         mandatory true;
       }
       leaf ipv4-address {
         description "Show sessions for matching IPv4 address";
         type string;
       }
       leaf ipv6-address {
         description "Show sessions for matching IPv6 address";
         type string;
       }
       leaf subscriber-name {
         description "Show sessions for matching Subscriber name";
         type string;
       }
     }
   }
   rpc get-service-tdf-hcm-sessions-stats {
     description "Show hcm session statistics";
     junos:command "show services traffic-detection-function hcm statistics";
     input {
       leaf routing-instance {
         description "Name of routing instance";
         type string;
         mandatory true;
       }
       leaf ipv4-address {
         description "Show sessions for matching IPv4 address";
         type string;
       }
       leaf ipv6-address {
         description "Show sessions for matching IPv6 address";
         type string;
       }
       leaf subscriber-name {
         description "Show sessions for matching Subscriber name";
         type string;
       }
     }
   }
   rpc get-global-pcp-statistics-information {
     description "Show global PCP statistics";
     junos:command "show services pcp statistics";
     input {
       leaf interface {
         description "Name of adaptive services interface";
         type string;
       }
       leaf level {
         junos:cli-feature "nokeyword";
         type enumeration {
           enum "protocol" {
             description "Display PCP protocol statistics";
           }
         }
       }
     }
   }
   rpc get-traffic-load-balance-statistics {
     description "Traffic load balance statistics";
     junos:command "show services traffic-load-balance statistics";
     input {
       leaf verbose {
         junos:cli-feature "nokeyword";
         type enumeration {
           enum "summary" {
             description "Display summary output";
           }
           enum "extensive" {
             description "Display extensive output";
           }
         }
       }
       leaf group {
         description "Group name";
         default "all";
         type string;
       }
       leaf instance {
         description "Instance name";
         default "all";
         type string;
       }
       leaf real-service {
         description "Real service name";
         default "all";
         type string;
       }
       leaf virtual-service {
         description "Virtual service name";
         default "all";
         type string;
       }
       leaf num-instances {
         description "Number of instances to be displayed";
         default "200";
         type union {
           type uint32;
           type string {
             pattern "<.*>|$.*";
           }
         }
       }
     }
   }
   rpc get-flb-statistics {
     description "FLB  statistics";
     junos:command "show services traffic-load-balance flb-statistics";
     input {
       leaf all {
         description "All flb instances";
         type empty;
       }
     }
   }
   rpc traffic-load-balance-commit-status {
     description "Display commit status";
     junos:command "show services traffic-load-balance commit-status";
     output {
       container tdir-commit-status {
         uses tdir-commit-status-block;
       }
     }
   }
   grouping command-forwarding {
     leaf no-forwarding {
       description "No forwarding";
       type empty;
     }
     choice chassis-selector {
       case case_1 {
         leaf all-chassis {
           description "All chassis";
           type empty;
         }
       }
       case case_2 {
         leaf all-lcc {
           description "All LCC chassis";
           type empty;
         }
       }
       case case_3 {
         leaf scc {
           description "SCC";
           type empty;
         }
       }
       case case_4 {
         leaf sfc {
           description "SFC";
           type union {
             type string {
               pattern "<.*>|$.*";
             }
             type uint32;
           }
         }
       }
       case case_5 {
         leaf lcc {
           description "Specific LCC";
           type union {
             type string {
               pattern "<.*>|$.*";
             }
             type uint32;
           }
         }
       }
       case case_6 {
         leaf node {
           description "Specific node";
           type string;
         }
       }
       case case_7 {
         leaf bsys {
           description "Base system";
           type empty;
         }
       }
       case case_8 {
         leaf gnf {
           description "Specific guest network function";
           type union {
             type string {
               pattern "<.*>|$.*";
             }
             type uint32 {
               range "1 .. 10";
             }
           }
         }
       }
       case case_9 {
         leaf all-gnfs {
           description "All guest network functions";
           type empty;
         }
       }
       case case_10 {
         leaf all-system {
           description "All system (BSYS and GNFs)";
           type empty;
         }
       }
       case case_11 {
         leaf server {
           description "Specific server slot";
           type union {
             type string {
               pattern "<.*>|$.*";
             }
             type uint32 {
               range "0 .. 1";
             }
           }
         }
       }
       case case_12 {
         leaf all-servers {
           description "All servers";
           type empty;
         }
       }
       case case_13 {
         leaf vnf {
           description "Specific virtual-network-function";
           type string;
         }
       }
       case case_14 {
         leaf all-vnfs {
           description "All virtual-network-functions";
           type empty;
         }
       }
     }
     choice re-selector {
       case case_1 {
         leaf re0 {
           description "RE0";
           type empty;
         }
       }
       case case_2 {
         leaf re1 {
           description "RE1";
           type empty;
         }
       }
       case case_3 {
         leaf routing-engine {
           description "Specific routing engine";
           type enumeration {
             enum "local" {
               description "Local routing engine";
             }
             enum "other" {
               description "Other routing engine";
             }
             enum "master" {
               description "Master routing engine";
             }
             enum "backup" {
               description "Backup routing engine";
             }
             enum "both" {
               description "Both routing engines";
             }
           }
         }
       }
     }
     choice lr-selector {
       case case_1 {
         leaf logical-system {
           description "Name of logical system, or 'all'";
           type string;
         }
       }
     }
     choice tenant-selector {
       case case_1 {
         leaf tenant {
           description "Name of tenant, or 'all'";
           type string;
         }
       }
     }
     choice vc-selector {
       case case_1 {
         leaf local {
           description "Local virtual chassis member";
           type empty;
         }
       }
       case case_2 {
         leaf all-members {
           description "All virtual chassis members";
           type empty;
         }
       }
       case case_3 {
         leaf member {
           description "Specific virtual chassis member which is master";
           type union {
             type string {
               pattern "<.*>|$.*";
             }
             type uint32;
           }
         }
       }
     }
   }
   grouping uac-debug-counters-block {
     leaf uac-debug-counters-title {
       type string;
       description "Uac debug counters";
     }
     list uac-debug-counter-info {
       description "Uac debug counter info";
       leaf uac-debug-counter-name {
         type string;
       }
       leaf uac-debug-counter-value {
         type uint32;
       }
     }
   }
   grouping uac-counters-block {
     list uac-counter {
       description "UAC counter for the PFE";
       leaf pfe-name {
         type string;
         description "PFE";
       }
       leaf allowed-policy-action {
         type uint32;
         description "Sessions allowed due to policy action";
       }
       leaf allowed-timeout-action {
         type uint32;
         description "Sessions allowed due to timeout action";
       }
       leaf denied-unauthenticated {
         type uint32;
         description "Sessions denied due to lack of authentication";
       }
       leaf denied-policy-action {
         type uint32;
         description "Sessions denied due to policy action";
       }
       leaf denied-policy-unmatched {
         type uint32;
         description "Sessions denied due to unmatched policy";
       }
       leaf denied-timeout-action {
         type uint32;
         description "Sessions denied due to timeout action";
       }
       leaf terminated-reevaluation {
         type uint32;
         description "Sessions terminated due to reevaluation";
       }
       leaf terminated-signout {
         type uint32;
         description "Sessions terminated due to user signout";
       }
       leaf auth-added {
         type uint32;
         description "Auth entry added to PFE";
       }
       leaf auth-deleted {
         type uint32;
         description "Auth entry deleted from PFE";
       }
       leaf current-auth-cnt {
         type uint32;
         description "UAC total auth count";
       }
     }
   }
   grouping ift-global-information-block {
     container ift-global {
       leaf device-id {
         type uint32;
         description "Unique device identifier";
       }
       leaf meta-data-stack-length {
         type uint32;
         description "Maximum length of the meta-data";
       }
       leaf hop-limit {
         type uint32;
         description "Maximum hop limit";
       }
       leaf flow-type {
         type string;
         description "Traffic flow type";
       }
       leaf no-ipv6-address-match {
         type uint32;
         description "IPV6 address match allowed or not";
       }
       leaf clock-source {
         type string;
         description "Clock source for timestamping";
       }
     }
   }
   grouping ift-profile-information-block {
     list ift-profile {
       leaf profile-name {
         type string;
         description "Profile name";
       }
       leaf sample-rate {
         type uint32;
         description "Ratio of packets to be sampled (1 out of N)";
       }
       container collector-info {
         leaf source-address {
           type string;
           description "Source address";
         }
         leaf destination-address {
           type string;
           description "Destination address";
         }
         leaf destination-port {
           type int32;
           description "Destination port";
         }
         leaf maximum-clip-length {
           type int32;
           description "Clip length of data packet";
         }
         leaf mtu {
           type int32;
           description "MTU of export packets";
         }
       }
     }
   }
   grouping ift-stats-information-block {
     container ift-stats {
       leaf init-packets {
         type uint64;
         description "IFA initator statistics";
       }
       leaf transit-packets {
         type uint64;
         description "IFA transit statistics";
       }
       leaf terminate-rx-packets {
         type uint64;
         description "IFA termination rx statistics";
       }
       leaf terminate-tx-packets {
         type uint64;
         description "IFA termination tx statistics";
       }
       leaf terminate-tx-records {
         type uint64;
         description "IFA termination tx records";
       }
     }
   }
   grouping services-security-associations-information-block {
     list services-security-associations-block {
       leaf svc-set-name {
         type string;
         description "Name of the service set";
       }
       leaf outside-service-interface-routing-instance {
         type string;
         description "Name of routing instance that hosts outside service interface";
       }
       container sa-tunnel-information {
         leaf sa-rule-name {
           type string;
           description "Name of the rule";
         }
         leaf sa-term-name {
           type string;
           description "Name of the term";
         }
         leaf sa-tunnel-index {
           type int32;
           description "Tunnel index";
         }
         leaf sa-anchored-pic {
           type string;
           description "Anchored pic";
         }
         leaf sa-local-gateway-interface {
           type string;
           description "Local gateway  interface";
         }
         leaf sa-local-gateway {
           type jt:ipaddr;
           description "Local gateway address";
         }
         leaf sa-remote-gateway {
           type jt:ipaddr;
           description "Remote gateway address";
         }
         leaf sa-local-identity {
           type string;
           description "Local identity information";
         }
         leaf sa-remote-identity {
           type string;
           description "Remote identity information";
         }
         leaf sa-inside-interface {
           type string;
           description "Name of IPSec interface to internal network";
         }
         leaf sa-tunnel-mtu {
           type int32;
           description "MTU of the IPSec Tunnel";
         }
         leaf sa-udp-encapsulate {
           type string;
           description "UDP encapsulation related information";
         }
         leaf sa-udp-dst-port {
           type string;
           description "UDP encapsulation port related information";
         }
         leaf sa-no-information {
           type empty;
           description "Output string when there are no security associations present";
         }
         leaf sa-detect-natt {
           type string;
           description "NAT-T is detected/not detected";
         }
         leaf sa-nat-keepalive {
           type int32;
           description "NAT-T keepalive interval in secs";
         }
         list tunnel-information-detail {
           leaf tunnel-total-uptime {
             type string;
             description "Total tunnel uptime in mins";
           }
         }
       }
       list security-associations {
         leaf sa-direction {
           type string;
           description "Direction of the security association";
         }
         leaf sa-spi {
           type string;
           description "Security Parameter Index";
         }
         leaf sa-aux-spi {
           type string;
           description "Auxiliary Security Parameter Index";
         }
         leaf sa-mode {
           type string;
           description "Mode of the security association";
         }
         leaf sa-type {
           type string;
           description "SA Type";
         }
         leaf sa-protocol {
           type string;
           description "IPSec security protocol";
         }
         leaf sa-extended-seq-number {
           type string;
           description "Extended-Sequnce-Number";
         }
         leaf sa-state {
           type string;
           description "Status of the SA";
         }
         leaf sa-authentication-algorithm {
           type string;
           description "Authentication algorithm";
         }
         leaf sa-encryption-algorithm {
           type string;
           description "Encryption algorithm";
         }
         leaf sa-soft-lifetime {
           type string;
           description "Remaining lifetime, in seconds or kilobytes, before soft lifetime expires";
         }
         leaf sa-hard-lifetime {
           type string;
           description "Remaining lifetime, in seconds or kilobytes, before hard lifetime expires";
         }
         leaf sa-anti-replay-service {
           type string;
           description "Anti-replay service";
         }
         leaf sa-replay-window-size {
           type int32;
           description "Replay window size";
         }
         leaf sa-copy-tos-from-inner-ip-header {
           type string;
           description "Copy ToS from inner ip header";
         }
         leaf sa-tos-value {
           type int32;
           description "ToS value";
         }
         leaf sa-copy-ttl-from-inner-ip-header {
           type string;
           description "Copy TTL from inner ip header";
         }
         leaf sa-ttl-value {
           type int32;
           description "TTL value";
         }
         leaf sa-configured-lifetime {
           type string;
           description "SA lifetime configured/accepted in secs";
         }
       }
       list tunnel-redundancy-extensive {
         leaf ipsec-tunnel-redundancy-primary-remote-address {
           type jt:ipaddr;
           description "Address of primary remote gateway";
         }
         leaf ipsec-redundancy-primary-state {
           type string;
           description "State of primary remote gateway";
         }
         leaf ipsec-redundancy-counter {
           type int32;
           description "Failover counter";
         }
         leaf ipsec-tunnel-redundancy-backup-remote-address {
           type jt:ipaddr;
           description "Address of backup remote gateway";
         }
         leaf ipsec-redundancy-backup-state {
           type string;
           description "State of backup remote gateway";
         }
         leaf ipsec-redundancy-tunnel-no-information {
           type empty;
           description "Output string when tunnel redundancy is not configured";
         }
       }
     }
     container sa-tunnel-information {
     }
     list security-associations {
       leaf sa-extended-seq-number {
         type string;
         description "Extended-Sequnce-Number";
       }
     }
   }
   grouping ipsec-total-statistics-information-block {
     list ipsec-service-set-statistics {
       leaf pic-name {
         type string;
         description "PIC name";
       }
       leaf service-set-name {
         type string;
         description "Service set name";
       }
       list ipsec-statistics {
         leaf statistics-no-information {
           type empty;
           description "Output string when there are no statistics to report";
         }
         container esp-statistics {
           leaf esp-encrypted-bytes {
             type uint64;
             description "ESP encrypted bytes information";
           }
           leaf esp-decrypted-bytes {
             type uint64;
             description "ESP decrypted bytes information";
           }
           leaf esp-encrypted-packets {
             type uint64;
             description "ESP encrypted packets information";
           }
           leaf esp-decrypted-packets {
             type uint64;
             description "ESP decrypted packets information";
           }
         }
         container ah-statistics {
           leaf ah-input-bytes {
             type uint64;
             description "AH input bytes information";
           }
           leaf ah-output-bytes {
             type uint64;
             description "AH output bytes information";
           }
           leaf ah-input-packets {
             type uint64;
             description "AH input packets information";
           }
           leaf ah-output-packets {
             type uint64;
             description "AH output packets information";
           }
         }
         container d3p-statistics {
           leaf d3p-old-packets {
             type uint64;
             description "D3p packets information";
           }
           leaf d3p-new-packets {
             type uint64;
             description "D3p packets information";
           }
           leaf d3p-no-header-packets {
             type uint64;
             description "D3p packets information";
           }
           leaf d3p-unexpected-header-packets {
             type uint64;
             description "D3p packets information";
           }
         }
         container fail-open-statistics {
           leaf fail-open-packets-received {
             type uint64;
             description "Fail open packets information";
           }
           leaf fail-open-packets-sent {
             type uint64;
             description "Fail open packets information";
           }
         }
         container error-statistics {
           leaf ah-authentication-failures {
             type int32;
             description "AH authentication failures information";
           }
           leaf replay-errors {
             type int32;
             description "Replay error information";
           }
           leaf esp-authentication-failures {
             type int32;
             description "ESP authentication failures information";
           }
           leaf esp-decryption-failures {
             type int32;
             description "ESP decryption failures information";
           }
           leaf bad-headers {
             type int32;
             description "Bad header information";
           }
           leaf bad-trailers {
             type int32;
             description "Bad trailer information";
           }
           leaf replay-before-window-drops {
             type int32;
             description "Replay before window drop information";
           }
           leaf replay-pkts {
             type int32;
             description "Replayed pkt information";
           }
           leaf rule-lookup-fail {
             type int32;
             description "Rule lookup failure information";
           }
           leaf no-sa-errors {
             type int32;
             description "No SA error information";
           }
           leaf ip-integrity-errors {
             type int32;
             description "IP Integrity error information";
           }
           leaf exceeds-tunnel-mtu {
             type int32;
             description "Exceeds Tunnel MTU";
           }
           leaf flow-errors {
             type int32;
             description "Flow error information";
           }
           leaf misc-errors {
             type int32;
             description "Misc error information";
           }
           leaf invalid-spi-errors {
             type int32;
             description "Invalid SPI error information";
           }
           leaf ts-check-fail-errors {
             type int32;
             description "TS check fail error information";
           }
           leaf discard-errors {
             type int32;
             description "Discard error information";
           }
         }
         leaf local-gateway {
           type jt:ipaddr;
           description "Local gateway address";
         }
         leaf remote-gateway {
           type jt:ipaddr;
           description "Remote gateway address";
         }
         leaf tunnel-index {
           type int32;
           description "Tunnel index";
         }
       }
     }
   }
   grouping ike-security-associations-information-block {
     list ike-security-associations {
       leaf ike-sa-index {
         type uint32;
         description "Index";
       }
       leaf ike-sa-state {
         type string;
         description "Status of the SA";
       }
       leaf ike-sa-initiator-cookie {
         type string;
         description "IKE SA initiator cookie";
       }
       leaf ike-sa-responder-cookie {
         type string;
         description "IKE SA responder cookie";
       }
       leaf ike-sa-exchange-type {
         type string;
         description "Exchange type";
       }
       leaf ike-sa-remote-address {
         type jt:ipaddr;
         description "Remote address";
       }
       leaf ike-sa-routing-instance {
         type string;
         description "Local-gateway routing instance";
       }
       leaf ike-sa-local-gateway-interface {
         type string;
         description "Local gateway  interface";
       }
       leaf ike-ike-id {
         type string;
         description "IKE ID";
       }
       container ike-sa-algorithms {
         leaf ike-sa-sig-key-length {
           type uint32;
           description "Signature Key Length";
         }
       }
       container ike-sa-traffic-statistics {
         leaf ike-sa-output-invalid-spi-packets {
           type int32;
           description "Number of invalid SPI notifications send";
         }
         leaf ike-sa-input-invalid-spi-packets {
           type int32;
           description "Number of invalid SPI notifications received";
         }
         leaf ike-sa-input-frag-packets {
           type int32;
           description "Input fragmentation packets, including retransmissions";
         }
         leaf ike-sa-output-frag-packets {
           type int32;
           description "Output fragmentation packets, including retransmissions";
         }
       }
       container ike-sa-misc {
         leaf ike-sa-num-ipsec-rekeys {
           type int32;
           description "Number of IPSec rekeys using this SA";
         }
         leaf ike-sa-exchange-type {
           type string;
           description "Exchange type";
         }
       }
       container ike-sa-payload-statistics {
         leaf ike-sa-delete-payloads-received {
           type int32;
           description "Number of delete payloads received";
         }
         leaf ike-sa-delete-payloads-sent {
           type int32;
           description "Number of delete payloads sent";
         }
         leaf ike-sa-r-u-there-payloads-received {
           type int32;
           description "Number of DPD R-U-THERE payloads received";
         }
         leaf ike-sa-r-u-there-payloads-sent {
           type int32;
           description "Number of DPD R-U-THERE payloads sent";
         }
         leaf ike-sa-r-u-there-ack-payloads-received {
           type int32;
           description "Number of DPD R-U-THERE-ACK payloads received";
         }
         leaf ike-sa-r-u-there-ack-payloads-sent {
           type int32;
           description "Number of DPD R-U-THERE-ACK payloads sent";
         }
         leaf ike-sa-r-u-there-ack-payloads-missed {
           type int32;
           description "Number of DPD R-U-THERE-ACK payloads missed";
         }
         leaf ike-sa-r-u-there-ack-payloads-maximum-delay {
           type int32;
           description "Worst case delay for the DPD R-U-THERE-ACK";
         }
         leaf ike-sa-r-u-there-ack-seq-payloads-missed {
           type int32;
           description "Number of DPD R-U-THERE-ACK payloads missed in sequence";
         }
         leaf ike-sa-dpd-request-payloads-received {
           type int32;
           description "Number of DPD request payloads received";
         }
         leaf ike-sa-dpd-request-payloads-sent {
           type int32;
           description "Number of DPD request payloads sent";
         }
         leaf ike-sa-dpd-response-payloads-received {
           type int32;
           description "Number of DPD response payloads received";
         }
         leaf ike-sa-dpd-response-payloads-sent {
           type int32;
           description "Number of DPD response payloads sent";
         }
         leaf ike-sa-dpd-response-payloads-missed {
           type int32;
           description "Number of DPD response payloads missed";
         }
         leaf ike-sa-dpd-response-payloads-maximum-delay {
           type int32;
           description "Worst case delay for the DPD response";
         }
         leaf ike-sa-dpd-response-seq-payloads-missed {
           type int32;
           description "Number of DPD response payloads missed in sequence";
         }
         leaf ike-sa-invalid-spi-notifications-received {
           type int32;
           description "Number of invalid SPI notifications received";
         }
         leaf ike-sa-invalid-spi-notifications-sent {
           type int32;
           description "Number of invalid SPI notifications sent";
         }
       }
       container ike-sa-stats-information {
       }
       leaf ike-sa-reauthlifetime {
         type string;
         description "Remaining IKE Hard lifetime before re-authentication, in seconds";
       }
       leaf ike-sa-ike-frag {
         type string;
         description "IKE Fragmentation Flag";
       }
       leaf ike-sa-frag-size {
         type int32;
         description "IKE Fragmentation Size";
       }
     }
     container ike-security-associations-block {
       list ike-security-associations {
         leaf ike-sa-routing-instance {
           type string;
           description "Local-gateway routing instance";
         }
         leaf ike-sa-local-gateway-interface {
           type string;
           description "Local gateway  interface";
         }
         leaf ike-ike-id {
           type string;
           description "IKE ID";
         }
         container ike-sa-algorithms {
           leaf ike-sa-sig-key-length {
             type uint32;
             description "Signature Key Length";
           }
           leaf ike-sa-authentication-algorithm {
             type string;
             description "Authentication algorithm";
           }
           leaf ike-sa-encryption-algorithm {
             type string;
             description "Encryption algorithm";
           }
           leaf ike-sa-prf-algorithm {
             type string;
             description "PRF algorithm";
           }
           leaf ike-sa-dhgroup {
             type string;
             description "DH group";
           }
           leaf ike-sa-sign-hash-algo {
             type string;
             description "Signature hash algorithms";
           }
         }
         container ike-sa-traffic-statistics {
           leaf ike-sa-output-invalid-spi-packets {
             type int32;
             description "Number of invalid SPI notifications send";
           }
           leaf ike-sa-input-invalid-spi-packets {
             type int32;
             description "Number of invalid SPI notifications received";
           }
           leaf ike-sa-input-frag-packets {
             type int32;
             description "Input fragmentation packets, including retransmissions";
           }
           leaf ike-sa-output-frag-packets {
             type int32;
             description "Output fragmentation packets, including retransmissions";
           }
           leaf ike-sa-input-bytes {
             type int32;
             description "Input bytes, including retransmissions";
           }
           leaf ike-sa-output-bytes {
             type int32;
             description "Output bytes, including retransmissions";
           }
           leaf ike-sa-input-packets {
             type int32;
             description "Input packets, including retransmissions";
           }
           leaf ike-sa-output-packets {
             type int32;
             description "Output packets, including retransmissions";
           }
         }
         container ike-sa-misc {
           leaf ike-sa-num-ipsec-rekeys {
             type int32;
             description "Number of IPSec rekeys using this SA";
           }
           leaf ike-sa-exchange-type {
             type string;
             description "Exchange type";
           }
           leaf ike-sa-flags {
             type string;
             description "IKE SA flags";
           }
           leaf ike-sa-num-ipsec-sas-created {
             type int32;
             description "Number of IPSec SAs created using this SA";
           }
           leaf ike-sa-num-ipsec-sas-deleted {
             type int32;
             description "Number of IPSec SAs deleted using this SA";
           }
           leaf ike-sa-num-phase2-negotiations {
             type int32;
             description "Number of negotiations in progress on this SA";
           }
           leaf ike-ipsec-sa-tunnel-ids {
             type string;
             description "Ipsec SA tunnel Indexes";
           }
         }
         container ike-sa-payload-statistics {
           leaf ike-sa-delete-payloads-received {
             type int32;
             description "Number of delete payloads received";
           }
           leaf ike-sa-delete-payloads-sent {
             type int32;
             description "Number of delete payloads sent";
           }
           leaf ike-sa-r-u-there-payloads-received {
             type int32;
             description "Number of DPD R-U-THERE payloads received";
           }
           leaf ike-sa-r-u-there-payloads-sent {
             type int32;
             description "Number of DPD R-U-THERE payloads sent";
           }
           leaf ike-sa-r-u-there-ack-payloads-received {
             type int32;
             description "Number of DPD R-U-THERE-ACK payloads received";
           }
           leaf ike-sa-r-u-there-ack-payloads-sent {
             type int32;
             description "Number of DPD R-U-THERE-ACK payloads sent";
           }
           leaf ike-sa-r-u-there-ack-payloads-missed {
             type int32;
             description "Number of DPD R-U-THERE-ACK payloads missed";
           }
           leaf ike-sa-r-u-there-ack-payloads-maximum-delay {
             type int32;
             description "Worst case delay for the DPD R-U-THERE-ACK";
           }
           leaf ike-sa-r-u-there-ack-seq-payloads-missed {
             type int32;
             description "Number of DPD R-U-THERE-ACK payloads missed in sequence";
           }
           leaf ike-sa-dpd-request-payloads-received {
             type int32;
             description "Number of DPD request payloads received";
           }
           leaf ike-sa-dpd-request-payloads-sent {
             type int32;
             description "Number of DPD request payloads sent";
           }
           leaf ike-sa-dpd-response-payloads-received {
             type int32;
             description "Number of DPD response payloads received";
           }
           leaf ike-sa-dpd-response-payloads-sent {
             type int32;
             description "Number of DPD response payloads sent";
           }
           leaf ike-sa-dpd-response-payloads-missed {
             type int32;
             description "Number of DPD response payloads missed";
           }
           leaf ike-sa-dpd-response-payloads-maximum-delay {
             type int32;
             description "Worst case delay for the DPD response";
           }
           leaf ike-sa-dpd-response-seq-payloads-missed {
             type int32;
             description "Number of DPD response payloads missed in sequence";
           }
           leaf ike-sa-invalid-spi-notifications-received {
             type int32;
             description "Number of invalid SPI notifications received";
           }
           leaf ike-sa-invalid-spi-notifications-sent {
             type int32;
             description "Number of invalid SPI notifications sent";
           }
         }
         container ike-sa-stats-information {
           container ikev2-ipsec-sa-rekey-stats {
             leaf ikev2-initiator-ipsec-sa-rekey-request-out {
               type int32;
               description "Number of IPsec SA rekey CREATE_CHILD_SA request sent by Initiator";
             }
             leaf ikev2-responder-ipsec-sa-rekey-request-in {
               type int32;
               description "Number of IPsec SA rekey CREATE_CHILD_SA request recv by Responder";
             }
             leaf ikev2-initiator-ipsec-sa-rekey-response-in {
               type int32;
               description "Number of IPsec SA rekey CREATE_CHILD_SA response recv by Initiator";
             }
             leaf ikev2-responder-ipsec-sa-rekey-response-out {
               type int32;
               description "Number of IPsec SA rekey CREATE_CHILD_SA response sent by Responder";
             }
             leaf ikev2-initiator-ipsec-sa-rekey-no-proposal-chosen-in {
               type int32;
               description "Number of IPsec SA rekey NO_PROPSAL_CHOSEN notify recv by Initiator";
             }
             leaf ikev2-responder-ipsec-sa-rekey-no-proposal-chosen-out {
               type int32;
               description "Number of IPsec SA rekey NO_PROPSAL_CHOSEN notify sent by Responder";
             }
             leaf ikev2-initiator-ipsec-sa-rekey-invalid-key-in {
               type int32;
               description "Number of IPsec SA rekey INVALID_KE_PAYLOAD notify recv by Initiator";
             }
             leaf ikev2-responder-ipsec-sa-rekey-invalid-key-out {
               type int32;
               description "Number of IPsec SA rekey INVALID_KE_PAYLOAD notify sent by Responder";
             }
             leaf ikev2-initiator-ipsec-sa-rekey-ts-unacceptable-in {
               type int32;
               description "Number of IPsec SA rekey TS_UNACCEPTABLE notify recv by Initiator";
             }
             leaf ikev2-responder-ipsec-sa-rekey-ts-unacceptable-out {
               type int32;
               description "Number of IPsec SA rekey TS_UNACCEPTABLE notify sent by Responder";
             }
             leaf ikev2-initiator-ipsec-sa-rekey-res-dh-compute-key-fail {
               type int32;
               description "Number of IPsec SA rekey response, DH compute key failed at Initiator";
             }
             leaf ikev2-responder-ipsec-sa-rekey-res-dh-compute-key-fail {
               type int32;
               description "Number of IPsec SA rekey response, DH compute key failed at Responder";
             }
             leaf ikev2-initiator-ipsec-sa-rekey-res-verify-sa-fail {
               type int32;
               description "Number of IPsec SA rekey response, verify of peer SA failed at Initiator";
             }
             leaf ikev2-initiator-ipsec-sa-rekey-res-verify-dh-group-fail {
               type int32;
               description "Number of IPsec SA rekey response, verify of DH group failed at Initiator";
             }
             leaf ikev2-initiator-ipsec-sa-rekey-res-verify-ts-fail {
               type int32;
               description "Number of IPsec SA rekey response, verify of TS failed at Initiator";
             }
           }
         }
         leaf ike-sa-reauthlifetime {
           type string;
           description "Remaining IKE Hard lifetime before re-authentication, in seconds";
         }
         leaf ike-sa-ike-frag {
           type string;
           description "IKE Fragmentation Flag";
         }
         leaf ike-sa-frag-size {
           type int32;
           description "IKE Fragmentation Size";
         }
         leaf ike-sa-role {
           type string;
           description "Role of our end";
         }
         leaf ike-sa-state {
           type string;
           description "Status of the SA";
         }
         leaf ike-sa-initiator-cookie {
           type string;
           description "IKE SA initiator cookie";
         }
         leaf ike-sa-responder-cookie {
           type string;
           description "IKE SA responder cookie";
         }
         leaf ike-sa-exchange-type {
           type string;
           description "Exchange type";
         }
         leaf ike-sa-authentication-method {
           type string;
         }
         leaf ike-sa-local-address {
           type jt:ipaddr;
           description "Local address";
         }
         leaf ike-sa-local-port {
           type int32;
           description "Local port";
         }
         leaf ike-sa-remote-address {
           type jt:ipaddr;
           description "Remote address";
         }
         leaf ike-sa-remote-port {
           type int32;
           description "Remote port";
         }
         leaf ike-sa-lifetime {
           type string;
           description "Remaining lifetime before expiration, in seconds or kilobytes";
         }
         leaf ike-sa-remote-client-info {
           type string;
           description "Remote access client information ";
         }
         leaf ike-trusted-ca-profile-name {
           type string;
           description "Trusted CA profile";
         }
         leaf ike-trusted-ca-group-name {
           type string;
           description "Trusted CA group";
         }
         container ike-xauth-user-info {
           leaf ike-ike-id {
             type string;
             description "IKE ID";
           }
           leaf ike-xauth-username {
             type string;
             description "AAA username";
           }
           leaf ike-xauth-user-assigned-ip {
             type jt:ipaddr;
             description "IP assigned to AAA user";
           }
           leaf ike-xauth-user-assigned-ipv6 {
             type jt:ipaddr;
             description "IPv6 assigned to AAA user";
           }
         }
         list ike-sa-phase2-information {
           leaf ike-sa-phase2-type {
             type string;
             description "Type of phase 2 negotiation";
           }
           leaf ike-sa-role {
             type string;
             description "Role of our end";
           }
           leaf ike-sa-msg-id {
             type int32;
             description "Message ID of the quick mode negotiation";
           }
           leaf ike-sa-local-address {
             type jt:ipaddr;
             description "Local address";
           }
           leaf ike-sa-local-port {
             type int32;
             description "Local port";
           }
           leaf ike-sa-remote-address {
             type jt:ipaddr;
             description "Remote address";
           }
           leaf ike-sa-remote-port {
             type int32;
             description "Remote port";
           }
           leaf ike-sa-local-id {
             type string;
             description "Local end identity in phase 2";
           }
           leaf ike-sa-remote-id {
             type string;
             description "Remote end identity in phase 2";
           }
           leaf ike-sa-flags {
             type string;
             description "IKE SA flags";
           }
         }
         leaf ike-sa-srg-id {
           type int32;
           description "SRG ID";
         }
         container ike-ppk-profile {
           leaf ike-ppk-profile-name {
             type string;
             description "Indicates the PPK profile name configured for IKE Peer";
           }
           leaf ike-ppk-profile-optional {
             type string;
             description "Indicates whether PPK profile is configured as optional or not ";
           }
           leaf ike-ppk-profile-state {
             type string;
             description "Indicates whether PPK is used for IKE SA after negotiation";
           }
         }
       }
       leaf ike-sa-remote-address {
         type jt:ipaddr;
         description "Remote address";
       }
       leaf ike-sa-index {
         type uint32;
         description "Index";
       }
       leaf ike-gw-name {
         type string;
         description "Gateway Name";
       }
       container ike-sa-location {
         leaf ike-sa-fpc {
           type int32;
           description "FPC number";
         }
         leaf ike-sa-pic {
           type int32;
           description "PIC number";
         }
         leaf ike-sa-kmd-instance {
           type int32;
           description "KMD instance number";
         }
       }
       container ike-sa-advpn-info {
         leaf ike-sa-type {
           type string;
           description "SA Type";
         }
         leaf ike-sa-advpn-local-capability {
           type string;
           description "Shortcut Local Capability";
         }
         leaf ike-sa-advpn-peer-capability {
           type string;
           description "Shortcut Peer Capability";
         }
       }
       container ike-sa-advpn-suggester-shortcut-statistics {
         leaf ike-sa-advpn-shortcut-suggestions-sent {
           type int32;
           description "Number of Shortcut Suggestions sent";
         }
         leaf ike-sa-advpn-shortcut-suggestions-response-accepted {
           type int32;
           description "Number of Responses accepted for Shortcut Suggestions sent";
         }
         leaf ike-sa-advpn-shortcut-suggestions-response-declined {
           type int32;
           description "Number of Responses declined for Shortcut Suggestions sent";
         }
       }
       container ike-sa-advpn-partner-shortcut-statistics {
         leaf ike-sa-advpn-shortcut-suggestions-received {
           type int32;
           description "Number of Shortcut Suggestions received";
         }
         leaf ike-sa-advpn-shortcut-suggestions-accepted {
           type int32;
           description "Number of Shortcut Suggestions accepted";
         }
         leaf ike-sa-advpn-shortcut-suggestions-declined {
           type int32;
           description "Number of Shortcut Suggestions declined";
         }
       }
     }
     container ike-sa-stats-information {
     }
   }
   grouping ike-security-associations-statistics-block {
     list ike-security-associations {
       leaf ike-sa-reauthlifetime {
         type string;
         description "Remaining IKE Hard lifetime before re-authentication, in seconds";
       }
       leaf ike-sa-ike-frag {
         type string;
         description "IKE Fragmentation Flag";
       }
       leaf ike-sa-frag-size {
         type int32;
         description "IKE Fragmentation Size";
       }
       container ike-sa-algorithms {
         leaf ike-sa-sig-key-length {
           type uint32;
           description "Signature Key Length";
         }
       }
       container ike-sa-traffic-statistics {
         leaf ike-sa-input-frag-packets {
           type int32;
           description "Input fragmentation packets, including retransmissions";
         }
         leaf ike-sa-output-frag-packets {
           type int32;
           description "Output fragmentation packets, including retransmissions";
         }
         leaf ike-sa-output-invalid-spi-packets {
           type int32;
           description "Number of invalid SPI notifications send";
         }
         leaf ike-sa-input-invalid-spi-packets {
           type int32;
           description "Number of invalid SPI notifications received";
         }
       }
     }
     container ike-security-associations-block {
       leaf ike-sa-remote-address {
         type jt:ipaddr;
         description "Remote address";
       }
       list ike-security-associations {
         leaf ike-sa-initiator-cookie {
           type string;
           description "IKE SA initiator cookie";
         }
         leaf ike-sa-responder-cookie {
           type string;
           description "IKE SA responder cookie";
         }
         leaf ike-sa-routing-instance {
           type string;
           description "Local-gateway routing instance";
         }
         leaf ike-sa-local-address {
           type jt:ipaddr;
           description "Local address";
         }
         leaf ike-sa-local-port {
           type int32;
           description "Local port";
         }
         leaf ike-sa-remote-address {
           type jt:ipaddr;
           description "Remote address";
         }
         leaf ike-sa-remote-port {
           type int32;
           description "Remote port";
         }
         leaf ike-sa-reauthlifetime {
           type string;
           description "Remaining IKE Hard lifetime before re-authentication, in seconds";
         }
         leaf ike-sa-ike-frag {
           type string;
           description "IKE Fragmentation Flag";
         }
         leaf ike-sa-frag-size {
           type int32;
           description "IKE Fragmentation Size";
         }
         container ike-sa-algorithms {
           leaf ike-sa-sig-key-length {
             type uint32;
             description "Signature Key Length";
           }
         }
         container ike-sa-traffic-statistics {
           leaf ike-sa-input-bytes {
             type int32;
             description "Input bytes, including retransmissions";
           }
           leaf ike-sa-output-bytes {
             type int32;
             description "Output bytes, including retransmissions";
           }
           leaf ike-sa-input-packets {
             type int32;
             description "Input packets, including retransmissions";
           }
           leaf ike-sa-output-packets {
             type int32;
             description "Output packets, including retransmissions";
           }
           leaf ike-sa-input-frag-packets {
             type int32;
             description "Input fragmentation packets, including retransmissions";
           }
           leaf ike-sa-output-frag-packets {
             type int32;
             description "Output fragmentation packets, including retransmissions";
           }
           leaf ike-sa-output-invalid-spi-packets {
             type int32;
             description "Number of invalid SPI notifications send";
           }
           leaf ike-sa-input-invalid-spi-packets {
             type int32;
             description "Number of invalid SPI notifications received";
           }
         }
         container ike-sa-misc {
           leaf ike-sa-num-ipsec-sas-created {
             type int32;
             description "Number of IPSec SAs created using this SA";
           }
           leaf ike-sa-num-ipsec-sas-deleted {
             type int32;
             description "Number of IPSec SAs deleted using this SA";
           }
           leaf ike-sa-num-ipsec-rekeys {
             type int32;
             description "Number of IPSec rekeys using this SA";
           }
           leaf ike-sa-exchange-type {
             type string;
             description "Exchange type";
           }
         }
         container ike-sa-payload-statistics {
           leaf ike-sa-delete-payloads-received {
             type int32;
             description "Number of delete payloads received";
           }
           leaf ike-sa-delete-payloads-sent {
             type int32;
             description "Number of delete payloads sent";
           }
           leaf ike-sa-r-u-there-payloads-received {
             type int32;
             description "Number of DPD R-U-THERE payloads received";
           }
           leaf ike-sa-r-u-there-payloads-sent {
             type int32;
             description "Number of DPD R-U-THERE payloads sent";
           }
           leaf ike-sa-r-u-there-ack-payloads-received {
             type int32;
             description "Number of DPD R-U-THERE-ACK payloads received";
           }
           leaf ike-sa-r-u-there-ack-payloads-sent {
             type int32;
             description "Number of DPD R-U-THERE-ACK payloads sent";
           }
           leaf ike-sa-r-u-there-ack-payloads-missed {
             type int32;
             description "Number of DPD R-U-THERE-ACK payloads missed";
           }
           leaf ike-sa-r-u-there-ack-payloads-maximum-delay {
             type int32;
             description "Worst case delay for the DPD R-U-THERE-ACK";
           }
           leaf ike-sa-r-u-there-ack-seq-payloads-missed {
             type int32;
             description "Number of DPD R-U-THERE-ACK payloads missed in sequence";
           }
           leaf ike-sa-dpd-request-payloads-received {
             type int32;
             description "Number of DPD request payloads received";
           }
           leaf ike-sa-dpd-request-payloads-sent {
             type int32;
             description "Number of DPD request payloads sent";
           }
           leaf ike-sa-dpd-response-payloads-received {
             type int32;
             description "Number of DPD response payloads received";
           }
           leaf ike-sa-dpd-response-payloads-sent {
             type int32;
             description "Number of DPD response payloads sent";
           }
           leaf ike-sa-dpd-response-payloads-missed {
             type int32;
             description "Number of DPD response payloads missed";
           }
           leaf ike-sa-dpd-response-payloads-maximum-delay {
             type int32;
             description "Worst case delay for the DPD response";
           }
           leaf ike-sa-dpd-response-seq-payloads-missed {
             type int32;
             description "Number of DPD response payloads missed in sequence";
           }
           leaf ike-sa-invalid-spi-notifications-received {
             type int32;
             description "Number of invalid SPI notifications received";
           }
           leaf ike-sa-invalid-spi-notifications-sent {
             type int32;
             description "Number of invalid SPI notifications sent";
           }
         }
       }
     }
   }
   grouping fips-pic-status-information-block {
     list fips-pic-status {
       leaf fpc-slot {
         type int32;
         description "FPC slot";
       }
       leaf pic-slot {
         type int32;
         description "PIC slot";
       }
       leaf serial-number {
         type string;
         description "PIC serial number";
       }
       leaf authorization-status {
         type string;
         description "PIC authorization status";
       }
     }
   }
   grouping lrf-statistics-summary-block {
     list lrf-statistics {
       description "LRF statistics";
       leaf interface-name {
         type string;
         description "Name of the adaptive services interface";
       }
       leaf flow-packets {
         type int32;
         description "Flow packets";
       }
       leaf flow-bytes {
         type int32;
         description "Flow bytes";
       }
       leaf active-flows {
         type int32;
         description "Active flows";
       }
       leaf total-flows {
         type int32;
         description "Total flows";
       }
     }
   }
   grouping lrf-collector-statistics-summary-block {
     list lrf-collector-statistics {
       description "LRF collector statistics";
       leaf interface-name {
         type string;
         description "Name of the adaptive services interface";
       }
       leaf tmpl-reg {
         type int32;
         description "Templates registered";
       }
       leaf tmpl-reg-failures {
         type int32;
         description "Template registration failures";
       }
       leaf tmpl-active {
         type int32;
         description "Templates active";
       }
       leaf sessions-received {
         type int32;
         description "Sessions received";
       }
       leaf sessions-ignored {
         type int32;
         description "Sessions ignored";
       }
       leaf records-logged {
         type int32;
         description "Records logged";
       }
       leaf rec-export {
         type int32;
         description "Records exported";
       }
       leaf rec-export-failures {
         type int32;
         description "Record export failures";
       }
       leaf rec-export-volume {
         type int32;
         description "Records exported for volume";
       }
       leaf rec-export-time {
         type int32;
         description "Records exported for time";
       }
       leaf rec-export-session-close {
         type int32;
         description "Records exported for session close";
       }
     }
   }
   grouping lrf-rule-statistics-summary-block {
     list lrf-rule-statistics {
       description "LRF rule statistics";
       leaf interface-name {
         type string;
         description "Name of the adaptive services interface";
       }
       leaf rule-name {
         type string;
         description "Rule name";
       }
       leaf rule-tmpl-name {
         type string;
         description "Template name";
       }
       leaf rule-tmpl-reg {
         type int32;
         description "Templates registered";
       }
       leaf rule-tmpl-reg-failures {
         type int32;
         description "Template registration failures";
       }
       leaf rule-coll-name {
         type string;
         description "Collector name";
       }
       leaf rule-sessions-received {
         type int32;
         description "Sessions received";
       }
       leaf rule-sessions-ignored {
         type int32;
         description "Sessions ignored";
       }
       leaf rule-sessions-logged {
         type int32;
         description "Sessions logged";
       }
       leaf rule-rec-export {
         type int32;
         description "Records exported";
       }
       leaf rule-rec-export-failures {
         type int32;
         description "Record export failures";
       }
       leaf rule-rec-export-volume {
         type int32;
         description "Records exported for volume";
       }
       leaf rule-rec-export-time {
         type int32;
         description "Records exported for time";
       }
       leaf rule-rec-export-session-close {
         type int32;
         description "Records exported for session close";
       }
     }
   }
   grouping lrf-template-block {
     leaf-list export-field {
       type string;
     }
     leaf-list export-field-id {
       type int32;
     }
     leaf-list export-field-len {
       type int32;
     }
     leaf-list export-field-vendor {
       type string;
     }
   }
   grouping analytics-agent-information-block {
     list analytics-service-agent-information {
       leaf analytics-service-agent-name {
         type string;
         description "Service agent ID";
       }
       leaf analytics-service-agent-output-plugin-count {
         type int32;
         description "Number of output plugins configured";
       }
       leaf analytics-service-agent-input-plugin-count {
         type int32;
         description "Number of input plugins configured";
       }
       leaf analytics-service-agent-process-id {
         type int32;
         description "Service agent process id(PID)";
       }
       leaf analytics-service-agent-input-plugins {
         type string;
         description "Service agent input plugin list";
       }
       leaf analytics-service-agent-output-plugins {
         type string;
         description "Service agent output plugin list";
       }
     }
     container analytics-controller-information {
       leaf analytics-controller-process-id {
         type int32;
         description "Analytics agent process id(PID)";
       }
       leaf analytics-controller-conf-file {
         type string;
         description "Analytics agent configuration file";
       }
       leaf analytics-controller-log-file {
         type string;
         description "Analytics agent log file";
       }
       leaf analytics-controller-service-agent-count {
         type int32;
         description "Number of service agents";
       }
     }
   }
   grouping probe-results-block {
     list probe-results-terse {
       leaf test-name {
         type string;
         description "Name of test";
       }
       leaf destination-interface {
         type string;
         description "Name of output interface for probes";
       }
       leaf target-address {
         type string;
         description "Target address of test";
       }
       leaf last-status {
         type string;
         description "Status";
       }
       leaf last-status-changed {
         type string;
         description "Last time when status updated";
       }
       leaf twl-local-link {
         type string;
         description "Name of local link for TWAMP-Light probes";
       }
       leaf last-probe-status {
         type string;
         description "Probe status";
       }
     }
     list probe-test-results {
       leaf owner {
         type string;
         description "Test owner name";
       }
       leaf test-name {
         type string;
         description "Name of test";
       }
       leaf target-address {
         type string;
         description "Target address of test";
       }
       leaf target-url {
         type string;
         description "Target URL of test";
       }
       leaf source-address {
         type string;
         description "Source address of test";
       }
       leaf probe-type {
         type string;
         description "Name of the probe";
       }
       leaf icmp-id {
         type uint32;
         description "Icmp id for icmp-ping probes";
       }
       leaf test-size {
         type uint32;
         description "Number of probes in test";
       }
       leaf server-status {
         type string;
         description "TWAMP server is Connected or Not";
       }
       leaf twamp-client-retries {
         type uint32;
         description "Retries to connect TWAMP server at every test-interval";
       }
       leaf server-address {
         type jt:ipaddr;
         description "Server address";
       }
       leaf server-port {
         type uint32;
         description "Server port";
       }
       leaf client-address {
         type jt:ipaddr;
         description "Client address";
       }
       leaf client-port {
         type uint32;
         description "Client port";
       }
       leaf reflector-address {
         type jt:ipaddr;
         description "Reflector address";
       }
       leaf reflector-port {
         type uint32;
         description "Reflector port";
       }
       leaf sender-address {
         type jt:ipaddr;
         description "Sender address";
       }
       leaf sender-port {
         type uint32;
         description "Sender port";
       }
       leaf routing-instance-name {
         type string;
         description "Routing Instance Name";
       }
       leaf destination-interface {
         type string;
         description "Name of output interface for probes";
       }
       leaf twl-local-link {
         type string;
         description "Name of local link for TWAMP-Light probes";
       }
       leaf http-status {
         type uint32;
         description "HTTP Status Code";
       }
       leaf loss-thresh-total {
         type uint32;
         description "Maximum number of all lost probes";
       }
       leaf loss-thresh-succ {
         type uint32;
         description "Maximum number of successive lost probes";
       }
       leaf delay-thresh {
         type uint32;
         description "Maximum delay threshold";
       }
       leaf jitter-thresh {
         type uint32;
         description "Maximum jitter threshold";
       }
       leaf stddev-thresh {
         type uint32;
         description "Maximum standard deviation threshold";
       }
       leaf egress-thresh {
         type uint32;
         description "Maximum egress delay threshold";
       }
       leaf egress-jitter-thresh {
         type uint32;
         description "Maximum egress jitter threshold";
       }
       leaf egress-stddev-thresh {
         type uint32;
         description "Maximum egress standard deviation threshold";
       }
       leaf ingress-thresh {
         type uint32;
         description "Maximum ingress delay threshold";
       }
       leaf ingress-jitter-thresh {
         type uint32;
         description "Maximum ingress jitter threshold";
       }
       leaf ingress-stddev-thresh {
         type uint32;
         description "Maximum ingress standard deviation threshold";
       }
       container probe-single-results {
         leaf probe-sent-time {
           type string;
           description "Time at which probe was sent";
         }
         leaf probe-status {
           type string;
           description "Operation response status from probes";
         }
         leaf probe-time {
           type string;
           description "Time at which probe response was received or timed out";
         }
         leaf hardware-timestamp-status {
           type string;
           description "Use of hardware timestamps in probes";
         }
         leaf http-status {
           type uint32;
           description "HTTP Status Code";
         }
         leaf rtt {
           type uint32;
           description "Round trip time of probes";
         }
         leaf ingress {
           type uint32;
           description "Ingress trip time of probes";
         }
         leaf egress {
           type uint32;
           description "Egress trip time of probes";
         }
         leaf egress-jitter {
           type int32;
           description "Egress jitter of probes";
         }
         leaf ingress-jitter {
           type int32;
           description "Ingress jitter of probes";
         }
         leaf round-trip-jitter {
           type int32;
           description "Round trip jitter of probes";
         }
         leaf egress-interarrival-jitter {
           type int32;
           description "Egress interarrival jitter of probes";
         }
         leaf ingress-interarrival-jitter {
           type int32;
           description "Ingress interarrival jitter of probes";
         }
         leaf round-trip-interarrival-jitter {
           type int32;
           description "Round trip interarrival jitter of probes";
         }
         leaf owner {
           type string;
           description "Test owner name";
         }
         leaf test-name {
           type string;
           description "Name of test";
         }
       }
       container probe-test-current-results {
         container probe-test-generic-results {
           leaf results-scope {
             type string;
             description "Scope of results";
           }
           leaf probes-sent {
             type uint32;
             description "Number of probes sent";
           }
           leaf probe-responses {
             type uint32;
             description "Responses from probes";
           }
           leaf loss-percentage {
             type string;
             description "Percentage of probes lost (no response)";
           }
           container probe-last-test-info {
             leaf last-test-time {
               type string;
               description "Time at which last test was completed";
             }
           }
           container probe-test-rtt {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-egress {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-ingress {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-positive-egress-jitter {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-negative-egress-jitter {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-egress-jitter {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-positive-ingress-jitter {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-negative-ingress-jitter {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-ingress-jitter {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-positive-round-trip-jitter {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-negative-round-trip-jitter {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-round-trip-jitter {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container rpm-results-thresh {
             leaf rtt-thresh {
               type uint32;
               description "Round trip time thresh";
             }
             leaf rtt-jitter-thresh {
               type uint32;
               description "Round trip jitter threshold";
             }
             leaf rtt-stddev-thresh {
               type uint32;
               description "Round trip standard deviaion thresh";
             }
             leaf igr-thresh {
               type uint32;
               description "Ingress threshold";
             }
             leaf igr-jitter-thresh {
               type uint32;
               description "Ingress jitter threshold";
             }
             leaf igr-stddev-thresh {
               type uint32;
               description "Ingress standard deviation threshold";
             }
             leaf egr-thresh {
               type uint32;
               description "Egress threshold";
             }
             leaf egr-jitter-thresh {
               type uint32;
               description "Egress jitter threshold";
             }
             leaf egr-stddev-thresh {
               type uint32;
               description "Egress standared deviation threshold";
             }
           }
         }
       }
       container probe-last-test-results {
         container probe-test-generic-results {
           leaf results-scope {
             type string;
             description "Scope of results";
           }
           leaf probes-sent {
             type uint32;
             description "Number of probes sent";
           }
           leaf probe-responses {
             type uint32;
             description "Responses from probes";
           }
           leaf loss-percentage {
             type string;
             description "Percentage of probes lost (no response)";
           }
           container probe-last-test-info {
             leaf last-test-time {
               type string;
               description "Time at which last test was completed";
             }
           }
           container probe-test-rtt {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-egress {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-ingress {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-positive-egress-jitter {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-negative-egress-jitter {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-egress-jitter {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-positive-ingress-jitter {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-negative-ingress-jitter {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-ingress-jitter {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-positive-round-trip-jitter {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-negative-round-trip-jitter {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-round-trip-jitter {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container rpm-results-thresh {
             leaf rtt-thresh {
               type uint32;
               description "Round trip time thresh";
             }
             leaf rtt-jitter-thresh {
               type uint32;
               description "Round trip jitter threshold";
             }
             leaf rtt-stddev-thresh {
               type uint32;
               description "Round trip standard deviaion thresh";
             }
             leaf igr-thresh {
               type uint32;
               description "Ingress threshold";
             }
             leaf igr-jitter-thresh {
               type uint32;
               description "Ingress jitter threshold";
             }
             leaf igr-stddev-thresh {
               type uint32;
               description "Ingress standard deviation threshold";
             }
             leaf egr-thresh {
               type uint32;
               description "Egress threshold";
             }
             leaf egr-jitter-thresh {
               type uint32;
               description "Egress jitter threshold";
             }
             leaf egr-stddev-thresh {
               type uint32;
               description "Egress standared deviation threshold";
             }
           }
         }
       }
       container probe-test-moving-results {
         container probe-test-generic-results {
           leaf results-scope {
             type string;
             description "Scope of results";
           }
           leaf probes-sent {
             type uint32;
             description "Number of probes sent";
           }
           leaf probe-responses {
             type uint32;
             description "Responses from probes";
           }
           leaf loss-percentage {
             type string;
             description "Percentage of probes lost (no response)";
           }
           container probe-last-test-info {
             leaf last-test-time {
               type string;
               description "Time at which last test was completed";
             }
           }
           container probe-test-rtt {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-egress {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-ingress {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-positive-egress-jitter {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-negative-egress-jitter {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-egress-jitter {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-positive-ingress-jitter {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-negative-ingress-jitter {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-ingress-jitter {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-positive-round-trip-jitter {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-negative-round-trip-jitter {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-round-trip-jitter {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container rpm-results-thresh {
             leaf rtt-thresh {
               type uint32;
               description "Round trip time thresh";
             }
             leaf rtt-jitter-thresh {
               type uint32;
               description "Round trip jitter threshold";
             }
             leaf rtt-stddev-thresh {
               type uint32;
               description "Round trip standard deviaion thresh";
             }
             leaf igr-thresh {
               type uint32;
               description "Ingress threshold";
             }
             leaf igr-jitter-thresh {
               type uint32;
               description "Ingress jitter threshold";
             }
             leaf igr-stddev-thresh {
               type uint32;
               description "Ingress standard deviation threshold";
             }
             leaf egr-thresh {
               type uint32;
               description "Egress threshold";
             }
             leaf egr-jitter-thresh {
               type uint32;
               description "Egress jitter threshold";
             }
             leaf egr-stddev-thresh {
               type uint32;
               description "Egress standared deviation threshold";
             }
           }
         }
       }
       container probe-test-global-results {
         container probe-test-generic-results {
           leaf results-scope {
             type string;
             description "Scope of results";
           }
           leaf probes-sent {
             type uint32;
             description "Number of probes sent";
           }
           leaf probe-responses {
             type uint32;
             description "Responses from probes";
           }
           leaf loss-percentage {
             type string;
             description "Percentage of probes lost (no response)";
           }
           container probe-last-test-info {
             leaf last-test-time {
               type string;
               description "Time at which last test was completed";
             }
           }
           container probe-test-rtt {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-egress {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-ingress {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-positive-egress-jitter {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-negative-egress-jitter {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-egress-jitter {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-positive-ingress-jitter {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-negative-ingress-jitter {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-ingress-jitter {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-positive-round-trip-jitter {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-negative-round-trip-jitter {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-round-trip-jitter {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container rpm-results-thresh {
             leaf rtt-thresh {
               type uint32;
               description "Round trip time thresh";
             }
             leaf rtt-jitter-thresh {
               type uint32;
               description "Round trip jitter threshold";
             }
             leaf rtt-stddev-thresh {
               type uint32;
               description "Round trip standard deviaion thresh";
             }
             leaf igr-thresh {
               type uint32;
               description "Ingress threshold";
             }
             leaf igr-jitter-thresh {
               type uint32;
               description "Ingress jitter threshold";
             }
             leaf igr-stddev-thresh {
               type uint32;
               description "Ingress standard deviation threshold";
             }
             leaf egr-thresh {
               type uint32;
               description "Egress threshold";
             }
             leaf egr-jitter-thresh {
               type uint32;
               description "Egress jitter threshold";
             }
             leaf egr-stddev-thresh {
               type uint32;
               description "Egress standared deviation threshold";
             }
           }
         }
       }
       container probe-test-hwts-err-stats {
         leaf invalid-client-recv-ts-cntr {
           type uint32;
           description "Client recv timestamp less than Client send timestamp";
         }
         leaf invalid-client-nots-cntr {
           type uint32;
           description "Client timestamps (T1, T4) are marked as deadbeef";
         }
         leaf invalid-server-send-ts-cntr {
           type uint32;
           description "Server send timestamp less than Server recv timestamp";
         }
         leaf invalid-server-spent-time-cntr {
           type uint32;
           description "Server side spent time greater than RTT";
         }
         leaf pkt-rcvd-after-timeout-cntr {
           type uint32;
           description "RTT is greater than probe-interval";
         }
       }
     }
   }
   grouping history-results-block {
     list history-test-results {
       leaf owner {
         type string;
         description "Test owner name";
       }
       leaf test-name {
         type string;
         description "Name of test";
       }
       leaf probe-type {
         type string;
         description "Name of the probe";
       }
       leaf icmp-id {
         type uint32;
         description "Icmp id for icmp-ping probes";
       }
       leaf target-address {
         type string;
         description "Target address of test";
       }
       leaf target-url {
         type string;
         description "Target URL of test";
       }
       leaf source-address {
         type string;
         description "Source address of test";
       }
       leaf destination-interface {
         type string;
         description "Name of output interface for probes";
       }
       leaf twl-local-link {
         type string;
         description "Name of local link for TWAMP-Light probes";
       }
       leaf loss-thresh-total {
         type uint32;
         description "Maximum number of all lost probes";
       }
       leaf loss-thresh-succ {
         type uint32;
         description "Maximum number of successive lost probes";
       }
       leaf delay-thresh {
         type uint32;
         description "Maximum delay threshold";
       }
       leaf jitter-thresh {
         type uint32;
         description "Maximum jitter threshold";
       }
       leaf stddev-thresh {
         type uint32;
         description "Maximum standard deviation threshold";
       }
       leaf egress-thresh {
         type uint32;
         description "Maximum egress delay threshold";
       }
       leaf egress-jitter-thresh {
         type uint32;
         description "Maximum egress jitter threshold";
       }
       leaf ingress-thresh {
         type uint32;
         description "Maximum ingress delay threshold";
       }
       leaf ingress-jitter-thresh {
         type uint32;
         description "Maximum ingress jitter threshold";
       }
       container probe-single-results {
         leaf probe-sent-time {
           type string;
           description "Time at which probe was sent";
         }
         leaf probe-status {
           type string;
           description "Operation response status from probes";
         }
         leaf probe-time {
           type string;
           description "Time at which probe response was received or timed out";
         }
         leaf hardware-timestamp-status {
           type string;
           description "Use of hardware timestamps in probes";
         }
         leaf http-status {
           type uint32;
           description "HTTP Status Code";
         }
         leaf rtt {
           type uint32;
           description "Round trip time of probes";
         }
         leaf ingress {
           type uint32;
           description "Ingress trip time of probes";
         }
         leaf egress {
           type uint32;
           description "Egress trip time of probes";
         }
         leaf egress-jitter {
           type int32;
           description "Egress jitter of probes";
         }
         leaf ingress-jitter {
           type int32;
           description "Ingress jitter of probes";
         }
         leaf round-trip-jitter {
           type int32;
           description "Round trip jitter of probes";
         }
         leaf egress-interarrival-jitter {
           type int32;
           description "Egress interarrival jitter of probes";
         }
         leaf ingress-interarrival-jitter {
           type int32;
           description "Ingress interarrival jitter of probes";
         }
         leaf round-trip-interarrival-jitter {
           type int32;
           description "Round trip interarrival jitter of probes";
         }
         leaf owner {
           type string;
           description "Test owner name";
         }
         leaf test-name {
           type string;
           description "Name of test";
         }
       }
       container probe-test-current-results {
         container probe-test-generic-results {
           leaf results-scope {
             type string;
             description "Scope of results";
           }
           leaf probes-sent {
             type uint32;
             description "Number of probes sent";
           }
           leaf probe-responses {
             type uint32;
             description "Responses from probes";
           }
           leaf loss-percentage {
             type string;
             description "Percentage of probes lost (no response)";
           }
           container probe-last-test-info {
             leaf last-test-time {
               type string;
               description "Time at which last test was completed";
             }
           }
           container probe-test-rtt {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-egress {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-ingress {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-positive-egress-jitter {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-negative-egress-jitter {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-egress-jitter {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-positive-ingress-jitter {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-negative-ingress-jitter {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-ingress-jitter {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-positive-round-trip-jitter {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-negative-round-trip-jitter {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-round-trip-jitter {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container rpm-results-thresh {
             leaf rtt-thresh {
               type uint32;
               description "Round trip time thresh";
             }
             leaf rtt-jitter-thresh {
               type uint32;
               description "Round trip jitter threshold";
             }
             leaf rtt-stddev-thresh {
               type uint32;
               description "Round trip standard deviaion thresh";
             }
             leaf igr-thresh {
               type uint32;
               description "Ingress threshold";
             }
             leaf igr-jitter-thresh {
               type uint32;
               description "Ingress jitter threshold";
             }
             leaf igr-stddev-thresh {
               type uint32;
               description "Ingress standard deviation threshold";
             }
             leaf egr-thresh {
               type uint32;
               description "Egress threshold";
             }
             leaf egr-jitter-thresh {
               type uint32;
               description "Egress jitter threshold";
             }
             leaf egr-stddev-thresh {
               type uint32;
               description "Egress standared deviation threshold";
             }
           }
         }
       }
     }
   }
   grouping active-servers-block {
     list configured-servers {
       leaf protocol {
         type string;
         description "Protocol";
       }
       leaf port {
         type uint32;
         description "Port";
       }
       leaf destination-interface {
         type string;
         description "Name of output interface for probes";
       }
     }
   }
   grouping tdir-commit-status-block {
     leaf tdir-config-status {
       type string;
       description "Prints config status of previous commit";
     }
   }
 }
