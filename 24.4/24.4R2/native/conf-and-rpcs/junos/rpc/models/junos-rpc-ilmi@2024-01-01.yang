/*
 * Copyright (c) 2025 Juniper Networks, Inc.
 * All rights reserved.
 */
 module junos-rpc-ilmi {
   namespace "http://yang.juniper.net/junos/rpc/ilmi";

   prefix ilmi;

   import junos-common-types {
     prefix jt;
     revision-date 2024-01-01;
   }

   organization "Juniper Networks, Inc.";

   contact "yang-support@juniper.net";

   description "Junos RPC YANG module for ilmi command(s)";

   revision 2024-01-01 {
     description "Junos: 24.4R2.25";
   }

   rpc get-ilmi-information {
     description "Show interim local management interface information";
     input {
       leaf level {
         default "all";
         type enumeration {
           enum "all" {
             description "Show ILMI information for all interfaces";
           }
         }
       }
     }
     output {
       container ilmi-information {
         uses ilmi-information-block;
       }
     }
   }
   rpc get-ilmi-statistics {
     description "Show ILMI statistics";
     output {
       container ilmi-statistics {
         uses ilmi-statistics-block;
       }
     }
   }
   rpc get-ilmi-interface-information {
     description "Show ILMI information for interface";
     input {
       leaf interface_name {
         description "Interface name";
         type string;
         mandatory true;
       }
     }
     output {
       container ilmi-interface-information {
         uses ilmi-interface-information-block;
       }
     }
   }
   grouping command-forwarding {
     leaf no-forwarding {
       description "No forwarding";
       type empty;
     }
     choice chassis-selector {
       case case_1 {
         leaf all-chassis {
           description "All chassis";
           type empty;
         }
       }
       case case_2 {
         leaf all-lcc {
           description "All LCC chassis";
           type empty;
         }
       }
       case case_3 {
         leaf scc {
           description "SCC";
           type empty;
         }
       }
       case case_4 {
         leaf sfc {
           description "SFC";
           type union {
             type string {
               pattern "<.*>|$.*";
             }
             type uint32;
           }
         }
       }
       case case_5 {
         leaf lcc {
           description "Specific LCC";
           type union {
             type string {
               pattern "<.*>|$.*";
             }
             type uint32;
           }
         }
       }
       case case_6 {
         leaf node {
           description "Specific node";
           type string;
         }
       }
       case case_7 {
         leaf bsys {
           description "Base system";
           type empty;
         }
       }
       case case_8 {
         leaf gnf {
           description "Specific guest network function";
           type union {
             type string {
               pattern "<.*>|$.*";
             }
             type uint32 {
               range "1 .. 10";
             }
           }
         }
       }
       case case_9 {
         leaf all-gnfs {
           description "All guest network functions";
           type empty;
         }
       }
       case case_10 {
         leaf all-system {
           description "All system (BSYS and GNFs)";
           type empty;
         }
       }
       case case_11 {
         leaf server {
           description "Specific server slot";
           type union {
             type string {
               pattern "<.*>|$.*";
             }
             type uint32 {
               range "0 .. 1";
             }
           }
         }
       }
       case case_12 {
         leaf all-servers {
           description "All servers";
           type empty;
         }
       }
       case case_13 {
         leaf vnf {
           description "Specific virtual-network-function";
           type string;
         }
       }
       case case_14 {
         leaf all-vnfs {
           description "All virtual-network-functions";
           type empty;
         }
       }
     }
     choice re-selector {
       case case_1 {
         leaf re0 {
           description "RE0";
           type empty;
         }
       }
       case case_2 {
         leaf re1 {
           description "RE1";
           type empty;
         }
       }
       case case_3 {
         leaf routing-engine {
           description "Specific routing engine";
           type enumeration {
             enum "local" {
               description "Local routing engine";
             }
             enum "other" {
               description "Other routing engine";
             }
             enum "master" {
               description "Master routing engine";
             }
             enum "backup" {
               description "Backup routing engine";
             }
             enum "both" {
               description "Both routing engines";
             }
           }
         }
       }
     }
     choice lr-selector {
       case case_1 {
         leaf logical-system {
           description "Name of logical system, or 'all'";
           type string;
         }
       }
     }
     choice tenant-selector {
       case case_1 {
         leaf tenant {
           description "Name of tenant, or 'all'";
           type string;
         }
       }
     }
     choice vc-selector {
       case case_1 {
         leaf local {
           description "Local virtual chassis member";
           type empty;
         }
       }
       case case_2 {
         leaf all-members {
           description "All virtual chassis members";
           type empty;
         }
       }
       case case_3 {
         leaf member {
           description "Specific virtual chassis member which is master";
           type union {
             type string {
               pattern "<.*>|$.*";
             }
             type uint32;
           }
         }
       }
     }
   }
   grouping ilmi-information-block {
     container ilmi-interface-information {
       leaf interface-name {
         type string;
       }
       leaf atm-vpi {
         type int32;
       }
       leaf atm-vci {
         type int32;
       }
       leaf peer-ipaddr {
         type jt:ipaddr;
       }
       leaf peer-interface-name {
         type string;
       }
     }
   }
   grouping ilmi-statistics-block {
     container ilmi-input-statistics {
       leaf packets {
         type int32;
       }
       leaf bad-versions {
         type int32;
       }
       leaf bad-community-names {
         type int32;
       }
       leaf bad-community-uses {
         type int32;
       }
       leaf asn-parse-errors {
         type int32;
       }
       leaf too-bigs {
         type int32;
       }
       leaf no-such-names {
         type int32;
       }
       leaf bad-values {
         type int32;
       }
       leaf read-onlys {
         type int32;
       }
       leaf general-errors {
         type int32;
       }
       leaf total-request-varbinds {
         type int32;
       }
       leaf total-set-varbinds {
         type int32;
       }
       leaf get-requests {
         type int32;
       }
       leaf get-nexts {
         type int32;
       }
       leaf set-requests {
         type int32;
       }
       leaf get-responses {
         type int32;
       }
       leaf traps {
         type int32;
       }
       leaf silent-drops {
         type int32;
       }
       leaf proxy-drops {
         type int32;
       }
     }
     container ilmi-output-statistics {
       leaf packets {
         type int32;
       }
       leaf too-bigs {
         type int32;
       }
       leaf no-such-names {
         type int32;
       }
       leaf bad-values {
         type int32;
       }
       leaf general-errors {
         type int32;
       }
       leaf get-requests {
         type int32;
       }
       leaf get-nexts {
         type int32;
       }
       leaf set-requests {
         type int32;
       }
       leaf get-responses {
         type int32;
       }
       leaf traps {
         type int32;
       }
     }
   }
   grouping ilmi-interface-information-block {
     leaf interface-name {
       type string;
     }
     leaf atm-vpi {
       type int32;
     }
     leaf atm-vci {
       type int32;
     }
     leaf peer-ipaddr {
       type jt:ipaddr;
     }
     leaf peer-interface-name {
       type string;
     }
   }
 }
