/*
 * Copyright (c) 2025 Juniper Networks, Inc.
 * All rights reserved.
 */
 module junos-es-rpc-shmlog {
   namespace "http://yang.juniper.net/junos-es/rpc/shmlog";

   prefix shmlog;

   import junos-common-types {
     prefix jt;
     revision-date 2024-01-01;
   }

   organization "Juniper Networks, Inc.";

   contact "yang-support@juniper.net";

   description "Junos RPC YANG module for shmlog command(s)";

   revision 2024-01-01 {
     description "Junos: 24.4R2.25";
   }

   rpc get-shmlog-argument-mappings {
     description "Show argument mapping information";
     input {
       leaf argument-name {
         description "Name of shmlog argument";
         type string;
         mandatory true;
       }
       leaf memory-filename {
         description "Filename that holds copy of memory to use for display";
         type string;
       }
       leaf files-path {
         description "Root path to use to find files with info";
         type string;
       }
     }
   }
   rpc get-shmlog-entries {
     description "Show log entry information";
     input {
       leaf logname {
         description "Log name(s). Comma delimited list and wildcarding supported";
         type string;
         mandatory true;
       }
       leaf memory-filename {
         description "Filename that holds copy of memory to use for display";
         type string;
       }
       leaf filename {
         description "Filename to trace the logs";
         type string;
       }
       leaf files-path {
         description "Root path to use to find files with info";
         type string;
       }
       container filters {
         leaf name {
           description "Filter to be applied";
           type string;
         }
         leaf value {
           description "Variable value";
           type string;
         }
       }
       leaf context-switch {
         type enumeration {
           enum "context-switches" {
             description "Show context switch information";
           }
         }
       }
       leaf cpu-usage {
         type enumeration {
           enum "cpu-usage" {
             description "Show cpu usage information";
           }
         }
       }
       leaf date-time {
         type enumeration {
           enum "date-time" {
             description "Show time in date/time format (Mon DD HH:MM:SS.uuuuuu)";
           }
         }
       }
       leaf short-time {
         type enumeration {
           enum "short-time" {
             description "Show time in short date/time format (Mon DD HH:MM:SS)";
           }
         }
       }
       leaf flag-name {
         description "Display logs pertaining to applied flag events";
         type enumeration {
           enum "accounting-statistics" {
             description "Display ppp accounting statistics events";
           }
           enum "authentication" {
             description "Display authentication code events";
           }
           enum "chap" {
             description "Display ppp chap code events";
           }
           enum "events" {
             description "Display interface events";
           }
           enum "gres" {
             description "Display gres events";
           }
           enum "init" {
             description "Display daemon initialization events";
           }
           enum "interface-db" {
             description "Display ppp interface database code events";
           }
           enum "lcp" {
             description "Display ppp lcp state machine code events";
           }
           enum "memory" {
             description "Display memory management code events";
           }
           enum "ncp" {
             description "Display ppp ncp state machine code events";
           }
           enum "packet-error" {
             description "Display Packet events";
           }
           enum "pap" {
             description "Display ppp pap code events";
           }
           enum "parse" {
             description "Display parsing events ";
           }
           enum "profile" {
             description "Display libdynamic-profile events";
           }
           enum "packets" {
             description "Display packet events";
           }
           enum "routing-process" {
             description "Display routing process interactions events";
           }
           enum "rtp" {
             description "Display ppp Real Time Priority code events";
           }
           enum "rtsock" {
             description "Display routing socket code";
           }
           enum "session-db" {
             description "Display session database interactions code";
           }
           enum "smi-services-sentry" {
             description "Display ppp smi-services-sentry code";
           }
           enum "states" {
             description "Display state machine events";
           }
           enum "tunnel" {
             description "Display l2tp tunneling events";
           }
           enum "database" {
             description "Display dhcp Database operations";
           }
           enum "flow" {
             description "Display dhcp Flow related operations";
           }
           enum "fwd" {
             description "Display dhcp Firewall process operations";
           }
           enum "ha" {
             description "Display dhcp High Availability related operations";
           }
           enum "liveness-detection" {
             description "Display dhcp Liveness detection operations";
           }
           enum "persistent" {
             description "Display dhcp Persistent file operations";
           }
           enum "general" {
             description "Display dhcp General operations";
           }
           enum "message" {
             description "Display l2tp message operations";
           }
           enum "protocol" {
             description "Display l2tp protocol operations";
           }
           enum "ipc-tx" {
             description "Display l2tp IPC transmit operations";
           }
           enum "ipc-rx" {
             description "Display l2tp IPC receive operations";
           }
           enum "timer" {
             description "Display l2tp timer operations";
           }
           enum "error" {
             description "Display l2tp error operations";
           }
           enum "user-access" {
             description "Display authd Subscriber events";
           }
           enum "gx-plus" {
             description "Display authd gx-plus events";
           }
           enum "jsrc" {
             description "Display authd jsrc events";
           }
           enum "authd-framework" {
             description "Display authd authentication framework events";
           }
           enum "radius" {
             description "Display authd radius authentication events";
           }
           enum "addr-assign" {
             description "Display authd address-assignment events";
           }
           enum "local-auth" {
             description "Display authd local authentication events";
           }
           enum "lib-stats" {
             description "Display authd lib stats events";
           }
           enum "ldap" {
             description "Display authd  ldap authentication eventss";
           }
           enum "securid" {
             description "Display authd securid events";
           }
         }
       }
       leaf delta-time {
         type enumeration {
           enum "delta-time" {
             description "Show delta time";
           }
         }
       }
       leaf display-time-order {
         default "older-first";
         type enumeration {
           enum "older-first" {
             description "Show entries from oldest to newest";
           }
           enum "newer-first" {
             description "Show entries from newest to oldest";
           }
         }
       }
       leaf earliest-maximum {
         description "Maximum entries to show starting with earliest";
         type union {
           type string {
             pattern "<.*>|$.*";
           }
           type int32 {
             range "1 .. 1000000000";
           }
         }
       }
       leaf end-from-latest-days {
         description "Show entries ending with specified duration from latest";
         type union {
           type string {
             pattern "<.*>|$.*";
           }
           type int32 {
             range "1 .. 1000000000";
           }
         }
       }
       leaf end-from-latest-hours {
         description "Show entries ending with specified duration from latest";
         type union {
           type string {
             pattern "<.*>|$.*";
           }
           type int32 {
             range "1 .. 1000000000";
           }
         }
       }
       leaf end-from-latest-minutes {
         description "Show entries ending with specified duration from latest";
         type union {
           type string {
             pattern "<.*>|$.*";
           }
           type int32 {
             range "1 .. 1000000000";
           }
         }
       }
       leaf end-from-latest-seconds {
         type union {
           type string {
             pattern "<.*>|$.*";
           }
           type int32 {
             range "1 .. 1000000000";
           }
         }
       }
       leaf epoch-time {
         type enumeration {
           enum "epoch-time" {
             description "Show time from 1970 epoch in decimal format (ssssssssss.uuuuuu)";
           }
         }
       }
       leaf event-id-options {
         description "Event ids options to show mask (hex value 0x[A-Fa-f0-9])";
         type string {
         }
       }
       leaf latest-maximum {
         description "Maximum entries to show starting with latest";
         type union {
           type string {
             pattern "<.*>|$.*";
           }
           type int32 {
             range "1 .. 1000000000";
           }
         }
       }
       leaf min-log-type {
         description "Minimum log type to display from (number or user definition)";
         type string;
       }
       leaf max-log-type {
         description "Maximum log type to display from (number or user definition)";
         type string;
       }
       leaf no-time-display {
         type enumeration {
           enum "no-time-display" {
             description "Don't show time";
           }
         }
       }
       leaf pid {
         type enumeration {
           enum "pid-info" {
             description "Show pid information";
           }
         }
       }
       leaf remember {
         type enumeration {
           enum "remember" {
             description "Remember these display options";
           }
           enum "no-remember" {
             description "No remember these display options";
           }
         }
       }
       leaf repeat-count {
         description "Number of times to show the log";
         type union {
           type string {
             pattern "<.*>|$.*";
           }
           type int32 {
             range "1 .. 1000000";
           }
         }
       }
       leaf repeat-interval {
         description "Interval in seconds between each showing";
         type union {
           type string {
             pattern "<.*>|$.*";
           }
           type int32 {
             range "1 .. 1000000";
           }
         }
       }
       leaf start-from-latest-days {
         description "Show entries starting with specified duration from latest";
         type union {
           type string {
             pattern "<.*>|$.*";
           }
           type int32 {
             range "1 .. 1000000000";
           }
         }
       }
       leaf start-from-latest-hours {
         description "Show entries starting with specified duration from latest";
         type union {
           type string {
             pattern "<.*>|$.*";
           }
           type int32 {
             range "1 .. 1000000000";
           }
         }
       }
       leaf start-from-latest-minutes {
         description "Show entries starting with specified duration from latest";
         type union {
           type string {
             pattern "<.*>|$.*";
           }
           type int32 {
             range "1 .. 1000000000";
           }
         }
       }
       leaf start-from-latest-seconds {
         description "Show entries starting with specified duration from latest";
         type union {
           type string {
             pattern "<.*>|$.*";
           }
           type int32 {
             range "1 .. 1000000000";
           }
         }
       }
       leaf thread {
         type enumeration {
           enum "thread-info" {
             description "Show thread information";
           }
         }
       }
       leaf verbose-time {
         type enumeration {
           enum "verbose-time" {
             description "Show verbose time";
           }
         }
       }
       leaf no-entry-num {
         type enumeration {
           enum "no-entry-num" {
             description "Do not show the entry number";
           }
         }
       }
       leaf pack-event {
         type enumeration {
           enum "pack-event" {
             description "Pack event string immediately after its ID";
           }
         }
       }
     }
   }
   rpc get-shmlog-configuration {
     description "Show log configuration";
     input {
       leaf logname {
         description "Log name(s). Comma delimited list and wildcarding supported";
         type string;
         mandatory true;
       }
       leaf memory-filename {
         description "Filename that holds copy of memory to use for display";
         type string;
       }
       leaf files-path {
         description "Root path to use to find files with info";
         type string;
       }
     }
   }
   rpc get-shmlog-statistics {
     description "Show log statistics";
     input {
       leaf logname {
         description "Log name(s). Comma delimited list and wildcarding supported";
         type string;
         mandatory true;
       }
       leaf memory-filename {
         description "Filename that holds copy of memory to use for display";
         type string;
       }
       leaf files-path {
         description "Root path to use to find files with info";
         type string;
       }
     }
   }
   rpc get-shmlog-logsummary {
     description "Show summary of all logs";
     input {
       leaf memory-filename {
         description "Filename that holds copy of memory to use for display";
         type string;
       }
       leaf files-path {
         description "Root path to use to find files with info";
         type string;
       }
     }
   }
   grouping command-forwarding {
     leaf no-forwarding {
       description "No forwarding";
       type empty;
     }
     choice chassis-selector {
       case case_1 {
         leaf all-chassis {
           description "All chassis";
           type empty;
         }
       }
       case case_2 {
         leaf all-lcc {
           description "All LCC chassis";
           type empty;
         }
       }
       case case_3 {
         leaf scc {
           description "SCC";
           type empty;
         }
       }
       case case_4 {
         leaf sfc {
           description "SFC";
           type union {
             type string {
               pattern "<.*>|$.*";
             }
             type uint32;
           }
         }
       }
       case case_5 {
         leaf lcc {
           description "Specific LCC";
           type union {
             type string {
               pattern "<.*>|$.*";
             }
             type uint32;
           }
         }
       }
       case case_6 {
         leaf node {
           description "Specific node";
           type string;
         }
       }
       case case_7 {
         leaf bsys {
           description "Base system";
           type empty;
         }
       }
       case case_8 {
         leaf gnf {
           description "Specific guest network function";
           type union {
             type string {
               pattern "<.*>|$.*";
             }
             type uint32 {
               range "1 .. 10";
             }
           }
         }
       }
       case case_9 {
         leaf all-gnfs {
           description "All guest network functions";
           type empty;
         }
       }
       case case_10 {
         leaf all-system {
           description "All system (BSYS and GNFs)";
           type empty;
         }
       }
       case case_11 {
         leaf server {
           description "Specific server slot";
           type union {
             type string {
               pattern "<.*>|$.*";
             }
             type uint32 {
               range "0 .. 1";
             }
           }
         }
       }
       case case_12 {
         leaf all-servers {
           description "All servers";
           type empty;
         }
       }
       case case_13 {
         leaf vnf {
           description "Specific virtual-network-function";
           type string;
         }
       }
       case case_14 {
         leaf all-vnfs {
           description "All virtual-network-functions";
           type empty;
         }
       }
     }
     choice re-selector {
       case case_1 {
         leaf re0 {
           description "RE0";
           type empty;
         }
       }
       case case_2 {
         leaf re1 {
           description "RE1";
           type empty;
         }
       }
       case case_3 {
         leaf routing-engine {
           description "Specific routing engine";
           type enumeration {
             enum "local" {
               description "Local routing engine";
             }
             enum "other" {
               description "Other routing engine";
             }
             enum "master" {
               description "Master routing engine";
             }
             enum "backup" {
               description "Backup routing engine";
             }
             enum "both" {
               description "Both routing engines";
             }
           }
         }
       }
     }
     choice lr-selector {
       case case_1 {
         leaf logical-system {
           description "Name of logical system, or 'all'";
           type string;
         }
       }
     }
     choice tenant-selector {
       case case_1 {
         leaf tenant {
           description "Name of tenant, or 'all'";
           type string;
         }
       }
     }
     choice vc-selector {
       case case_1 {
         leaf local {
           description "Local virtual chassis member";
           type empty;
         }
       }
       case case_2 {
         leaf all-members {
           description "All virtual chassis members";
           type empty;
         }
       }
       case case_3 {
         leaf member {
           description "Specific virtual chassis member which is master";
           type union {
             type string {
               pattern "<.*>|$.*";
             }
             type uint32;
           }
         }
       }
     }
   }
 }
