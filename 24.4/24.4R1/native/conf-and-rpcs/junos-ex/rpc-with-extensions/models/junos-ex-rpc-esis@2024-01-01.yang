/*
 * Copyright (c) 2025 Juniper Networks, Inc.
 * All rights reserved.
 */
 module junos-ex-rpc-esis {
   namespace "http://yang.juniper.net/junos-ex/rpc/esis";

   prefix esis;

   import junos-common-ddl-extensions {
     prefix junos;
     revision-date 2024-01-01;
   }

   import junos-common-types {
     prefix jt;
     revision-date 2024-01-01;
   }

   organization "Juniper Networks, Inc.";

   contact "yang-support@juniper.net";

   description "Junos RPC YANG module for esis command(s)";

   revision 2024-01-01 {
     description "Junos: 24.4R1.11";
   }

   rpc get-esis-adjacency-information {
     description "Show ES-IS adjacency database";
     junos:command "show esis adjacency";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf verbosity_level {
         junos:cli-feature "nokeyword";
         default "brief";
         type enumeration {
           enum "brief" {
             description "Display brief output (default)";
           }
           enum "detail" {
             description "Display detailed output";
           }
           enum "extensive" {
             description "Display extensive output";
           }
         }
       }
       leaf instance {
         description "Name of ES-IS instance";
         type string;
       }
       leaf esis-neighbor-id {
         description "NSAP/NET of end system";
         junos:cli-feature "nokeyword";
         type string;
       }
     }
     output {
       container esis-adjacency-information {
         uses esis-adjacency-information-block;
       }
     }
   }
   rpc get-esis-interface-information {
     description "Show ES-IS interface information";
     junos:command "show esis interface";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf verbosity_level {
         junos:cli-feature "nokeyword";
         default "brief";
         type enumeration {
           enum "brief" {
             description "Display brief output (default)";
           }
           enum "detail" {
             description "Display detailed output";
           }
           enum "extensive" {
             description "Display extensive output";
           }
         }
       }
       leaf instance {
         description "Name of ES-IS instance";
         type string;
       }
       leaf interface-name {
         description "Name of interface";
         junos:cli-feature "nokeyword";
         type string;
       }
     }
     output {
       container esis-interface-information {
         uses esis-interface-information-block;
       }
     }
   }
   rpc get-esis-statistics-information {
     description "Show ES-IS performance statistics";
     junos:command "show esis statistics";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf instance {
         description "Name of ES-IS instance";
         type string;
       }
     }
     output {
       container esis-statistics-information {
         uses esis-statistics-information-block;
       }
     }
   }
   grouping command-forwarding {
     leaf no-forwarding {
       description "No forwarding";
       type empty;
     }
     choice chassis-selector {
       case case_1 {
         leaf all-chassis {
           description "All chassis";
           type empty;
         }
       }
       case case_2 {
         leaf all-lcc {
           description "All LCC chassis";
           type empty;
         }
       }
       case case_3 {
         leaf scc {
           description "SCC";
           type empty;
         }
       }
       case case_4 {
         leaf sfc {
           description "SFC";
           type union {
             type string {
               pattern "<.*>|$.*";
             }
             type uint32;
           }
         }
       }
       case case_5 {
         leaf lcc {
           description "Specific LCC";
           type union {
             type string {
               pattern "<.*>|$.*";
             }
             type uint32;
           }
         }
       }
       case case_6 {
         leaf node {
           description "Specific node";
           type string;
         }
       }
       case case_7 {
         leaf bsys {
           description "Base system";
           type empty;
         }
       }
       case case_8 {
         leaf gnf {
           description "Specific guest network function";
           type union {
             type string {
               pattern "<.*>|$.*";
             }
             type uint32 {
               range "1 .. 10";
             }
           }
         }
       }
       case case_9 {
         leaf all-gnfs {
           description "All guest network functions";
           type empty;
         }
       }
       case case_10 {
         leaf all-system {
           description "All system (BSYS and GNFs)";
           type empty;
         }
       }
       case case_11 {
         leaf server {
           description "Specific server slot";
           type union {
             type string {
               pattern "<.*>|$.*";
             }
             type uint32 {
               range "0 .. 1";
             }
           }
         }
       }
       case case_12 {
         leaf all-servers {
           description "All servers";
           type empty;
         }
       }
       case case_13 {
         leaf vnf {
           description "Specific virtual-network-function";
           type string;
         }
       }
       case case_14 {
         leaf all-vnfs {
           description "All virtual-network-functions";
           type empty;
         }
       }
     }
     choice re-selector {
       case case_1 {
         leaf re0 {
           description "RE0";
           type empty;
         }
       }
       case case_2 {
         leaf re1 {
           description "RE1";
           type empty;
         }
       }
       case case_3 {
         leaf routing-engine {
           description "Specific routing engine";
           type enumeration {
             enum "local" {
               description "Local routing engine";
             }
             enum "other" {
               description "Other routing engine";
             }
             enum "master" {
               description "Master routing engine";
             }
             enum "backup" {
               description "Backup routing engine";
             }
             enum "both" {
               description "Both routing engines";
             }
           }
         }
       }
     }
     choice lr-selector {
       case case_1 {
         leaf logical-system {
           description "Name of logical system, or 'all'";
           type string;
         }
       }
     }
     choice tenant-selector {
       case case_1 {
         leaf tenant {
           description "Name of tenant, or 'all'";
           type string;
         }
       }
     }
     choice vc-selector {
       case case_1 {
         leaf local {
           description "Local virtual chassis member";
           type empty;
         }
       }
       case case_2 {
         leaf all-members {
           description "All virtual chassis members";
           type empty;
         }
       }
       case case_3 {
         leaf member {
           description "Specific virtual chassis member which is master";
           type union {
             type string {
               pattern "<.*>|$.*";
             }
             type uint32;
           }
         }
       }
     }
   }
   grouping esis-adjacency-information-block {
     container esis-adjacency {
       leaf esis-neighbor-type {
         type string;
       }
       leaf esis-neighbor-id {
         type string;
       }
       leaf holdtime {
         type int32;
         description "Delay before timing out the adjacency (default is 180 seconds)";
       }
       leaf interface-name {
         type string;
         description "Name of interface";
       }
       list snpa {
         leaf snpa-type {
           type string;
           description "Type of SNPA";
         }
         list pfe-port-snpa {
           leaf pfe-id {
             type int32;
           }
           leaf port-id {
             type int32;
           }
         }
         list network-element-port-snpa {
           leaf port-id {
             type int32;
           }
         }
         list mstp-root-snpa {
           leaf mstp-root-id {
             type int32;
           }
         }
         list gateway-snpa {
           leaf gateway-addr {
             type jt:ipaddr;
           }
         }
         list layer2-domain-port-snpa {
           leaf port-id {
             type int32;
           }
         }
         list replication-block-snpa {
           leaf replication-block-id {
             type int32;
           }
         }
         list replication-route-snpa {
           leaf network-element-id {
             type jt:ipaddr;
           }
         }
         list layer2-multicast-port-snpa {
           leaf layer2-multicast-port-id {
             type int32;
           }
         }
         list inh-snpa {
           leaf inh-id {
             type int32;
           }
         }
       }
       leaf esis-adjacency-advertised-holdtime {
         type string;
         description "Hold time advertised by the adjacency";
       }
       list esis-adjacency-log {
         leaf esis-adjacency-when {
           type string;
           description "Time at which the transition occurred";
         }
         leaf esis-adjacency-state {
           type string;
           description "State of the adjacency";
         }
         leaf esis-adjacency-event {
           type string;
           description "Event that triggered the transition";
         }
         leaf esis-adjacency-down-reason {
           type string;
           description "Reason for the down transition event";
         }
       }
     }
   }
   grouping esis-interface-information-block {
     container esis-interface {
       leaf interface-name {
         type string;
         description "Name of interface";
       }
       leaf esis-interface-receives {
         type string;
         description "Types of hellos received on this interface - ESH and/or ISH";
       }
       leaf esis-interface-sends {
         type string;
         description "Type of hello message sent out on this interface - ESH or ISH";
       }
       leaf esis-hello-interval {
         type string;
         description "Interval between subsequent hellos (one-third of the hold time)";
       }
       leaf esis-adjacency-count {
         type int32;
         description "Number of adjacencies";
       }
       leaf holdtime {
         type int32;
         description "Delay before timing out the adjacency (default is 180 seconds)";
       }
       leaf esis-esct {
         type string;
         description "Suggested hold time for end systems (default is 180 seconds)";
       }
       leaf interface-index {
         type int32;
       }
       leaf esis-interface-state-value {
         type int32;
         description "State of ES-IS interface";
       }
       leaf esis-interface-net {
         type string;
       }
     }
   }
   grouping esis-statistics-information-block {
     list esis-pdu-statistics {
       leaf esis-pdu-type {
         type string;
         description "Type of ES-IS Protocol Data Unit";
       }
       leaf packets-received {
         type uint64;
       }
       leaf packets-processed {
         type uint64;
       }
       leaf packets-dropped {
         type uint64;
       }
       leaf packets-sent {
         type uint64;
       }
       leaf packets-retransmitted {
         type uint64;
       }
     }
     container esis-totals-information {
       leaf packets-received {
         type uint64;
       }
       leaf packets-sent {
         type uint64;
       }
     }
   }
 }
