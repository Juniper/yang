/*
 * Copyright (c) 2025 Juniper Networks, Inc.
 * All rights reserved.
 */
 module junos-ex-rpc-programmable-rpd {
   namespace "http://yang.juniper.net/junos-ex/rpc/programmable-rpd";

   prefix programmable-rpd;

   import junos-common-types {
     prefix jt;
     revision-date 2024-01-01;
   }

   organization "Juniper Networks, Inc.";

   contact "yang-support@juniper.net";

   description "Junos RPC YANG module for programmable-rpd command(s)";

   revision 2024-01-01 {
     description "Junos: 24.4R1.11";
   }

   rpc get-programmable-rpd-client-information {
     description "Show RPD Server client information";
     input {
       leaf verbosity_level {
         default "brief";
         type enumeration {
           enum "brief" {
             description "Display brief output (default)";
           }
           enum "detail" {
             description "Display detailed output";
           }
         }
       }
       leaf client-id {
         description "Name of programmable rpd client";
         type string;
       }
     }
     output {
       container programmable-rpd-client-information {
         uses programmable-rpd-client-information-block;
       }
     }
   }
   rpc get-prpd-client-rt-summary-information {
     description "Show PRPD statistics";
     input {
       leaf client-id {
         description "Name of programmable rpd client";
         type string;
       }
       leaf table {
         description "Name of the routing table";
         type string;
       }
       leaf instance {
         description "Name of the routing instance";
         type string;
       }
       leaf display-vni-data {
         description "Show vni counts";
         type empty;
       }
     }
     output {
       container prpd-client-rt-summary-information {
         uses prpd-client-rt-summary-information-block;
       }
     }
   }
   rpc get-prpd-flex-rt-stats-information {
     description "Show flex route statistics";
     input {
       leaf table {
         description "Name of the routing table";
         type string;
       }
       leaf destination {
         description "IP address of destination";
         type jt:ipprefix-optional;
       }
     }
     output {
       container prpd-flex-rt-stats-information {
         uses prpd-flex-rt-stats-information-block;
       }
     }
   }
   grouping command-forwarding {
     leaf no-forwarding {
       description "No forwarding";
       type empty;
     }
     choice chassis-selector {
       case case_1 {
         leaf all-chassis {
           description "All chassis";
           type empty;
         }
       }
       case case_2 {
         leaf all-lcc {
           description "All LCC chassis";
           type empty;
         }
       }
       case case_3 {
         leaf scc {
           description "SCC";
           type empty;
         }
       }
       case case_4 {
         leaf sfc {
           description "SFC";
           type union {
             type string {
               pattern "<.*>|$.*";
             }
             type uint32;
           }
         }
       }
       case case_5 {
         leaf lcc {
           description "Specific LCC";
           type union {
             type string {
               pattern "<.*>|$.*";
             }
             type uint32;
           }
         }
       }
       case case_6 {
         leaf node {
           description "Specific node";
           type string;
         }
       }
       case case_7 {
         leaf bsys {
           description "Base system";
           type empty;
         }
       }
       case case_8 {
         leaf gnf {
           description "Specific guest network function";
           type union {
             type string {
               pattern "<.*>|$.*";
             }
             type uint32 {
               range "1 .. 10";
             }
           }
         }
       }
       case case_9 {
         leaf all-gnfs {
           description "All guest network functions";
           type empty;
         }
       }
       case case_10 {
         leaf all-system {
           description "All system (BSYS and GNFs)";
           type empty;
         }
       }
       case case_11 {
         leaf server {
           description "Specific server slot";
           type union {
             type string {
               pattern "<.*>|$.*";
             }
             type uint32 {
               range "0 .. 1";
             }
           }
         }
       }
       case case_12 {
         leaf all-servers {
           description "All servers";
           type empty;
         }
       }
       case case_13 {
         leaf vnf {
           description "Specific virtual-network-function";
           type string;
         }
       }
       case case_14 {
         leaf all-vnfs {
           description "All virtual-network-functions";
           type empty;
         }
       }
     }
     choice re-selector {
       case case_1 {
         leaf re0 {
           description "RE0";
           type empty;
         }
       }
       case case_2 {
         leaf re1 {
           description "RE1";
           type empty;
         }
       }
       case case_3 {
         leaf routing-engine {
           description "Specific routing engine";
           type enumeration {
             enum "local" {
               description "Local routing engine";
             }
             enum "other" {
               description "Other routing engine";
             }
             enum "master" {
               description "Master routing engine";
             }
             enum "backup" {
               description "Backup routing engine";
             }
             enum "both" {
               description "Both routing engines";
             }
           }
         }
       }
     }
     choice lr-selector {
       case case_1 {
         leaf logical-system {
           description "Name of logical system, or 'all'";
           type string;
         }
       }
     }
     choice tenant-selector {
       case case_1 {
         leaf tenant {
           description "Name of tenant, or 'all'";
           type string;
         }
       }
     }
     choice vc-selector {
       case case_1 {
         leaf local {
           description "Local virtual chassis member";
           type empty;
         }
       }
       case case_2 {
         leaf all-members {
           description "All virtual chassis members";
           type empty;
         }
       }
       case case_3 {
         leaf member {
           description "Specific virtual chassis member which is master";
           type union {
             type string {
               pattern "<.*>|$.*";
             }
             type uint32;
           }
         }
       }
     }
   }
   grouping programmable-rpd-client-information-block {
     leaf global-purge-time {
       type int32;
       description "Global purge time";
     }
     list programmable-rpd-client {
       leaf client-id {
         type string;
         description "Client id";
       }
       leaf purge-time {
         type int32;
         description "Client purge time configured";
       }
       leaf client-status {
         type string;
         description "Client connection status";
       }
       leaf purge-time-remain {
         type int32;
         description "Purge time left after client disconnect";
       }
       list programmable-rpd-client-gw {
         leaf client-protocol {
           type string;
           description "Protocol registered";
         }
         leaf client-routes {
           type int32;
           description "Number of client routes";
         }
       }
       leaf numerical-client-id {
         type uint32;
         description "Numeric Client Id";
       }
       leaf client-context-id {
         type uint64;
         description "Client Context Id";
       }
       leaf group-identifier {
         type string;
         description "Group Identifier";
       }
       leaf numerical-group-id {
         type string;
         description "Numeric Group Id";
       }
       leaf election-id-higher-order {
         type uint64;
         description "Election Id Higher Order 64 bits";
       }
       leaf election-id-lower-order {
         type uint64;
         description "Election Id Lower Order 64 bits";
       }
       leaf client-role {
         type string;
         description "Primary or Non-Primary";
       }
       container session-params {
         leaf redundancy {
           type string;
           description "ALL_PRIMARY or SINGLE_PRIMARY";
         }
         leaf persistence {
           type string;
           description "DELETE or PRESERVE";
         }
         leaf acknowledgement {
           type string;
           description "RIB_ACK or RIB_AND_FIB_ACK";
         }
       }
     }
   }
   grouping prpd-client-rt-summary-information-block {
     leaf total-programmed-routes {
       type int32;
       description "Total programmed route count";
     }
     leaf total-programmed-primary-routes {
       type int32;
       description "Number of programmed primary routes";
     }
     leaf total-programmed-secondary-routes {
       type int32;
       description "Number of programmed secondary routes";
     }
     list prpd-table-rt-summary {
       leaf prpd-table-name {
         type string;
         description "Name of the routing-table";
       }
       leaf prpd-table-state {
         type string;
         description "State of the routing-table";
       }
       leaf prpd-table-primary-routes {
         type int32;
         description "Number of programmed primary routes in the table";
       }
       leaf prpd-table-secondary-routes {
         type int32;
         description "Number of programmed secondary routes in the table";
       }
     }
     list prpd-client-info {
       leaf client-id {
         type string;
         description "Client id";
       }
       list prpd-client-proto-info {
         leaf client-protocol {
           type string;
           description "Protocol registered";
         }
         leaf client-primary-routes {
           type int32;
           description "Number of primary routes programmed by the client";
         }
         list prpd-client-proto-table-info {
           leaf client-table-name {
             type string;
             description "Name of the routing-table";
           }
           leaf client-table-state {
             type string;
             description "State of the routing-table";
           }
           leaf client-table-primary-routes {
             type int32;
             description "Number of client specific programmed primary routes in the table";
           }
           leaf client-table-secondary-routes {
             type int32;
             description "Number of client specific programmed secondary routes in the table";
           }
           list prpd-vni-count-info {
             leaf prpd-vni-name {
               type string;
               description "Name of the VNI";
             }
             leaf prpd-vni-count {
               type int32;
               description "Number of client routes beloinging to this VNI";
             }
           }
         }
       }
     }
   }
   grouping prpd-flex-rt-stats-information-block {
     leaf flex-rt-table {
       type string;
       description "Table";
     }
     container flex-rt-destination {
       description "Destination Info";
       leaf flex-rt-destination-value {
         type string;
         description "Destination";
       }
     }
     container flex-rt-stats {
       description "Statistics associated with route";
       leaf flex-rt-stats-pkts-count {
         type int32;
         description "Packet count";
       }
       leaf flex-rt-stats-pps {
         type int32;
         description "Pps";
       }
       leaf flex-rt-stats-bytes-count {
         type int32;
         description "Byte count";
       }
       leaf flex-rt-stats-bps {
         type int32;
         description "Bps";
       }
     }
   }
 }
