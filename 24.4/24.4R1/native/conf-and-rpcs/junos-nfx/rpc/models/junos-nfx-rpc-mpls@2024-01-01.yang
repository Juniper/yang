/*
 * Copyright (c) 2025 Juniper Networks, Inc.
 * All rights reserved.
 */
 module junos-nfx-rpc-mpls {
   namespace "http://yang.juniper.net/junos-nfx/rpc/mpls";

   prefix mpls;

   import junos-common-types {
     prefix jt;
     revision-date 2024-01-01;
   }

   organization "Juniper Networks, Inc.";

   contact "yang-support@juniper.net";

   description "Junos RPC YANG module for mpls command(s)";

   revision 2024-01-01 {
     description "Junos: 24.4R1.11";
   }

   rpc get-egress-protection-information {
     description "Show egress-protection information";
     input {
       choice daemon-select {
         case logical-system {
           leaf logical-system {
             description "Name of logical system, or 'all'";
             type string {
             }
           }
         }
       }
       leaf verbosity_level {
         default "brief";
         type enumeration {
           enum "brief" {
             description "Display brief output (default)";
           }
           enum "detail" {
             description "Display detailed output";
           }
         }
       }
     }
     output {
       container ep-operational-information {
         uses ep-operational-information-block;
       }
     }
   }
   rpc get-mpls-admin-group-information {
     description "Show MPLS administrative groups";
     input {
       choice daemon-select {
         case logical-system {
           leaf logical-system {
             description "Name of logical system, or 'all'";
             type string {
             }
           }
         }
       }
       leaf instance {
         description "Name of routing instance";
         type string;
       }
     }
     output {
       container mpls-admin-group-information {
         uses mpls-admin-group-information-block;
       }
     }
   }
   rpc get-mpls-admin-group-extended-information {
     description "Show MPLS extended administrative groups";
     input {
       choice daemon-select {
         case logical-system {
           leaf logical-system {
             description "Name of logical system, or 'all'";
             type string {
             }
           }
         }
       }
       leaf instance {
         description "Name of routing instance";
         type string;
       }
     }
     output {
       container mpls-admin-group-extended-information {
         uses mpls-admin-group-extended-information-block;
       }
     }
   }
   rpc get-mpls-abstract-hop-membership-information {
     description "Show MPLS abstract hop membership tables";
     input {
       choice daemon-select {
         case logical-system {
           leaf logical-system {
             description "Name of logical system, or 'all'";
             type string {
             }
           }
         }
       }
       leaf instance {
         description "Name of routing instance";
         type string;
       }
       leaf abstract-hop {
         description "Name of abstract hop";
         type string;
       }
     }
     output {
       container mpls-abstract-hop-membership-information {
         uses mpls-abstract-hop-membership-information-block;
       }
     }
   }
   rpc get-mpls-cspf-information {
     description "Show Constrained Shortest Path First statistics";
     input {
       choice daemon-select {
         case logical-system {
           leaf logical-system {
             description "Name of logical system, or 'all'";
             type string {
             }
           }
         }
       }
       leaf instance {
         description "Name of routing instance";
         type string;
       }
     }
     output {
       container mpls-cspf-information {
         uses mpls-cspf-information-block;
       }
     }
   }
   rpc get-mpls-path-information {
     description "Show configured named paths";
     input {
       choice daemon-select {
         case logical-system {
           leaf logical-system {
             description "Name of logical system, or 'all'";
             type string {
             }
           }
         }
       }
       leaf instance {
         description "Name of routing instance";
         type string;
       }
       leaf path {
         description "Name of label-switched path";
         type string;
       }
     }
     output {
       container mpls-path-information {
         uses mpls-path-information-block;
       }
     }
   }
   rpc get-mpls-diffserv-te-information {
     description "Show MPLS Differentiated Services traffic engineering global properties";
     input {
       choice daemon-select {
         case logical-system {
           leaf logical-system {
             description "Name of logical system, or 'all'";
             type string {
             }
           }
         }
       }
       leaf instance {
         description "Name of routing instance";
         type string;
       }
     }
     output {
       container mpls-diffserv-te-information {
         uses mpls-diffserv-te-information-block;
       }
     }
   }
   rpc get-mpls-lsp-information {
     description "Show configured label-switched paths";
     input {
       choice daemon-select {
         case logical-system {
           leaf logical-system {
             description "Name of logical system, or 'all'";
             type string {
             }
           }
         }
       }
       leaf instance {
         description "Name of routing instance";
         type string;
       }
       leaf lsp-type {
         type enumeration {
           enum "ingress" {
             description "Display LSPs originating at this router";
           }
           enum "egress" {
             description "Display LSPs ending at this router";
           }
           enum "transit" {
             description "Display LSPs transiting this router";
           }
         }
       }
       leaf level {
         default "brief";
         type enumeration {
           enum "terse" {
             description "Display terse output";
           }
           enum "brief" {
             description "Display brief output (default)";
           }
           enum "detail" {
             description "Display detailed output";
           }
           enum "extensive" {
             description "Display extensive output";
           }
           enum "descriptions" {
             description "Display LSP description strings";
           }
         }
       }
       leaf lsp-state {
         type enumeration {
           enum "up" {
             description "Display active LSPs";
           }
           enum "down" {
             description "Display inactive LSPs";
           }
         }
       }
       leaf lsp-direction {
         type enumeration {
           enum "unidirectional" {
             description "Display unidirectional LSPs";
           }
           enum "bidirectional" {
             description "Display bidirectional LSPs";
           }
           enum "p2mp" {
             description "Display point-to-multipoint LSPs";
           }
           enum "externally-controlled" {
             description "Display externally controlled LSPs";
           }
         }
       }
       leaf lsp-provisioning {
         type enumeration {
           enum "externally-provisioned" {
             description "Display externally provisioned LSPs";
           }
           enum "locally-provisioned" {
             description "Display locally provisioned LSPs";
           }
         }
       }
       leaf lsp-stat {
         type enumeration {
           enum "statistics" {
             description "Display packet statistics for LSPs";
           }
           enum "reverse-statistics" {
             description "Display packet statistics for reverse direction of LSPs";
           }
         }
       }
       leaf bypass-lsp {
         type enumeration {
           enum "bypass" {
             description "Display LSPs used for protecting other LSPs";
           }
         }
       }
       leaf activeroutes {
         type enumeration {
           enum "count-active-routes" {
             description "Show active routes for LSPs";
           }
         }
       }
       leaf mbb-state {
         type enumeration {
           enum "make-before-break" {
             description "Display LSPs undergoing make-before-break";
           }
         }
       }
       leaf regex {
         description "Regular expression for LSP names to match";
         type string;
       }
     }
     output {
       container mpls-lsp-information {
         uses mpls-lsp-information-block;
       }
     }
   }
   rpc get-mpls-lsp-defaults-information {
     description "Display LSP defaults";
     input {
       choice daemon-select {
         case logical-system {
           leaf logical-system {
             description "Name of logical system, or 'all'";
             type string {
             }
           }
         }
       }
       leaf instance {
         description "Name of routing instance";
         type string;
       }
     }
     output {
       container mpls-lsp-defaults-information {
         uses mpls-lsp-defaults-information-block;
       }
     }
   }
   rpc get-mpls-lsp-autobandwidth {
     description "Display autobandwidth statistics for LSPs";
     input {
       choice daemon-select {
         case logical-system {
           leaf logical-system {
             description "Name of logical system, or 'all'";
             type string {
             }
           }
         }
       }
       leaf level {
         default "brief";
         type enumeration {
           enum "brief" {
             description "Display brief output (default)";
           }
           enum "detail" {
             description "Display detailed output";
           }
           enum "extensive" {
             description "Display extensive output";
           }
         }
       }
       leaf regex {
         description "Regular expression for LSP names to match";
         type string;
       }
     }
     output {
       container mpls-lsp-information {
         uses mpls-lsp-information-block;
       }
     }
   }
   rpc get-mpls-lsp-abstract-computation {
     description "Display abstract computation preprocessing for LSPs";
     input {
       choice daemon-select {
         case logical-system {
           leaf logical-system {
             description "Name of logical system, or 'all'";
             type string {
             }
           }
         }
       }
       leaf level {
         default "brief";
         type enumeration {
           enum "brief" {
             description "Display brief output (default)";
           }
           enum "detail" {
             description "Display detailed output";
           }
           enum "extensive" {
             description "Display extensive output";
           }
         }
       }
       leaf regex {
         description "Regular expression for LSP names to match";
         type string;
       }
     }
     output {
       container mpls-lsp-information {
         uses mpls-lsp-information-block;
       }
     }
   }
   rpc get-mpls-container-lsp-information {
     description "Show configured container-label-switched paths";
     input {
       choice daemon-select {
         case logical-system {
           leaf logical-system {
             description "Name of logical system, or 'all'";
             type string {
             }
           }
         }
       }
       leaf instance {
         description "Name of routing instance";
         type string;
       }
       leaf lsp-type {
         type enumeration {
           enum "ingress" {
             description "Display LSPs originating at this router";
           }
           enum "egress" {
             description "Display LSPs ending at this router";
           }
           enum "transit" {
             description "Display LSPs transiting this router";
           }
         }
       }
       leaf level {
         default "brief";
         type enumeration {
           enum "terse" {
             description "Display terse output";
           }
           enum "brief" {
             description "Display brief output (default)";
           }
           enum "detail" {
             description "Display detailed output";
           }
           enum "extensive" {
             description "Display extensive output";
           }
           enum "descriptions" {
             description "Display LSP description strings";
           }
         }
       }
       leaf lsp-state {
         type enumeration {
           enum "up" {
             description "Display active LSPs";
           }
           enum "down" {
             description "Display inactive LSPs";
           }
         }
       }
       leaf lsp-direction {
         type enumeration {
           enum "unidirectional" {
             description "Display unidirectional container LSPs";
           }
         }
       }
       leaf lsp-stat {
         type enumeration {
           enum "statistics" {
             description "Display packet statistics for LSPs";
           }
         }
       }
       leaf activeroutes {
         type enumeration {
           enum "count-active-routes" {
             description "Show active routes for LSPs";
           }
         }
       }
       leaf regex {
         description "Regular expression for LSP names to match";
         type string;
       }
     }
     output {
       container mpls-container-lsp-information {
         uses mpls-container-lsp-information-block;
       }
     }
   }
   rpc get-mpls-container-lsp-defaults-information {
     description "Display container LSP defaults";
     input {
       choice daemon-select {
         case logical-system {
           leaf logical-system {
             description "Name of logical system, or 'all'";
             type string {
             }
           }
         }
       }
     }
     output {
       container mpls-container-lsp-defaults-information {
         uses mpls-container-lsp-defaults-information-block;
       }
     }
   }
   rpc get-mpls-call-admission-control-information {
     description "Show CAC information for MPLS LSPs";
     input {
       choice daemon-select {
         case logical-system {
           leaf logical-system {
             description "Name of logical system, or 'all'";
             type string {
             }
           }
         }
       }
       leaf lsp-name {
         description "Name of LSP";
         type string {
           length "1 .. 64";
         }
       }
       leaf instance {
         description "Name of routing instance";
         type string;
       }
     }
     output {
       container mpls-call-admission-control-information {
         uses mpls-call-admission-control-information-block;
       }
     }
   }
   rpc get-mpls-context-identifier-information {
     description "Show configured egress protection context identifiers";
     input {
       choice daemon-select {
         case logical-system {
           leaf logical-system {
             description "Name of logical system, or 'all'";
             type string {
             }
           }
         }
       }
       leaf instance {
         description "Name of routing instance";
         type string;
       }
       leaf context-type {
         type enumeration {
           enum "primary" {
             description "Display primary context identifier(s)";
           }
           enum "protector" {
             description "Display protector context identifier(s)";
           }
         }
       }
       leaf level {
         default "brief";
         type enumeration {
           enum "brief" {
             description "Display brief output (default)";
           }
           enum "detail" {
             description "Display detailed output";
           }
         }
       }
       leaf id {
         description "Identifier";
         type string;
       }
     }
     output {
       container mpls-context-identifier-information {
         uses mpls-context-identifier-information-block;
       }
     }
   }
   rpc get-mpls-srlg-information {
     description "Show MPLS SRLG";
     input {
       choice daemon-select {
         case logical-system {
           leaf logical-system {
             description "Name of logical system, or 'all'";
             type string {
             }
           }
         }
       }
       leaf instance {
         description "Name of routing instance";
         type string;
       }
     }
     output {
       container mpls-srlg-information {
         uses mpls-srlg-information-block;
       }
     }
   }
   rpc get-mpls-association-path-information {
     description "Display all LSPs that share same path";
     input {
       choice daemon-select {
         case logical-system {
           leaf logical-system {
             description "Name of logical system, or 'all'";
             type string {
             }
           }
         }
       }
       leaf path-name {
         description "Name of path";
         type string;
         mandatory true;
       }
     }
     output {
       container mpls-association-path {
         uses mpls-association-path-block;
       }
     }
   }
   rpc get-mpls-association-iif-information {
     description "Display all LSPs that share same incoming interface";
     input {
       choice daemon-select {
         case logical-system {
           leaf logical-system {
             description "Name of logical system, or 'all'";
             type string {
             }
           }
         }
       }
       leaf interface-name {
         description "Name of incoming interface";
         type string;
         mandatory true;
       }
     }
     output {
       container mpls-association-iif {
         uses mpls-association-iif-block;
       }
     }
   }
   rpc get-mpls-association-oif-information {
     description "Display all LSPs that share same outgoing interface";
     input {
       choice daemon-select {
         case logical-system {
           leaf logical-system {
             description "Name of logical system, or 'all'";
             type string {
             }
           }
         }
       }
       leaf interface-name {
         description "Name of outgoing interface";
         type string;
         mandatory true;
       }
     }
     output {
       container mpls-association-oif {
         uses mpls-association-oif-block;
       }
     }
   }
   rpc get-mpls-correlation-nexthop-information {
     description "Display MPLS LSP info for the owner of this nexthop";
     input {
       choice daemon-select {
         case logical-system {
           leaf logical-system {
             description "Name of logical system, or 'all'";
             type string {
             }
           }
         }
       }
       leaf nhid {
         description "NH-ID";
         type union {
           type int32;
           type string {
             pattern "<.*>|$.*";
           }
         }
         mandatory true;
       }
       leaf level {
         default "brief";
         type enumeration {
           enum "terse" {
             description "Display terse output";
           }
           enum "brief" {
             description "Display brief output (default)";
           }
           enum "detail" {
             description "Display detailed output";
           }
           enum "extensive" {
             description "Display extensive output";
           }
           enum "descriptions" {
             description "Display LSP description strings";
           }
         }
       }
     }
     output {
       container mpls-correlation-nhid {
         uses mpls-correlation-nhid-block;
       }
     }
   }
   rpc get-mpls-correlation-label-information {
     description "Display MPLS LSP info for the owner of this label";
     input {
       choice daemon-select {
         case logical-system {
           leaf logical-system {
             description "Name of logical system, or 'all'";
             type string {
             }
           }
         }
       }
       leaf nhid {
         description "Label value";
         type union {
           type int32;
           type string {
             pattern "<.*>|$.*";
           }
         }
         mandatory true;
       }
       leaf level {
         default "brief";
         type enumeration {
           enum "terse" {
             description "Display terse output";
           }
           enum "brief" {
             description "Display brief output (default)";
           }
           enum "detail" {
             description "Display detailed output";
           }
           enum "extensive" {
             description "Display extensive output";
           }
           enum "descriptions" {
             description "Display LSP description strings";
           }
         }
       }
     }
     output {
       container mpls-correlation-label {
         uses mpls-correlation-label-block;
       }
     }
   }
   rpc get-mpls-interface-information {
     description "Show MPLS interfaces";
     input {
       choice daemon-select {
         case logical-system {
           leaf logical-system {
             description "Name of logical system, or 'all'";
             type string {
             }
           }
         }
       }
       leaf verbosity_level {
         default "brief";
         type enumeration {
           enum "brief" {
             description "Display brief output (default)";
           }
           enum "detail" {
             description "Display detailed output";
           }
         }
       }
       leaf instance {
         description "Name of routing instance";
         type string;
       }
     }
     output {
       container mpls-interface-information {
         uses mpls-interface-information-block;
       }
     }
   }
   rpc mpls-label-space {
     description "Mpls label space";
     input {
       choice daemon-select {
         case logical-system {
           leaf logical-system {
             description "Name of logical system, or 'all'";
             type string {
             }
           }
         }
       }
     }
     output {
       choice output_c {
         case output-tag {
           leaf output {
             type string;
           }
         }
         case multichassis-tag {
           anyxml multi-routing-engine-results;
         }
       }
     }
   }
   rpc mpls-label-history {
     description "Show MPLS label history";
     input {
       choice daemon-select {
         case logical-system {
           leaf logical-system {
             description "Name of logical system, or 'all'";
             type string {
             }
           }
         }
       }
     }
     output {
       container mpls-label-history {
         uses mpls-label-history-block;
       }
     }
   }
   rpc mpls-label-history-range {
     description "Show MPLS label history in range";
     input {
       choice daemon-select {
         case logical-system {
           leaf logical-system {
             description "Name of logical system, or 'all'";
             type string {
             }
           }
         }
       }
       leaf label-history-range-start {
         description "Value of the start of label-range";
         type union {
           type string {
             pattern "<.*>|$.*";
           }
           type uint32 {
             range "1 .. 1048575";
           }
         }
         mandatory true;
       }
       leaf label-history-range-end {
         description "Value of the end of label-range";
         type union {
           type string {
             pattern "<.*>|$.*";
           }
           type uint32 {
             range "1 .. 1048575";
           }
         }
         mandatory true;
       }
     }
   }
   rpc mpls-history-label-value {
     description "MPLS label value";
     input {
       choice daemon-select {
         case logical-system {
           leaf logical-system {
             description "Name of logical system, or 'all'";
             type string {
             }
           }
         }
       }
       leaf label-history-value {
         description "Value of the label";
         type union {
           type string {
             pattern "<.*>|$.*";
           }
           type uint32 {
             range "1 .. 1048575";
           }
         }
         mandatory true;
       }
     }
     output {
       container mpls-label-value {
         uses mpls-label-value-block;
       }
     }
   }
   rpc mpls-label-space-usage {
     description "Show MPLS label space usage statistics";
     input {
       choice daemon-select {
         case logical-system {
           leaf logical-system {
             description "Name of logical system, or 'all'";
             type string {
             }
           }
         }
       }
     }
     output {
       container mpls-label-usage {
         uses mpls-label-usage-block;
       }
     }
   }
   rpc mpls-label-space-usage-range {
     description "Show MPLS label space usage statistics in range";
     input {
       choice daemon-select {
         case logical-system {
           leaf logical-system {
             description "Name of logical system, or 'all'";
             type string {
             }
           }
         }
       }
       leaf label-range-start {
         description "Value of the start of label-range";
         type union {
           type string {
             pattern "<.*>|$.*";
           }
           type uint32 {
             range "1 .. 1048575";
           }
         }
         mandatory true;
       }
       leaf label-range-end {
         description "Value of the end of label-range";
         type union {
           type string {
             pattern "<.*>|$.*";
           }
           type uint32 {
             range "1 .. 1048575";
           }
         }
         mandatory true;
       }
     }
     output {
       container mpls-label-usage {
         uses mpls-label-usage-block;
       }
     }
   }
   rpc mpls-usage-label-value {
     description "MPLS label value";
     input {
       choice daemon-select {
         case logical-system {
           leaf logical-system {
             description "Name of logical system, or 'all'";
             type string {
             }
           }
         }
       }
       leaf label-value {
         description "Value of the label";
         type union {
           type string {
             pattern "<.*>|$.*";
           }
           type uint32 {
             range "1 .. 1048575";
           }
         }
         mandatory true;
       }
     }
     output {
       container mpls-label-value {
         uses mpls-label-value-block;
       }
     }
   }
   rpc get-mpls-tunnel-manager-statistics-information {
     description "Show Multiprotocol Label Switching manager statistics";
     input {
       choice daemon-select {
         case logical-system {
           leaf logical-system {
             description "Name of logical system, or 'all'";
             type string {
             }
           }
         }
       }
       leaf instance {
         description "Name of routing instance";
         type string;
       }
     }
     output {
       container mpls-tunnel-manager-statistics-information {
         uses mpls-tunnel-manager-statistics-information-block;
       }
     }
   }
   rpc get-mpls-static-lsp-information {
     description "Show configured static label-switched paths";
     input {
       choice daemon-select {
         case logical-system {
           leaf logical-system {
             description "Name of logical system, or 'all'";
             type string {
             }
           }
         }
       }
       leaf instance {
         description "Name of routing instance";
         type string;
       }
       leaf lsp-type {
         type enumeration {
           enum "bypass" {
             description "Display bypass LSPs originating at this router";
           }
           enum "ingress" {
             description "Display LSPs originating at this router";
           }
           enum "transit" {
             description "Display LSPs transiting this router";
           }
           enum "segment" {
             description "Display segment identifier (SID) labels";
           }
         }
       }
       leaf level {
         default "brief";
         type enumeration {
           enum "terse" {
             description "Display terse output";
           }
           enum "brief" {
             description "Display brief output (default)";
           }
           enum "detail" {
             description "Display detailed output";
           }
           enum "extensive" {
             description "Display extensive output";
           }
           enum "descriptions" {
             description "Display LSP description strings";
           }
           enum "statistics" {
             description "Display packet statistics for LSPs";
           }
         }
       }
       leaf lsp-state {
         type enumeration {
           enum "up" {
             description "Display active LSPs";
           }
           enum "down" {
             description "Display inactive LSPs";
           }
         }
       }
       leaf regex {
         description "Regular expression for LSP names to match";
         type string;
       }
     }
     output {
       container mpls-static-lsp-information {
         uses mpls-static-lsp-information-block;
       }
     }
   }
   rpc get-mpls-traceroute-database-ldp {
     description "Show FECs";
     input {
       choice daemon-select {
         case logical-system {
           leaf logical-system {
             description "Name of logical system, or 'all'";
             type string {
             }
           }
         }
       }
       leaf fec {
         description "IP address and optional prefix length of FEC";
         type jt:ipprefix;
       }
       leaf detail {
         description "Display detailed output";
         type empty;
       }
       leaf no-resolve {
         description "Don't attempt to print addresses symbolically";
         type empty;
       }
       leaf routing-instance {
         description "Name of routing instance, or 'all'";
         type string {
         }
       }
     }
   }
   grouping command-forwarding {
     choice chassis-selector {
       case case_1 {
         leaf all-chassis {
           description "All chassis";
           type empty;
         }
       }
       case case_2 {
         leaf all-lcc {
           description "All LCC chassis";
           type empty;
         }
       }
       case case_3 {
         leaf scc {
           description "SCC";
           type empty;
         }
       }
       case case_4 {
         leaf sfc {
           description "SFC";
           type union {
             type string {
               pattern "<.*>|$.*";
             }
             type uint32;
           }
         }
       }
       case case_5 {
         leaf lcc {
           description "Specific LCC";
           type union {
             type string {
               pattern "<.*>|$.*";
             }
             type uint32;
           }
         }
       }
       case case_6 {
         leaf node {
           description "Specific node";
           type string;
         }
       }
       case case_7 {
         leaf bsys {
           description "Base system";
           type empty;
         }
       }
       case case_8 {
         leaf gnf {
           description "Specific guest network function";
           type union {
             type string {
               pattern "<.*>|$.*";
             }
             type uint32 {
               range "1 .. 10";
             }
           }
         }
       }
       case case_9 {
         leaf all-gnfs {
           description "All guest network functions";
           type empty;
         }
       }
       case case_10 {
         leaf all-system {
           description "All system (BSYS and GNFs)";
           type empty;
         }
       }
       case case_11 {
         leaf server {
           description "Specific server slot";
           type union {
             type string {
               pattern "<.*>|$.*";
             }
             type uint32 {
               range "0 .. 1";
             }
           }
         }
       }
       case case_12 {
         leaf all-servers {
           description "All servers";
           type empty;
         }
       }
       case case_13 {
         leaf vnf {
           description "Specific virtual-network-function";
           type string;
         }
       }
       case case_14 {
         leaf all-vnfs {
           description "All virtual-network-functions";
           type empty;
         }
       }
     }
     choice re-selector {
       case case_1 {
         leaf re0 {
           description "RE0";
           type empty;
         }
       }
       case case_2 {
         leaf re1 {
           description "RE1";
           type empty;
         }
       }
       case case_3 {
         leaf routing-engine {
           description "Specific routing engine";
           type enumeration {
             enum "local" {
               description "Local routing engine";
             }
             enum "other" {
               description "Other routing engine";
             }
             enum "master" {
               description "Master routing engine";
             }
             enum "backup" {
               description "Backup routing engine";
             }
             enum "both" {
               description "Both routing engines";
             }
           }
         }
       }
     }
     choice lr-selector {
       case case_1 {
         leaf logical-system {
           description "Name of logical system, or 'all'";
           type string;
         }
       }
     }
     choice tenant-selector {
       case case_1 {
         leaf tenant {
           description "Name of tenant, or 'all'";
           type string;
         }
       }
     }
     choice vc-selector {
       case case_1 {
         leaf local {
           description "Local virtual chassis member";
           type empty;
         }
       }
       case case_2 {
         leaf all-members {
           description "All virtual chassis members";
           type empty;
         }
       }
       case case_3 {
         leaf member {
           description "Specific virtual chassis member which is master";
           type union {
             type string {
               pattern "<.*>|$.*";
             }
             type uint32;
           }
         }
       }
     }
   }
   grouping ep-operational-information-block {
     container egress-protection {
       leaf-list ep-backup-rib-name {
         type string;
         description "Instance backup RIB";
       }
       leaf-list ep-cid {
         type jt:ipaddr;
         description "Context-ID";
       }
       leaf-list ep-route-cnt {
         type int32;
         description "Protection requrested routes";
       }
       leaf ep-backup-link {
         type string;
         description "Vt interface";
       }
       leaf ep-backup-table-nh {
         type string;
         description "Enhanced table nexthop";
       }
       leaf-list ep-instance-route-targets {
         type string;
         description "Instance route targets";
       }
       container nlri-egress-protection {
         leaf nlri-type {
           type string;
           description "Type of NLRI being limited";
         }
         leaf bgp-context-id {
           type jt:ipaddr;
         }
         leaf bgp-import-policy {
           type string;
         }
       }
       list ep-backup-table {
         leaf-list ep-backup-rib-name {
           type string;
           description "Instance backup RIB";
         }
         leaf ep-backup-link {
           type string;
           description "Vt interface";
         }
         leaf ep-backup-rib-id {
           type int32;
           description "RIB Identifier";
         }
         leaf ep-backup-kern-id {
           type int32;
           description "FIB Identifier";
         }
         leaf ep-backup-table-nh {
           type string;
           description "Enhanced table nexthop";
         }
         leaf-list ep-instance-route-targets {
           type string;
           description "Instance route targets";
         }
         leaf ep-backup-instance {
           type string;
         }
         leaf ep-backup-context {
           type string;
           description "Instance backup context";
         }
       }
       list ep-instance-table {
         leaf ep-instance-name {
           type string;
         }
         leaf ep-instance-type {
           type string;
           description "Instance type";
         }
         leaf ep-instance-protection-type {
           type string;
           description "Instance request protected";
         }
         leaf ep-instance-context-id {
           type jt:ipaddr;
           description "Context-id";
         }
         leaf-list ep-backup-rib-name {
           type string;
           description "Instance backup RIB";
         }
       }
     }
     list ep-instance-table {
       leaf ep-instance-name {
         type string;
       }
       leaf ep-instance-type {
         type string;
         description "Instance type";
       }
       leaf ep-instance-protection-type {
         type string;
         description "Instance request protected";
       }
       leaf ep-instance-context-id {
         type jt:ipaddr;
         description "Context-id";
       }
       leaf-list ep-backup-rib-name {
         type string;
         description "Instance backup RIB";
       }
     }
     list ep-backup-table {
       leaf ep-backup-table-nh {
         type string;
         description "Enhanced table nexthop";
       }
       leaf-list ep-instance-route-targets {
         type string;
         description "Instance route targets";
       }
       leaf ep-backup-instance {
         type string;
       }
       leaf ep-backup-context {
         type string;
         description "Instance backup context";
       }
       leaf-list ep-backup-rib-name {
         type string;
         description "Instance backup RIB";
       }
       leaf ep-backup-link {
         type string;
         description "Vt interface";
       }
       leaf ep-backup-rib-id {
         type int32;
         description "RIB Identifier";
       }
       leaf ep-backup-kern-id {
         type int32;
         description "FIB Identifier";
       }
     }
   }
   grouping mpls-admin-group-information-block {
     container mpls-admin-group {
       leaf-list admin-group-name {
         type string;
         description "Name of the admin group";
       }
       leaf index {
         type int32;
       }
     }
   }
   grouping mpls-admin-group-extended-information-block {
     container mpls-admin-group-extended {
       leaf-list admin-group-name {
         type string;
         description "Name of the admin group";
       }
       leaf admin-group-index {
         type uint32;
       }
       leaf range {
         type string;
       }
     }
   }
   grouping mpls-abstract-hop-membership-information-block {
     list mpls-abstract-hop-membership {
       leaf-list abstract-hop-name {
         type string;
       }
       list mpls-abstract-hop-credibility-table {
         container mpls-abstract-hop-credibility-info {
           leaf abstract-hop-credibility {
             type int32;
           }
           list mpls-abstract-hop-member-table {
             leaf member-address {
               type jt:ipaddr;
             }
           }
         }
       }
     }
   }
   grouping mpls-cspf-information-block {
     container mpls-cspf {
       leaf mpls-cspf.heading {
         type string;
       }
       container cspf-queue {
         description "CSPF queue statistics";
         leaf current {
           type int32;
         }
         leaf maximum {
           type int32;
         }
         leaf dequeued {
           type int32;
         }
       }
       container cspf-paths {
         description "CSPF path computations statistics";
         leaf total-paths {
           type int32;
         }
         leaf successful {
           type int32;
         }
         leaf no-route {
           type int32;
         }
         leaf sys-error {
           type int32;
         }
         leaf cspfs {
           type int32;
         }
       }
       container cspf-timing {
         description "CSPF timing statistics";
         leaf total-time {
           type string;
         }
         leaf cspf-time {
           type string;
         }
         leaf average-time {
           type string;
         }
         leaf rpd-time {
           type string;
         }
       }
     }
   }
   grouping mpls-path-information-block {
     list mpls-path {
       leaf name {
         type string;
       }
       leaf address {
         type jt:ipaddr;
       }
       leaf path-type {
         type string;
       }
       leaf telink-id {
         type int32;
         description "Link identifier of unnumbered link";
       }
       leaf is-abstract-hop {
         type string;
         description "Indicates if the hop is an abstract hop or a real hop";
       }
     }
   }
   grouping mpls-diffserv-te-information-block {
     leaf bandwidth-model {
       type string;
       description "Bandwidth model in use";
     }
     container te-class-map {
       leaf te-class {
         type string;
         description "TE class";
       }
       leaf traffic-class {
         type string;
         description "Traffic class";
       }
       leaf te-prio {
         type int32;
         description "Priority associated with a particular traffic class";
       }
     }
   }
   grouping mpls-lsp-information-block {
     list rsvp-session-data {
       leaf session-type {
         type string;
         description "Type of session with respect to this router";
       }
       leaf count {
         type int32;
       }
       leaf detours {
         type int32;
         description "Number of detour sessions";
       }
       leaf display-count {
         type int32;
         description "Number of sessions displayed";
       }
       leaf up-count {
         type int32;
         description "Number of sessions in up state";
       }
       leaf down-count {
         type int32;
         description "Number of sessions in down state";
       }
       list rsvp-session {
         description "Single RSVP session";
         leaf destination-address {
           type jt:ipaddr;
           description "Session destination address";
         }
         leaf source-address {
           type jt:ipaddr;
         }
         leaf lsp-state {
           type string;
           description "State of an LSP";
         }
         leaf route-count {
           type int32;
           description "Number of active routes";
         }
         leaf rsb-count {
           type int32;
           description "Number of RSBs";
         }
         leaf resv-style {
           type string;
         }
         leaf label-in {
           type string;
           description "Incoming label";
         }
         leaf label-out {
           type string;
           description "Outgoing label";
         }
         leaf name {
           type string;
         }
         leaf bidirectional {
           type empty;
           description "LSP is bidirectional";
         }
         leaf associated-bidirectional {
           type empty;
           description "LSP is associated-bidirectional";
         }
         leaf entropy-label {
           type string;
           description "Entropy label";
         }
         leaf p2mp-self-id {
           type string;
           description "Statistics identifier for RSVP P2MP path state control block";
         }
         container rsvp-lp-bw-optimize-info {
           leaf rsvp-lp-bw-optimize-info.heading {
             type string;
           }
           leaf rsvp-lp-path-avail-bw {
             type string;
             description "Bandwidth available on the bypass path";
           }
           leaf rsvp-lp-optimize-interval {
             type int32;
             description "Optimization interval for the bypass";
           }
         }
         container packet-information {
           leaf packet-information.heading {
             type string;
             description "RSVP packets sent or received per session";
           }
           leaf previous-hop {
             type jt:ipaddr;
             description "Previous-hop address";
           }
           leaf next-hop {
             type jt:ipaddr;
             description "Next-hop address";
           }
           leaf interface-name {
             type string;
             description "Name of interface";
           }
           leaf count {
             type int32;
           }
           leaf notify-destination {
             type jt:ipaddr;
             description "Notify address";
           }
           leaf entropy-label {
             type string;
             description "Entropy label";
           }
           leaf in-message-handle {
             type string;
             description "RSVP I/O handle for incoming message";
           }
           leaf in-message-id {
             type uint32;
             description "Incoming Message ID";
           }
           leaf in-epoch {
             type uint32;
             description "Incoming Epoch";
           }
           leaf out-message-state {
             type string;
             description "RSVP I/O state for outgoing message";
           }
           leaf out-message-id {
             type uint32;
             description "Outgoing Message ID";
           }
           leaf out-epoch {
             type uint32;
             description "Outgoing Epoch";
           }
         }
         container explicit-route {
           leaf explicit-route.heading {
             type string;
             description "Explicit Route Object (ERO)";
           }
           container explicit-route-element {
             leaf address {
               type jt:ipaddr;
             }
             leaf explicit-route-type {
               type string;
             }
             leaf telink-id {
               type int32;
               description "Link identifier of unnumbered link";
             }
           }
         }
         container rsvp-telink {
           leaf static-bandwidth-bps {
             type uint64;
             description "Static bandwidth capacity of the link in bits per second";
           }
           leaf available-bandwidth-bps {
             type uint64;
             description "Amount of bandwidth available for reservations in bits per second";
           }
           leaf max-available-bandwidth-bps {
             type uint64;
             description "Maximum amount of bandwidth available for reservations, including the subscription factor in bits per second";
           }
           leaf static-bc-bandwidth-bps {
             type uint64;
             description "Static bandwidth capacity for a bandwidth constraint in bits per second";
           }
           leaf total-reserved-bandwidth-bps {
             type uint64;
             description "Total amount of bandwidth currently reserved in bits per second";
           }
           leaf ct-bw0 {
             type string;
           }
           leaf ct-bw0-bps {
             type uint64;
           }
           leaf ct-bw1 {
             type string;
           }
           leaf ct-bw1-bps {
             type uint64;
           }
           leaf ct-bw2 {
             type string;
           }
           leaf ct-bw2-bps {
             type uint64;
           }
           leaf ct-bw3 {
             type string;
           }
           leaf ct-bw3-bps {
             type uint64;
           }
           leaf ct-bw4 {
             type string;
           }
           leaf ct-bw4-bps {
             type uint64;
           }
           leaf ct-bw5 {
             type string;
           }
           leaf ct-bw5-bps {
             type uint64;
           }
           leaf ct-bw6 {
             type string;
           }
           leaf ct-bw6-bps {
             type uint64;
           }
           leaf ct-bw7 {
             type string;
           }
           leaf ct-bw7-bps {
             type uint64;
           }
           leaf high-watermark-bps {
             type uint64;
             description "Maximum bandwidth that was ever reserved in bps";
           }
           leaf update-threshold-value-bps {
             type uint64;
             description "Change in reserved bandwidth to trigger IGP update in bits per second";
           }
           leaf update-threshold-max-reservable-bps {
             type uint64;
             description "Change in non-rsvp bandwidth to trigger IGP update in bits per second";
           }
           container priority-subscription {
             leaf priority-subscription.heading {
               type string;
             }
             list priority-subscription-pair {
               leaf priority-value {
                 type int32;
                 description "Priority value corresponding to bandwidth subscription reserved";
               }
               leaf priority-subscription-percent {
                 type int32;
                 description "Percentage of link capacity available for specific priority";
               }
             }
           }
           list reserved-bandwidth {
             leaf total-reserved-bandwidth-bps {
               type uint64;
               description "Total amount of bandwidth currently reserved in bits per second";
             }
           }
           list reserved-ct-bandwidth {
             leaf ct-bw0 {
               type string;
             }
             leaf ct-bw1 {
               type string;
             }
             leaf ct-bw2 {
               type string;
             }
             leaf ct-bw3 {
               type string;
             }
             leaf ct-bw4 {
               type string;
             }
             leaf ct-bw5 {
               type string;
             }
             leaf ct-bw6 {
               type string;
             }
             leaf ct-bw7 {
               type string;
             }
             leaf ct-class {
               type int32;
               description "Class type (0..7)";
             }
             leaf ct-bw0-bps {
               type uint64;
             }
             leaf ct-bw1-bps {
               type uint64;
             }
             leaf ct-bw2-bps {
               type uint64;
             }
             leaf ct-bw3-bps {
               type uint64;
             }
             leaf ct-bw4-bps {
               type uint64;
             }
             leaf ct-bw5-bps {
               type uint64;
             }
             leaf ct-bw6-bps {
               type uint64;
             }
             leaf ct-bw7-bps {
               type uint64;
             }
           }
           list detour-bandwidth {
             leaf total-reserved-bandwidth-bps {
               type uint64;
               description "Total amount of bandwidth currently reserved in bits per second";
             }
           }
           list overbooked-bandwidth {
             leaf total-reserved-bandwidth-bps {
               type uint64;
               description "Total amount of bandwidth currently reserved in bits per second";
             }
           }
           list overbooked-ct-bandwidth {
             leaf ct-bw0-bps {
               type uint64;
             }
             leaf ct-bw1-bps {
               type uint64;
             }
             leaf ct-bw2-bps {
               type uint64;
             }
             leaf ct-bw3-bps {
               type uint64;
             }
             leaf ct-bw4-bps {
               type uint64;
             }
             leaf ct-bw5-bps {
               type uint64;
             }
             leaf ct-bw6-bps {
               type uint64;
             }
             leaf ct-bw7-bps {
               type uint64;
             }
           }
           leaf active-reservation {
             type int32;
             description "Number of active reservations";
           }
           leaf preemption-count {
             type int32;
             description "Number of preemptions that occurred on an interface";
           }
           leaf update-threshold-max-reservable {
             type string;
             description "Change in non-rsvp bandwidth to trigger IGP update with units appended";
           }
           leaf update-threshold-max-reservable-percent {
             type int32;
             description "Percentage change in max-reservable bandwidth to trigger IGP update";
           }
           leaf update-threshold {
             type jt:unsigned-float;
             description "Percentage change in reserved bandwidth to trigger IGP update";
           }
           leaf update-threshold-value {
             type string;
             description "Change in reserved bandwidth to trigger IGP update with appended units";
           }
           leaf subscription {
             type int32;
             description "Percentage of link capacity available for bandwidth reservations";
           }
           leaf sr-subscription {
             type int32;
             description "Percentage of link capacity available after spring traffic";
           }
           leaf bc {
             type int32;
             description "Bandwidth constraint (0..7)";
           }
           leaf bc-description {
             type string;
             description "Description of the bandwidth constraint";
           }
           leaf static-bc-bandwidth {
             type string;
             description "Static bandwidth capacity for a bandwidth constraint with units appended";
           }
           leaf ct-class {
             type int32;
             description "Class type (0..7)";
           }
           leaf static-bandwidth {
             type string;
             description "Static bandwidth capacity of the link with units appended";
           }
           leaf available-bandwidth {
             type string;
             description "Amount of bandwidth available for reservations with units appended";
           }
           leaf ct-subscription {
             type int32;
             description "Subscription percentage per traffic class";
           }
           leaf max-available-bandwidth {
             type string;
             description "Maximum amount of bandwidth available for reservations, including the subscription factor, with units appended";
           }
           leaf max-available-description {
             type string;
             description "Description of the computation of the maximum available bandwidth";
           }
         }
         container detour {
           container explicit-route {
             leaf explicit-route.heading {
               type string;
               description "Explicit Route Object (ERO)";
             }
             container explicit-route-element {
               leaf address {
                 type jt:ipaddr;
               }
               leaf explicit-route-type {
                 type string;
               }
               leaf telink-id {
                 type int32;
                 description "Link identifier of unnumbered link";
               }
             }
           }
           leaf lsp-state {
             type string;
             description "State of an LSP";
           }
           leaf sender-tspec {
             type string;
             description "Sender TSpec";
           }
           leaf lsp-diffserv-info {
             type string;
             description "LSP DiffServ info";
           }
           leaf ct-bw {
             type string;
             description "Per-class bandwidth requested for E-LSPs and L-LSPs";
           }
           leaf adspec {
             type string;
             description "Adspec data element in an RSVP Path message";
           }
           leaf path-mtu {
             type int32;
             description "The value of the path MTU, as negotiated by the network";
           }
           leaf path-mtu-in-kernel {
             type int32;
             description "The value of the MTU used locally for forwarding";
           }
           leaf label-out {
             type string;
             description "Outgoing label";
           }
           container packet-information {
             leaf packet-information.heading {
               type string;
               description "RSVP packets sent or received per session";
             }
             leaf previous-hop {
               type jt:ipaddr;
               description "Previous-hop address";
             }
             leaf next-hop {
               type jt:ipaddr;
               description "Next-hop address";
             }
             leaf interface-name {
               type string;
               description "Name of interface";
             }
             leaf count {
               type int32;
             }
             leaf notify-destination {
               type jt:ipaddr;
               description "Notify address";
             }
             leaf entropy-label {
               type string;
               description "Entropy label";
             }
             leaf in-message-handle {
               type string;
               description "RSVP I/O handle for incoming message";
             }
             leaf in-message-id {
               type uint32;
               description "Incoming Message ID";
             }
             leaf in-epoch {
               type uint32;
               description "Incoming Epoch";
             }
             leaf out-message-state {
               type string;
               description "RSVP I/O state for outgoing message";
             }
             leaf out-message-id {
               type uint32;
               description "Outgoing Message ID";
             }
             leaf out-epoch {
               type uint32;
               description "Outgoing Epoch";
             }
           }
           container record-route {
             leaf record-route.heading {
               type string;
               description "Record Route Object (RRO)";
             }
             leaf address {
               type jt:ipaddr;
             }
             leaf telink-id {
               type int32;
               description "Link identifier of unnumbered link";
             }
             leaf self {
               type empty;
             }
             leaf incomplete {
               type empty;
             }
           }
         }
         container detour-branch {
           container explicit-route {
             leaf explicit-route.heading {
               type string;
               description "Explicit Route Object (ERO)";
             }
             container explicit-route-element {
               leaf address {
                 type jt:ipaddr;
               }
               leaf explicit-route-type {
                 type string;
               }
               leaf telink-id {
                 type int32;
                 description "Link identifier of unnumbered link";
               }
             }
           }
           leaf source-address {
             type jt:ipaddr;
           }
           leaf skip-address {
             type jt:ipaddr;
             description "Address of node or link to be skipped";
           }
           leaf lsp-state {
             type string;
             description "State of an LSP";
           }
           leaf sender-tspec {
             type string;
             description "Sender TSpec";
           }
           leaf adspec {
             type string;
             description "Adspec data element in an RSVP Path message";
           }
           leaf path-mtu {
             type int32;
             description "The value of the path MTU, as negotiated by the network";
           }
           container record-route {
             leaf record-route.heading {
               type string;
               description "Record Route Object (RRO)";
             }
             leaf address {
               type jt:ipaddr;
             }
             leaf telink-id {
               type int32;
               description "Link identifier of unnumbered link";
             }
             leaf self {
               type empty;
             }
             leaf incomplete {
               type empty;
             }
           }
           container packet-information {
             leaf packet-information.heading {
               type string;
               description "RSVP packets sent or received per session";
             }
             leaf previous-hop {
               type jt:ipaddr;
               description "Previous-hop address";
             }
             leaf next-hop {
               type jt:ipaddr;
               description "Next-hop address";
             }
             leaf interface-name {
               type string;
               description "Name of interface";
             }
             leaf count {
               type int32;
             }
             leaf notify-destination {
               type jt:ipaddr;
               description "Notify address";
             }
             leaf entropy-label {
               type string;
               description "Entropy label";
             }
             leaf in-message-handle {
               type string;
               description "RSVP I/O handle for incoming message";
             }
             leaf in-message-id {
               type uint32;
               description "Incoming Message ID";
             }
             leaf in-epoch {
               type uint32;
               description "Incoming Epoch";
             }
             leaf out-message-state {
               type string;
               description "RSVP I/O state for outgoing message";
             }
             leaf out-message-id {
               type uint32;
               description "Outgoing Message ID";
             }
             leaf out-epoch {
               type uint32;
               description "Outgoing Epoch";
             }
           }
           container detour-branch-labels {
             leaf label-in {
               type string;
               description "Incoming label";
             }
             leaf label-out {
               type string;
               description "Outgoing label";
             }
           }
         }
         container mpls-lsp {
           leaf destination-address {
             type jt:ipaddr;
             description "Session destination address";
           }
           leaf source-address {
             type jt:ipaddr;
           }
           leaf lsp-state {
             type string;
             description "State of an LSP";
           }
           leaf route-count {
             type int32;
             description "Number of active routes";
           }
           leaf is-primary {
             type empty;
             description "Path is a primary path";
           }
           leaf active-path {
             type string;
             description "Path that the LSP is currently using";
           }
           leaf name {
             type string;
           }
           leaf bidirectional {
             type empty;
             description "LSP is bidirectional";
           }
           leaf associated-bidirectional {
             type empty;
             description "LSP is associated-bidirectional";
           }
           leaf ext-assoc-bidir {
             type empty;
             description "Extended associated bidirectional LSP";
           }
           leaf lsp-packets {
             type string;
             description "LSP packet counters";
           }
           leaf lsp-bytes {
             type string;
             description "LSP byte counters";
           }
           container mpls-lsp-path {
             leaf path-active {
               type empty;
               description "Whether the path is active or not";
             }
             leaf title {
               type string;
             }
             leaf name {
               type string;
             }
             leaf received-rro {
               type string;
               description "RRO returned by the signaling protocol";
             }
             container admin-groups {
               leaf admin-groups.heading {
                 type string;
               }
               leaf color {
                 type int32;
               }
               leaf no-group-flag {
                 type empty;
               }
               leaf-list admin-group-name {
                 type string;
                 description "Name of the admin group";
               }
               leaf admin-group-number {
                 type int32;
                 description "Number of the admin group";
               }
             }
             container admin-groups-extended {
               leaf admin-groups-extended.heading {
                 type string;
               }
               leaf-list admin-group-name {
                 type string;
                 description "Name of the admin group";
               }
               leaf admin-group-number {
                 type int32;
                 description "Number of the admin group";
               }
             }
             container srlg {
               leaf srlg.heading {
                 type string;
               }
               leaf-list srlg-name {
                 type string;
                 description "Name of the srlg";
               }
             }
             container mpls-lsp-upstream-label {
               leaf vlan-id-label {
                 type uint32;
                 description "VLAN ID label configured for the LSP";
               }
             }
             container explicit-route {
               leaf explicit-route.heading {
                 type string;
                 description "Explicit Route Object (ERO)";
               }
               container explicit-route-element {
                 leaf address {
                   type jt:ipaddr;
                 }
                 leaf explicit-route-type {
                   type string;
                 }
                 leaf telink-id {
                   type int32;
                   description "Link identifier of unnumbered link";
                 }
               }
             }
             container oam-state {
               leaf oam-bfd-session-state {
                 type string;
               }
               leaf oam-lsp-ping-state {
                 type string;
               }
             }
             list path-history {
               leaf sequence-number {
                 type int64;
                 description "History event number";
               }
               leaf time {
                 type string;
                 description "Time of the event";
               }
               leaf log {
                 type string;
                 description "Supplemental information of the event";
               }
               leaf route {
                 type string;
                 description "Latest RRO contents, as reported by RSVP";
               }
             }
             container path-available-bandwidth {
               leaf path-available-bandwidth.heading {
                 type string;
                 description "Available bandwidth on an LSP path";
               }
               leaf bandwidth {
                 type int32;
               }
               leaf class-type {
                 type int32;
               }
               leaf class-bandwidth {
                 type int32;
               }
             }
             container layer2-connection {
               leaf neighbor-address {
                 type jt:ipaddr;
                 description "IP address of this neighbor";
               }
               leaf interface-name {
                 type string;
                 description "Name of interface";
               }
               leaf vc-id {
                 type int32;
               }
               container connection-bandwidth {
                 leaf connection-bandwidth.heading {
                   type string;
                   description "Bandwidth of a layer 2 connection";
                 }
                 leaf bandwidth {
                   type int32;
                 }
                 leaf class-type {
                   type int32;
                 }
                 leaf class-bandwidth {
                   type int32;
                 }
               }
             }
             leaf path-state {
               type string;
               description "State of the MPLS path";
             }
             leaf cos {
               type int32;
               description "CoS value";
             }
             leaf no-decrement-ttl {
               type empty;
               description "TTL";
             }
             leaf preference {
               type int32;
               description "Preference for the route";
             }
             leaf path-soft-preemption-pending {
               type empty;
               description "Soft preemption pending for this path";
             }
             leaf setup-priority {
               type int32;
               description "Priority with respect to taking resources";
             }
             leaf hold-priority {
               type int32;
               description "Priority with respect to holding resources";
             }
             leaf actual-setup-priority {
               type int32;
             }
             leaf actual-hold-priority {
               type int32;
             }
             leaf non-active-hold-priority {
               type int32;
               description "Signaled hold priority for non-active path";
             }
             leaf external-lsp-cspf-type {
               type string;
             }
             leaf bandwidth {
               type int32;
             }
             leaf actual-bandwidth {
               type int32;
             }
             leaf per-class-bandwidth-heading {
               type string;
             }
             leaf bandwidth_ct0 {
               type int32;
             }
             leaf bandwidth_ct1 {
               type int32;
             }
             leaf bandwidth_ct2 {
               type int32;
             }
             leaf bandwidth_ct3 {
               type int32;
             }
             leaf path-adaptive {
               type empty;
               description "LSP is adaptive";
             }
             leaf path-no-recordroute {
               type empty;
               description "Record route disabled";
             }
             leaf hoplimit {
               type int32;
               description "Maximum number of hops that can be traversed";
             }
             leaf optimize-timer {
               type int32;
               description "Optimize timer";
             }
             leaf smart-optimize-timer {
               type int32;
               description "Smart optimize timer";
             }
             leaf retry-timer {
               type int32;
             }
             leaf retry-limit {
               type int32;
             }
             leaf path-flap-count {
               type int32;
             }
             leaf path-mbb-count {
               type int32;
             }
             leaf path-in-place-update-count {
               type int32;
             }
             leaf external-cspf-status {
               type string;
               description "Status provided by External CSPF computation";
             }
             leaf cspf-status {
               type string;
               description "Status returned by CSPF computation";
             }
             container mpls-srlg {
               leaf-list srlg-name {
                 type string;
                 description "Name of the srlg";
               }
               leaf srlg-value {
                 type uint32;
                 description "Value of the srlg";
               }
               leaf srlg-cost {
                 type uint32;
                 description "Cost of the srlg";
               }
             }
           }
           container mpls-lsp-attributes {
             container mpls-lsp-upstream-label {
               leaf vlan-id-label {
                 type uint32;
                 description "VLAN ID label configured for the LSP";
               }
             }
             leaf signal-type {
               type string;
             }
             leaf encoding-type {
               type string;
               description "LSP encoding type";
             }
             leaf switching-type {
               type string;
               description "LSP switching capability";
             }
             leaf gpid {
               type string;
               description "LSP generalized PID";
             }
             leaf-list protection-type {
               type string;
               description "LSP protection desired";
             }
           }
           leaf lsp-description {
             type string;
             description "LSP description string (up to 80 characters)";
           }
           leaf lsp-pktbytes {
             type string;
             description "LSP packet and byte counters";
           }
           leaf lsp-id {
             type string;
           }
           leaf lsp-type {
             type string;
             description "Type of LSP";
           }
           leaf egress-label-operation {
             type string;
             description "Label advertised by egress";
           }
           leaf lsp-control-status {
             type string;
             description "Control status of LSP configured to be externally controlled";
           }
           leaf lsp-selfping-status {
             type string;
           }
           leaf lsp-diffserv-te-info {
             type string;
             description "LSP support of DiffServ-TE extensions";
           }
           leaf lsp-associated-lspname {
             type string;
             description "Associated LSP name";
           }
           leaf lsp-associated-lspsrc {
             type string;
             description "Associated LSP source address";
           }
           leaf ext-assoc-bidir-direction {
             type string;
             description "Ext-Assoc-Bidir direction";
           }
           leaf aggregate-lsp-pktbytes {
             type string;
             description "Aggregate LSP packet and byte counters";
           }
           leaf no-statistics {
             type empty;
             description "No statistics are available for this session";
           }
           leaf mpls-p2mp-name {
             type string;
           }
           leaf is-fastreroute {
             type empty;
             description "Fast reroute (one-to-one backup) is desired";
           }
           leaf is-linkprotection {
             type empty;
             description "Link protection (facility backup) is desired";
           }
           leaf is-nodeprotection {
             type empty;
             description "Link-Node protection (facility backup) is desired";
           }
           leaf is-inter-domain-path {
             type empty;
             description "Inter-domain LSP";
           }
           leaf load-balance {
             type string;
             description "Load-balancing algorithm chosen";
           }
           leaf metric {
             type int32;
           }
           leaf metric-follows-igp {
             type empty;
             description "LSP routes follow the destination IGP metric";
           }
           leaf metric-follows-igp-conditionally {
             type empty;
             description "LSP routes follow the destination IGP metric conditionally";
           }
           leaf actual-metric {
             type int32;
           }
           leaf track-install-prefix-igp-metric {
             type string;
             description "Install prefixes tracking their IGP metric";
           }
           leaf revert-timer {
             type string;
             description "Hold-down time before reverting to primary path.";
           }
           leaf revert-timer-remain {
             type string;
             description "Time remaining before reverting:";
           }
           leaf optimize-protection-timer {
             type int32;
             description "Optimize protection timer";
           }
           leaf lsp-creation-time {
             type string;
             description "Time when the LSP was created";
           }
           leaf lsp-soft-preemption-counter {
             type int32;
             description "Number of times the LSP was soft preempted";
           }
           leaf lsp-soft-preemption-time {
             type string;
             description "Time when the LSP was last soft preempted";
           }
           leaf retry-timer {
             type int32;
           }
           leaf retry-limit {
             type int32;
           }
           container admin-groups {
             leaf admin-groups.heading {
               type string;
             }
             leaf color {
               type int32;
             }
             leaf no-group-flag {
               type empty;
             }
             leaf-list admin-group-name {
               type string;
               description "Name of the admin group";
             }
             leaf admin-group-number {
               type int32;
               description "Number of the admin group";
             }
           }
           container admin-groups-extended {
             leaf admin-groups-extended.heading {
               type string;
             }
             leaf-list admin-group-name {
               type string;
               description "Name of the admin group";
             }
             leaf admin-group-number {
               type int32;
               description "Number of the admin group";
             }
           }
           container mpls-srlg {
             leaf-list srlg-name {
               type string;
               description "Name of the srlg";
             }
             leaf srlg-value {
               type uint32;
               description "Value of the srlg";
             }
             leaf srlg-cost {
               type uint32;
               description "Cost of the srlg";
             }
           }
           container mpls-lsp-autobandwidth {
             leaf monitor-lsp-bandwidth {
               type empty;
               description "Enable the bandwidth monitoring mode";
             }
             leaf minimum-bandwidth {
               type int32;
               description "Configured LSP minimum bandwidth";
             }
             leaf maximum-bandwidth {
               type int32;
               description "Configured LSP maximum bandwidth";
             }
             leaf dynamic-minimum-bandwidth {
               type int32;
               description "LSP dynamic minimum bandwidth (or last Max Avg Bw)";
             }
             leaf adjust-timer {
               type int32;
               description "Configured LSP adjust timer";
             }
             leaf adjust-threshold {
               type int32;
               description "Percentage change in average LSP utilization to trigger autoadjustment";
             }
             leaf adjust-threshold-absolute {
               type int32;
               description "Configured LSP Adjustment Threshold Absolute Bandwidth value";
             }
             leaf adjust-threshold-activate-bandwidth {
               type int32;
               description "Configured LSP adjust threshold bandwidth";
             }
             leaf maximum-average-bandwidth {
               type int32;
               description "Maximum Average BW";
             }
             leaf time-to-adjust {
               type int32;
               description "Time in which LSP will autoadjust bandwidth";
             }
             leaf autobw-minimum-bandwidth-adjust-interval {
               type int32;
             }
             leaf autobw-minimum-bandwidth-adjust-threshold-percent {
               type int32;
             }
             leaf autobw-minimum-bandwidth-adjust-threshold-value {
               type int32;
             }
             leaf time-to-expire-minimum-bandwidth-adjust {
               type int32;
               description "Time in which LSP will start changing minimum bandwidth";
             }
             leaf overflow-limit {
               type int32;
               description "Configured limit of consecutive overflow samples for LSP";
             }
             leaf overflow-sample-count {
               type int32;
               description "Number of consecutive overflow samples encountered";
             }
             leaf underflow-limit {
               type int32;
               description "Configured limit of consecutive underflow samples for LSP";
             }
             leaf underflow-sample-count {
               type int32;
               description "Number of consecutive underflow samples encountered";
             }
             leaf underflow-max-avg-bandwidth {
               type int32;
               description "Highest average bandwidth recorded so far for underflow samples";
             }
           }
         }
         leaf lsp-description {
           type string;
           description "LSP description string (up to 80 characters)";
         }
         leaf lsp-pktbytes {
           type string;
           description "LSP packet and byte counters";
         }
         leaf lsp-id {
           type string;
         }
         leaf p2mp-branch-id {
           type uint32;
         }
         leaf xc-psb-list {
           type string;
           description "List of PSBs part of the RSVP xc";
         }
         leaf xc-rsb-list {
           type string;
           description "List of RSBs part of the RSVP xc";
         }
         leaf is-detour {
           type empty;
           description "Session is a detour session";
         }
         leaf lsp-path-type {
           type string;
           description "Primary or secondary LSP path";
         }
         leaf graceful-deletion-triggered {
           type empty;
           description "Initiated graceful deletion procedure for the LSP";
         }
         leaf mpls-lsp-type {
           type string;
           description "Type of LSP";
         }
         leaf source-tna-address {
           type jt:ipaddr;
           description "Source TNA address for the connection";
         }
         leaf destination-tna-address {
           type jt:ipaddr;
           description "Destination TNA address for the connection";
         }
         leaf upstream-label-in {
           type string;
           description "Incoming upstream label";
         }
         leaf upstream-label-out {
           type string;
           description "Outgoing upstream label";
         }
         leaf lsp-associated-lspname {
           type string;
           description "Associated LSP name";
         }
         leaf lsp-associated-lspsrc {
           type string;
           description "Associated LSP source address";
         }
         leaf mpls-p2mp-lsp-name {
           type string;
         }
         leaf p2mp-remerge-state {
           type string;
           description "Re-merge status of the P2MP sub-LSP";
         }
         leaf lsp-aggregation {
           type string;
           description "Supports LSP aggregation";
         }
         leaf suggested-label-in {
           type int32;
           description "Suggested label received";
         }
         leaf suggested-label-out {
           type int32;
           description "Suggested label sent";
         }
         leaf recovery-label-in {
           type int32;
         }
         leaf recovery-label-out {
           type int32;
         }
         leaf no-statistics {
           type empty;
           description "No statistics are available for this session";
         }
         leaf psb-lifetime {
           type int32;
           description "Lifetime for a PSB after which the entry expires";
         }
         leaf psb-creation-time {
           type string;
           description "Time when this PSB was created";
         }
         leaf path-mtu {
           type int32;
           description "The value of the path MTU, as negotiated by the network";
         }
         leaf path-mtu-in-kernel {
           type int32;
           description "The value of the MTU used locally for forwarding";
         }
         leaf sender-tspec {
           type string;
           description "Sender TSpec";
         }
         leaf resv-fspec {
           type string;
           description "Resv FSpec";
         }
         leaf session-priority {
           type string;
           description "Setup/hold Priority";
         }
         leaf adspec {
           type string;
           description "Adspec data element in an RSVP Path message";
         }
         leaf lsp-diffserv-info {
           type string;
           description "LSP DiffServ info";
         }
         leaf ct-bw {
           type string;
           description "Per-class bandwidth requested for E-LSPs and L-LSPs";
         }
         leaf tunnel-id {
           type int32;
         }
         leaf proto-id {
           type int32;
         }
         leaf p2mp-subgroup-orig {
           type jt:ipaddr;
         }
         leaf self-id {
           type string;
           description "Statistics identifier for RSVP path state control block";
         }
         leaf nh-statistics-id {
           type string;
           description "Nexthop statistics identifier for RSVP path at ingress";
         }
         leaf route-statistics-id {
           type string;
           description "Route statistics identifier for RSVP path at egress";
         }
         leaf nh-traffic-class-statistics {
           type empty;
           description "Traffic class statistics are enabled at ingress";
         }
         leaf route-traffic-class-statistics {
           type empty;
           description "Traffic class statistics are enabled at egress";
         }
         leaf session-id {
           type int32;
           description "Unique identifier for RSVP session";
         }
         leaf is-fastreroute {
           type empty;
           description "Fast reroute (one-to-one backup) is desired";
         }
         leaf is-linkprotection {
           type empty;
           description "Link protection (facility backup) is desired";
         }
         leaf is-nodeprotection {
           type empty;
           description "Link-Node protection (facility backup) is desired";
         }
         leaf ep-plr-protector {
           type string;
         }
         leaf is-soft-preemption {
           type empty;
           description "Soft-preemption is desired";
         }
         leaf rsvp-path-status {
           type string;
         }
         leaf bypass-name {
           type string;
           description "Name of the bypass";
         }
         leaf rsvp-lp-backup-route-cnt {
           type int32;
           description "Number of routes tunneled through this bypass";
         }
         leaf rsvp-lp-backup-lsp-cnt {
           type int32;
           description "Number of backup RSVP LSPs tunneled through this bypass";
         }
         leaf rsvp-lp-psb-cnt {
           type int32;
           description "Number of sessions tunneled through this bypass";
         }
         leaf explicit-hop-expanded {
           type string;
           description "Explicit hop(s) expanded by this LSR";
         }
         container layer2-tspec {
           leaf switching-granularity {
             type string;
             description "Layer 2 switching granularity";
           }
           leaf mtu {
             type int32;
             description "MTU along an interface";
           }
           leaf atm-vp-bundle-size {
             type int32;
             description "VP bundle size";
           }
           leaf atm-cell-bundle-size {
             type int32;
             description "Maximum cell bundle size";
           }
         }
         container rsvp-lsp-enh-local-prot-status {
           leaf rsvp-lsp-enh-local-prot-admin-status {
             type string;
             description "Enhanced FRR local protection admin status";
           }
           leaf rsvp-lsp-enh-local-prot-disabled-reason {
             type string;
             description "Enhanced FRR local protection disabled reason";
           }
           leaf rsvp-lsp-enh-local-prot-refresh-interval {
             type string;
             description "Enhanced FRR refresh interval set for LSP";
           }
         }
         container rsvp-lsp-enh-local-prot-upstream {
           leaf rsvp-lsp-enh-lp-upstream-status {
             type string;
             description "Enhanced FRR local protection status upstream";
           }
           leaf rsvp-lsp-enh-lp-upstream-lp {
             type string;
             description "The node is LP-MP for Phop";
           }
           leaf rsvp-lsp-enh-lp-phop-addr {
             type jt:ipaddr;
             description "Phop PLR for which this node is LP-MP";
           }
           leaf rsvp-lsp-enh-lp-upstream-lp-status {
             type string;
             description "Current upstream LP-MP status";
           }
           leaf rsvp-lsp-enh-lp-upstream-np {
             type string;
             description "The node is NP-MP for PPhop";
           }
           leaf rsvp-lsp-enh-lp-pphop-addr {
             type jt:ipaddr;
             description "PPhop PLR for which this node is NP-MP";
           }
           leaf rsvp-lsp-enh-lp-upstream-np-status {
             type string;
             description "Current upstream NP-MP status";
           }
           leaf rsvp-lsp-enh-lp-upstream-disabled-reason {
             type string;
             description "Reason enhanced local protection is disabled upstream";
           }
           leaf rsvp-lsp-enh-local-prot-refresh-interval {
             type string;
             description "Enhanced FRR refresh interval set for LSP";
           }
         }
         container rsvp-lsp-enh-local-prot-downstream {
           leaf rsvp-lsp-enh-lp-downstream-status {
             type string;
             description "Enhanced FRR local protection status downstream";
           }
           leaf rsvp-lsp-enh-lp-downstream-lp {
             type string;
             description "The node has made link protection available";
           }
           leaf rsvp-lsp-enh-lp-nhop-addr {
             type jt:ipaddr;
             description "Nhop MP neigbor address";
           }
           leaf rsvp-lsp-enh-lp-downstream-np {
             type string;
             description "The node has made node protection available";
           }
           leaf rsvp-lsp-enh-lp-nnhop-addr {
             type jt:ipaddr;
             description "NNhop MP neighbor address";
           }
           leaf rsvp-lsp-enh-lp-current-status {
             type string;
             description "Current downstream protection status";
           }
           leaf rsvp-lsp-enh-lp-downstream-disabled-reason {
             type string;
             description "Reason enhanced local protection is disabled downstream";
           }
           leaf rsvp-lsp-enh-local-prot-refresh-interval {
             type string;
             description "Enhanced FRR refresh interval set for LSP";
           }
         }
         container lsp-bypass-constraints {
           leaf rsvp-lsp-bypass-constr {
             type empty;
             description "Bypass constraints for LSP";
           }
           leaf rsvp-lsp-bypass-constr-hop {
             type int32;
             description "Hop limit for bypass LSP";
           }
         }
         container record-route {
           leaf record-route.heading {
             type string;
             description "Record Route Object (RRO)";
           }
           leaf address {
             type jt:ipaddr;
           }
           leaf telink-id {
             type int32;
             description "Link identifier of unnumbered link";
           }
           leaf self {
             type empty;
           }
           leaf incomplete {
             type empty;
           }
         }
         container exclude-route {
           leaf exclude-route.heading {
             type string;
             description "Exclude Route Object (XRO)";
           }
           leaf address {
             type jt:ipaddr;
           }
         }
         container rsvp-lsp-pop-and-fwd {
           leaf rsvp-lsp-pop-and-fwd.heading {
             type string;
           }
           leaf etld-in {
             type uint32;
             description "Incoming effective transport label stack depth";
           }
           leaf etld-out {
             type uint32;
             description "Outgoing effective transport label stack depth";
           }
           leaf delegation-hop {
             type string;
             description "Delegation state";
           }
         }
         container lsp-attribute-flags {
           leaf non-php {
             type empty;
             description "Non-PHP";
           }
           leaf oob {
             type empty;
             description "Out-of-band mapping";
           }
         }
         list lp-history {
           leaf sequence-number {
             type int64;
             description "History event number";
           }
           leaf time {
             type string;
             description "Time of the event";
           }
           leaf log {
             type string;
             description "Supplemental information of the event";
           }
           leaf route {
             type string;
             description "Latest RRO contents, as reported by RSVP";
           }
         }
         container admin-groups {
           leaf admin-groups.heading {
             type string;
           }
           leaf color {
             type int32;
           }
           leaf no-group-flag {
             type empty;
           }
           leaf-list admin-group-name {
             type string;
             description "Name of the admin group";
           }
           leaf admin-group-number {
             type int32;
             description "Number of the admin group";
           }
         }
         container protection-attribute {
           leaf protect-lsp-type {
             type string;
             description "Type of LSP for protection purposes";
           }
           leaf protect-lsp-role {
             type string;
             description "Role of LSP for protection purposes";
           }
           leaf protect-protection-type {
             type string;
             description "Type of protection being used";
           }
           leaf protect-secondary-operational {
             type empty;
             description "Protecting LSP is operational and carrying protected traffic";
           }
         }
         container association-attribute {
           leaf association-type {
             type string;
             description "Type of association object";
           }
           leaf association-source {
             type jt:ipaddr;
             description "Source node defining the association";
           }
           leaf association-id {
             type int32;
             description "Identifier for the association";
           }
         }
         list lsp-history {
           leaf lsp-history-sequence-number {
             type int32;
             description "LSP history event number";
           }
           leaf lsp-history-time {
             type string;
             description "Time of the event";
           }
           leaf lsp-history-log {
             type string;
             description "Supplementatal information of the event";
           }
           leaf lsp-history-route {
             type string;
             description "RRO contents received in latest Resv message";
           }
         }
         list lsp-message-statistics {
           leaf rsvp-message {
             type string;
           }
           leaf messages-sent {
             type int32;
             description "Total number of messages sent";
           }
           leaf messages-received {
             type int32;
             description "Total number of messages received";
           }
         }
       }
       container mpls-p2mp-lsp {
         leaf mpls-p2mp-name {
           type string;
         }
         leaf mpls-p2mp-branch-count {
           type string;
         }
       }
       container mpls-container-lsp {
         description "MPLS container-label-switched path information";
         leaf mpls-container-lsp-name {
           type string;
         }
         leaf mpls-container-lsp-state {
           type string;
         }
         leaf mpls-container-member-count {
           type string;
         }
         leaf container-active-path {
           type string;
           description "Path that the member LSP is currently using";
         }
         leaf container-is-primary {
           type empty;
           description "Path is a primary path";
         }
         leaf lsp-packets {
           type string;
           description "LSP packet counters";
         }
         leaf lsp-bytes {
           type string;
           description "LSP byte counters";
         }
         leaf lsp-control-status {
           type string;
           description "Control status of LSP configured to be externally controlled";
         }
         leaf lsp-selfping-status {
           type string;
         }
         container mpls-lsp-path {
           description "Primary or secondary LSP path";
           leaf received-rro {
             type string;
             description "RRO returned by the signaling protocol";
           }
           container admin-groups {
             leaf admin-groups.heading {
               type string;
             }
             leaf color {
               type int32;
             }
             leaf no-group-flag {
               type empty;
             }
             leaf-list admin-group-name {
               type string;
               description "Name of the admin group";
             }
             leaf admin-group-number {
               type int32;
               description "Number of the admin group";
             }
           }
           container admin-groups-extended {
             leaf admin-groups-extended.heading {
               type string;
             }
             leaf-list admin-group-name {
               type string;
               description "Name of the admin group";
             }
             leaf admin-group-number {
               type int32;
               description "Number of the admin group";
             }
           }
           container srlg {
             leaf srlg.heading {
               type string;
             }
             leaf-list srlg-name {
               type string;
               description "Name of the srlg";
             }
           }
           container mpls-lsp-upstream-label {
             description "Upstream label configured for the LSP";
             leaf vlan-id-label {
               type uint32;
               description "VLAN ID label configured for the LSP";
             }
           }
           container explicit-route {
             description "Explicit Route Object (ERO)";
             leaf explicit-route.heading {
               type string;
               description "Explicit Route Object (ERO)";
             }
             container explicit-route-element {
               leaf address {
                 type jt:ipaddr;
               }
               leaf explicit-route-type {
                 type string;
               }
               leaf telink-id {
                 type int32;
                 description "Link identifier of unnumbered link";
               }
             }
           }
           container oam-state {
             description "OAM state information";
             leaf oam-bfd-session-state {
               type string;
             }
             leaf oam-lsp-ping-state {
               type string;
             }
           }
           list path-history {
             description "Log over time of LSP path-related events";
             leaf sequence-number {
               type int64;
               description "History event number";
             }
             leaf time {
               type string;
               description "Time of the event";
             }
             leaf log {
               type string;
               description "Supplemental information of the event";
             }
             leaf route {
               type string;
               description "Latest RRO contents, as reported by RSVP";
             }
           }
           container path-available-bandwidth {
             description "Available bandwidth on an LSP path";
             leaf path-available-bandwidth.heading {
               type string;
               description "Available bandwidth on an LSP path";
             }
             leaf bandwidth {
               type int32;
             }
             leaf class-type {
               type int32;
             }
             leaf class-bandwidth {
               type int32;
             }
           }
           container layer2-connection {
             description "Layer 2 connection using the LSP path";
             leaf neighbor-address {
               type jt:ipaddr;
               description "IP address of this neighbor";
             }
             leaf interface-name {
               type string;
               description "Name of interface";
             }
             leaf vc-id {
               type int32;
             }
             container connection-bandwidth {
               description "Bandwidth of a layer 2 connection";
               leaf connection-bandwidth.heading {
                 type string;
                 description "Bandwidth of a layer 2 connection";
               }
               leaf bandwidth {
                 type int32;
               }
               leaf class-type {
                 type int32;
               }
               leaf class-bandwidth {
                 type int32;
               }
             }
           }
         }
         container mpls-container-lsp-splitting-merging {
           leaf minimum-member-lsps {
             type int32;
             description "Configured minimum LSPs";
           }
           leaf maximum-member-lsps {
             type int32;
             description "Configured maximum LSPs";
           }
           leaf aggregate-bandwidth {
             type int32;
             description "Aggregate bandwidth";
           }
           leaf current-bandwidth {
             type int32;
             description "Sampled Aggregate bandwidth";
           }
           leaf normalize-interval {
             type int32;
             description "Configured LSP normalize timer";
           }
           leaf splitting-merging-threshold {
             type int32;
             description "Percentage change in aggregate LSP utilization to trigger normalization";
           }
           leaf maximum-signaling-bandwidth {
             type int32;
             description "Configured signaling maximum bandwidth";
           }
           leaf minimum-signaling-bandwidth {
             type int32;
             description "Configured signaling minimum bandwidth";
           }
           leaf maximum-splitting-bandwidth {
             type int32;
             description "Configured splitting maximum bandwidth";
           }
           leaf minimum-splitting-bandwidth {
             type int32;
             description "Configured splitting minimum bandwidth";
           }
           leaf normalization-mode {
             type string;
           }
           leaf sampling-mode {
             type string;
             description "Sampling Attributes";
           }
           leaf time-to-normalize {
             type int32;
             description "Time in which LSP will normalize";
           }
           leaf aggregate-packets {
             type int32;
             description "Aggregate packets";
           }
           leaf aggregate-bytes {
             type int32;
             description "Aggregate bytes";
           }
         }
         container mpls-container-lsp-history {
           description "Log over time of container LSP related events";
           leaf sequence-number {
             type int64;
             description "History event number";
           }
           leaf time {
             type string;
             description "Time of the event";
           }
           leaf log {
             type string;
             description "Supplemental information of the event";
           }
           leaf route {
             type string;
             description "Latest RRO contents, as reported by RSVP";
           }
         }
         container mpls-lsp-attributes {
           container mpls-lsp-upstream-label {
             description "Upstream label configured for the LSP";
             leaf vlan-id-label {
               type uint32;
               description "VLAN ID label configured for the LSP";
             }
           }
         }
       }
       container mpls-container-lsp-member-summary {
         container mpls-container-lsp {
           description "MPLS container-label-switched path information";
           leaf mpls-container-lsp-name {
             type string;
           }
           leaf mpls-container-lsp-state {
             type string;
           }
           leaf mpls-container-member-count {
             type string;
           }
           leaf container-active-path {
             type string;
             description "Path that the member LSP is currently using";
           }
           leaf container-is-primary {
             type empty;
             description "Path is a primary path";
           }
           leaf lsp-packets {
             type string;
             description "LSP packet counters";
           }
           leaf lsp-bytes {
             type string;
             description "LSP byte counters";
           }
           leaf lsp-control-status {
             type string;
             description "Control status of LSP configured to be externally controlled";
           }
           leaf lsp-selfping-status {
             type string;
           }
           container mpls-lsp-path {
             description "Primary or secondary LSP path";
             leaf received-rro {
               type string;
               description "RRO returned by the signaling protocol";
             }
             container admin-groups {
               leaf admin-groups.heading {
                 type string;
               }
               leaf color {
                 type int32;
               }
               leaf no-group-flag {
                 type empty;
               }
               leaf-list admin-group-name {
                 type string;
                 description "Name of the admin group";
               }
               leaf admin-group-number {
                 type int32;
                 description "Number of the admin group";
               }
             }
             container admin-groups-extended {
               leaf admin-groups-extended.heading {
                 type string;
               }
               leaf-list admin-group-name {
                 type string;
                 description "Name of the admin group";
               }
               leaf admin-group-number {
                 type int32;
                 description "Number of the admin group";
               }
             }
             container srlg {
               leaf srlg.heading {
                 type string;
               }
               leaf-list srlg-name {
                 type string;
                 description "Name of the srlg";
               }
             }
             container mpls-lsp-upstream-label {
               description "Upstream label configured for the LSP";
               leaf vlan-id-label {
                 type uint32;
                 description "VLAN ID label configured for the LSP";
               }
             }
             container explicit-route {
               description "Explicit Route Object (ERO)";
               leaf explicit-route.heading {
                 type string;
                 description "Explicit Route Object (ERO)";
               }
               container explicit-route-element {
                 leaf address {
                   type jt:ipaddr;
                 }
                 leaf explicit-route-type {
                   type string;
                 }
                 leaf telink-id {
                   type int32;
                   description "Link identifier of unnumbered link";
                 }
               }
             }
             container oam-state {
               description "OAM state information";
               leaf oam-bfd-session-state {
                 type string;
               }
               leaf oam-lsp-ping-state {
                 type string;
               }
             }
             list path-history {
               description "Log over time of LSP path-related events";
               leaf sequence-number {
                 type int64;
                 description "History event number";
               }
               leaf time {
                 type string;
                 description "Time of the event";
               }
               leaf log {
                 type string;
                 description "Supplemental information of the event";
               }
               leaf route {
                 type string;
                 description "Latest RRO contents, as reported by RSVP";
               }
             }
             container path-available-bandwidth {
               description "Available bandwidth on an LSP path";
               leaf path-available-bandwidth.heading {
                 type string;
                 description "Available bandwidth on an LSP path";
               }
               leaf bandwidth {
                 type int32;
               }
               leaf class-type {
                 type int32;
               }
               leaf class-bandwidth {
                 type int32;
               }
             }
             container layer2-connection {
               description "Layer 2 connection using the LSP path";
               leaf neighbor-address {
                 type jt:ipaddr;
                 description "IP address of this neighbor";
               }
               leaf interface-name {
                 type string;
                 description "Name of interface";
               }
               leaf vc-id {
                 type int32;
               }
               container connection-bandwidth {
                 description "Bandwidth of a layer 2 connection";
                 leaf connection-bandwidth.heading {
                   type string;
                   description "Bandwidth of a layer 2 connection";
                 }
                 leaf bandwidth {
                   type int32;
                 }
                 leaf class-type {
                   type int32;
                 }
                 leaf class-bandwidth {
                   type int32;
                 }
               }
             }
           }
           container mpls-container-lsp-splitting-merging {
             leaf minimum-member-lsps {
               type int32;
               description "Configured minimum LSPs";
             }
             leaf maximum-member-lsps {
               type int32;
               description "Configured maximum LSPs";
             }
             leaf aggregate-bandwidth {
               type int32;
               description "Aggregate bandwidth";
             }
             leaf current-bandwidth {
               type int32;
               description "Sampled Aggregate bandwidth";
             }
             leaf normalize-interval {
               type int32;
               description "Configured LSP normalize timer";
             }
             leaf splitting-merging-threshold {
               type int32;
               description "Percentage change in aggregate LSP utilization to trigger normalization";
             }
             leaf maximum-signaling-bandwidth {
               type int32;
               description "Configured signaling maximum bandwidth";
             }
             leaf minimum-signaling-bandwidth {
               type int32;
               description "Configured signaling minimum bandwidth";
             }
             leaf maximum-splitting-bandwidth {
               type int32;
               description "Configured splitting maximum bandwidth";
             }
             leaf minimum-splitting-bandwidth {
               type int32;
               description "Configured splitting minimum bandwidth";
             }
             leaf normalization-mode {
               type string;
             }
             leaf sampling-mode {
               type string;
               description "Sampling Attributes";
             }
             leaf time-to-normalize {
               type int32;
               description "Time in which LSP will normalize";
             }
             leaf aggregate-packets {
               type int32;
               description "Aggregate packets";
             }
             leaf aggregate-bytes {
               type int32;
               description "Aggregate bytes";
             }
           }
           container mpls-container-lsp-history {
             description "Log over time of container LSP related events";
             leaf sequence-number {
               type int64;
               description "History event number";
             }
             leaf time {
               type string;
               description "Time of the event";
             }
             leaf log {
               type string;
               description "Supplemental information of the event";
             }
             leaf route {
               type string;
               description "Latest RRO contents, as reported by RSVP";
             }
           }
           container mpls-lsp-attributes {
             container mpls-lsp-upstream-label {
               description "Upstream label configured for the LSP";
               leaf vlan-id-label {
                 type uint32;
                 description "VLAN ID label configured for the LSP";
               }
             }
           }
         }
       }
       container container-rsvp-session {
         container mpls-container-lsp {
           leaf destination-address {
             type jt:ipaddr;
             description "Session destination address";
           }
           leaf source-address {
             type jt:ipaddr;
           }
           leaf lsp-state {
             type string;
             description "State of an LSP";
           }
           leaf route-count {
             type int32;
             description "Number of active routes";
           }
           leaf is-primary {
             type empty;
             description "Path is a primary path";
           }
           leaf active-path {
             type string;
             description "Path that the LSP is currently using";
           }
           leaf container-member-name {
             type string;
             description "Path that the member LSP is currently using";
           }
           leaf label-out {
             type string;
             description "Outgoing label";
           }
           container explicit-route {
             leaf explicit-route.heading {
               type string;
               description "Explicit Route Object (ERO)";
             }
             container explicit-route-element {
               leaf address {
                 type jt:ipaddr;
               }
               leaf explicit-route-type {
                 type string;
               }
               leaf telink-id {
                 type int32;
                 description "Link identifier of unnumbered link";
               }
             }
           }
           leaf lsp-description {
             type string;
             description "LSP description string (up to 80 characters)";
           }
           leaf container-active-path {
             type string;
             description "Path that the member LSP is currently using";
           }
           leaf container-is-primary {
             type empty;
             description "Path is a primary path";
           }
           leaf lsp-packets {
             type string;
             description "LSP packet counters";
           }
           leaf lsp-bytes {
             type string;
             description "LSP byte counters";
           }
           leaf lsp-control-status {
             type string;
             description "Control status of LSP configured to be externally controlled";
           }
           leaf lsp-selfping-status {
             type string;
           }
           container mpls-lsp-path {
             leaf name {
               type string;
             }
             leaf received-rro {
               type string;
               description "RRO returned by the signaling protocol";
             }
             container admin-groups {
               leaf admin-groups.heading {
                 type string;
               }
               leaf color {
                 type int32;
               }
               leaf no-group-flag {
                 type empty;
               }
               leaf-list admin-group-name {
                 type string;
                 description "Name of the admin group";
               }
               leaf admin-group-number {
                 type int32;
                 description "Number of the admin group";
               }
             }
             container admin-groups-extended {
               leaf admin-groups-extended.heading {
                 type string;
               }
               leaf-list admin-group-name {
                 type string;
                 description "Name of the admin group";
               }
               leaf admin-group-number {
                 type int32;
                 description "Number of the admin group";
               }
             }
             container srlg {
               leaf srlg.heading {
                 type string;
               }
               leaf-list srlg-name {
                 type string;
                 description "Name of the srlg";
               }
             }
             container mpls-lsp-upstream-label {
               leaf vlan-id-label {
                 type uint32;
                 description "VLAN ID label configured for the LSP";
               }
             }
             container explicit-route {
               leaf explicit-route.heading {
                 type string;
                 description "Explicit Route Object (ERO)";
               }
               container explicit-route-element {
                 leaf address {
                   type jt:ipaddr;
                 }
                 leaf explicit-route-type {
                   type string;
                 }
                 leaf telink-id {
                   type int32;
                   description "Link identifier of unnumbered link";
                 }
               }
             }
             container oam-state {
               leaf oam-bfd-session-state {
                 type string;
               }
               leaf oam-lsp-ping-state {
                 type string;
               }
             }
             list path-history {
               leaf sequence-number {
                 type int64;
                 description "History event number";
               }
               leaf time {
                 type string;
                 description "Time of the event";
               }
               leaf log {
                 type string;
                 description "Supplemental information of the event";
               }
               leaf route {
                 type string;
                 description "Latest RRO contents, as reported by RSVP";
               }
             }
             container path-available-bandwidth {
               leaf path-available-bandwidth.heading {
                 type string;
                 description "Available bandwidth on an LSP path";
               }
               leaf bandwidth {
                 type int32;
               }
               leaf class-type {
                 type int32;
               }
               leaf class-bandwidth {
                 type int32;
               }
             }
             container layer2-connection {
               leaf neighbor-address {
                 type jt:ipaddr;
                 description "IP address of this neighbor";
               }
               leaf interface-name {
                 type string;
                 description "Name of interface";
               }
               leaf vc-id {
                 type int32;
               }
               container connection-bandwidth {
                 leaf connection-bandwidth.heading {
                   type string;
                   description "Bandwidth of a layer 2 connection";
                 }
                 leaf bandwidth {
                   type int32;
                 }
                 leaf class-type {
                   type int32;
                 }
                 leaf class-bandwidth {
                   type int32;
                 }
               }
             }
             leaf path-active {
               type empty;
               description "Whether the path is active or not";
             }
             leaf title {
               type string;
             }
           }
           container mpls-container-lsp-splitting-merging {
             leaf minimum-member-lsps {
               type int32;
               description "Configured minimum LSPs";
             }
             leaf maximum-member-lsps {
               type int32;
               description "Configured maximum LSPs";
             }
             leaf aggregate-bandwidth {
               type int32;
               description "Aggregate bandwidth";
             }
             leaf current-bandwidth {
               type int32;
               description "Sampled Aggregate bandwidth";
             }
             leaf normalize-interval {
               type int32;
               description "Configured LSP normalize timer";
             }
             leaf splitting-merging-threshold {
               type int32;
               description "Percentage change in aggregate LSP utilization to trigger normalization";
             }
             leaf maximum-signaling-bandwidth {
               type int32;
               description "Configured signaling maximum bandwidth";
             }
             leaf minimum-signaling-bandwidth {
               type int32;
               description "Configured signaling minimum bandwidth";
             }
             leaf maximum-splitting-bandwidth {
               type int32;
               description "Configured splitting maximum bandwidth";
             }
             leaf minimum-splitting-bandwidth {
               type int32;
               description "Configured splitting minimum bandwidth";
             }
             leaf normalization-mode {
               type string;
             }
             leaf sampling-mode {
               type string;
               description "Sampling Attributes";
             }
             leaf time-to-normalize {
               type int32;
               description "Time in which LSP will normalize";
             }
             leaf aggregate-packets {
               type int32;
               description "Aggregate packets";
             }
             leaf aggregate-bytes {
               type int32;
               description "Aggregate bytes";
             }
           }
           container mpls-container-lsp-history {
             leaf sequence-number {
               type int64;
               description "History event number";
             }
             leaf time {
               type string;
               description "Time of the event";
             }
             leaf log {
               type string;
               description "Supplemental information of the event";
             }
             leaf route {
               type string;
               description "Latest RRO contents, as reported by RSVP";
             }
           }
           container mpls-lsp-attributes {
             container mpls-lsp-upstream-label {
               leaf vlan-id-label {
                 type uint32;
                 description "VLAN ID label configured for the LSP";
               }
             }
           }
           leaf lsp-pktbytes {
             type string;
             description "LSP packet and byte counters";
           }
           leaf name {
             type string;
           }
           leaf bidirectional {
             type empty;
             description "LSP is bidirectional";
           }
           leaf associated-bidirectional {
             type empty;
             description "LSP is associated-bidirectional";
           }
           leaf lsp-type {
             type string;
             description "Type of LSP";
           }
           leaf egress-label-operation {
             type string;
             description "Label advertised by egress";
           }
           leaf lsp-diffserv-te-info {
             type string;
             description "LSP support of DiffServ-TE extensions";
           }
           leaf aggregate-lsp-pktbytes {
             type string;
             description "Aggregate LSP packet and byte counters";
           }
           leaf no-statistics {
             type empty;
             description "No statistics are available for this session";
           }
           leaf mpls-container-name {
             type string;
             description "Name of the container LSP";
           }
           leaf is-fastreroute {
             type empty;
             description "Fast reroute (one-to-one backup) is desired";
           }
           leaf is-linkprotection {
             type empty;
             description "Link protection (facility backup) is desired";
           }
           leaf is-nodeprotection {
             type empty;
             description "Link-Node protection (facility backup) is desired";
           }
           leaf is-inter-domain-path {
             type empty;
             description "Inter-domain LSP";
           }
           leaf load-balance {
             type string;
             description "Load-balancing algorithm chosen";
           }
           leaf metric {
             type int32;
           }
           leaf optimize-protection-timer {
             type int32;
             description "Optimize protection timer";
           }
           leaf lsp-creation-time {
             type string;
             description "Time when the LSP was created";
           }
           leaf lsp-soft-preemption-counter {
             type int32;
             description "Number of times the LSP was soft preempted";
           }
           leaf lsp-soft-preemption-time {
             type string;
             description "Time when the LSP was last soft preempted";
           }
           leaf retry-timer {
             type int32;
           }
           leaf retry-limit {
             type int32;
           }
           leaf received-rro {
             type string;
             description "RRO returned by the signaling protocol";
           }
           container admin-groups {
             leaf admin-groups.heading {
               type string;
             }
             leaf color {
               type int32;
             }
             leaf no-group-flag {
               type empty;
             }
             leaf-list admin-group-name {
               type string;
               description "Name of the admin group";
             }
             leaf admin-group-number {
               type int32;
               description "Number of the admin group";
             }
           }
           container admin-groups-extended {
             leaf admin-groups-extended.heading {
               type string;
             }
             leaf-list admin-group-name {
               type string;
               description "Name of the admin group";
             }
             leaf admin-group-number {
               type int32;
               description "Number of the admin group";
             }
           }
           container srlg {
             leaf srlg.heading {
               type string;
             }
             leaf-list srlg-name {
               type string;
               description "Name of the srlg";
             }
           }
           container mpls-lsp-upstream-label {
             leaf vlan-id-label {
               type uint32;
               description "VLAN ID label configured for the LSP";
             }
           }
           container oam-state {
             leaf oam-bfd-session-state {
               type string;
             }
             leaf oam-lsp-ping-state {
               type string;
             }
           }
           list path-history {
             leaf sequence-number {
               type int64;
               description "History event number";
             }
             leaf time {
               type string;
               description "Time of the event";
             }
             leaf log {
               type string;
               description "Supplemental information of the event";
             }
             leaf route {
               type string;
               description "Latest RRO contents, as reported by RSVP";
             }
           }
           container path-available-bandwidth {
             leaf path-available-bandwidth.heading {
               type string;
               description "Available bandwidth on an LSP path";
             }
             leaf bandwidth {
               type int32;
             }
             leaf class-type {
               type int32;
             }
             leaf class-bandwidth {
               type int32;
             }
           }
           container layer2-connection {
             leaf neighbor-address {
               type jt:ipaddr;
               description "IP address of this neighbor";
             }
             leaf interface-name {
               type string;
               description "Name of interface";
             }
             leaf vc-id {
               type int32;
             }
             container connection-bandwidth {
               leaf connection-bandwidth.heading {
                 type string;
                 description "Bandwidth of a layer 2 connection";
               }
               leaf bandwidth {
                 type int32;
               }
               leaf class-type {
                 type int32;
               }
               leaf class-bandwidth {
                 type int32;
               }
             }
           }
           container mpls-srlg {
             leaf-list srlg-name {
               type string;
               description "Name of the srlg";
             }
             leaf srlg-value {
               type uint32;
               description "Value of the srlg";
             }
             leaf srlg-cost {
               type uint32;
               description "Cost of the srlg";
             }
           }
         }
         container mpls-lsp {
           leaf destination-address {
             type jt:ipaddr;
             description "Session destination address";
           }
           leaf source-address {
             type jt:ipaddr;
           }
           leaf lsp-state {
             type string;
             description "State of an LSP";
           }
           leaf label-out {
             type string;
             description "Outgoing label";
           }
           container explicit-route {
           }
           leaf name {
             type string;
           }
           leaf lsp-description {
             type string;
             description "LSP description string (up to 80 characters)";
           }
           leaf lsp-packets {
             type string;
             description "LSP packet counters";
           }
           leaf lsp-bytes {
             type string;
             description "LSP byte counters";
           }
           container mpls-lsp-path {
             leaf path-active {
               type empty;
               description "Whether the path is active or not";
             }
             leaf title {
               type string;
             }
             leaf name {
               type string;
             }
             leaf received-rro {
               type string;
               description "RRO returned by the signaling protocol";
             }
             container admin-groups {
               leaf admin-groups.heading {
                 type string;
               }
               leaf color {
                 type int32;
               }
               leaf no-group-flag {
                 type empty;
               }
               leaf-list admin-group-name {
                 type string;
                 description "Name of the admin group";
               }
               leaf admin-group-number {
                 type int32;
                 description "Number of the admin group";
               }
             }
             container admin-groups-extended {
               leaf admin-groups-extended.heading {
                 type string;
               }
               leaf-list admin-group-name {
                 type string;
                 description "Name of the admin group";
               }
               leaf admin-group-number {
                 type int32;
                 description "Number of the admin group";
               }
             }
             container srlg {
               leaf srlg.heading {
                 type string;
               }
               leaf-list srlg-name {
                 type string;
                 description "Name of the srlg";
               }
             }
             container mpls-lsp-upstream-label {
               leaf vlan-id-label {
                 type uint32;
                 description "VLAN ID label configured for the LSP";
               }
             }
             container explicit-route {
               leaf explicit-route.heading {
                 type string;
                 description "Explicit Route Object (ERO)";
               }
               container explicit-route-element {
                 leaf address {
                   type jt:ipaddr;
                 }
                 leaf explicit-route-type {
                   type string;
                 }
                 leaf telink-id {
                   type int32;
                   description "Link identifier of unnumbered link";
                 }
               }
             }
             container oam-state {
               leaf oam-bfd-session-state {
                 type string;
               }
               leaf oam-lsp-ping-state {
                 type string;
               }
             }
             list path-history {
               leaf sequence-number {
                 type int64;
                 description "History event number";
               }
               leaf time {
                 type string;
                 description "Time of the event";
               }
               leaf log {
                 type string;
                 description "Supplemental information of the event";
               }
               leaf route {
                 type string;
                 description "Latest RRO contents, as reported by RSVP";
               }
             }
             container path-available-bandwidth {
               leaf path-available-bandwidth.heading {
                 type string;
                 description "Available bandwidth on an LSP path";
               }
               leaf bandwidth {
                 type int32;
               }
               leaf class-type {
                 type int32;
               }
               leaf class-bandwidth {
                 type int32;
               }
             }
             container layer2-connection {
               leaf neighbor-address {
                 type jt:ipaddr;
                 description "IP address of this neighbor";
               }
               leaf interface-name {
                 type string;
                 description "Name of interface";
               }
               leaf vc-id {
                 type int32;
               }
               container connection-bandwidth {
                 leaf connection-bandwidth.heading {
                   type string;
                   description "Bandwidth of a layer 2 connection";
                 }
                 leaf bandwidth {
                   type int32;
                 }
                 leaf class-type {
                   type int32;
                 }
                 leaf class-bandwidth {
                   type int32;
                 }
               }
             }
           }
           container mpls-lsp-attributes {
             container mpls-lsp-upstream-label {
               leaf vlan-id-label {
                 type uint32;
                 description "VLAN ID label configured for the LSP";
               }
             }
           }
           leaf lsp-pktbytes {
             type string;
             description "LSP packet and byte counters";
           }
           leaf bidirectional {
             type empty;
             description "LSP is bidirectional";
           }
           leaf associated-bidirectional {
             type empty;
             description "LSP is associated-bidirectional";
           }
           leaf path-mtu {
             type int32;
             description "The value of the path MTU, as negotiated by the network";
           }
           leaf path-mtu-in-kernel {
             type int32;
             description "The value of the MTU used locally for forwarding";
           }
           leaf sender-tspec {
             type string;
             description "Sender TSpec";
           }
           leaf adspec {
             type string;
             description "Adspec data element in an RSVP Path message";
           }
           leaf lsp-diffserv-info {
             type string;
             description "LSP DiffServ info";
           }
           leaf ct-bw {
             type string;
             description "Per-class bandwidth requested for E-LSPs and L-LSPs";
           }
           container packet-information {
             leaf packet-information.heading {
               type string;
               description "RSVP packets sent or received per session";
             }
             leaf previous-hop {
               type jt:ipaddr;
               description "Previous-hop address";
             }
             leaf next-hop {
               type jt:ipaddr;
               description "Next-hop address";
             }
             leaf interface-name {
               type string;
               description "Name of interface";
             }
             leaf count {
               type int32;
             }
             leaf notify-destination {
               type jt:ipaddr;
               description "Notify address";
             }
             leaf entropy-label {
               type string;
               description "Entropy label";
             }
             leaf in-message-handle {
               type string;
               description "RSVP I/O handle for incoming message";
             }
             leaf in-message-id {
               type uint32;
               description "Incoming Message ID";
             }
             leaf in-epoch {
               type uint32;
               description "Incoming Epoch";
             }
             leaf out-message-state {
               type string;
               description "RSVP I/O state for outgoing message";
             }
             leaf out-message-id {
               type uint32;
               description "Outgoing Message ID";
             }
             leaf out-epoch {
               type uint32;
               description "Outgoing Epoch";
             }
           }
         }
         container detour {
           leaf lsp-state {
             type string;
             description "State of an LSP";
           }
           leaf label-out {
             type string;
             description "Outgoing label";
           }
           container explicit-route {
           }
           leaf sender-tspec {
             type string;
             description "Sender TSpec";
           }
           leaf lsp-diffserv-info {
             type string;
             description "LSP DiffServ info";
           }
           leaf ct-bw {
             type string;
             description "Per-class bandwidth requested for E-LSPs and L-LSPs";
           }
           leaf adspec {
             type string;
             description "Adspec data element in an RSVP Path message";
           }
           leaf path-mtu {
             type int32;
             description "The value of the path MTU, as negotiated by the network";
           }
           leaf path-mtu-in-kernel {
             type int32;
             description "The value of the MTU used locally for forwarding";
           }
           container packet-information {
             leaf packet-information.heading {
               type string;
               description "RSVP packets sent or received per session";
             }
             leaf previous-hop {
               type jt:ipaddr;
               description "Previous-hop address";
             }
             leaf next-hop {
               type jt:ipaddr;
               description "Next-hop address";
             }
             leaf interface-name {
               type string;
               description "Name of interface";
             }
             leaf count {
               type int32;
             }
             leaf notify-destination {
               type jt:ipaddr;
               description "Notify address";
             }
             leaf entropy-label {
               type string;
               description "Entropy label";
             }
             leaf in-message-handle {
               type string;
               description "RSVP I/O handle for incoming message";
             }
             leaf in-message-id {
               type uint32;
               description "Incoming Message ID";
             }
             leaf in-epoch {
               type uint32;
               description "Incoming Epoch";
             }
             leaf out-message-state {
               type string;
               description "RSVP I/O state for outgoing message";
             }
             leaf out-message-id {
               type uint32;
               description "Outgoing Message ID";
             }
             leaf out-epoch {
               type uint32;
               description "Outgoing Epoch";
             }
           }
         }
         container detour-branch {
           container explicit-route {
           }
           container detour-branch-labels {
             leaf label-in {
               type string;
               description "Incoming label";
             }
             leaf label-out {
               type string;
               description "Outgoing label";
             }
             container explicit-route {
             }
             leaf path-mtu {
               type int32;
               description "The value of the path MTU, as negotiated by the network";
             }
             leaf path-mtu-in-kernel {
               type int32;
               description "The value of the MTU used locally for forwarding";
             }
             leaf sender-tspec {
               type string;
               description "Sender TSpec";
             }
             leaf adspec {
               type string;
               description "Adspec data element in an RSVP Path message";
             }
             leaf lsp-diffserv-info {
               type string;
               description "LSP DiffServ info";
             }
             leaf ct-bw {
               type string;
               description "Per-class bandwidth requested for E-LSPs and L-LSPs";
             }
             container packet-information {
               leaf packet-information.heading {
                 type string;
                 description "RSVP packets sent or received per session";
               }
               leaf previous-hop {
                 type jt:ipaddr;
                 description "Previous-hop address";
               }
               leaf next-hop {
                 type jt:ipaddr;
                 description "Next-hop address";
               }
               leaf interface-name {
                 type string;
                 description "Name of interface";
               }
               leaf count {
                 type int32;
               }
               leaf notify-destination {
                 type jt:ipaddr;
                 description "Notify address";
               }
               leaf entropy-label {
                 type string;
                 description "Entropy label";
               }
               leaf in-message-handle {
                 type string;
                 description "RSVP I/O handle for incoming message";
               }
               leaf in-message-id {
                 type uint32;
                 description "Incoming Message ID";
               }
               leaf in-epoch {
                 type uint32;
                 description "Incoming Epoch";
               }
               leaf out-message-state {
                 type string;
                 description "RSVP I/O state for outgoing message";
               }
               leaf out-message-id {
                 type uint32;
                 description "Outgoing Message ID";
               }
               leaf out-epoch {
                 type uint32;
                 description "Outgoing Epoch";
               }
             }
           }
           leaf source-address {
             type jt:ipaddr;
           }
           leaf skip-address {
             type jt:ipaddr;
             description "Address of node or link to be skipped";
           }
           leaf lsp-state {
             type string;
             description "State of an LSP";
           }
           leaf sender-tspec {
             type string;
             description "Sender TSpec";
           }
           leaf adspec {
             type string;
             description "Adspec data element in an RSVP Path message";
           }
           leaf path-mtu {
             type int32;
             description "The value of the path MTU, as negotiated by the network";
           }
           container packet-information {
             leaf packet-information.heading {
               type string;
               description "RSVP packets sent or received per session";
             }
             leaf previous-hop {
               type jt:ipaddr;
               description "Previous-hop address";
             }
             leaf next-hop {
               type jt:ipaddr;
               description "Next-hop address";
             }
             leaf interface-name {
               type string;
               description "Name of interface";
             }
             leaf count {
               type int32;
             }
             leaf notify-destination {
               type jt:ipaddr;
               description "Notify address";
             }
             leaf entropy-label {
               type string;
               description "Entropy label";
             }
             leaf in-message-handle {
               type string;
               description "RSVP I/O handle for incoming message";
             }
             leaf in-message-id {
               type uint32;
               description "Incoming Message ID";
             }
             leaf in-epoch {
               type uint32;
               description "Incoming Epoch";
             }
             leaf out-message-state {
               type string;
               description "RSVP I/O state for outgoing message";
             }
             leaf out-message-id {
               type uint32;
               description "Outgoing Message ID";
             }
             leaf out-epoch {
               type uint32;
               description "Outgoing Epoch";
             }
           }
         }
         container packet-information {
           leaf packet-information.heading {
             type string;
             description "RSVP packets sent or received per session";
           }
           leaf previous-hop {
             type jt:ipaddr;
             description "Previous-hop address";
           }
           leaf next-hop {
             type jt:ipaddr;
             description "Next-hop address";
           }
           leaf interface-name {
             type string;
             description "Name of interface";
           }
           leaf count {
             type int32;
           }
           leaf notify-destination {
             type jt:ipaddr;
             description "Notify address";
           }
           leaf entropy-label {
             type string;
             description "Entropy label";
           }
           leaf in-message-handle {
             type string;
             description "RSVP I/O handle for incoming message";
           }
           leaf in-message-id {
             type uint32;
             description "Incoming Message ID";
           }
           leaf in-epoch {
             type uint32;
             description "Incoming Epoch";
           }
           leaf out-message-state {
             type string;
             description "RSVP I/O state for outgoing message";
           }
           leaf out-message-id {
             type uint32;
             description "Outgoing Message ID";
           }
           leaf out-epoch {
             type uint32;
             description "Outgoing Epoch";
           }
         }
       }
     }
   }
   grouping mpls-lsp-defaults-information-block {
     container mpls-lsp-defaults {
       leaf lsp-hold-priority {
         type int32;
         description "Default priority for holding resources";
       }
       leaf lsp-setup-priority {
         type int32;
         description "Default priority for taking resources";
       }
       leaf lsp-hoplimit {
         type int32;
         description "Maximum number of hops that can be traversed";
       }
       leaf lsp-bandwidth {
         type int32;
         description "Default LSP Bandwidth";
       }
       leaf lsp-retry-timer {
         type int32;
       }
     }
   }
   grouping mpls-container-lsp-information-block {
     list rsvp-session-data {
       leaf session-type {
         type string;
         description "Type of session with respect to this router";
       }
       leaf count {
         type int32;
       }
       leaf detours {
         type int32;
         description "Number of detour sessions";
       }
       leaf display-count {
         type int32;
         description "Number of sessions displayed";
       }
       leaf up-count {
         type int32;
         description "Number of sessions in up state";
       }
       leaf down-count {
         type int32;
         description "Number of sessions in down state";
       }
       list rsvp-session {
         description "Single RSVP session";
         leaf destination-address {
           type jt:ipaddr;
           description "Session destination address";
         }
         leaf source-address {
           type jt:ipaddr;
         }
         leaf lsp-state {
           type string;
           description "State of an LSP";
         }
         leaf route-count {
           type int32;
           description "Number of active routes";
         }
         leaf rsb-count {
           type int32;
           description "Number of RSBs";
         }
         leaf resv-style {
           type string;
         }
         leaf label-in {
           type string;
           description "Incoming label";
         }
         leaf label-out {
           type string;
           description "Outgoing label";
         }
         leaf name {
           type string;
         }
         leaf bidirectional {
           type empty;
           description "LSP is bidirectional";
         }
         leaf associated-bidirectional {
           type empty;
           description "LSP is associated-bidirectional";
         }
         leaf entropy-label {
           type string;
           description "Entropy label";
         }
         leaf p2mp-self-id {
           type string;
           description "Statistics identifier for RSVP P2MP path state control block";
         }
         container rsvp-lp-bw-optimize-info {
           leaf rsvp-lp-bw-optimize-info.heading {
             type string;
           }
           leaf rsvp-lp-path-avail-bw {
             type string;
             description "Bandwidth available on the bypass path";
           }
           leaf rsvp-lp-optimize-interval {
             type int32;
             description "Optimization interval for the bypass";
           }
         }
         container packet-information {
           leaf packet-information.heading {
             type string;
             description "RSVP packets sent or received per session";
           }
           leaf previous-hop {
             type jt:ipaddr;
             description "Previous-hop address";
           }
           leaf next-hop {
             type jt:ipaddr;
             description "Next-hop address";
           }
           leaf interface-name {
             type string;
             description "Name of interface";
           }
           leaf count {
             type int32;
           }
           leaf notify-destination {
             type jt:ipaddr;
             description "Notify address";
           }
           leaf entropy-label {
             type string;
             description "Entropy label";
           }
           leaf in-message-handle {
             type string;
             description "RSVP I/O handle for incoming message";
           }
           leaf in-message-id {
             type uint32;
             description "Incoming Message ID";
           }
           leaf in-epoch {
             type uint32;
             description "Incoming Epoch";
           }
           leaf out-message-state {
             type string;
             description "RSVP I/O state for outgoing message";
           }
           leaf out-message-id {
             type uint32;
             description "Outgoing Message ID";
           }
           leaf out-epoch {
             type uint32;
             description "Outgoing Epoch";
           }
         }
         container explicit-route {
           leaf explicit-route.heading {
             type string;
             description "Explicit Route Object (ERO)";
           }
           container explicit-route-element {
             leaf address {
               type jt:ipaddr;
             }
             leaf explicit-route-type {
               type string;
             }
             leaf telink-id {
               type int32;
               description "Link identifier of unnumbered link";
             }
           }
         }
         container rsvp-telink {
           leaf static-bandwidth-bps {
             type uint64;
             description "Static bandwidth capacity of the link in bits per second";
           }
           leaf available-bandwidth-bps {
             type uint64;
             description "Amount of bandwidth available for reservations in bits per second";
           }
           leaf max-available-bandwidth-bps {
             type uint64;
             description "Maximum amount of bandwidth available for reservations, including the subscription factor in bits per second";
           }
           leaf static-bc-bandwidth-bps {
             type uint64;
             description "Static bandwidth capacity for a bandwidth constraint in bits per second";
           }
           leaf total-reserved-bandwidth-bps {
             type uint64;
             description "Total amount of bandwidth currently reserved in bits per second";
           }
           leaf ct-bw0 {
             type string;
           }
           leaf ct-bw0-bps {
             type uint64;
           }
           leaf ct-bw1 {
             type string;
           }
           leaf ct-bw1-bps {
             type uint64;
           }
           leaf ct-bw2 {
             type string;
           }
           leaf ct-bw2-bps {
             type uint64;
           }
           leaf ct-bw3 {
             type string;
           }
           leaf ct-bw3-bps {
             type uint64;
           }
           leaf ct-bw4 {
             type string;
           }
           leaf ct-bw4-bps {
             type uint64;
           }
           leaf ct-bw5 {
             type string;
           }
           leaf ct-bw5-bps {
             type uint64;
           }
           leaf ct-bw6 {
             type string;
           }
           leaf ct-bw6-bps {
             type uint64;
           }
           leaf ct-bw7 {
             type string;
           }
           leaf ct-bw7-bps {
             type uint64;
           }
           leaf high-watermark-bps {
             type uint64;
             description "Maximum bandwidth that was ever reserved in bps";
           }
           leaf update-threshold-value-bps {
             type uint64;
             description "Change in reserved bandwidth to trigger IGP update in bits per second";
           }
           leaf update-threshold-max-reservable-bps {
             type uint64;
             description "Change in non-rsvp bandwidth to trigger IGP update in bits per second";
           }
           container priority-subscription {
             leaf priority-subscription.heading {
               type string;
             }
             list priority-subscription-pair {
               leaf priority-value {
                 type int32;
                 description "Priority value corresponding to bandwidth subscription reserved";
               }
               leaf priority-subscription-percent {
                 type int32;
                 description "Percentage of link capacity available for specific priority";
               }
             }
           }
           list reserved-bandwidth {
             leaf total-reserved-bandwidth-bps {
               type uint64;
               description "Total amount of bandwidth currently reserved in bits per second";
             }
           }
           list reserved-ct-bandwidth {
             leaf ct-bw0 {
               type string;
             }
             leaf ct-bw1 {
               type string;
             }
             leaf ct-bw2 {
               type string;
             }
             leaf ct-bw3 {
               type string;
             }
             leaf ct-bw4 {
               type string;
             }
             leaf ct-bw5 {
               type string;
             }
             leaf ct-bw6 {
               type string;
             }
             leaf ct-bw7 {
               type string;
             }
             leaf ct-class {
               type int32;
               description "Class type (0..7)";
             }
             leaf ct-bw0-bps {
               type uint64;
             }
             leaf ct-bw1-bps {
               type uint64;
             }
             leaf ct-bw2-bps {
               type uint64;
             }
             leaf ct-bw3-bps {
               type uint64;
             }
             leaf ct-bw4-bps {
               type uint64;
             }
             leaf ct-bw5-bps {
               type uint64;
             }
             leaf ct-bw6-bps {
               type uint64;
             }
             leaf ct-bw7-bps {
               type uint64;
             }
           }
           list detour-bandwidth {
             leaf total-reserved-bandwidth-bps {
               type uint64;
               description "Total amount of bandwidth currently reserved in bits per second";
             }
           }
           list overbooked-bandwidth {
             leaf total-reserved-bandwidth-bps {
               type uint64;
               description "Total amount of bandwidth currently reserved in bits per second";
             }
           }
           list overbooked-ct-bandwidth {
             leaf ct-bw0-bps {
               type uint64;
             }
             leaf ct-bw1-bps {
               type uint64;
             }
             leaf ct-bw2-bps {
               type uint64;
             }
             leaf ct-bw3-bps {
               type uint64;
             }
             leaf ct-bw4-bps {
               type uint64;
             }
             leaf ct-bw5-bps {
               type uint64;
             }
             leaf ct-bw6-bps {
               type uint64;
             }
             leaf ct-bw7-bps {
               type uint64;
             }
           }
           leaf active-reservation {
             type int32;
             description "Number of active reservations";
           }
           leaf preemption-count {
             type int32;
             description "Number of preemptions that occurred on an interface";
           }
           leaf update-threshold-max-reservable {
             type string;
             description "Change in non-rsvp bandwidth to trigger IGP update with units appended";
           }
           leaf update-threshold-max-reservable-percent {
             type int32;
             description "Percentage change in max-reservable bandwidth to trigger IGP update";
           }
           leaf update-threshold {
             type jt:unsigned-float;
             description "Percentage change in reserved bandwidth to trigger IGP update";
           }
           leaf update-threshold-value {
             type string;
             description "Change in reserved bandwidth to trigger IGP update with appended units";
           }
           leaf subscription {
             type int32;
             description "Percentage of link capacity available for bandwidth reservations";
           }
           leaf sr-subscription {
             type int32;
             description "Percentage of link capacity available after spring traffic";
           }
           leaf bc {
             type int32;
             description "Bandwidth constraint (0..7)";
           }
           leaf bc-description {
             type string;
             description "Description of the bandwidth constraint";
           }
           leaf static-bc-bandwidth {
             type string;
             description "Static bandwidth capacity for a bandwidth constraint with units appended";
           }
           leaf ct-class {
             type int32;
             description "Class type (0..7)";
           }
           leaf static-bandwidth {
             type string;
             description "Static bandwidth capacity of the link with units appended";
           }
           leaf available-bandwidth {
             type string;
             description "Amount of bandwidth available for reservations with units appended";
           }
           leaf ct-subscription {
             type int32;
             description "Subscription percentage per traffic class";
           }
           leaf max-available-bandwidth {
             type string;
             description "Maximum amount of bandwidth available for reservations, including the subscription factor, with units appended";
           }
           leaf max-available-description {
             type string;
             description "Description of the computation of the maximum available bandwidth";
           }
         }
         container detour {
           container explicit-route {
             leaf explicit-route.heading {
               type string;
               description "Explicit Route Object (ERO)";
             }
             container explicit-route-element {
               leaf address {
                 type jt:ipaddr;
               }
               leaf explicit-route-type {
                 type string;
               }
               leaf telink-id {
                 type int32;
                 description "Link identifier of unnumbered link";
               }
             }
           }
           leaf lsp-state {
             type string;
             description "State of an LSP";
           }
           leaf sender-tspec {
             type string;
             description "Sender TSpec";
           }
           leaf lsp-diffserv-info {
             type string;
             description "LSP DiffServ info";
           }
           leaf ct-bw {
             type string;
             description "Per-class bandwidth requested for E-LSPs and L-LSPs";
           }
           leaf adspec {
             type string;
             description "Adspec data element in an RSVP Path message";
           }
           leaf path-mtu {
             type int32;
             description "The value of the path MTU, as negotiated by the network";
           }
           leaf path-mtu-in-kernel {
             type int32;
             description "The value of the MTU used locally for forwarding";
           }
           leaf label-out {
             type string;
             description "Outgoing label";
           }
           container packet-information {
             leaf packet-information.heading {
               type string;
               description "RSVP packets sent or received per session";
             }
             leaf previous-hop {
               type jt:ipaddr;
               description "Previous-hop address";
             }
             leaf next-hop {
               type jt:ipaddr;
               description "Next-hop address";
             }
             leaf interface-name {
               type string;
               description "Name of interface";
             }
             leaf count {
               type int32;
             }
             leaf notify-destination {
               type jt:ipaddr;
               description "Notify address";
             }
             leaf entropy-label {
               type string;
               description "Entropy label";
             }
             leaf in-message-handle {
               type string;
               description "RSVP I/O handle for incoming message";
             }
             leaf in-message-id {
               type uint32;
               description "Incoming Message ID";
             }
             leaf in-epoch {
               type uint32;
               description "Incoming Epoch";
             }
             leaf out-message-state {
               type string;
               description "RSVP I/O state for outgoing message";
             }
             leaf out-message-id {
               type uint32;
               description "Outgoing Message ID";
             }
             leaf out-epoch {
               type uint32;
               description "Outgoing Epoch";
             }
           }
           container record-route {
             leaf record-route.heading {
               type string;
               description "Record Route Object (RRO)";
             }
             leaf address {
               type jt:ipaddr;
             }
             leaf telink-id {
               type int32;
               description "Link identifier of unnumbered link";
             }
             leaf self {
               type empty;
             }
             leaf incomplete {
               type empty;
             }
           }
         }
         container detour-branch {
           container explicit-route {
             leaf explicit-route.heading {
               type string;
               description "Explicit Route Object (ERO)";
             }
             container explicit-route-element {
               leaf address {
                 type jt:ipaddr;
               }
               leaf explicit-route-type {
                 type string;
               }
               leaf telink-id {
                 type int32;
                 description "Link identifier of unnumbered link";
               }
             }
           }
           leaf source-address {
             type jt:ipaddr;
           }
           leaf skip-address {
             type jt:ipaddr;
             description "Address of node or link to be skipped";
           }
           leaf lsp-state {
             type string;
             description "State of an LSP";
           }
           leaf sender-tspec {
             type string;
             description "Sender TSpec";
           }
           leaf adspec {
             type string;
             description "Adspec data element in an RSVP Path message";
           }
           leaf path-mtu {
             type int32;
             description "The value of the path MTU, as negotiated by the network";
           }
           container record-route {
             leaf record-route.heading {
               type string;
               description "Record Route Object (RRO)";
             }
             leaf address {
               type jt:ipaddr;
             }
             leaf telink-id {
               type int32;
               description "Link identifier of unnumbered link";
             }
             leaf self {
               type empty;
             }
             leaf incomplete {
               type empty;
             }
           }
           container packet-information {
             leaf packet-information.heading {
               type string;
               description "RSVP packets sent or received per session";
             }
             leaf previous-hop {
               type jt:ipaddr;
               description "Previous-hop address";
             }
             leaf next-hop {
               type jt:ipaddr;
               description "Next-hop address";
             }
             leaf interface-name {
               type string;
               description "Name of interface";
             }
             leaf count {
               type int32;
             }
             leaf notify-destination {
               type jt:ipaddr;
               description "Notify address";
             }
             leaf entropy-label {
               type string;
               description "Entropy label";
             }
             leaf in-message-handle {
               type string;
               description "RSVP I/O handle for incoming message";
             }
             leaf in-message-id {
               type uint32;
               description "Incoming Message ID";
             }
             leaf in-epoch {
               type uint32;
               description "Incoming Epoch";
             }
             leaf out-message-state {
               type string;
               description "RSVP I/O state for outgoing message";
             }
             leaf out-message-id {
               type uint32;
               description "Outgoing Message ID";
             }
             leaf out-epoch {
               type uint32;
               description "Outgoing Epoch";
             }
           }
           container detour-branch-labels {
             leaf label-in {
               type string;
               description "Incoming label";
             }
             leaf label-out {
               type string;
               description "Outgoing label";
             }
           }
         }
         container mpls-lsp {
           leaf destination-address {
             type jt:ipaddr;
             description "Session destination address";
           }
           leaf source-address {
             type jt:ipaddr;
           }
           leaf lsp-state {
             type string;
             description "State of an LSP";
           }
           leaf route-count {
             type int32;
             description "Number of active routes";
           }
           leaf is-primary {
             type empty;
             description "Path is a primary path";
           }
           leaf active-path {
             type string;
             description "Path that the LSP is currently using";
           }
           leaf name {
             type string;
           }
           leaf bidirectional {
             type empty;
             description "LSP is bidirectional";
           }
           leaf associated-bidirectional {
             type empty;
             description "LSP is associated-bidirectional";
           }
           leaf ext-assoc-bidir {
             type empty;
             description "Extended associated bidirectional LSP";
           }
           leaf lsp-packets {
             type string;
             description "LSP packet counters";
           }
           leaf lsp-bytes {
             type string;
             description "LSP byte counters";
           }
           container mpls-lsp-path {
             leaf path-active {
               type empty;
               description "Whether the path is active or not";
             }
             leaf title {
               type string;
             }
             leaf name {
               type string;
             }
             leaf received-rro {
               type string;
               description "RRO returned by the signaling protocol";
             }
             container admin-groups {
               leaf admin-groups.heading {
                 type string;
               }
               leaf color {
                 type int32;
               }
               leaf no-group-flag {
                 type empty;
               }
               leaf-list admin-group-name {
                 type string;
                 description "Name of the admin group";
               }
               leaf admin-group-number {
                 type int32;
                 description "Number of the admin group";
               }
             }
             container admin-groups-extended {
               leaf admin-groups-extended.heading {
                 type string;
               }
               leaf-list admin-group-name {
                 type string;
                 description "Name of the admin group";
               }
               leaf admin-group-number {
                 type int32;
                 description "Number of the admin group";
               }
             }
             container srlg {
               leaf srlg.heading {
                 type string;
               }
               leaf-list srlg-name {
                 type string;
                 description "Name of the srlg";
               }
             }
             container mpls-lsp-upstream-label {
               leaf vlan-id-label {
                 type uint32;
                 description "VLAN ID label configured for the LSP";
               }
             }
             container explicit-route {
               leaf explicit-route.heading {
                 type string;
                 description "Explicit Route Object (ERO)";
               }
               container explicit-route-element {
                 leaf address {
                   type jt:ipaddr;
                 }
                 leaf explicit-route-type {
                   type string;
                 }
                 leaf telink-id {
                   type int32;
                   description "Link identifier of unnumbered link";
                 }
               }
             }
             container oam-state {
               leaf oam-bfd-session-state {
                 type string;
               }
               leaf oam-lsp-ping-state {
                 type string;
               }
             }
             list path-history {
               leaf sequence-number {
                 type int64;
                 description "History event number";
               }
               leaf time {
                 type string;
                 description "Time of the event";
               }
               leaf log {
                 type string;
                 description "Supplemental information of the event";
               }
               leaf route {
                 type string;
                 description "Latest RRO contents, as reported by RSVP";
               }
             }
             container path-available-bandwidth {
               leaf path-available-bandwidth.heading {
                 type string;
                 description "Available bandwidth on an LSP path";
               }
               leaf bandwidth {
                 type int32;
               }
               leaf class-type {
                 type int32;
               }
               leaf class-bandwidth {
                 type int32;
               }
             }
             container layer2-connection {
               leaf neighbor-address {
                 type jt:ipaddr;
                 description "IP address of this neighbor";
               }
               leaf interface-name {
                 type string;
                 description "Name of interface";
               }
               leaf vc-id {
                 type int32;
               }
               container connection-bandwidth {
                 leaf connection-bandwidth.heading {
                   type string;
                   description "Bandwidth of a layer 2 connection";
                 }
                 leaf bandwidth {
                   type int32;
                 }
                 leaf class-type {
                   type int32;
                 }
                 leaf class-bandwidth {
                   type int32;
                 }
               }
             }
             leaf path-state {
               type string;
               description "State of the MPLS path";
             }
             leaf cos {
               type int32;
               description "CoS value";
             }
             leaf no-decrement-ttl {
               type empty;
               description "TTL";
             }
             leaf preference {
               type int32;
               description "Preference for the route";
             }
             leaf path-soft-preemption-pending {
               type empty;
               description "Soft preemption pending for this path";
             }
             leaf setup-priority {
               type int32;
               description "Priority with respect to taking resources";
             }
             leaf hold-priority {
               type int32;
               description "Priority with respect to holding resources";
             }
             leaf actual-setup-priority {
               type int32;
             }
             leaf actual-hold-priority {
               type int32;
             }
             leaf non-active-hold-priority {
               type int32;
               description "Signaled hold priority for non-active path";
             }
             leaf external-lsp-cspf-type {
               type string;
             }
             leaf bandwidth {
               type int32;
             }
             leaf actual-bandwidth {
               type int32;
             }
             leaf per-class-bandwidth-heading {
               type string;
             }
             leaf bandwidth_ct0 {
               type int32;
             }
             leaf bandwidth_ct1 {
               type int32;
             }
             leaf bandwidth_ct2 {
               type int32;
             }
             leaf bandwidth_ct3 {
               type int32;
             }
             leaf path-adaptive {
               type empty;
               description "LSP is adaptive";
             }
             leaf path-no-recordroute {
               type empty;
               description "Record route disabled";
             }
             leaf hoplimit {
               type int32;
               description "Maximum number of hops that can be traversed";
             }
             leaf optimize-timer {
               type int32;
               description "Optimize timer";
             }
             leaf smart-optimize-timer {
               type int32;
               description "Smart optimize timer";
             }
             leaf retry-timer {
               type int32;
             }
             leaf retry-limit {
               type int32;
             }
             leaf path-flap-count {
               type int32;
             }
             leaf path-mbb-count {
               type int32;
             }
             leaf path-in-place-update-count {
               type int32;
             }
             leaf external-cspf-status {
               type string;
               description "Status provided by External CSPF computation";
             }
             leaf cspf-status {
               type string;
               description "Status returned by CSPF computation";
             }
             container mpls-srlg {
               leaf-list srlg-name {
                 type string;
                 description "Name of the srlg";
               }
               leaf srlg-value {
                 type uint32;
                 description "Value of the srlg";
               }
               leaf srlg-cost {
                 type uint32;
                 description "Cost of the srlg";
               }
             }
           }
           container mpls-lsp-attributes {
             container mpls-lsp-upstream-label {
               leaf vlan-id-label {
                 type uint32;
                 description "VLAN ID label configured for the LSP";
               }
             }
             leaf signal-type {
               type string;
             }
             leaf encoding-type {
               type string;
               description "LSP encoding type";
             }
             leaf switching-type {
               type string;
               description "LSP switching capability";
             }
             leaf gpid {
               type string;
               description "LSP generalized PID";
             }
             leaf-list protection-type {
               type string;
               description "LSP protection desired";
             }
           }
           leaf lsp-description {
             type string;
             description "LSP description string (up to 80 characters)";
           }
           leaf lsp-pktbytes {
             type string;
             description "LSP packet and byte counters";
           }
           leaf lsp-id {
             type string;
           }
           leaf lsp-type {
             type string;
             description "Type of LSP";
           }
           leaf egress-label-operation {
             type string;
             description "Label advertised by egress";
           }
           leaf lsp-control-status {
             type string;
             description "Control status of LSP configured to be externally controlled";
           }
           leaf lsp-selfping-status {
             type string;
           }
           leaf lsp-diffserv-te-info {
             type string;
             description "LSP support of DiffServ-TE extensions";
           }
           leaf lsp-associated-lspname {
             type string;
             description "Associated LSP name";
           }
           leaf lsp-associated-lspsrc {
             type string;
             description "Associated LSP source address";
           }
           leaf ext-assoc-bidir-direction {
             type string;
             description "Ext-Assoc-Bidir direction";
           }
           leaf aggregate-lsp-pktbytes {
             type string;
             description "Aggregate LSP packet and byte counters";
           }
           leaf no-statistics {
             type empty;
             description "No statistics are available for this session";
           }
           leaf mpls-p2mp-name {
             type string;
           }
           leaf is-fastreroute {
             type empty;
             description "Fast reroute (one-to-one backup) is desired";
           }
           leaf is-linkprotection {
             type empty;
             description "Link protection (facility backup) is desired";
           }
           leaf is-nodeprotection {
             type empty;
             description "Link-Node protection (facility backup) is desired";
           }
           leaf is-inter-domain-path {
             type empty;
             description "Inter-domain LSP";
           }
           leaf load-balance {
             type string;
             description "Load-balancing algorithm chosen";
           }
           leaf metric {
             type int32;
           }
           leaf metric-follows-igp {
             type empty;
             description "LSP routes follow the destination IGP metric";
           }
           leaf metric-follows-igp-conditionally {
             type empty;
             description "LSP routes follow the destination IGP metric conditionally";
           }
           leaf actual-metric {
             type int32;
           }
           leaf track-install-prefix-igp-metric {
             type string;
             description "Install prefixes tracking their IGP metric";
           }
           leaf revert-timer {
             type string;
             description "Hold-down time before reverting to primary path.";
           }
           leaf revert-timer-remain {
             type string;
             description "Time remaining before reverting:";
           }
           leaf optimize-protection-timer {
             type int32;
             description "Optimize protection timer";
           }
           leaf lsp-creation-time {
             type string;
             description "Time when the LSP was created";
           }
           leaf lsp-soft-preemption-counter {
             type int32;
             description "Number of times the LSP was soft preempted";
           }
           leaf lsp-soft-preemption-time {
             type string;
             description "Time when the LSP was last soft preempted";
           }
           leaf retry-timer {
             type int32;
           }
           leaf retry-limit {
             type int32;
           }
           container admin-groups {
             leaf admin-groups.heading {
               type string;
             }
             leaf color {
               type int32;
             }
             leaf no-group-flag {
               type empty;
             }
             leaf-list admin-group-name {
               type string;
               description "Name of the admin group";
             }
             leaf admin-group-number {
               type int32;
               description "Number of the admin group";
             }
           }
           container admin-groups-extended {
             leaf admin-groups-extended.heading {
               type string;
             }
             leaf-list admin-group-name {
               type string;
               description "Name of the admin group";
             }
             leaf admin-group-number {
               type int32;
               description "Number of the admin group";
             }
           }
           container mpls-srlg {
             leaf-list srlg-name {
               type string;
               description "Name of the srlg";
             }
             leaf srlg-value {
               type uint32;
               description "Value of the srlg";
             }
             leaf srlg-cost {
               type uint32;
               description "Cost of the srlg";
             }
           }
           container mpls-lsp-autobandwidth {
             leaf monitor-lsp-bandwidth {
               type empty;
               description "Enable the bandwidth monitoring mode";
             }
             leaf minimum-bandwidth {
               type int32;
               description "Configured LSP minimum bandwidth";
             }
             leaf maximum-bandwidth {
               type int32;
               description "Configured LSP maximum bandwidth";
             }
             leaf dynamic-minimum-bandwidth {
               type int32;
               description "LSP dynamic minimum bandwidth (or last Max Avg Bw)";
             }
             leaf adjust-timer {
               type int32;
               description "Configured LSP adjust timer";
             }
             leaf adjust-threshold {
               type int32;
               description "Percentage change in average LSP utilization to trigger autoadjustment";
             }
             leaf adjust-threshold-absolute {
               type int32;
               description "Configured LSP Adjustment Threshold Absolute Bandwidth value";
             }
             leaf adjust-threshold-activate-bandwidth {
               type int32;
               description "Configured LSP adjust threshold bandwidth";
             }
             leaf maximum-average-bandwidth {
               type int32;
               description "Maximum Average BW";
             }
             leaf time-to-adjust {
               type int32;
               description "Time in which LSP will autoadjust bandwidth";
             }
             leaf autobw-minimum-bandwidth-adjust-interval {
               type int32;
             }
             leaf autobw-minimum-bandwidth-adjust-threshold-percent {
               type int32;
             }
             leaf autobw-minimum-bandwidth-adjust-threshold-value {
               type int32;
             }
             leaf time-to-expire-minimum-bandwidth-adjust {
               type int32;
               description "Time in which LSP will start changing minimum bandwidth";
             }
             leaf overflow-limit {
               type int32;
               description "Configured limit of consecutive overflow samples for LSP";
             }
             leaf overflow-sample-count {
               type int32;
               description "Number of consecutive overflow samples encountered";
             }
             leaf underflow-limit {
               type int32;
               description "Configured limit of consecutive underflow samples for LSP";
             }
             leaf underflow-sample-count {
               type int32;
               description "Number of consecutive underflow samples encountered";
             }
             leaf underflow-max-avg-bandwidth {
               type int32;
               description "Highest average bandwidth recorded so far for underflow samples";
             }
           }
         }
         leaf lsp-description {
           type string;
           description "LSP description string (up to 80 characters)";
         }
         leaf lsp-pktbytes {
           type string;
           description "LSP packet and byte counters";
         }
         leaf lsp-id {
           type string;
         }
         leaf p2mp-branch-id {
           type uint32;
         }
         leaf xc-psb-list {
           type string;
           description "List of PSBs part of the RSVP xc";
         }
         leaf xc-rsb-list {
           type string;
           description "List of RSBs part of the RSVP xc";
         }
         leaf is-detour {
           type empty;
           description "Session is a detour session";
         }
         leaf lsp-path-type {
           type string;
           description "Primary or secondary LSP path";
         }
         leaf graceful-deletion-triggered {
           type empty;
           description "Initiated graceful deletion procedure for the LSP";
         }
         leaf mpls-lsp-type {
           type string;
           description "Type of LSP";
         }
         leaf source-tna-address {
           type jt:ipaddr;
           description "Source TNA address for the connection";
         }
         leaf destination-tna-address {
           type jt:ipaddr;
           description "Destination TNA address for the connection";
         }
         leaf upstream-label-in {
           type string;
           description "Incoming upstream label";
         }
         leaf upstream-label-out {
           type string;
           description "Outgoing upstream label";
         }
         leaf lsp-associated-lspname {
           type string;
           description "Associated LSP name";
         }
         leaf lsp-associated-lspsrc {
           type string;
           description "Associated LSP source address";
         }
         leaf mpls-p2mp-lsp-name {
           type string;
         }
         leaf p2mp-remerge-state {
           type string;
           description "Re-merge status of the P2MP sub-LSP";
         }
         leaf lsp-aggregation {
           type string;
           description "Supports LSP aggregation";
         }
         leaf suggested-label-in {
           type int32;
           description "Suggested label received";
         }
         leaf suggested-label-out {
           type int32;
           description "Suggested label sent";
         }
         leaf recovery-label-in {
           type int32;
         }
         leaf recovery-label-out {
           type int32;
         }
         leaf no-statistics {
           type empty;
           description "No statistics are available for this session";
         }
         leaf psb-lifetime {
           type int32;
           description "Lifetime for a PSB after which the entry expires";
         }
         leaf psb-creation-time {
           type string;
           description "Time when this PSB was created";
         }
         leaf path-mtu {
           type int32;
           description "The value of the path MTU, as negotiated by the network";
         }
         leaf path-mtu-in-kernel {
           type int32;
           description "The value of the MTU used locally for forwarding";
         }
         leaf sender-tspec {
           type string;
           description "Sender TSpec";
         }
         leaf resv-fspec {
           type string;
           description "Resv FSpec";
         }
         leaf session-priority {
           type string;
           description "Setup/hold Priority";
         }
         leaf adspec {
           type string;
           description "Adspec data element in an RSVP Path message";
         }
         leaf lsp-diffserv-info {
           type string;
           description "LSP DiffServ info";
         }
         leaf ct-bw {
           type string;
           description "Per-class bandwidth requested for E-LSPs and L-LSPs";
         }
         leaf tunnel-id {
           type int32;
         }
         leaf proto-id {
           type int32;
         }
         leaf p2mp-subgroup-orig {
           type jt:ipaddr;
         }
         leaf self-id {
           type string;
           description "Statistics identifier for RSVP path state control block";
         }
         leaf nh-statistics-id {
           type string;
           description "Nexthop statistics identifier for RSVP path at ingress";
         }
         leaf route-statistics-id {
           type string;
           description "Route statistics identifier for RSVP path at egress";
         }
         leaf nh-traffic-class-statistics {
           type empty;
           description "Traffic class statistics are enabled at ingress";
         }
         leaf route-traffic-class-statistics {
           type empty;
           description "Traffic class statistics are enabled at egress";
         }
         leaf session-id {
           type int32;
           description "Unique identifier for RSVP session";
         }
         leaf is-fastreroute {
           type empty;
           description "Fast reroute (one-to-one backup) is desired";
         }
         leaf is-linkprotection {
           type empty;
           description "Link protection (facility backup) is desired";
         }
         leaf is-nodeprotection {
           type empty;
           description "Link-Node protection (facility backup) is desired";
         }
         leaf ep-plr-protector {
           type string;
         }
         leaf is-soft-preemption {
           type empty;
           description "Soft-preemption is desired";
         }
         leaf rsvp-path-status {
           type string;
         }
         leaf bypass-name {
           type string;
           description "Name of the bypass";
         }
         leaf rsvp-lp-backup-route-cnt {
           type int32;
           description "Number of routes tunneled through this bypass";
         }
         leaf rsvp-lp-backup-lsp-cnt {
           type int32;
           description "Number of backup RSVP LSPs tunneled through this bypass";
         }
         leaf rsvp-lp-psb-cnt {
           type int32;
           description "Number of sessions tunneled through this bypass";
         }
         leaf explicit-hop-expanded {
           type string;
           description "Explicit hop(s) expanded by this LSR";
         }
         container layer2-tspec {
           leaf switching-granularity {
             type string;
             description "Layer 2 switching granularity";
           }
           leaf mtu {
             type int32;
             description "MTU along an interface";
           }
           leaf atm-vp-bundle-size {
             type int32;
             description "VP bundle size";
           }
           leaf atm-cell-bundle-size {
             type int32;
             description "Maximum cell bundle size";
           }
         }
         container rsvp-lsp-enh-local-prot-status {
           leaf rsvp-lsp-enh-local-prot-admin-status {
             type string;
             description "Enhanced FRR local protection admin status";
           }
           leaf rsvp-lsp-enh-local-prot-disabled-reason {
             type string;
             description "Enhanced FRR local protection disabled reason";
           }
           leaf rsvp-lsp-enh-local-prot-refresh-interval {
             type string;
             description "Enhanced FRR refresh interval set for LSP";
           }
         }
         container rsvp-lsp-enh-local-prot-upstream {
           leaf rsvp-lsp-enh-lp-upstream-status {
             type string;
             description "Enhanced FRR local protection status upstream";
           }
           leaf rsvp-lsp-enh-lp-upstream-lp {
             type string;
             description "The node is LP-MP for Phop";
           }
           leaf rsvp-lsp-enh-lp-phop-addr {
             type jt:ipaddr;
             description "Phop PLR for which this node is LP-MP";
           }
           leaf rsvp-lsp-enh-lp-upstream-lp-status {
             type string;
             description "Current upstream LP-MP status";
           }
           leaf rsvp-lsp-enh-lp-upstream-np {
             type string;
             description "The node is NP-MP for PPhop";
           }
           leaf rsvp-lsp-enh-lp-pphop-addr {
             type jt:ipaddr;
             description "PPhop PLR for which this node is NP-MP";
           }
           leaf rsvp-lsp-enh-lp-upstream-np-status {
             type string;
             description "Current upstream NP-MP status";
           }
           leaf rsvp-lsp-enh-lp-upstream-disabled-reason {
             type string;
             description "Reason enhanced local protection is disabled upstream";
           }
           leaf rsvp-lsp-enh-local-prot-refresh-interval {
             type string;
             description "Enhanced FRR refresh interval set for LSP";
           }
         }
         container rsvp-lsp-enh-local-prot-downstream {
           leaf rsvp-lsp-enh-lp-downstream-status {
             type string;
             description "Enhanced FRR local protection status downstream";
           }
           leaf rsvp-lsp-enh-lp-downstream-lp {
             type string;
             description "The node has made link protection available";
           }
           leaf rsvp-lsp-enh-lp-nhop-addr {
             type jt:ipaddr;
             description "Nhop MP neigbor address";
           }
           leaf rsvp-lsp-enh-lp-downstream-np {
             type string;
             description "The node has made node protection available";
           }
           leaf rsvp-lsp-enh-lp-nnhop-addr {
             type jt:ipaddr;
             description "NNhop MP neighbor address";
           }
           leaf rsvp-lsp-enh-lp-current-status {
             type string;
             description "Current downstream protection status";
           }
           leaf rsvp-lsp-enh-lp-downstream-disabled-reason {
             type string;
             description "Reason enhanced local protection is disabled downstream";
           }
           leaf rsvp-lsp-enh-local-prot-refresh-interval {
             type string;
             description "Enhanced FRR refresh interval set for LSP";
           }
         }
         container lsp-bypass-constraints {
           leaf rsvp-lsp-bypass-constr {
             type empty;
             description "Bypass constraints for LSP";
           }
           leaf rsvp-lsp-bypass-constr-hop {
             type int32;
             description "Hop limit for bypass LSP";
           }
         }
         container record-route {
           leaf record-route.heading {
             type string;
             description "Record Route Object (RRO)";
           }
           leaf address {
             type jt:ipaddr;
           }
           leaf telink-id {
             type int32;
             description "Link identifier of unnumbered link";
           }
           leaf self {
             type empty;
           }
           leaf incomplete {
             type empty;
           }
         }
         container exclude-route {
           leaf exclude-route.heading {
             type string;
             description "Exclude Route Object (XRO)";
           }
           leaf address {
             type jt:ipaddr;
           }
         }
         container rsvp-lsp-pop-and-fwd {
           leaf rsvp-lsp-pop-and-fwd.heading {
             type string;
           }
           leaf etld-in {
             type uint32;
             description "Incoming effective transport label stack depth";
           }
           leaf etld-out {
             type uint32;
             description "Outgoing effective transport label stack depth";
           }
           leaf delegation-hop {
             type string;
             description "Delegation state";
           }
         }
         container lsp-attribute-flags {
           leaf non-php {
             type empty;
             description "Non-PHP";
           }
           leaf oob {
             type empty;
             description "Out-of-band mapping";
           }
         }
         list lp-history {
           leaf sequence-number {
             type int64;
             description "History event number";
           }
           leaf time {
             type string;
             description "Time of the event";
           }
           leaf log {
             type string;
             description "Supplemental information of the event";
           }
           leaf route {
             type string;
             description "Latest RRO contents, as reported by RSVP";
           }
         }
         container admin-groups {
           leaf admin-groups.heading {
             type string;
           }
           leaf color {
             type int32;
           }
           leaf no-group-flag {
             type empty;
           }
           leaf-list admin-group-name {
             type string;
             description "Name of the admin group";
           }
           leaf admin-group-number {
             type int32;
             description "Number of the admin group";
           }
         }
         container protection-attribute {
           leaf protect-lsp-type {
             type string;
             description "Type of LSP for protection purposes";
           }
           leaf protect-lsp-role {
             type string;
             description "Role of LSP for protection purposes";
           }
           leaf protect-protection-type {
             type string;
             description "Type of protection being used";
           }
           leaf protect-secondary-operational {
             type empty;
             description "Protecting LSP is operational and carrying protected traffic";
           }
         }
         container association-attribute {
           leaf association-type {
             type string;
             description "Type of association object";
           }
           leaf association-source {
             type jt:ipaddr;
             description "Source node defining the association";
           }
           leaf association-id {
             type int32;
             description "Identifier for the association";
           }
         }
         list lsp-history {
           leaf lsp-history-sequence-number {
             type int32;
             description "LSP history event number";
           }
           leaf lsp-history-time {
             type string;
             description "Time of the event";
           }
           leaf lsp-history-log {
             type string;
             description "Supplementatal information of the event";
           }
           leaf lsp-history-route {
             type string;
             description "RRO contents received in latest Resv message";
           }
         }
         list lsp-message-statistics {
           leaf rsvp-message {
             type string;
           }
           leaf messages-sent {
             type int32;
             description "Total number of messages sent";
           }
           leaf messages-received {
             type int32;
             description "Total number of messages received";
           }
         }
       }
       container mpls-p2mp-lsp {
         leaf mpls-p2mp-name {
           type string;
         }
         leaf mpls-p2mp-branch-count {
           type string;
         }
       }
       container mpls-container-lsp {
         description "MPLS container-label-switched path information";
         leaf mpls-container-lsp-name {
           type string;
         }
         leaf mpls-container-lsp-state {
           type string;
         }
         leaf mpls-container-member-count {
           type string;
         }
         leaf container-active-path {
           type string;
           description "Path that the member LSP is currently using";
         }
         leaf container-is-primary {
           type empty;
           description "Path is a primary path";
         }
         leaf lsp-packets {
           type string;
           description "LSP packet counters";
         }
         leaf lsp-bytes {
           type string;
           description "LSP byte counters";
         }
         leaf lsp-control-status {
           type string;
           description "Control status of LSP configured to be externally controlled";
         }
         leaf lsp-selfping-status {
           type string;
         }
         container mpls-lsp-path {
           description "Primary or secondary LSP path";
           leaf received-rro {
             type string;
             description "RRO returned by the signaling protocol";
           }
           container admin-groups {
             leaf admin-groups.heading {
               type string;
             }
             leaf color {
               type int32;
             }
             leaf no-group-flag {
               type empty;
             }
             leaf-list admin-group-name {
               type string;
               description "Name of the admin group";
             }
             leaf admin-group-number {
               type int32;
               description "Number of the admin group";
             }
           }
           container admin-groups-extended {
             leaf admin-groups-extended.heading {
               type string;
             }
             leaf-list admin-group-name {
               type string;
               description "Name of the admin group";
             }
             leaf admin-group-number {
               type int32;
               description "Number of the admin group";
             }
           }
           container srlg {
             leaf srlg.heading {
               type string;
             }
             leaf-list srlg-name {
               type string;
               description "Name of the srlg";
             }
           }
           container mpls-lsp-upstream-label {
             description "Upstream label configured for the LSP";
             leaf vlan-id-label {
               type uint32;
               description "VLAN ID label configured for the LSP";
             }
           }
           container explicit-route {
             description "Explicit Route Object (ERO)";
             leaf explicit-route.heading {
               type string;
               description "Explicit Route Object (ERO)";
             }
             container explicit-route-element {
               leaf address {
                 type jt:ipaddr;
               }
               leaf explicit-route-type {
                 type string;
               }
               leaf telink-id {
                 type int32;
                 description "Link identifier of unnumbered link";
               }
             }
           }
           container oam-state {
             description "OAM state information";
             leaf oam-bfd-session-state {
               type string;
             }
             leaf oam-lsp-ping-state {
               type string;
             }
           }
           list path-history {
             description "Log over time of LSP path-related events";
             leaf sequence-number {
               type int64;
               description "History event number";
             }
             leaf time {
               type string;
               description "Time of the event";
             }
             leaf log {
               type string;
               description "Supplemental information of the event";
             }
             leaf route {
               type string;
               description "Latest RRO contents, as reported by RSVP";
             }
           }
           container path-available-bandwidth {
             description "Available bandwidth on an LSP path";
             leaf path-available-bandwidth.heading {
               type string;
               description "Available bandwidth on an LSP path";
             }
             leaf bandwidth {
               type int32;
             }
             leaf class-type {
               type int32;
             }
             leaf class-bandwidth {
               type int32;
             }
           }
           container layer2-connection {
             description "Layer 2 connection using the LSP path";
             leaf neighbor-address {
               type jt:ipaddr;
               description "IP address of this neighbor";
             }
             leaf interface-name {
               type string;
               description "Name of interface";
             }
             leaf vc-id {
               type int32;
             }
             container connection-bandwidth {
               description "Bandwidth of a layer 2 connection";
               leaf connection-bandwidth.heading {
                 type string;
                 description "Bandwidth of a layer 2 connection";
               }
               leaf bandwidth {
                 type int32;
               }
               leaf class-type {
                 type int32;
               }
               leaf class-bandwidth {
                 type int32;
               }
             }
           }
         }
         container mpls-container-lsp-splitting-merging {
           leaf minimum-member-lsps {
             type int32;
             description "Configured minimum LSPs";
           }
           leaf maximum-member-lsps {
             type int32;
             description "Configured maximum LSPs";
           }
           leaf aggregate-bandwidth {
             type int32;
             description "Aggregate bandwidth";
           }
           leaf current-bandwidth {
             type int32;
             description "Sampled Aggregate bandwidth";
           }
           leaf normalize-interval {
             type int32;
             description "Configured LSP normalize timer";
           }
           leaf splitting-merging-threshold {
             type int32;
             description "Percentage change in aggregate LSP utilization to trigger normalization";
           }
           leaf maximum-signaling-bandwidth {
             type int32;
             description "Configured signaling maximum bandwidth";
           }
           leaf minimum-signaling-bandwidth {
             type int32;
             description "Configured signaling minimum bandwidth";
           }
           leaf maximum-splitting-bandwidth {
             type int32;
             description "Configured splitting maximum bandwidth";
           }
           leaf minimum-splitting-bandwidth {
             type int32;
             description "Configured splitting minimum bandwidth";
           }
           leaf normalization-mode {
             type string;
           }
           leaf sampling-mode {
             type string;
             description "Sampling Attributes";
           }
           leaf time-to-normalize {
             type int32;
             description "Time in which LSP will normalize";
           }
           leaf aggregate-packets {
             type int32;
             description "Aggregate packets";
           }
           leaf aggregate-bytes {
             type int32;
             description "Aggregate bytes";
           }
         }
         container mpls-container-lsp-history {
           description "Log over time of container LSP related events";
           leaf sequence-number {
             type int64;
             description "History event number";
           }
           leaf time {
             type string;
             description "Time of the event";
           }
           leaf log {
             type string;
             description "Supplemental information of the event";
           }
           leaf route {
             type string;
             description "Latest RRO contents, as reported by RSVP";
           }
         }
         container mpls-lsp-attributes {
           container mpls-lsp-upstream-label {
             description "Upstream label configured for the LSP";
             leaf vlan-id-label {
               type uint32;
               description "VLAN ID label configured for the LSP";
             }
           }
         }
       }
       container mpls-container-lsp-member-summary {
         container mpls-container-lsp {
           description "MPLS container-label-switched path information";
           leaf mpls-container-lsp-name {
             type string;
           }
           leaf mpls-container-lsp-state {
             type string;
           }
           leaf mpls-container-member-count {
             type string;
           }
           leaf container-active-path {
             type string;
             description "Path that the member LSP is currently using";
           }
           leaf container-is-primary {
             type empty;
             description "Path is a primary path";
           }
           leaf lsp-packets {
             type string;
             description "LSP packet counters";
           }
           leaf lsp-bytes {
             type string;
             description "LSP byte counters";
           }
           leaf lsp-control-status {
             type string;
             description "Control status of LSP configured to be externally controlled";
           }
           leaf lsp-selfping-status {
             type string;
           }
           container mpls-lsp-path {
             description "Primary or secondary LSP path";
             leaf received-rro {
               type string;
               description "RRO returned by the signaling protocol";
             }
             container admin-groups {
               leaf admin-groups.heading {
                 type string;
               }
               leaf color {
                 type int32;
               }
               leaf no-group-flag {
                 type empty;
               }
               leaf-list admin-group-name {
                 type string;
                 description "Name of the admin group";
               }
               leaf admin-group-number {
                 type int32;
                 description "Number of the admin group";
               }
             }
             container admin-groups-extended {
               leaf admin-groups-extended.heading {
                 type string;
               }
               leaf-list admin-group-name {
                 type string;
                 description "Name of the admin group";
               }
               leaf admin-group-number {
                 type int32;
                 description "Number of the admin group";
               }
             }
             container srlg {
               leaf srlg.heading {
                 type string;
               }
               leaf-list srlg-name {
                 type string;
                 description "Name of the srlg";
               }
             }
             container mpls-lsp-upstream-label {
               description "Upstream label configured for the LSP";
               leaf vlan-id-label {
                 type uint32;
                 description "VLAN ID label configured for the LSP";
               }
             }
             container explicit-route {
               description "Explicit Route Object (ERO)";
               leaf explicit-route.heading {
                 type string;
                 description "Explicit Route Object (ERO)";
               }
               container explicit-route-element {
                 leaf address {
                   type jt:ipaddr;
                 }
                 leaf explicit-route-type {
                   type string;
                 }
                 leaf telink-id {
                   type int32;
                   description "Link identifier of unnumbered link";
                 }
               }
             }
             container oam-state {
               description "OAM state information";
               leaf oam-bfd-session-state {
                 type string;
               }
               leaf oam-lsp-ping-state {
                 type string;
               }
             }
             list path-history {
               description "Log over time of LSP path-related events";
               leaf sequence-number {
                 type int64;
                 description "History event number";
               }
               leaf time {
                 type string;
                 description "Time of the event";
               }
               leaf log {
                 type string;
                 description "Supplemental information of the event";
               }
               leaf route {
                 type string;
                 description "Latest RRO contents, as reported by RSVP";
               }
             }
             container path-available-bandwidth {
               description "Available bandwidth on an LSP path";
               leaf path-available-bandwidth.heading {
                 type string;
                 description "Available bandwidth on an LSP path";
               }
               leaf bandwidth {
                 type int32;
               }
               leaf class-type {
                 type int32;
               }
               leaf class-bandwidth {
                 type int32;
               }
             }
             container layer2-connection {
               description "Layer 2 connection using the LSP path";
               leaf neighbor-address {
                 type jt:ipaddr;
                 description "IP address of this neighbor";
               }
               leaf interface-name {
                 type string;
                 description "Name of interface";
               }
               leaf vc-id {
                 type int32;
               }
               container connection-bandwidth {
                 description "Bandwidth of a layer 2 connection";
                 leaf connection-bandwidth.heading {
                   type string;
                   description "Bandwidth of a layer 2 connection";
                 }
                 leaf bandwidth {
                   type int32;
                 }
                 leaf class-type {
                   type int32;
                 }
                 leaf class-bandwidth {
                   type int32;
                 }
               }
             }
           }
           container mpls-container-lsp-splitting-merging {
             leaf minimum-member-lsps {
               type int32;
               description "Configured minimum LSPs";
             }
             leaf maximum-member-lsps {
               type int32;
               description "Configured maximum LSPs";
             }
             leaf aggregate-bandwidth {
               type int32;
               description "Aggregate bandwidth";
             }
             leaf current-bandwidth {
               type int32;
               description "Sampled Aggregate bandwidth";
             }
             leaf normalize-interval {
               type int32;
               description "Configured LSP normalize timer";
             }
             leaf splitting-merging-threshold {
               type int32;
               description "Percentage change in aggregate LSP utilization to trigger normalization";
             }
             leaf maximum-signaling-bandwidth {
               type int32;
               description "Configured signaling maximum bandwidth";
             }
             leaf minimum-signaling-bandwidth {
               type int32;
               description "Configured signaling minimum bandwidth";
             }
             leaf maximum-splitting-bandwidth {
               type int32;
               description "Configured splitting maximum bandwidth";
             }
             leaf minimum-splitting-bandwidth {
               type int32;
               description "Configured splitting minimum bandwidth";
             }
             leaf normalization-mode {
               type string;
             }
             leaf sampling-mode {
               type string;
               description "Sampling Attributes";
             }
             leaf time-to-normalize {
               type int32;
               description "Time in which LSP will normalize";
             }
             leaf aggregate-packets {
               type int32;
               description "Aggregate packets";
             }
             leaf aggregate-bytes {
               type int32;
               description "Aggregate bytes";
             }
           }
           container mpls-container-lsp-history {
             description "Log over time of container LSP related events";
             leaf sequence-number {
               type int64;
               description "History event number";
             }
             leaf time {
               type string;
               description "Time of the event";
             }
             leaf log {
               type string;
               description "Supplemental information of the event";
             }
             leaf route {
               type string;
               description "Latest RRO contents, as reported by RSVP";
             }
           }
           container mpls-lsp-attributes {
             container mpls-lsp-upstream-label {
               description "Upstream label configured for the LSP";
               leaf vlan-id-label {
                 type uint32;
                 description "VLAN ID label configured for the LSP";
               }
             }
           }
         }
       }
       container container-rsvp-session {
         container mpls-container-lsp {
           leaf destination-address {
             type jt:ipaddr;
             description "Session destination address";
           }
           leaf source-address {
             type jt:ipaddr;
           }
           leaf lsp-state {
             type string;
             description "State of an LSP";
           }
           leaf route-count {
             type int32;
             description "Number of active routes";
           }
           leaf is-primary {
             type empty;
             description "Path is a primary path";
           }
           leaf active-path {
             type string;
             description "Path that the LSP is currently using";
           }
           leaf container-member-name {
             type string;
             description "Path that the member LSP is currently using";
           }
           leaf label-out {
             type string;
             description "Outgoing label";
           }
           container explicit-route {
             leaf explicit-route.heading {
               type string;
               description "Explicit Route Object (ERO)";
             }
             container explicit-route-element {
               leaf address {
                 type jt:ipaddr;
               }
               leaf explicit-route-type {
                 type string;
               }
               leaf telink-id {
                 type int32;
                 description "Link identifier of unnumbered link";
               }
             }
           }
           leaf lsp-description {
             type string;
             description "LSP description string (up to 80 characters)";
           }
           leaf container-active-path {
             type string;
             description "Path that the member LSP is currently using";
           }
           leaf container-is-primary {
             type empty;
             description "Path is a primary path";
           }
           leaf lsp-packets {
             type string;
             description "LSP packet counters";
           }
           leaf lsp-bytes {
             type string;
             description "LSP byte counters";
           }
           leaf lsp-control-status {
             type string;
             description "Control status of LSP configured to be externally controlled";
           }
           leaf lsp-selfping-status {
             type string;
           }
           container mpls-lsp-path {
             leaf name {
               type string;
             }
             leaf received-rro {
               type string;
               description "RRO returned by the signaling protocol";
             }
             container admin-groups {
               leaf admin-groups.heading {
                 type string;
               }
               leaf color {
                 type int32;
               }
               leaf no-group-flag {
                 type empty;
               }
               leaf-list admin-group-name {
                 type string;
                 description "Name of the admin group";
               }
               leaf admin-group-number {
                 type int32;
                 description "Number of the admin group";
               }
             }
             container admin-groups-extended {
               leaf admin-groups-extended.heading {
                 type string;
               }
               leaf-list admin-group-name {
                 type string;
                 description "Name of the admin group";
               }
               leaf admin-group-number {
                 type int32;
                 description "Number of the admin group";
               }
             }
             container srlg {
               leaf srlg.heading {
                 type string;
               }
               leaf-list srlg-name {
                 type string;
                 description "Name of the srlg";
               }
             }
             container mpls-lsp-upstream-label {
               leaf vlan-id-label {
                 type uint32;
                 description "VLAN ID label configured for the LSP";
               }
             }
             container explicit-route {
               leaf explicit-route.heading {
                 type string;
                 description "Explicit Route Object (ERO)";
               }
               container explicit-route-element {
                 leaf address {
                   type jt:ipaddr;
                 }
                 leaf explicit-route-type {
                   type string;
                 }
                 leaf telink-id {
                   type int32;
                   description "Link identifier of unnumbered link";
                 }
               }
             }
             container oam-state {
               leaf oam-bfd-session-state {
                 type string;
               }
               leaf oam-lsp-ping-state {
                 type string;
               }
             }
             list path-history {
               leaf sequence-number {
                 type int64;
                 description "History event number";
               }
               leaf time {
                 type string;
                 description "Time of the event";
               }
               leaf log {
                 type string;
                 description "Supplemental information of the event";
               }
               leaf route {
                 type string;
                 description "Latest RRO contents, as reported by RSVP";
               }
             }
             container path-available-bandwidth {
               leaf path-available-bandwidth.heading {
                 type string;
                 description "Available bandwidth on an LSP path";
               }
               leaf bandwidth {
                 type int32;
               }
               leaf class-type {
                 type int32;
               }
               leaf class-bandwidth {
                 type int32;
               }
             }
             container layer2-connection {
               leaf neighbor-address {
                 type jt:ipaddr;
                 description "IP address of this neighbor";
               }
               leaf interface-name {
                 type string;
                 description "Name of interface";
               }
               leaf vc-id {
                 type int32;
               }
               container connection-bandwidth {
                 leaf connection-bandwidth.heading {
                   type string;
                   description "Bandwidth of a layer 2 connection";
                 }
                 leaf bandwidth {
                   type int32;
                 }
                 leaf class-type {
                   type int32;
                 }
                 leaf class-bandwidth {
                   type int32;
                 }
               }
             }
             leaf path-active {
               type empty;
               description "Whether the path is active or not";
             }
             leaf title {
               type string;
             }
           }
           container mpls-container-lsp-splitting-merging {
             leaf minimum-member-lsps {
               type int32;
               description "Configured minimum LSPs";
             }
             leaf maximum-member-lsps {
               type int32;
               description "Configured maximum LSPs";
             }
             leaf aggregate-bandwidth {
               type int32;
               description "Aggregate bandwidth";
             }
             leaf current-bandwidth {
               type int32;
               description "Sampled Aggregate bandwidth";
             }
             leaf normalize-interval {
               type int32;
               description "Configured LSP normalize timer";
             }
             leaf splitting-merging-threshold {
               type int32;
               description "Percentage change in aggregate LSP utilization to trigger normalization";
             }
             leaf maximum-signaling-bandwidth {
               type int32;
               description "Configured signaling maximum bandwidth";
             }
             leaf minimum-signaling-bandwidth {
               type int32;
               description "Configured signaling minimum bandwidth";
             }
             leaf maximum-splitting-bandwidth {
               type int32;
               description "Configured splitting maximum bandwidth";
             }
             leaf minimum-splitting-bandwidth {
               type int32;
               description "Configured splitting minimum bandwidth";
             }
             leaf normalization-mode {
               type string;
             }
             leaf sampling-mode {
               type string;
               description "Sampling Attributes";
             }
             leaf time-to-normalize {
               type int32;
               description "Time in which LSP will normalize";
             }
             leaf aggregate-packets {
               type int32;
               description "Aggregate packets";
             }
             leaf aggregate-bytes {
               type int32;
               description "Aggregate bytes";
             }
           }
           container mpls-container-lsp-history {
             leaf sequence-number {
               type int64;
               description "History event number";
             }
             leaf time {
               type string;
               description "Time of the event";
             }
             leaf log {
               type string;
               description "Supplemental information of the event";
             }
             leaf route {
               type string;
               description "Latest RRO contents, as reported by RSVP";
             }
           }
           container mpls-lsp-attributes {
             container mpls-lsp-upstream-label {
               leaf vlan-id-label {
                 type uint32;
                 description "VLAN ID label configured for the LSP";
               }
             }
           }
           leaf lsp-pktbytes {
             type string;
             description "LSP packet and byte counters";
           }
           leaf name {
             type string;
           }
           leaf bidirectional {
             type empty;
             description "LSP is bidirectional";
           }
           leaf associated-bidirectional {
             type empty;
             description "LSP is associated-bidirectional";
           }
           leaf lsp-type {
             type string;
             description "Type of LSP";
           }
           leaf egress-label-operation {
             type string;
             description "Label advertised by egress";
           }
           leaf lsp-diffserv-te-info {
             type string;
             description "LSP support of DiffServ-TE extensions";
           }
           leaf aggregate-lsp-pktbytes {
             type string;
             description "Aggregate LSP packet and byte counters";
           }
           leaf no-statistics {
             type empty;
             description "No statistics are available for this session";
           }
           leaf mpls-container-name {
             type string;
             description "Name of the container LSP";
           }
           leaf is-fastreroute {
             type empty;
             description "Fast reroute (one-to-one backup) is desired";
           }
           leaf is-linkprotection {
             type empty;
             description "Link protection (facility backup) is desired";
           }
           leaf is-nodeprotection {
             type empty;
             description "Link-Node protection (facility backup) is desired";
           }
           leaf is-inter-domain-path {
             type empty;
             description "Inter-domain LSP";
           }
           leaf load-balance {
             type string;
             description "Load-balancing algorithm chosen";
           }
           leaf metric {
             type int32;
           }
           leaf optimize-protection-timer {
             type int32;
             description "Optimize protection timer";
           }
           leaf lsp-creation-time {
             type string;
             description "Time when the LSP was created";
           }
           leaf lsp-soft-preemption-counter {
             type int32;
             description "Number of times the LSP was soft preempted";
           }
           leaf lsp-soft-preemption-time {
             type string;
             description "Time when the LSP was last soft preempted";
           }
           leaf retry-timer {
             type int32;
           }
           leaf retry-limit {
             type int32;
           }
           leaf received-rro {
             type string;
             description "RRO returned by the signaling protocol";
           }
           container admin-groups {
             leaf admin-groups.heading {
               type string;
             }
             leaf color {
               type int32;
             }
             leaf no-group-flag {
               type empty;
             }
             leaf-list admin-group-name {
               type string;
               description "Name of the admin group";
             }
             leaf admin-group-number {
               type int32;
               description "Number of the admin group";
             }
           }
           container admin-groups-extended {
             leaf admin-groups-extended.heading {
               type string;
             }
             leaf-list admin-group-name {
               type string;
               description "Name of the admin group";
             }
             leaf admin-group-number {
               type int32;
               description "Number of the admin group";
             }
           }
           container srlg {
             leaf srlg.heading {
               type string;
             }
             leaf-list srlg-name {
               type string;
               description "Name of the srlg";
             }
           }
           container mpls-lsp-upstream-label {
             leaf vlan-id-label {
               type uint32;
               description "VLAN ID label configured for the LSP";
             }
           }
           container oam-state {
             leaf oam-bfd-session-state {
               type string;
             }
             leaf oam-lsp-ping-state {
               type string;
             }
           }
           list path-history {
             leaf sequence-number {
               type int64;
               description "History event number";
             }
             leaf time {
               type string;
               description "Time of the event";
             }
             leaf log {
               type string;
               description "Supplemental information of the event";
             }
             leaf route {
               type string;
               description "Latest RRO contents, as reported by RSVP";
             }
           }
           container path-available-bandwidth {
             leaf path-available-bandwidth.heading {
               type string;
               description "Available bandwidth on an LSP path";
             }
             leaf bandwidth {
               type int32;
             }
             leaf class-type {
               type int32;
             }
             leaf class-bandwidth {
               type int32;
             }
           }
           container layer2-connection {
             leaf neighbor-address {
               type jt:ipaddr;
               description "IP address of this neighbor";
             }
             leaf interface-name {
               type string;
               description "Name of interface";
             }
             leaf vc-id {
               type int32;
             }
             container connection-bandwidth {
               leaf connection-bandwidth.heading {
                 type string;
                 description "Bandwidth of a layer 2 connection";
               }
               leaf bandwidth {
                 type int32;
               }
               leaf class-type {
                 type int32;
               }
               leaf class-bandwidth {
                 type int32;
               }
             }
           }
           container mpls-srlg {
             leaf-list srlg-name {
               type string;
               description "Name of the srlg";
             }
             leaf srlg-value {
               type uint32;
               description "Value of the srlg";
             }
             leaf srlg-cost {
               type uint32;
               description "Cost of the srlg";
             }
           }
         }
         container mpls-lsp {
           leaf destination-address {
             type jt:ipaddr;
             description "Session destination address";
           }
           leaf source-address {
             type jt:ipaddr;
           }
           leaf lsp-state {
             type string;
             description "State of an LSP";
           }
           leaf label-out {
             type string;
             description "Outgoing label";
           }
           container explicit-route {
           }
           leaf name {
             type string;
           }
           leaf lsp-description {
             type string;
             description "LSP description string (up to 80 characters)";
           }
           leaf lsp-packets {
             type string;
             description "LSP packet counters";
           }
           leaf lsp-bytes {
             type string;
             description "LSP byte counters";
           }
           container mpls-lsp-path {
             leaf path-active {
               type empty;
               description "Whether the path is active or not";
             }
             leaf title {
               type string;
             }
             leaf name {
               type string;
             }
             leaf received-rro {
               type string;
               description "RRO returned by the signaling protocol";
             }
             container admin-groups {
               leaf admin-groups.heading {
                 type string;
               }
               leaf color {
                 type int32;
               }
               leaf no-group-flag {
                 type empty;
               }
               leaf-list admin-group-name {
                 type string;
                 description "Name of the admin group";
               }
               leaf admin-group-number {
                 type int32;
                 description "Number of the admin group";
               }
             }
             container admin-groups-extended {
               leaf admin-groups-extended.heading {
                 type string;
               }
               leaf-list admin-group-name {
                 type string;
                 description "Name of the admin group";
               }
               leaf admin-group-number {
                 type int32;
                 description "Number of the admin group";
               }
             }
             container srlg {
               leaf srlg.heading {
                 type string;
               }
               leaf-list srlg-name {
                 type string;
                 description "Name of the srlg";
               }
             }
             container mpls-lsp-upstream-label {
               leaf vlan-id-label {
                 type uint32;
                 description "VLAN ID label configured for the LSP";
               }
             }
             container explicit-route {
               leaf explicit-route.heading {
                 type string;
                 description "Explicit Route Object (ERO)";
               }
               container explicit-route-element {
                 leaf address {
                   type jt:ipaddr;
                 }
                 leaf explicit-route-type {
                   type string;
                 }
                 leaf telink-id {
                   type int32;
                   description "Link identifier of unnumbered link";
                 }
               }
             }
             container oam-state {
               leaf oam-bfd-session-state {
                 type string;
               }
               leaf oam-lsp-ping-state {
                 type string;
               }
             }
             list path-history {
               leaf sequence-number {
                 type int64;
                 description "History event number";
               }
               leaf time {
                 type string;
                 description "Time of the event";
               }
               leaf log {
                 type string;
                 description "Supplemental information of the event";
               }
               leaf route {
                 type string;
                 description "Latest RRO contents, as reported by RSVP";
               }
             }
             container path-available-bandwidth {
               leaf path-available-bandwidth.heading {
                 type string;
                 description "Available bandwidth on an LSP path";
               }
               leaf bandwidth {
                 type int32;
               }
               leaf class-type {
                 type int32;
               }
               leaf class-bandwidth {
                 type int32;
               }
             }
             container layer2-connection {
               leaf neighbor-address {
                 type jt:ipaddr;
                 description "IP address of this neighbor";
               }
               leaf interface-name {
                 type string;
                 description "Name of interface";
               }
               leaf vc-id {
                 type int32;
               }
               container connection-bandwidth {
                 leaf connection-bandwidth.heading {
                   type string;
                   description "Bandwidth of a layer 2 connection";
                 }
                 leaf bandwidth {
                   type int32;
                 }
                 leaf class-type {
                   type int32;
                 }
                 leaf class-bandwidth {
                   type int32;
                 }
               }
             }
           }
           container mpls-lsp-attributes {
             container mpls-lsp-upstream-label {
               leaf vlan-id-label {
                 type uint32;
                 description "VLAN ID label configured for the LSP";
               }
             }
           }
           leaf lsp-pktbytes {
             type string;
             description "LSP packet and byte counters";
           }
           leaf bidirectional {
             type empty;
             description "LSP is bidirectional";
           }
           leaf associated-bidirectional {
             type empty;
             description "LSP is associated-bidirectional";
           }
           leaf path-mtu {
             type int32;
             description "The value of the path MTU, as negotiated by the network";
           }
           leaf path-mtu-in-kernel {
             type int32;
             description "The value of the MTU used locally for forwarding";
           }
           leaf sender-tspec {
             type string;
             description "Sender TSpec";
           }
           leaf adspec {
             type string;
             description "Adspec data element in an RSVP Path message";
           }
           leaf lsp-diffserv-info {
             type string;
             description "LSP DiffServ info";
           }
           leaf ct-bw {
             type string;
             description "Per-class bandwidth requested for E-LSPs and L-LSPs";
           }
           container packet-information {
             leaf packet-information.heading {
               type string;
               description "RSVP packets sent or received per session";
             }
             leaf previous-hop {
               type jt:ipaddr;
               description "Previous-hop address";
             }
             leaf next-hop {
               type jt:ipaddr;
               description "Next-hop address";
             }
             leaf interface-name {
               type string;
               description "Name of interface";
             }
             leaf count {
               type int32;
             }
             leaf notify-destination {
               type jt:ipaddr;
               description "Notify address";
             }
             leaf entropy-label {
               type string;
               description "Entropy label";
             }
             leaf in-message-handle {
               type string;
               description "RSVP I/O handle for incoming message";
             }
             leaf in-message-id {
               type uint32;
               description "Incoming Message ID";
             }
             leaf in-epoch {
               type uint32;
               description "Incoming Epoch";
             }
             leaf out-message-state {
               type string;
               description "RSVP I/O state for outgoing message";
             }
             leaf out-message-id {
               type uint32;
               description "Outgoing Message ID";
             }
             leaf out-epoch {
               type uint32;
               description "Outgoing Epoch";
             }
           }
         }
         container detour {
           leaf lsp-state {
             type string;
             description "State of an LSP";
           }
           leaf label-out {
             type string;
             description "Outgoing label";
           }
           container explicit-route {
           }
           leaf sender-tspec {
             type string;
             description "Sender TSpec";
           }
           leaf lsp-diffserv-info {
             type string;
             description "LSP DiffServ info";
           }
           leaf ct-bw {
             type string;
             description "Per-class bandwidth requested for E-LSPs and L-LSPs";
           }
           leaf adspec {
             type string;
             description "Adspec data element in an RSVP Path message";
           }
           leaf path-mtu {
             type int32;
             description "The value of the path MTU, as negotiated by the network";
           }
           leaf path-mtu-in-kernel {
             type int32;
             description "The value of the MTU used locally for forwarding";
           }
           container packet-information {
             leaf packet-information.heading {
               type string;
               description "RSVP packets sent or received per session";
             }
             leaf previous-hop {
               type jt:ipaddr;
               description "Previous-hop address";
             }
             leaf next-hop {
               type jt:ipaddr;
               description "Next-hop address";
             }
             leaf interface-name {
               type string;
               description "Name of interface";
             }
             leaf count {
               type int32;
             }
             leaf notify-destination {
               type jt:ipaddr;
               description "Notify address";
             }
             leaf entropy-label {
               type string;
               description "Entropy label";
             }
             leaf in-message-handle {
               type string;
               description "RSVP I/O handle for incoming message";
             }
             leaf in-message-id {
               type uint32;
               description "Incoming Message ID";
             }
             leaf in-epoch {
               type uint32;
               description "Incoming Epoch";
             }
             leaf out-message-state {
               type string;
               description "RSVP I/O state for outgoing message";
             }
             leaf out-message-id {
               type uint32;
               description "Outgoing Message ID";
             }
             leaf out-epoch {
               type uint32;
               description "Outgoing Epoch";
             }
           }
         }
         container detour-branch {
           container explicit-route {
           }
           container detour-branch-labels {
             leaf label-in {
               type string;
               description "Incoming label";
             }
             leaf label-out {
               type string;
               description "Outgoing label";
             }
             container explicit-route {
             }
             leaf path-mtu {
               type int32;
               description "The value of the path MTU, as negotiated by the network";
             }
             leaf path-mtu-in-kernel {
               type int32;
               description "The value of the MTU used locally for forwarding";
             }
             leaf sender-tspec {
               type string;
               description "Sender TSpec";
             }
             leaf adspec {
               type string;
               description "Adspec data element in an RSVP Path message";
             }
             leaf lsp-diffserv-info {
               type string;
               description "LSP DiffServ info";
             }
             leaf ct-bw {
               type string;
               description "Per-class bandwidth requested for E-LSPs and L-LSPs";
             }
             container packet-information {
               leaf packet-information.heading {
                 type string;
                 description "RSVP packets sent or received per session";
               }
               leaf previous-hop {
                 type jt:ipaddr;
                 description "Previous-hop address";
               }
               leaf next-hop {
                 type jt:ipaddr;
                 description "Next-hop address";
               }
               leaf interface-name {
                 type string;
                 description "Name of interface";
               }
               leaf count {
                 type int32;
               }
               leaf notify-destination {
                 type jt:ipaddr;
                 description "Notify address";
               }
               leaf entropy-label {
                 type string;
                 description "Entropy label";
               }
               leaf in-message-handle {
                 type string;
                 description "RSVP I/O handle for incoming message";
               }
               leaf in-message-id {
                 type uint32;
                 description "Incoming Message ID";
               }
               leaf in-epoch {
                 type uint32;
                 description "Incoming Epoch";
               }
               leaf out-message-state {
                 type string;
                 description "RSVP I/O state for outgoing message";
               }
               leaf out-message-id {
                 type uint32;
                 description "Outgoing Message ID";
               }
               leaf out-epoch {
                 type uint32;
                 description "Outgoing Epoch";
               }
             }
           }
           leaf source-address {
             type jt:ipaddr;
           }
           leaf skip-address {
             type jt:ipaddr;
             description "Address of node or link to be skipped";
           }
           leaf lsp-state {
             type string;
             description "State of an LSP";
           }
           leaf sender-tspec {
             type string;
             description "Sender TSpec";
           }
           leaf adspec {
             type string;
             description "Adspec data element in an RSVP Path message";
           }
           leaf path-mtu {
             type int32;
             description "The value of the path MTU, as negotiated by the network";
           }
           container packet-information {
             leaf packet-information.heading {
               type string;
               description "RSVP packets sent or received per session";
             }
             leaf previous-hop {
               type jt:ipaddr;
               description "Previous-hop address";
             }
             leaf next-hop {
               type jt:ipaddr;
               description "Next-hop address";
             }
             leaf interface-name {
               type string;
               description "Name of interface";
             }
             leaf count {
               type int32;
             }
             leaf notify-destination {
               type jt:ipaddr;
               description "Notify address";
             }
             leaf entropy-label {
               type string;
               description "Entropy label";
             }
             leaf in-message-handle {
               type string;
               description "RSVP I/O handle for incoming message";
             }
             leaf in-message-id {
               type uint32;
               description "Incoming Message ID";
             }
             leaf in-epoch {
               type uint32;
               description "Incoming Epoch";
             }
             leaf out-message-state {
               type string;
               description "RSVP I/O state for outgoing message";
             }
             leaf out-message-id {
               type uint32;
               description "Outgoing Message ID";
             }
             leaf out-epoch {
               type uint32;
               description "Outgoing Epoch";
             }
           }
         }
         container packet-information {
           leaf packet-information.heading {
             type string;
             description "RSVP packets sent or received per session";
           }
           leaf previous-hop {
             type jt:ipaddr;
             description "Previous-hop address";
           }
           leaf next-hop {
             type jt:ipaddr;
             description "Next-hop address";
           }
           leaf interface-name {
             type string;
             description "Name of interface";
           }
           leaf count {
             type int32;
           }
           leaf notify-destination {
             type jt:ipaddr;
             description "Notify address";
           }
           leaf entropy-label {
             type string;
             description "Entropy label";
           }
           leaf in-message-handle {
             type string;
             description "RSVP I/O handle for incoming message";
           }
           leaf in-message-id {
             type uint32;
             description "Incoming Message ID";
           }
           leaf in-epoch {
             type uint32;
             description "Incoming Epoch";
           }
           leaf out-message-state {
             type string;
             description "RSVP I/O state for outgoing message";
           }
           leaf out-message-id {
             type uint32;
             description "Outgoing Message ID";
           }
           leaf out-epoch {
             type uint32;
             description "Outgoing Epoch";
           }
         }
       }
     }
   }
   grouping mpls-container-lsp-defaults-information-block {
     container mpls-container-lsp-defaults {
       leaf minimum-splitting-bandwidth {
         type int32;
         description "Configured splitting minimum bandwidth";
       }
       leaf maximum-splitting-bandwidth {
         type int32;
         description "Configured splitting maximum bandwidth";
       }
       leaf minimum-signaling-bandwidth {
         type int32;
         description "Configured signaling minimum bandwidth";
       }
       leaf maximum-signaling-bandwidth {
         type int32;
         description "Configured signaling maximum bandwidth";
       }
       leaf maximum-member-lsps {
         type int32;
         description "Configured maximum LSPs";
       }
       leaf minimum-member-lsps {
         type int32;
         description "Configured minimum LSPs";
       }
       leaf splitting-merging-threshold {
         type int32;
         description "Percentage change in aggregate LSP utilization to trigger normalization";
       }
       leaf normalize-interval {
         type int32;
         description "Configured LSP normalize timer";
       }
       leaf normalization-mode {
         type string;
       }
       leaf normalize-retry-duration {
         type int32;
         description "Default normalize retry duration";
       }
       leaf normalize-retry-limit {
         type int32;
         description "Default normalize retry limit";
       }
       leaf sampling-mode {
         type string;
         description "Sampling Attributes";
       }
       leaf failover-normalization {
         type string;
         description "Default failover normalization";
       }
       leaf stats-sampling-interval {
         type int32;
         description "Default statistics collection interval";
       }
     }
   }
   grouping mpls-call-admission-control-information-block {
     container mpls-call-admission-control {
       container mpls-lsp {
         description "MPLS label-switched path information";
         leaf name {
           type string;
         }
         leaf lsp-packets {
           type string;
           description "LSP packet counters";
         }
         leaf lsp-bytes {
           type string;
           description "LSP byte counters";
         }
         container mpls-lsp-path {
           description "Primary or secondary LSP path";
           leaf path-active {
             type empty;
             description "Whether the path is active or not";
           }
           leaf title {
             type string;
           }
           leaf name {
             type string;
           }
           leaf received-rro {
             type string;
             description "RRO returned by the signaling protocol";
           }
           container admin-groups {
             leaf admin-groups.heading {
               type string;
             }
             leaf color {
               type int32;
             }
             leaf no-group-flag {
               type empty;
             }
             leaf-list admin-group-name {
               type string;
               description "Name of the admin group";
             }
             leaf admin-group-number {
               type int32;
               description "Number of the admin group";
             }
           }
           container admin-groups-extended {
             leaf admin-groups-extended.heading {
               type string;
             }
             leaf-list admin-group-name {
               type string;
               description "Name of the admin group";
             }
             leaf admin-group-number {
               type int32;
               description "Number of the admin group";
             }
           }
           container srlg {
             leaf srlg.heading {
               type string;
             }
             leaf-list srlg-name {
               type string;
               description "Name of the srlg";
             }
           }
           container mpls-lsp-upstream-label {
             description "Upstream label configured for the LSP";
             leaf vlan-id-label {
               type uint32;
               description "VLAN ID label configured for the LSP";
             }
           }
           container explicit-route {
             description "Explicit Route Object (ERO)";
             leaf explicit-route.heading {
               type string;
               description "Explicit Route Object (ERO)";
             }
             container explicit-route-element {
               leaf address {
                 type jt:ipaddr;
               }
               leaf explicit-route-type {
                 type string;
               }
               leaf telink-id {
                 type int32;
                 description "Link identifier of unnumbered link";
               }
             }
           }
           container oam-state {
             description "OAM state information";
             leaf oam-bfd-session-state {
               type string;
             }
             leaf oam-lsp-ping-state {
               type string;
             }
           }
           list path-history {
             description "Log over time of LSP path-related events";
             leaf sequence-number {
               type int64;
               description "History event number";
             }
             leaf time {
               type string;
               description "Time of the event";
             }
             leaf log {
               type string;
               description "Supplemental information of the event";
             }
             leaf route {
               type string;
               description "Latest RRO contents, as reported by RSVP";
             }
           }
           container path-available-bandwidth {
             description "Available bandwidth on an LSP path";
             leaf path-available-bandwidth.heading {
               type string;
               description "Available bandwidth on an LSP path";
             }
             leaf bandwidth {
               type int32;
             }
             leaf class-type {
               type int32;
             }
             leaf class-bandwidth {
               type int32;
             }
           }
           container layer2-connection {
             description "Layer 2 connection using the LSP path";
             leaf neighbor-address {
               type jt:ipaddr;
               description "IP address of this neighbor";
             }
             leaf interface-name {
               type string;
               description "Name of interface";
             }
             leaf vc-id {
               type int32;
             }
             container connection-bandwidth {
               description "Bandwidth of a layer 2 connection";
               leaf connection-bandwidth.heading {
                 type string;
                 description "Bandwidth of a layer 2 connection";
               }
               leaf bandwidth {
                 type int32;
               }
               leaf class-type {
                 type int32;
               }
               leaf class-bandwidth {
                 type int32;
               }
             }
           }
         }
         container mpls-lsp-attributes {
           container mpls-lsp-upstream-label {
             description "Upstream label configured for the LSP";
             leaf vlan-id-label {
               type uint32;
               description "VLAN ID label configured for the LSP";
             }
           }
         }
       }
     }
   }
   grouping mpls-context-identifier-information-block {
     leaf context-total-count {
       type int32;
       description "Number context identifiers";
     }
     leaf primary-context-count {
       type int32;
       description "Number primary context identifiers";
     }
     leaf protector-context-count {
       type int32;
       description "Number primary context identifiers";
     }
     list mpls-context-identifier {
       description "Egress protection context identifier";
       leaf context-identifier {
         type jt:ipaddr;
         description "IP address";
       }
       leaf context-type {
         type string;
         description "Type";
       }
       leaf metric {
         type int32;
       }
       leaf context-table {
         type string;
         description "Context table name";
       }
       list context-lsps {
         leaf context-lsp-name {
           type string;
           description "Context LSP's name";
         }
         leaf context-lsp-ingress-router {
           type jt:ipaddr;
           description "Context LSP's ingress router";
         }
         leaf context-lsp-is-detour {
           type empty;
           description "LSP is a detour";
         }
       }
       leaf advertise-mode {
         type string;
         description "Context-id advertise mode";
       }
       leaf label-out {
         type string;
         description "Outgoing label";
       }
       leaf-list admin-group-name {
         type string;
         description "Name of the admin group";
       }
     }
   }
   grouping mpls-srlg-information-block {
     container mpls-srlg {
       leaf-list srlg-name {
         type string;
         description "Name of the srlg";
       }
       leaf srlg-value {
         type uint32;
         description "Value of the srlg";
       }
       leaf srlg-cost {
         type uint32;
         description "Cost of the srlg";
       }
     }
   }
   grouping mpls-association-path-block {
     leaf mpls-association-path-count {
       type int32;
     }
     leaf-list mpls-association-path-using-lsp-name {
       type string;
     }
     leaf mpls-association-path-lsp-count {
       type int32;
     }
     leaf lsp-name {
       type string;
       description "Tunneled into an RSVP LSP";
     }
     container mpls-association-summary {
       leaf lsp-name {
         type string;
         description "Tunneled into an RSVP LSP";
       }
     }
   }
   grouping mpls-association-iif-block {
     leaf destination-address {
       type jt:ipaddr;
       description "Session destination address";
     }
     leaf source-address {
       type jt:ipaddr;
     }
     leaf lsp-state {
       type string;
       description "State of an LSP";
     }
     leaf-list mpls-association-iif-lsp-name {
       type string;
     }
     leaf display-count {
       type int32;
       description "Number of sessions displayed";
     }
     leaf up-count {
       type int32;
       description "Number of sessions in up state";
     }
     leaf down-count {
       type int32;
       description "Number of sessions in down state";
     }
     leaf mpls-association-iif-lsp-count {
       type int32;
     }
   }
   grouping mpls-association-oif-block {
     leaf destination-address {
       type jt:ipaddr;
       description "Session destination address";
     }
     leaf source-address {
       type jt:ipaddr;
     }
     leaf lsp-state {
       type string;
       description "State of an LSP";
     }
     leaf-list mpls-association-oif-lsp-name {
       type string;
     }
     leaf display-count {
       type int32;
       description "Number of sessions displayed";
     }
     leaf up-count {
       type int32;
       description "Number of sessions in up state";
     }
     leaf down-count {
       type int32;
       description "Number of sessions in down state";
     }
     leaf mpls-association-oif-lsp-count {
       type int32;
     }
   }
   grouping mpls-correlation-nhid-block {
     leaf mpls-correlation-nhid-lsp-name {
       type string;
     }
   }
   grouping mpls-correlation-label-block {
     leaf mpls-correlation-label-lsp-name {
       type string;
     }
   }
   grouping mpls-interface-information-block {
     list mpls-interface {
       leaf interface-name {
         type string;
         description "Name of interface";
       }
       leaf mpls-interface-state {
         type string;
       }
       leaf no-group-flag {
         type empty;
       }
       leaf-list admin-group-name {
         type string;
         description "Name of the admin group";
       }
       leaf admin-group-number {
         type int32;
         description "Number of the admin group";
       }
     }
     list mpls-interface-detail {
       leaf interface-name {
         type string;
         description "Name of interface";
       }
       leaf mpls-interface-state {
         type string;
       }
       leaf no-group-flag {
         type empty;
       }
       leaf-list admin-group-name {
         type string;
         description "Name of the admin group";
       }
       leaf admin-group-number {
         type int32;
         description "Number of the admin group";
       }
       leaf admin-group-extended-name {
         type string;
         description "Name of the extended admin group";
       }
       leaf admin-group-extended-number {
         type uint32;
         description "Number of the extended admin group";
       }
       leaf-list srlg-name {
         type string;
         description "Name of the srlg";
       }
       leaf maximum-labels {
         type string;
         description "Maximum label";
       }
       leaf static-revert-time {
         type string;
         description "Static LSP revert wait time";
       }
       leaf always-mark-connection-protection-tlv {
         type string;
         description "Always-mark-connection-protection-tlv status on a MPLS interface";
       }
       leaf mpls-interface-switch-away-lsps {
         type string;
         description "Switch-away-lsps knob status of a MPLS interface";
       }
     }
   }
   grouping mpls-label-history-block {
     list label-history-entry {
       description "Label history";
       leaf time {
         type string;
         description "Time of the event";
       }
       leaf label {
         type int32;
         description "Label";
       }
       leaf action {
         type string;
       }
       leaf-list protocol {
         type string;
         description "Protocol from which route was learned";
       }
       leaf info {
         type string;
       }
     }
   }
   grouping mpls-label-value-block {
     list label-value {
       description "Label value";
       leaf label-value-string {
         type string;
       }
     }
   }
   grouping mpls-label-usage-block {
     list label-usage {
       description "Label space usage";
       leaf label-space-name {
         type string;
       }
       leaf total-labels {
         type int32;
       }
       leaf free-labels {
         type int32;
       }
       leaf free-labels-percent {
         type int32;
       }
       leaf applications {
         type string;
       }
     }
     container label-effective-ranges {
       leaf label-effective-ranges-attribute {
         type string;
       }
       list label-type-effective-ranges {
         leaf label-effective-range-type-name {
           type string;
         }
         leaf label-effective-range-start {
           type int32;
         }
         leaf label-effective-range-end {
           type int32;
         }
         leaf label-effective-range-subtype-name {
           type string;
         }
       }
     }
     container label-configured-ranges {
       leaf label-configured-ranges-attribute {
         type string;
       }
       list label-type-configured-ranges {
         leaf label-configured-range-type-name {
           type string;
         }
         leaf label-configured-range-start {
           type int32;
         }
         leaf label-configured-range-end {
           type int32;
         }
         leaf label-configured-range-subtype-name {
           type string;
         }
       }
     }
     container label-usage-range-total {
       leaf label-usage-range-name {
         type string;
       }
       leaf label-usage-range-total-count {
         type int32;
       }
     }
     list label-usage-range-type {
       leaf label-usage-range-type-name {
         type string;
       }
       leaf label-usage-range-type-count {
         type int32;
       }
     }
     list label-usage-range-app {
       leaf label-usage-range-app-name {
         type string;
       }
       leaf label-usage-range-app-count {
         type int32;
       }
     }
   }
   grouping mpls-tunnel-manager-statistics-information-block {
     leaf mpls-tunnel-manager-statistics-information.heading {
       type string;
     }
     container mpls-lsp-reroute-statistics {
       leaf lsp-make-before-break {
         type int32;
         description "LSP make-before-break count";
       }
       leaf lsp-path-mbb-time-taken-min {
         type int32;
         description "LSP path make-before-break time taken - minimum";
       }
       leaf lsp-path-mbb-time-taken-max {
         type int32;
         description "LSP path make-before-break time taken - maximum";
       }
       leaf lsp-path-mbb-time-taken-avg {
         type int32;
         description "LSP path make-before-break time taken - average";
       }
       leaf lsp-path-old-lsp-release-min {
         type int32;
         description "Min time for control plane users to release old LSP during MBB";
       }
       leaf lsp-path-old-lsp-release-max {
         type int32;
         description "Max time for control plane users to release old LSP during MBB";
       }
       leaf lsp-path-old-lsp-release-avg {
         type int32;
         description "Avg time for control plane users to release old LSP during MBB";
       }
       leaf lsp-local-repair-count {
         type int32;
         description "LSP local-repair count";
       }
       leaf lsp-path-local-repair-time-taken-min {
         type int32;
         description "LSP path local-repair time taken - minimum";
       }
       leaf lsp-path-local-repair-time-taken-max {
         type int32;
         description "LSP path local-repair time taken - maximum";
       }
       leaf lsp-path-local-repair-time-taken-avg {
         type int32;
         description "LSP path local-repair time taken - average";
       }
       leaf lsp-in-place-update-bw-increase {
         type int32;
         description "In-place LSP BW increase count";
       }
       leaf lsp-in-place-update-bw-decrease {
         type int32;
         description "In-place LSP BW decrease count";
       }
       leaf lsp-in-place-update-cspf-failure {
         type int32;
         description "In-place LSP update CSPF failure";
       }
       leaf lsp-in-place-update-signal-error {
         type int32;
         description "In-place LSP update signaling error";
       }
       leaf lsp-in-place-update-signal-timeout {
         type int32;
         description "In-place LSP update signaling timeout";
       }
       leaf lsp-in-place-upd-hold-prio-increase-req {
         type int32;
         description "In-place LSP hold-prio increase request";
       }
       leaf lsp-in-place-upd-hold-prio-decrease-req {
         type int32;
         description "In-place LSP hold-prio decrease request";
       }
       leaf lsp-in-place-upd-hold-prio-success {
         type int32;
         description "In-place LSP hold-prio update successful";
       }
       leaf lsp-in-place-upd-hold-prio-signal-error {
         type int32;
         description "In-place LSP hold-prio update error";
       }
       leaf lsp-in-place-upd-hold-prio-signal-timeout {
         type int32;
         description "In-place LSP hold-prio update timeout";
       }
       leaf lsp-rsvp-signal-initiate-count {
         type int32;
         description "RSVP path signaling initiated";
       }
       leaf lsp-rsvp-signal-success-or-error-count {
         type int32;
         description "RSVP path signaling success or error count";
       }
       leaf lsp-rsvp-signal-time-min {
         type int32;
         description "RSVP path signaling time taken - minimum";
       }
       leaf lsp-rsvp-signal-time-max {
         type int32;
         description "RSVP path signaling time taken - maximum";
       }
       leaf lsp-rsvp-signal-time-avg {
         type int32;
         description "RSVP path signaling time taken - average";
       }
       leaf lsp-rsvp-signal-timeout-count {
         type int32;
         description "RSVP path signaling timed out";
       }
     }
   }
   grouping mpls-static-lsp-information-block {
     container mpls-static-lsp-summary {
       leaf session-type {
         type string;
         description "Type of session with respect to this router";
       }
       leaf count {
         type int32;
       }
       leaf display-count {
         type int32;
         description "Number of sessions displayed";
       }
       leaf up-count {
         type int32;
         description "Number of sessions in up state";
       }
       leaf down-count {
         type int32;
         description "Number of sessions in down state";
       }
     }
     container mpls-static-ingress-lsp-brief {
       leaf lsp-name {
         type string;
         description "Tunneled into an RSVP LSP";
       }
       leaf destination-address {
         type jt:ipaddr;
         description "Session destination address";
       }
       leaf lsp-state {
         type string;
         description "State of an LSP";
       }
     }
     container mpls-static-transit-lsp-brief {
       leaf lsp-name {
         type string;
         description "Tunneled into an RSVP LSP";
       }
       leaf label-in {
         type string;
         description "Incoming label";
       }
       leaf lsp-state {
         type string;
         description "State of an LSP";
       }
     }
     container mpls-static-segment-lsp-brief {
       leaf lsp-name {
         type string;
         description "Tunneled into an RSVP LSP";
       }
       leaf sid-label {
         type string;
         description "SID label";
       }
       leaf lsp-state {
         type string;
         description "State of an LSP";
       }
     }
     container mpls-static-ingress-lsp-descriptions {
       leaf lsp-name {
         type string;
         description "Tunneled into an RSVP LSP";
       }
       leaf destination-address {
         type jt:ipaddr;
         description "Session destination address";
       }
       leaf lsp-description {
         type string;
         description "LSP description string (up to 80 characters)";
       }
     }
     container mpls-static-transit-lsp-descriptions {
       leaf lsp-name {
         type string;
         description "Tunneled into an RSVP LSP";
       }
       leaf label-in {
         type string;
         description "Incoming label";
       }
       leaf lsp-description {
         type string;
         description "LSP description string (up to 80 characters)";
       }
     }
     container mpls-static-segment-lsp-descriptions {
       leaf lsp-name {
         type string;
         description "Tunneled into an RSVP LSP";
       }
       leaf sid-label {
         type string;
         description "SID label";
       }
       leaf lsp-description {
         type string;
         description "LSP description string (up to 80 characters)";
       }
     }
     container mpls-static-ingress-lsp-statistics {
       leaf lsp-name {
         type string;
         description "Tunneled into an RSVP LSP";
       }
       leaf destination-address {
         type jt:ipaddr;
         description "Session destination address";
       }
       leaf lsp-state {
         type string;
         description "State of an LSP";
       }
       leaf lsp-pktbytes {
         type string;
         description "LSP packet and byte counters";
       }
       leaf lsp-packets {
         type string;
         description "LSP packet counters";
       }
       leaf lsp-bytes {
         type string;
         description "LSP byte counters";
       }
     }
     container mpls-static-transit-lsp-statistics {
       leaf lsp-name {
         type string;
         description "Tunneled into an RSVP LSP";
       }
       leaf label-in {
         type string;
         description "Incoming label";
       }
       leaf lsp-state {
         type string;
         description "State of an LSP";
       }
       leaf lsp-pktbytes {
         type string;
         description "LSP packet and byte counters";
       }
       leaf lsp-packets {
         type string;
         description "LSP packet counters";
       }
       leaf lsp-bytes {
         type string;
         description "LSP byte counters";
       }
     }
     container mpls-static-segment-lsp-statistics {
       leaf lsp-name {
         type string;
         description "Tunneled into an RSVP LSP";
       }
       leaf sid-label {
         type string;
         description "SID label";
       }
       leaf lsp-state {
         type string;
         description "State of an LSP";
       }
       leaf lsp-pktbytes {
         type string;
         description "LSP packet and byte counters";
       }
       leaf lsp-packets {
         type string;
         description "LSP packet counters";
       }
       leaf lsp-bytes {
         type string;
         description "LSP byte counters";
       }
     }
     container mpls-static-lsp-detail {
       leaf lsp-name {
         type string;
         description "Tunneled into an RSVP LSP";
       }
       leaf destination-address {
         type jt:ipaddr;
         description "Session destination address";
       }
       leaf label-in {
         type string;
         description "Incoming label";
       }
       leaf sid-label {
         type string;
         description "SID label";
       }
       leaf lsp-description {
         type string;
         description "LSP description string (up to 80 characters)";
       }
       leaf lsp-state {
         type string;
         description "State of an LSP";
       }
       leaf lsp-sub-state {
         type string;
         description "LSP sub state";
       }
       leaf next-hop {
         type jt:ipaddr;
         description "Next-hop address";
       }
       leaf interface-name {
         type string;
         description "Name of interface";
       }
       leaf ae-member-interface-name {
         type string;
         description "AE member interface name";
       }
       leaf label-operation {
         type string;
         description "Label operation";
       }
       leaf label-out {
         type string;
         description "Outgoing label";
       }
       leaf creation-time {
         type string;
         description "Creation time";
       }
       leaf lp-bypass-name {
         type string;
         description "Link protection bypass LSP name";
       }
       leaf np-bypass-name {
         type string;
         description "Node protection bypass LSP name";
       }
       leaf next-next-label {
         type string;
         description "Node protection next-next label";
       }
       leaf bandwidth_ct0 {
         type int32;
       }
       leaf spvc-id {
         type string;
         description "Unique id for the static lsp structure";
       }
       leaf self-id {
         type string;
         description "Statistics identifier for RSVP path state control block";
       }
       leaf lsp-pktbytes {
         type string;
         description "LSP packet and byte counters";
       }
       leaf lsp-packets {
         type string;
         description "LSP packet counters";
       }
       leaf lsp-bytes {
         type string;
         description "LSP byte counters";
       }
     }
   }
 }
