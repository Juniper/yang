/*
 * Copyright (c) 2025 Juniper Networks, Inc.
 * All rights reserved.
 */
 module junos-nfx-rpc-synchronous-ethernet {
   namespace "http://yang.juniper.net/junos-nfx/rpc/synchronous-ethernet";

   prefix synchronous-ethernet;

   import junos-common-ddl-extensions {
     prefix junos;
     revision-date 2024-01-01;
   }

   import junos-common-types {
     prefix jt;
     revision-date 2024-01-01;
   }

   organization "Juniper Networks, Inc.";

   contact "yang-support@juniper.net";

   description "Junos RPC YANG module for synchronous-ethernet command(s)";

   revision 2024-01-01 {
     description "Junos: 24.4R1.11";
   }

   rpc get-synchronous-ethernet-global-information {
     description "Show process related global information only";
     junos:command "show synchronous-ethernet global-information";
     input {
       leaf verbosity {
         junos:cli-feature "nokeyword";
         default "brief";
         type enumeration {
           enum "brief" {
             description "Display brief output";
           }
         }
       }
     }
     output {
       container clock-synchronization-global-information {
         uses clock-synchronization-global-information-block;
       }
     }
   }
   rpc get-synchronous-ethernet-esmc-transmit-information {
     description "Show ESMC enabled outgoing interfaces";
     junos:command "show synchronous-ethernet esmc transmit";
     input {
       leaf interface {
         description "Name of physical interface";
         type string;
       }
       leaf verbosity {
         junos:cli-feature "nokeyword";
         default "brief";
         type enumeration {
           enum "brief" {
             description "Display brief output";
           }
           enum "detail" {
             description "Display detail output";
           }
         }
       }
     }
     output {
       container clock-synchronization-esmc-transmit-information {
         uses clock-synchronization-esmc-transmit-information-block;
       }
     }
   }
   rpc get-synchronous-ethernet-esmc-statistics {
     description "Show ESMC related statistics";
     junos:command "show synchronous-ethernet esmc statistics";
     input {
       leaf interface {
         description "Name of physical interface";
         type string;
       }
       leaf verbosity {
         junos:cli-feature "nokeyword";
         default "brief";
         type enumeration {
           enum "brief" {
             description "Display brief output";
           }
           enum "detail" {
             description "Display detail output";
           }
         }
       }
     }
     output {
       container clock-synchronization-statistics {
         uses clock-synchronization-statistics-block;
       }
     }
   }
   grouping command-forwarding {
     choice chassis-selector {
       case case_1 {
         leaf all-chassis {
           description "All chassis";
           type empty;
         }
       }
       case case_2 {
         leaf all-lcc {
           description "All LCC chassis";
           type empty;
         }
       }
       case case_3 {
         leaf scc {
           description "SCC";
           type empty;
         }
       }
       case case_4 {
         leaf sfc {
           description "SFC";
           type union {
             type string {
               pattern "<.*>|$.*";
             }
             type uint32;
           }
         }
       }
       case case_5 {
         leaf lcc {
           description "Specific LCC";
           type union {
             type string {
               pattern "<.*>|$.*";
             }
             type uint32;
           }
         }
       }
       case case_6 {
         leaf node {
           description "Specific node";
           type string;
         }
       }
       case case_7 {
         leaf bsys {
           description "Base system";
           type empty;
         }
       }
       case case_8 {
         leaf gnf {
           description "Specific guest network function";
           type union {
             type string {
               pattern "<.*>|$.*";
             }
             type uint32 {
               range "1 .. 10";
             }
           }
         }
       }
       case case_9 {
         leaf all-gnfs {
           description "All guest network functions";
           type empty;
         }
       }
       case case_10 {
         leaf all-system {
           description "All system (BSYS and GNFs)";
           type empty;
         }
       }
       case case_11 {
         leaf server {
           description "Specific server slot";
           type union {
             type string {
               pattern "<.*>|$.*";
             }
             type uint32 {
               range "0 .. 1";
             }
           }
         }
       }
       case case_12 {
         leaf all-servers {
           description "All servers";
           type empty;
         }
       }
       case case_13 {
         leaf vnf {
           description "Specific virtual-network-function";
           type string;
         }
       }
       case case_14 {
         leaf all-vnfs {
           description "All virtual-network-functions";
           type empty;
         }
       }
     }
     choice re-selector {
       case case_1 {
         leaf re0 {
           description "RE0";
           type empty;
         }
       }
       case case_2 {
         leaf re1 {
           description "RE1";
           type empty;
         }
       }
       case case_3 {
         leaf routing-engine {
           description "Specific routing engine";
           type enumeration {
             enum "local" {
               description "Local routing engine";
             }
             enum "other" {
               description "Other routing engine";
             }
             enum "master" {
               description "Master routing engine";
             }
             enum "backup" {
               description "Backup routing engine";
             }
             enum "both" {
               description "Both routing engines";
             }
           }
         }
       }
     }
     choice lr-selector {
       case case_1 {
         leaf logical-system {
           description "Name of logical system, or 'all'";
           type string;
         }
       }
     }
     choice tenant-selector {
       case case_1 {
         leaf tenant {
           description "Name of tenant, or 'all'";
           type string;
         }
       }
     }
     choice vc-selector {
       case case_1 {
         leaf local {
           description "Local virtual chassis member";
           type empty;
         }
       }
       case case_2 {
         leaf all-members {
           description "All virtual chassis members";
           type empty;
         }
       }
       case case_3 {
         leaf member {
           description "Specific virtual chassis member which is master";
           type union {
             type string {
               pattern "<.*>|$.*";
             }
             type uint32;
           }
         }
       }
     }
   }
   grouping clock-synchronization-global-information-block {
     leaf network-option {
       type string;
       description "Synchronous ethernet SSM code";
     }
     leaf clock-mode {
       type string;
       description "Synchronous ethernet clock selection mode";
     }
     leaf quality-mode {
       type string;
       description "Synchronous ethernet ESMC mode";
     }
     leaf max-transmit-quality-level {
       type string;
       description "Max transmit quality level";
     }
     leaf selection-mode {
       type string;
       description "Whether clock selection is based on configured or received QL";
     }
     leaf switchover-mode {
       type string;
       description "Whether revert to higher priority valid source";
     }
     leaf switchover-hold-interval {
       type uint32;
       description "Wait time before switchover due to clock degradation";
     }
     leaf change-hold-interval {
       type uint32;
       description "Wait time before switchover due to change in configuration";
     }
     leaf reboot-hold-interval {
       type uint32;
       description "Wait time before switchover due to reboot";
     }
     leaf master-status {
       type string;
       description "Status of the RE (master/slave)";
     }
     leaf global-wait-to-restore {
       type uint32;
       description "Global wait to restore value";
     }
     leaf agentsmith-dpc-bitmap {
       type uint32;
       description "Bits indicating which dpc slot(s) are agentsmith";
     }
     leaf eec-support-dpc-bitmap {
       type uint32;
       description "Bits indicating which dpc slot support EEC";
     }
     leaf fpga-support-synchronous-ethernet {
       type string;
       description "FPGA is upgraded to support synce or not";
     }
   }
   grouping clock-synchronization-esmc-transmit-information-block {
     container clock-synchronization-esmc-transmit {
       description "ESMC Transmit interface details:";
       leaf esmc-transmit-interface-name {
         type string;
         description "Interface on which to send out ESMC packets";
       }
       leaf esmc-transmit-interface-status {
         type string;
         description "ESMC interface status";
       }
     }
   }
   grouping clock-synchronization-statistics-block {
     list clock-synchronization-interface-statistics {
       leaf clock-synchronization-interface-statistics-name {
         type string;
         description "Name of the interface";
       }
       leaf interface-transmit-esmc-count {
         type uint32;
         description "ESMC packets transmitted";
       }
       leaf interface-receive-esmc-count {
         type uint32;
         description "ESMC packets received";
       }
       leaf interface-receive-esmc-drop-count {
         type uint32;
         description "ESMC drop count";
       }
       leaf interface-esmc-ineligible-drop-count {
         type uint32;
         description "ESMC ineligible drop count";
       }
       leaf interface-adjacency-create-count {
         type uint32;
         description "ESMC adjacency create count";
       }
     }
   }
 }
