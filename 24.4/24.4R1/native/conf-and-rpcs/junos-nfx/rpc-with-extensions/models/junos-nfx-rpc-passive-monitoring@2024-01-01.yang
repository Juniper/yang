/*
 * Copyright (c) 2025 Juniper Networks, Inc.
 * All rights reserved.
 */
 module junos-nfx-rpc-passive-monitoring {
   namespace "http://yang.juniper.net/junos-nfx/rpc/passive-monitoring";

   prefix passive-monitoring;

   import junos-common-ddl-extensions {
     prefix junos;
     revision-date 2024-01-01;
   }

   import junos-common-types {
     prefix jt;
     revision-date 2024-01-01;
   }

   organization "Juniper Networks, Inc.";

   contact "yang-support@juniper.net";

   description "Junos RPC YANG module for passive-monitoring command(s)";

   revision 2024-01-01 {
     description "Junos: 24.4R1.11";
   }

   rpc get-passive-monitoring-information {
     description "Show information about passive monitoring";
     junos:command "show passive-monitoring";
     output {
       container passive-monitoring-information {
         uses passive-monitoring-information-block;
       }
     }
   }
   rpc get-passive-monitoring-usage-information {
     description "Show CPU utilization";
     junos:command "show passive-monitoring usage";
     input {
       leaf interface-name {
         description "Name of monitoring interface, wildcard, or 'all'";
         junos:cli-feature "nokeyword";
         type string;
         mandatory true;
       }
     }
   }
   rpc get-passive-monitoring-memory-information {
     description "Show memory utilization";
     junos:command "show passive-monitoring memory";
     input {
       leaf interface-name {
         description "Name of monitoring interface, wildcard, or 'all'";
         junos:cli-feature "nokeyword";
         type string;
         mandatory true;
       }
     }
   }
   rpc get-passive-monitoring-flow-information {
     description "Show flow statistics";
     junos:command "show passive-monitoring flow";
     input {
       leaf interface-name {
         description "Name of monitoring interface, wildcard, or 'all'";
         junos:cli-feature "nokeyword";
         type string;
         mandatory true;
       }
     }
   }
   rpc get-passive-monitoring-error-information {
     description "Show error statistics";
     junos:command "show passive-monitoring error";
     input {
       leaf interface-name {
         description "Name of monitoring interface, wildcard, or 'all'";
         junos:cli-feature "nokeyword";
         type string;
         mandatory true;
       }
     }
   }
   rpc get-passive-monitoring-status-information {
     description "Show status information";
     junos:command "show passive-monitoring status";
     input {
       leaf interface-name {
         description "Name of monitoring interface, wildcard, or 'all'";
         junos:cli-feature "nokeyword";
         type string;
         mandatory true;
       }
     }
   }
   grouping command-forwarding {
     choice chassis-selector {
       case case_1 {
         leaf all-chassis {
           description "All chassis";
           type empty;
         }
       }
       case case_2 {
         leaf all-lcc {
           description "All LCC chassis";
           type empty;
         }
       }
       case case_3 {
         leaf scc {
           description "SCC";
           type empty;
         }
       }
       case case_4 {
         leaf sfc {
           description "SFC";
           type union {
             type string {
               pattern "<.*>|$.*";
             }
             type uint32;
           }
         }
       }
       case case_5 {
         leaf lcc {
           description "Specific LCC";
           type union {
             type string {
               pattern "<.*>|$.*";
             }
             type uint32;
           }
         }
       }
       case case_6 {
         leaf node {
           description "Specific node";
           type string;
         }
       }
       case case_7 {
         leaf bsys {
           description "Base system";
           type empty;
         }
       }
       case case_8 {
         leaf gnf {
           description "Specific guest network function";
           type union {
             type string {
               pattern "<.*>|$.*";
             }
             type uint32 {
               range "1 .. 10";
             }
           }
         }
       }
       case case_9 {
         leaf all-gnfs {
           description "All guest network functions";
           type empty;
         }
       }
       case case_10 {
         leaf all-system {
           description "All system (BSYS and GNFs)";
           type empty;
         }
       }
       case case_11 {
         leaf server {
           description "Specific server slot";
           type union {
             type string {
               pattern "<.*>|$.*";
             }
             type uint32 {
               range "0 .. 1";
             }
           }
         }
       }
       case case_12 {
         leaf all-servers {
           description "All servers";
           type empty;
         }
       }
       case case_13 {
         leaf vnf {
           description "Specific virtual-network-function";
           type string;
         }
       }
       case case_14 {
         leaf all-vnfs {
           description "All virtual-network-functions";
           type empty;
         }
       }
     }
     choice re-selector {
       case case_1 {
         leaf re0 {
           description "RE0";
           type empty;
         }
       }
       case case_2 {
         leaf re1 {
           description "RE1";
           type empty;
         }
       }
       case case_3 {
         leaf routing-engine {
           description "Specific routing engine";
           type enumeration {
             enum "local" {
               description "Local routing engine";
             }
             enum "other" {
               description "Other routing engine";
             }
             enum "master" {
               description "Master routing engine";
             }
             enum "backup" {
               description "Backup routing engine";
             }
             enum "both" {
               description "Both routing engines";
             }
           }
         }
       }
     }
     choice lr-selector {
       case case_1 {
         leaf logical-system {
           description "Name of logical system, or 'all'";
           type string;
         }
       }
     }
     choice tenant-selector {
       case case_1 {
         leaf tenant {
           description "Name of tenant, or 'all'";
           type string;
         }
       }
     }
     choice vc-selector {
       case case_1 {
         leaf local {
           description "Local virtual chassis member";
           type empty;
         }
       }
       case case_2 {
         leaf all-members {
           description "All virtual chassis members";
           type empty;
         }
       }
       case case_3 {
         leaf member {
           description "Specific virtual chassis member which is master";
           type union {
             type string {
               pattern "<.*>|$.*";
             }
             type uint32;
           }
         }
       }
     }
   }
   grouping passive-monitoring-information-block {
     leaf interface-name {
       type string;
       description "Physical interface name";
     }
     leaf local-index {
       type int32;
       description "Local physical interface index";
     }
     leaf pic-status {
       type string;
       description "Current interface state";
     }
     container usage-information {
       description "Passive monitoring CPU utilization";
       leaf uptime {
         type int32;
         description "CPU uptime, in milliseconds";
       }
       leaf inttime {
         type int32;
         description "CPU interrupt time, in microseconds";
       }
       leaf five-second-load {
         type int32;
         description "5-second load";
       }
       leaf one-minute-load {
         type int32;
         description "1-minute load";
       }
     }
     container memory-information {
       description "Passive monitoring memory utilization";
       leaf allocation-count {
         type int32;
         description "Flow record allocations";
       }
       leaf free-count {
         type int32;
         description "Flow record frees";
       }
       leaf maximum-allocated {
         type int32;
         description "Maximum flow records allocated";
       }
       leaf allocations-per-second {
         type int32;
         description "Flow record allocations per second";
       }
       leaf frees-per-second {
         type int32;
         description "Flow record frees per second";
       }
       leaf memory-used {
         type int32;
         description "Total memory used";
       }
       leaf memory-free {
         type int32;
         description "Total memory free";
       }
     }
     container flow-information {
       description "Passive monitoring flow information";
       leaf flow-packets {
         type int32;
         description "Flow packets";
       }
       leaf flow-bytes {
         type int32;
         description "Flow bytes";
       }
       leaf flow-packets-ten-second-rate {
         type int32;
         description "Flow packets 10-second rate";
       }
       leaf flow-bytes-ten-second-rate {
         type int32;
         description "Flow bytes 10-second rate";
       }
       leaf active-flows {
         type int32;
         description "Active flows";
       }
       leaf flows {
         type int32;
         description "Flows";
       }
       leaf flows-exported {
         type int32;
         description "Flows exported";
       }
       leaf flow-packets-exported {
         type int32;
         description "Flows packets exported";
       }
       leaf flows-expired {
         type int32;
         description "Flows inactive timed out";
       }
       leaf flows-aged {
         type int32;
         description "Flows active timed out";
       }
     }
     container error-information {
       description "Passive monitoring error information";
       leaf error-packets-dropped-no-memory {
         type int32;
         description "Number of packets dropped because memory is exhausted";
       }
       leaf error-packets-dropped-not-ip {
         type int32;
         description "Number of packets dropped because they are not IP";
       }
       leaf error-packets-dropped-not-ipv4 {
         type int32;
         description "Number of packets dropped because they are not IPv4";
       }
       leaf error-packets-too-small {
         type int32;
         description "Number of packets dropped because their header is too small";
       }
       leaf error-allocation-failures {
         type int32;
         description "Number of failed attempts to allocate memory";
       }
       leaf error-free-failures {
         type int32;
         description "Number of failed attempts to free memory";
       }
       leaf error-free-list-failures {
         type int32;
         description "Number of operations that failed because free list memory is exhausted";
       }
       leaf error-memory-warning {
         type string;
         description "Reached low memory condition";
       }
       leaf error-memory-overload {
         type string;
         description "Whether memory is exhausted";
       }
       leaf error-packets-per-second-overload {
         type string;
         description "Whether the number of incoming packets exceeds the designed per-second limit";
       }
       leaf error-bytes-per-second-overload {
         type string;
         description "Whether the number of incoming bytes exceeds the designed per-second limit";
       }
     }
     container status-information {
       description "Passive monitoring status information";
       leaf status-group-index {
         type int32;
         description "Group index";
       }
       leaf status-export-interval {
         type int32;
         description "Export interval, in seconds";
       }
       leaf status-export-format {
         type int32;
         description "Export format";
       }
       leaf status-proto {
         type string;
         description "Protocol";
       }
       leaf status-engine-type {
         type int32;
         description "Engine type";
       }
       leaf status-engine-id {
         type int32;
         description "Engine ID";
       }
       leaf status-route-record-count {
         type int32;
         description "Route record count";
       }
       leaf status-ifl-snmp-map-count {
         type int32;
         description "Local index to SNMP index count";
       }
       leaf status-as-count {
         type int32;
         description "Autonomous system number count";
       }
       leaf status-monitor-time-set {
         type string;
         description "Time set on PIC";
       }
       leaf status-monitor-config-set {
         type string;
         description "Configuration set on PIC";
       }
       leaf status-monitor-route-record-set {
         type string;
         description "Route records set on PIC";
       }
       leaf status-monitor-ifl-snmp-set {
         type string;
         description "Local index to SNMP index map set on PIC";
       }
     }
   }
 }
