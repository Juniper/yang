/*
 * Copyright (c) 2025 Juniper Networks, Inc.
 * All rights reserved.
 */
 module junos-nfx-rpc-test {
   namespace "http://yang.juniper.net/junos-nfx/rpc/test";

   prefix test;

   import junos-common-ddl-extensions {
     prefix junos;
     revision-date 2024-01-01;
   }

   import junos-common-types {
     prefix jt;
     revision-date 2024-01-01;
   }

   organization "Juniper Networks, Inc.";

   contact "yang-support@juniper.net";

   description "Junos RPC YANG module for test command(s)";

   revision 2024-01-01 {
     description "Junos: 24.4R1.11";
   }

   rpc jdhcpd-set-counters {
     description "Execute function to set all counters";
     junos:command "test dhcp-service set-counters";
     output {
       choice output_c {
         case output-tag {
           leaf output {
             type string;
           }
         }
         case multichassis-tag {
           anyxml multi-routing-engine-results;
         }
       }
     }
   }
   rpc jdhcpd-clear-stateless-clients {
     description "Execute function clear any stateless clients";
     junos:command "test dhcp-service clear-stateless-clients";
     output {
       choice output_c {
         case output-tag {
           leaf output {
             type string;
           }
         }
         case multichassis-tag {
           anyxml multi-routing-engine-results;
         }
       }
     }
   }
   rpc jdhcpd-code-coverage {
     description "Execute functions for code coverage";
     junos:command "test dhcp-security code-coverage";
     output {
       choice output_c {
         case output-tag {
           leaf output {
             type string;
           }
         }
         case multichassis-tag {
           anyxml multi-routing-engine-results;
         }
       }
     }
   }
   rpc test-interface {
     description "Perform test on interface";
     junos:command "test interface";
     input {
       choice test-command {
         case send-modem-commands {
           leaf send-modem-commands {
             description "Send AT command string to modem";
             type string;
           }
         }
         case feac-loop-initiate {
           leaf feac-loop-initiate {
             description "Initiate FEAC loopback";
             type empty;
           }
         }
         case feac-loop-terminate {
           leaf feac-loop-terminate {
             description "Terminate FEAC loopback";
             type empty;
           }
         }
         case t3-bert-start {
           leaf t3-bert-start {
             description "Start bit error rate test on T3 interface";
             type empty;
           }
         }
         case e3-bert-start {
           leaf e3-bert-start {
             description "Start bit error rate test on E3 interface";
             type empty;
           }
         }
         case t1-bert-start {
           leaf t1-bert-start {
             description "Start bit error rate test on T1 interface";
             type empty;
           }
         }
         case ds0-bert-start {
           leaf ds0-bert-start {
             description "Start bit error rate test on DS-0 interface";
             type empty;
           }
         }
         case e1-bert-start {
           leaf e1-bert-start {
             description "Start bit error rate test on E1 interface";
             type empty;
           }
         }
         case t3-bert-stop {
           leaf t3-bert-stop {
             description "Stop bit error rate test on T3 interface";
             type empty;
           }
         }
         case e3-bert-stop {
           leaf e3-bert-stop {
             description "Stop bit error rate test on E3 interface";
             type empty;
           }
         }
         case t1-bert-stop {
           leaf t1-bert-stop {
             description "Stop bit error rate test on T1 interface";
             type empty;
           }
         }
         case ds0-bert-stop {
           leaf ds0-bert-stop {
             description "Stop bit error rate test on DS-0 interface";
             type empty;
           }
         }
         case e1-bert-stop {
           leaf e1-bert-stop {
             description "Stop bit error rate test on E1 interface";
             type empty;
           }
         }
         case restart-auto-negotiation {
           leaf restart-auto-negotiation {
             description "Restart autonegotiation";
             type empty;
           }
         }
         case ima-test-start {
           leaf ima-test-start {
             description "Start IMA group test";
             type empty;
           }
         }
         case ima-test-stop {
           leaf ima-test-stop {
             description "Stop IMA group test";
             type empty;
           }
         }
       }
       leaf prbs-test-start {
         description "Start prbs test on interface";
         type empty;
       }
       leaf prbs-test-stop {
         description "Stop prbs test on interface";
         type empty;
       }
       leaf pattern-type {
         description "Type of pattern to use";
         type enumeration {
           enum "7" {
             description "PRBS7";
           }
           enum "9" {
             description "PRBS9";
           }
           enum "11" {
             description "PRBS11";
           }
           enum "15" {
             description "PRBS15";
           }
           enum "23" {
             description "PRBS23";
           }
           enum "31" {
             description "PRBS31";
           }
           enum "58" {
             description "PRBS58";
           }
         }
       }
       leaf direction {
         description "PRBS pattern send or receive";
         type enumeration {
           enum "0" {
             description "Transmit";
           }
           enum "1" {
             description "Receive";
           }
         }
       }
       leaf flip {
         description "PRBS pattern flip";
         type enumeration {
           enum "0" {
             description "Normal pattern";
           }
           enum "1" {
             description "Inverted pattern";
           }
         }
       }
       leaf interface-name {
         description "Name of physical interface";
         junos:cli-feature "nokeyword";
         type string;
         mandatory true;
       }
     }
     output {
       choice output_c {
         case output-tag {
           leaf output {
             type string;
           }
         }
         case multichassis-tag {
           anyxml multi-routing-engine-results;
         }
       }
     }
   }
   rpc test-intf-inband-line-loop-terminate {
     description "Terminate loopback";
     junos:command "test interface inband-line-loop terminate";
     input {
       leaf interface-name {
         description "Name of physical interface";
         junos:cli-feature "nokeyword";
         type string;
         mandatory true;
       }
     }
     output {
       choice output_c {
         case output-tag {
           leaf output {
             type string;
           }
         }
         case multichassis-tag {
           anyxml multi-routing-engine-results;
         }
       }
     }
   }
   rpc test-intf-inband-line-loop-initiate {
     description "Initiate loopback";
     junos:command "test interface inband-line-loop initiate";
     input {
       leaf interface-name {
         description "Name of physical interface";
         junos:cli-feature "nokeyword";
         type string;
         mandatory true;
       }
     }
     output {
       choice output_c {
         case output-tag {
           leaf output {
             type string;
           }
         }
         case multichassis-tag {
           anyxml multi-routing-engine-results;
         }
       }
     }
   }
   rpc test-intf-inband-line-ansi-terminate {
     description "Terminate loopback";
     junos:command "test interface inband-line-loop ansi terminate";
     input {
       leaf interface-name {
         description "Name of physical interface";
         junos:cli-feature "nokeyword";
         type string;
         mandatory true;
       }
     }
     output {
       choice output_c {
         case output-tag {
           leaf output {
             type string;
           }
         }
         case multichassis-tag {
           anyxml multi-routing-engine-results;
         }
       }
     }
   }
   rpc test-intf-inband-line-ansi-initiate {
     description "Initiate loopback";
     junos:command "test interface inband-line-loop ansi initiate";
     input {
       leaf interface-name {
         description "Name of physical interface";
         junos:cli-feature "nokeyword";
         type string;
         mandatory true;
       }
     }
     output {
       choice output_c {
         case output-tag {
           leaf output {
             type string;
           }
         }
         case multichassis-tag {
           anyxml multi-routing-engine-results;
         }
       }
     }
   }
   rpc test-intf-inband-line-bellcore-terminate {
     description "Terminate loopback";
     junos:command "test interface inband-line-loop bellcore terminate";
     input {
       leaf interface-name {
         description "Name of physical interface";
         junos:cli-feature "nokeyword";
         type string;
         mandatory true;
       }
     }
     output {
       choice output_c {
         case output-tag {
           leaf output {
             type string;
           }
         }
         case multichassis-tag {
           anyxml multi-routing-engine-results;
         }
       }
     }
   }
   rpc test-intf-inband-line-bellcore-initiate {
     description "Initiate loopback";
     junos:command "test interface inband-line-loop bellcore initiate";
     input {
       leaf interface-name {
         description "Name of physical interface";
         junos:cli-feature "nokeyword";
         type string;
         mandatory true;
       }
     }
     output {
       choice output_c {
         case output-tag {
           leaf output {
             type string;
           }
         }
         case multichassis-tag {
           anyxml multi-routing-engine-results;
         }
       }
     }
   }
   rpc test-intf-fdl-payload-ansi-terminate {
     description "Terminate loopback";
     junos:command "test interface fdl-payload-loop ansi terminate";
     input {
       leaf interface-name {
         description "Name of physical interface";
         junos:cli-feature "nokeyword";
         type string;
         mandatory true;
       }
     }
     output {
       choice output_c {
         case output-tag {
           leaf output {
             type string;
           }
         }
         case multichassis-tag {
           anyxml multi-routing-engine-results;
         }
       }
     }
   }
   rpc test-intf-fdl-payload-ansi-initiate {
     description "Initiate loopback";
     junos:command "test interface fdl-payload-loop ansi initiate";
     input {
       leaf interface-name {
         description "Name of physical interface";
         junos:cli-feature "nokeyword";
         type string;
         mandatory true;
       }
     }
     output {
       choice output_c {
         case output-tag {
           leaf output {
             type string;
           }
         }
         case multichassis-tag {
           anyxml multi-routing-engine-results;
         }
       }
     }
   }
   rpc test-intf-fdl-payload-bellcore-terminate {
     description "Terminate loopback";
     junos:command "test interface fdl-payload-loop bellcore terminate";
     input {
       leaf interface-name {
         description "Name of physical interface";
         junos:cli-feature "nokeyword";
         type string;
         mandatory true;
       }
     }
     output {
       choice output_c {
         case output-tag {
           leaf output {
             type string;
           }
         }
         case multichassis-tag {
           anyxml multi-routing-engine-results;
         }
       }
     }
   }
   rpc test-intf-fdl-payload-bellcore-initiate {
     description "Initiate loopback";
     junos:command "test interface fdl-payload-loop bellcore initiate";
     input {
       leaf interface-name {
         description "Name of physical interface";
         junos:cli-feature "nokeyword";
         type string;
         mandatory true;
       }
     }
     output {
       choice output_c {
         case output-tag {
           leaf output {
             type string;
           }
         }
         case multichassis-tag {
           anyxml multi-routing-engine-results;
         }
       }
     }
   }
   rpc test-intf-fdl-line-ansi-terminate {
     description "Terminate loopback";
     junos:command "test interface fdl-line-loop ansi terminate";
     input {
       leaf interface-name {
         description "Name of physical interface";
         junos:cli-feature "nokeyword";
         type string;
         mandatory true;
       }
     }
     output {
       choice output_c {
         case output-tag {
           leaf output {
             type string;
           }
         }
         case multichassis-tag {
           anyxml multi-routing-engine-results;
         }
       }
     }
   }
   rpc test-intf-fdl-line-ansi-initiate {
     description "Initiate loopback";
     junos:command "test interface fdl-line-loop ansi initiate";
     input {
       leaf interface-name {
         description "Name of physical interface";
         junos:cli-feature "nokeyword";
         type string;
         mandatory true;
       }
     }
     output {
       choice output_c {
         case output-tag {
           leaf output {
             type string;
           }
         }
         case multichassis-tag {
           anyxml multi-routing-engine-results;
         }
       }
     }
   }
   rpc test-intf-fdl-line-bellcore-terminate {
     description "Terminate loopback";
     junos:command "test interface fdl-line-loop bellcore terminate";
     input {
       leaf interface-name {
         description "Name of physical interface";
         junos:cli-feature "nokeyword";
         type string;
         mandatory true;
       }
     }
     output {
       choice output_c {
         case output-tag {
           leaf output {
             type string;
           }
         }
         case multichassis-tag {
           anyxml multi-routing-engine-results;
         }
       }
     }
   }
   rpc test-intf-fdl-line-bellcore-initiate {
     description "Initiate loopback";
     junos:command "test interface fdl-line-loop bellcore initiate";
     input {
       leaf interface-name {
         description "Name of physical interface";
         junos:cli-feature "nokeyword";
         type string;
         mandatory true;
       }
     }
     output {
       choice output_c {
         case output-tag {
           leaf output {
             type string;
           }
         }
         case multichassis-tag {
           anyxml multi-routing-engine-results;
         }
       }
     }
   }
   rpc test-intf-inband-payload-ansi-terminate {
     description "Terminate loopback";
     junos:command "test interface inband-payload-loop ansi terminate";
     input {
       leaf interface-name {
         description "Name of physical interface";
         junos:cli-feature "nokeyword";
         type string;
         mandatory true;
       }
     }
     output {
       choice output_c {
         case output-tag {
           leaf output {
             type string;
           }
         }
         case multichassis-tag {
           anyxml multi-routing-engine-results;
         }
       }
     }
   }
   rpc test-intf-inband-payload-ansi-initiate {
     description "Initiate loopback";
     junos:command "test interface inband-payload-loop ansi initiate";
     input {
       leaf interface-name {
         description "Name of physical interface";
         junos:cli-feature "nokeyword";
         type string;
         mandatory true;
       }
     }
     output {
       choice output_c {
         case output-tag {
           leaf output {
             type string;
           }
         }
         case multichassis-tag {
           anyxml multi-routing-engine-results;
         }
       }
     }
   }
   rpc test-intf-inband-payload-bellcore-terminate {
     description "Terminate loopback";
     junos:command "test interface inband-payload-loop bellcore terminate";
     input {
       leaf interface-name {
         description "Name of physical interface";
         junos:cli-feature "nokeyword";
         type string;
         mandatory true;
       }
     }
     output {
       choice output_c {
         case output-tag {
           leaf output {
             type string;
           }
         }
         case multichassis-tag {
           anyxml multi-routing-engine-results;
         }
       }
     }
   }
   rpc test-intf-inband-payload-bellcore-initiate {
     description "Initiate loopback";
     junos:command "test interface inband-payload-loop bellcore initiate";
     input {
       leaf interface-name {
         description "Name of physical interface";
         junos:cli-feature "nokeyword";
         type string;
         mandatory true;
       }
     }
     output {
       choice output_c {
         case output-tag {
           leaf output {
             type string;
           }
         }
         case multichassis-tag {
           anyxml multi-routing-engine-results;
         }
       }
     }
   }
   rpc get-ppp-user-aaa-test-result {
     description "Test the aaa servers for a ppp user";
     junos:command "test aaa ppp";
     input {
       leaf user {
         description "The username to test";
         type string;
         mandatory true;
       }
       leaf password {
         description "The password associated with username";
         type string;
       }
       leaf agent-remote-id {
         description "DSL forum agent remote id";
         type string {
           length "1 .. 63";
         }
       }
       leaf profile {
         description "Specify the access profile name which to use for user";
         type string;
       }
       leaf logical-system {
         description "Specify the logical-system in which to authenticate user";
         type string;
       }
       leaf routing-instance {
         description "Specify the routing-instance in which to authenticate user";
         type string;
       }
       leaf no-address-request {
         description "Request is for authentication without address-allocation";
         type empty;
       }
       leaf service-type {
         description "Service type ";
         type string;
       }
       choice terminate-code-choice {
         case terminate-code {
           leaf terminate-code {
             description "Specify PPP terminate-code";
             type enumeration {
               enum "admin-logout" {
                 description "Terminated-id with default mapping to 10";
               }
               enum "admin-reconnect-request" {
                 description "Terminated-id with default mapping to 10";
               }
               enum "authenticate-authenticator-timeout" {
                 description "Terminated-id with default mapping to 10";
               }
               enum "authenticate-challenge-timeout" {
                 description "Terminated-id with default mapping to 17";
               }
               enum "authenticate-chap-no-resources" {
                 description "Terminated-id with default mapping to 10";
               }
               enum "authenticate-chap-peer-authenticator-timeout" {
                 description "Terminated-id with default mapping to 17";
               }
               enum "authenticate-chap-peer-challenge-timeout" {
                 description "Terminated-id with default mapping to 17";
               }
               enum "authenticate-deny-by-peer" {
                 description "Terminated-id with default mapping to 4";
               }
               enum "authenticate-eap-challenge-larger-than-mtu" {
                 description "Terminated-id with default mapping to 10";
               }
               enum "authenticate-eap-peer-authenticator-timeout" {
                 description "Terminated-id with default mapping to 10";
               }
               enum "authenticate-eap-request-timeout" {
                 description "Terminated-id with default mapping to 10";
               }
               enum "authenticate-inactivity-timeout" {
                 description "Terminated-id with default mapping to 8";
               }
               enum "authenticate-max-requests" {
                 description "Terminated-id with default mapping to 10";
               }
               enum "authenticate-no-authenticator" {
                 description "Terminated-id with default mapping to 10";
               }
               enum "authenticate-no-resources" {
                 description "Terminated-id with default mapping to 10";
               }
               enum "authenticate-pap-peer-authenticator-timeout" {
                 description "Terminated-id with default mapping to 10";
               }
               enum "authenticate-pap-request-timeout" {
                 description "Terminated-id with default mapping to 5";
               }
               enum "authenticate-session-timeout" {
                 description "Terminated-id with default mapping to 10";
               }
               enum "authenticate-too-many-requests" {
                 description "Terminated-id with default mapping to 17";
               }
               enum "authenticate-tunnel-fail-immediate" {
                 description "Terminated-id with default mapping to 10";
               }
               enum "authenticate-tunnel-unsupported-tunnel-type" {
                 description "Terminated-id with default mapping to 10";
               }
               enum "bridging-admin-disable" {
                 description "Terminated-id with default mapping to 10";
               }
               enum "bridging-failed-to-activate-family-bridging" {
                 description "Terminated-id with default mapping to 10";
               }
               enum "bridging-inhibited-by-authentication" {
                 description "Terminated-id with default mapping to 10";
               }
               enum "bridging-link-down" {
                 description "Terminated-id with default mapping to 10";
               }
               enum "bridging-max-configure-exceeded" {
                 description "Terminated-id with default mapping to 10";
               }
               enum "bridging-max-passive-retries-exceeded" {
                 description "Terminated-id with default mapping to 10";
               }
               enum "bridging-max-sevice-disable" {
                 description "Terminated-id with default mapping to 10";
               }
               enum "bridging-no-local-ieee802-tagged-frame-format" {
                 description "Terminated-id with default mapping to 10";
               }
               enum "bridging-no-local-mac-frame-format" {
                 description "Terminated-id with default mapping to 2";
               }
               enum "bridging-no-peer-ieee802-tagged-frame-format" {
                 description "Terminated-id with default mapping to 10";
               }
               enum "bridging-no-peer-mac-fram-fromat" {
                 description "Terminated-id with default mapping to 8";
               }
               enum "bridging-no-service" {
                 description "Terminated-id with default mapping to 10";
               }
               enum "bridging-renegotiate-rx-conf-ack" {
                 description "Terminated-id with default mapping to 10";
               }
               enum "bridging-renegotiate-rx-conf-nak" {
                 description "Terminated-id with default mapping to 10";
               }
               enum "bridging-renegotiate-rx-conf-rej" {
                 description "Terminated-id with default mapping to 10";
               }
               enum "bridging-renegotiate-rx-conf-req" {
                 description "Terminated-id with default mapping to 10";
               }
               enum "bridging-stale-stacking" {
                 description "Terminated-id with default mapping to 10";
               }
               enum "bridging-terminate-code-rej" {
                 description "Terminated-id with default mapping to 10";
               }
               enum "bridging-terminate-term-ack" {
                 description "Terminated-id with default mapping to 10";
               }
               enum "bridging-terminate-term-req" {
                 description "Terminated-id with default mapping to 10";
               }
               enum "bundle-fail-activation" {
                 description "Terminated-id with default mapping to 10";
               }
               enum "bundle-fail-create" {
                 description "Terminated-id with default mapping to 10";
               }
               enum "bundle-fail-engine-add" {
                 description "Terminated-id with default mapping to 10";
               }
               enum "bundle-fail-fragment-size-mismatch" {
                 description "Terminated-id with default mapping to 10";
               }
               enum "bundle-fail-fragmentation-location" {
                 description "Terminated-id with default mapping to 10";
               }
               enum "bundle-fail-fragmentation-mismatch" {
                 description "Terminated-id with default mapping to 10";
               }
               enum "bundle-fail-hash-link-selection-mismatch" {
                 description "Terminated-id with default mapping to 10";
               }
               enum "bundle-fail-join" {
                 description "Terminated-id with default mapping to 10";
               }
               enum "bundle-fail-local-mped-not-set-yet" {
                 description "Terminated-id with default mapping to 10";
               }
               enum "bundle-fail-local-mrru-mismatch" {
                 description "Terminated-id with default mapping to 10";
               }
               enum "bundle-fail-local-mru-mismatch" {
                 description "Terminated-id with default mapping to 10";
               }
               enum "bundle-fail-peer-endpoint-discriminator-mismatch" {
                 description "Terminated-id with default mapping to 10";
               }
               enum "bundle-fail-peer-mrru-mismatch" {
                 description "Terminated-id with default mapping to 6";
               }
               enum "bundle-fail-profile-nak" {
                 description "Terminated-id with default mapping to 10";
               }
               enum "bundle-fail-reassembly-location" {
                 description "Terminated-id with default mapping to 10";
               }
               enum "bundle-fail-reassembly-mismatch" {
                 description "Terminated-id with default mapping to 10";
               }
               enum "bundle-fail-record-network" {
                 description "Terminated-id with default mapping to 10";
               }
               enum "bundle-fail-server-location-mismatch" {
                 description "Terminated-id with default mapping to 10";
               }
               enum "bundle-fail-static-link" {
                 description "Terminated-id with default mapping to 10";
               }
               enum "bundle-fail-unrecoverable-ifl" {
                 description "Terminated-id with default mapping to 10";
               }
               enum "dynamic-profile-instantiation-failed" {
                 description "Terminated-id with default mapping to 9";
               }
               enum "failover-during-authentication" {
                 description "Terminated-id with default mapping to 17";
               }
               enum "interface-admin-disable" {
                 description "Terminated-id with default mapping to 6";
               }
               enum "interface-no-hardware" {
                 description "Terminated-id with default mapping to 8";
               }
               enum "ip-admin-disable" {
                 description "Terminated-id with default mapping to 10";
               }
               enum "ip-failed-to-activate-family-inet" {
                 description "Terminated-id with default mapping to 9";
               }
               enum "ip-failed-to-activate-services" {
                 description "Terminated-id with default mapping to 9";
               }
               enum "ip-failed-to-add-access-internal-route" {
                 description "Terminated-id with default mapping to 9";
               }
               enum "ip-inhibited-by-authentication" {
                 description "Terminated-id with default mapping to 10";
               }
               enum "ip-link-down" {
                 description "Terminated-id with default mapping to 10";
               }
               enum "ip-max-configure-exceeded" {
                 description "Terminated-id with default mapping to 10";
               }
               enum "ip-max-passive-retries-exceeded" {
                 description "Terminated-id with default mapping to 10";
               }
               enum "ip-no-local-ip-address" {
                 description "Terminated-id with default mapping to 10";
               }
               enum "ip-no-local-ip-address-mask" {
                 description "Terminated-id with default mapping to 10";
               }
               enum "ip-no-local-primary-dns-address" {
                 description "Terminated-id with default mapping to 10";
               }
               enum "ip-no-local-primary-nbns-address" {
                 description "Terminated-id with default mapping to 10";
               }
               enum "ip-no-local-secondary-dns-address" {
                 description "Terminated-id with default mapping to 10";
               }
               enum "ip-no-local-secondary-nbns-address" {
                 description "Terminated-id with default mapping to 10";
               }
               enum "ip-no-peer-ip-address" {
                 description "Terminated-id with default mapping to 10";
               }
               enum "ip-no-peer-ip-address-mask" {
                 description "Terminated-id with default mapping to 10";
               }
               enum "ip-no-peer-primary-dns-address" {
                 description "Terminated-id with default mapping to 10";
               }
               enum "ip-no-peer-primary-nbns-address" {
                 description "Terminated-id with default mapping to 10";
               }
               enum "ip-no-peer-secondary-dns-address" {
                 description "Terminated-id with default mapping to 10";
               }
               enum "ip-no-peer-secondary-nbns-address" {
                 description "Terminated-id with default mapping to 10";
               }
               enum "ip-no-service" {
                 description "Terminated-id with default mapping to 10";
               }
               enum "ip-peer-renegotiate-rx-conf-ack" {
                 description "Terminated-id with default mapping to 10";
               }
               enum "ip-peer-renegotiate-rx-conf-nak" {
                 description "Terminated-id with default mapping to 10";
               }
               enum "ip-peer-renegotiate-rx-conf-rej" {
                 description "Terminated-id with default mapping to 10";
               }
               enum "ip-peer-renegotiate-rx-conf-req" {
                 description "Terminated-id with default mapping to 10";
               }
               enum "ip-peer-terminate-code-rej" {
                 description "Terminated-id with default mapping to 10";
               }
               enum "ip-peer-terminate-term-ack" {
                 description "Terminated-id with default mapping to 10";
               }
               enum "ip-peer-terminate-term-req" {
                 description "Terminated-id with default mapping to 10";
               }
               enum "ip-service-disable" {
                 description "Terminated-id with default mapping to 10";
               }
               enum "ip-stale-stacking" {
                 description "Terminated-id with default mapping to 10";
               }
               enum "ipv6-admin-disable" {
                 description "Terminated-id with default mapping to 10";
               }
               enum "ipv6-failed-to-activate-family-inet6" {
                 description "Terminated-id with default mapping to 9";
               }
               enum "ipv6-failed-to-activate-services" {
                 description "Terminated-id with default mapping to 9";
               }
               enum "ipv6-inhibited-by-authentication" {
                 description "Terminated-id with default mapping to 10";
               }
               enum "ipv6-link-down" {
                 description "Terminated-id with default mapping to 10";
               }
               enum "ipv6-local-and-peer-interface-ids-identical" {
                 description "Terminated-id with default mapping to 10";
               }
               enum "ipv6-max-configure-exceeded" {
                 description "Terminated-id with default mapping to 10";
               }
               enum "ipv6-max-passive-retries-exceeded" {
                 description "Terminated-id with default mapping to 10";
               }
               enum "ipv6-no-local-ipv6-interface-id" {
                 description "Terminated-id with default mapping to 10";
               }
               enum "ipv6-no-peer-ipv6-interface-id" {
                 description "Terminated-id with default mapping to 10";
               }
               enum "ipv6-no-service" {
                 description "Terminated-id with default mapping to 10";
               }
               enum "ipv6-peer-renegotiate-rx-conf-ack" {
                 description "Terminated-id with default mapping to 10";
               }
               enum "ipv6-peer-renegotiate-rx-conf-nak" {
                 description "Terminated-id with default mapping to 10";
               }
               enum "ipv6-peer-renegotiate-rx-conf-rej" {
                 description "Terminated-id with default mapping to 10";
               }
               enum "ipv6-peer-renegotiate-rx-conf-req" {
                 description "Terminated-id with default mapping to 10";
               }
               enum "ipv6-peer-terminate-code-rej" {
                 description "Terminated-id with default mapping to 10";
               }
               enum "ipv6-peer-terminate-term-ack" {
                 description "Terminated-id with default mapping to 10";
               }
               enum "ipv6-peer-terminate-term-req" {
                 description "Terminated-id with default mapping to 10";
               }
               enum "ipv6-service-disable" {
                 description "Terminated-id with default mapping to 10";
               }
               enum "ipv6-stale-stacking" {
                 description "Terminated-id with default mapping to 10";
               }
               enum "l2tp-session-apply-link-attribute-failed" {
                 description "Terminated-id with default mapping to 10";
               }
               enum "lcp-authenticate-terminate-hold" {
                 description "Terminated-id with default mapping to 10";
               }
               enum "lcp-configured-mrru-too-small" {
                 description "Terminated-id with default mapping to 10";
               }
               enum "lcp-configured-mru-invalid" {
                 description "Terminated-id with default mapping to 10";
               }
               enum "lcp-configured-mru-too-small" {
                 description "Terminated-id with default mapping to 10";
               }
               enum "lcp-dynamic-interface-hold" {
                 description "Terminated-id with default mapping to 10";
               }
               enum "lcp-failed-to-activate-services" {
                 description "Terminated-id with default mapping to 10";
               }
               enum "lcp-keepalive-failure" {
                 description "Terminated-id with default mapping to 10";
               }
               enum "lcp-loopback-rx-conf-req" {
                 description "Terminated-id with default mapping to 10";
               }
               enum "lcp-loopback-rx-echo-reply" {
                 description "Terminated-id with default mapping to 10";
               }
               enum "lcp-loopback-rx-echo-req" {
                 description "Terminated-id with default mapping to 10";
               }
               enum "lcp-max-configure-exceeded" {
                 description "Terminated-id with default mapping to 10";
               }
               enum "lcp-max-passive-retries-exceeded" {
                 description "Terminated-id with default mapping to 10";
               }
               enum "lcp-mru-changed" {
                 description "Terminated-id with default mapping to 8";
               }
               enum "lcp-negotiation-timeout" {
                 description "Terminated-id with default mapping to 10";
               }
               enum "lcp-no-local-accm" {
                 description "Terminated-id with default mapping to 10";
               }
               enum "lcp-no-local-acfc" {
                 description "Terminated-id with default mapping to 10";
               }
               enum "lcp-no-local-authentication" {
                 description "Terminated-id with default mapping to 10";
               }
               enum "lcp-no-local-endpoint-discriminator" {
                 description "Terminated-id with default mapping to 10";
               }
               enum "lcp-no-local-magic-number" {
                 description "Terminated-id with default mapping to 10";
               }
               enum "lcp-no-local-mrru" {
                 description "Terminated-id with default mapping to 10";
               }
               enum "lcp-no-local-mru" {
                 description "Terminated-id with default mapping to 10";
               }
               enum "lcp-no-local-pfc" {
                 description "Terminated-id with default mapping to 10";
               }
               enum "lcp-no-peer-accm" {
                 description "Terminated-id with default mapping to 10";
               }
               enum "lcp-no-peer-acfc" {
                 description "Terminated-id with default mapping to 10";
               }
               enum "lcp-no-peer-authentication" {
                 description "Terminated-id with default mapping to 10";
               }
               enum "lcp-no-peer-endpoint-discriminator" {
                 description "Terminated-id with default mapping to 10";
               }
               enum "lcp-no-peer-magic-number" {
                 description "Terminated-id with default mapping to 10";
               }
               enum "lcp-no-peer-mrru" {
                 description "Terminated-id with default mapping to 10";
               }
               enum "lcp-no-peer-mru" {
                 description "Terminated-id with default mapping to 10";
               }
               enum "lcp-no-peer-pfc" {
                 description "Terminated-id with default mapping to 10";
               }
               enum "lcp-peer-renegotiate-rx-conf-ack" {
                 description "Terminated-id with default mapping to 1";
               }
               enum "lcp-peer-renegotiate-rx-conf-nak" {
                 description "Terminated-id with default mapping to 1";
               }
               enum "lcp-peer-renegotiate-rx-conf-rej" {
                 description "Terminated-id with default mapping to 1";
               }
               enum "lcp-peer-renegotiate-rx-conf-req" {
                 description "Terminated-id with default mapping to 1";
               }
               enum "lcp-peer-terminate-code-rej" {
                 description "Terminated-id with default mapping to 1";
               }
               enum "lcp-peer-terminate-protocol-reject" {
                 description "Terminated-id with default mapping to 1";
               }
               enum "lcp-peer-terminate-term-ack" {
                 description "Terminated-id with default mapping to 1";
               }
               enum "lcp-peer-terminate-term-req" {
                 description "Terminated-id with default mapping to 1";
               }
               enum "lcp-tunnel-disconnected" {
                 description "Terminated-id with default mapping to 10";
               }
               enum "lcp-tunnel-failed" {
                 description "Terminated-id with default mapping to 10";
               }
               enum "license-limit-exceeded" {
                 description "Terminated-id with default mapping to 10";
               }
               enum "link-interface-no-hardware" {
                 description "Terminated-id with default mapping to 10";
               }
               enum "lower-interface-attach-failed" {
                 description "Terminated-id with default mapping to 2";
               }
               enum "lower-interface-down" {
                 description "Terminated-id with default mapping to 2";
               }
               enum "lower-interface-teardown" {
                 description "Terminated-id with default mapping to 17";
               }
               enum "mpls-admin-disable" {
                 description "Terminated-id with default mapping to 10";
               }
               enum "mpls-failed-to-activate-family-mpls" {
                 description "Terminated-id with default mapping to 10";
               }
               enum "mpls-link-down" {
                 description "Terminated-id with default mapping to 10";
               }
               enum "mpls-max-configure-exceeded" {
                 description "Terminated-id with default mapping to 10";
               }
               enum "mpls-max-passive-retries-exceeded" {
                 description "Terminated-id with default mapping to 10";
               }
               enum "mpls-no-service" {
                 description "Terminated-id with default mapping to 10";
               }
               enum "mpls-peer-renegotiate-rx-conf-ack" {
                 description "Terminated-id with default mapping to 10";
               }
               enum "mpls-peer-renegotiate-rx-conf-nak" {
                 description "Terminated-id with default mapping to 10";
               }
               enum "mpls-peer-renegotiate-rx-conf-rej" {
                 description "Terminated-id with default mapping to 10";
               }
               enum "mpls-peer-renegotiate-rx-conf-req" {
                 description "Terminated-id with default mapping to 10";
               }
               enum "mpls-peer-terminate-code-rej" {
                 description "Terminated-id with default mapping to 10";
               }
               enum "mpls-peer-terminate-term-ack" {
                 description "Terminated-id with default mapping to 10";
               }
               enum "mpls-peer-terminate-term-req" {
                 description "Terminated-id with default mapping to 10";
               }
               enum "mpls-service-disable" {
                 description "Terminated-id with default mapping to 10";
               }
               enum "mpls-stale-stacking" {
                 description "Terminated-id with default mapping to 10";
               }
               enum "network-interface-admin-disable" {
                 description "Terminated-id with default mapping to 10";
               }
               enum "no-bundle" {
                 description "Terminated-id with default mapping to 8";
               }
               enum "no-interface" {
                 description "Terminated-id with default mapping to 10";
               }
               enum "no-link-interface" {
                 description "Terminated-id with default mapping to 10";
               }
               enum "no-ncps-available" {
                 description "Terminated-id with default mapping to 10";
               }
               enum "no-network-interface" {
                 description "Terminated-id with default mapping to 6";
               }
               enum "no-upper-interface" {
                 description "Terminated-id with default mapping to 9";
               }
               enum "osi-admin-disable" {
                 description "Terminated-id with default mapping to 10";
               }
               enum "osi-failed-to-activate-family-osi" {
                 description "Terminated-id with default mapping to 10";
               }
               enum "osi-link-down" {
                 description "Terminated-id with default mapping to 10";
               }
               enum "osi-max-configure-exceeded" {
                 description "Terminated-id with default mapping to 10";
               }
               enum "osi-max-passive-retries-exceeded" {
                 description "Terminated-id with default mapping to 10";
               }
               enum "osi-no-local-align-npdu" {
                 description "Terminated-id with default mapping to 10";
               }
               enum "osi-no-peer-align-npdu" {
                 description "Terminated-id with default mapping to 10";
               }
               enum "osi-no-service" {
                 description "Terminated-id with default mapping to 10";
               }
               enum "osi-peer-renegotiate-rx-conf-ack" {
                 description "Terminated-id with default mapping to 10";
               }
               enum "osi-peer-renegotiate-rx-conf-nak" {
                 description "Terminated-id with default mapping to 10";
               }
               enum "osi-peer-renegotiate-rx-conf-rej" {
                 description "Terminated-id with default mapping to 10";
               }
               enum "osi-peer-renegotiate-rx-conf-req" {
                 description "Terminated-id with default mapping to 10";
               }
               enum "osi-peer-terminate-code-rej" {
                 description "Terminated-id with default mapping to 10";
               }
               enum "osi-peer-terminate-term-ack" {
                 description "Terminated-id with default mapping to 10";
               }
               enum "osi-peer-terminate-term-req" {
                 description "Terminated-id with default mapping to 10";
               }
               enum "osi-service-disable" {
                 description "Terminated-id with default mapping to 10";
               }
               enum "osi-stale-stacking" {
                 description "Terminated-id with default mapping to 10";
               }
               enum "recovery-active-state-cleanup" {
                 description "Terminated-id with default mapping to 9";
               }
               enum "recovery-configured-state-cleanup" {
                 description "Terminated-id with default mapping to 9";
               }
               enum "recovery-init-state-cleanup" {
                 description "Terminated-id with default mapping to 9";
               }
               enum "recovery-terminated-state-cleanup" {
                 description "Terminated-id with default mapping to 9";
               }
               enum "recovery-terminating-state-cleanup" {
                 description "Terminated-id with default mapping to 9";
               }
               enum "session-init-failed" {
                 description "Terminated-id with default mapping to 9";
               }
               enum "subscriber-mgr-activation-failed" {
                 description "Terminated-id with default mapping to 9";
               }
               enum "subscriber-mgr-get-credentials-failed" {
                 description "Terminated-id with default mapping to 9";
               }
               enum "subscriber-mgr-link-interface-not-found" {
                 description "Terminated-id with default mapping to 9";
               }
               enum "subscriber-mgr-set-state-active-failed" {
                 description "Terminated-id with default mapping to 9";
               }
             }
           }
         }
         case l2tp-terminate-code {
           leaf l2tp-terminate-code {
             description "Specify L2TP terminate-code";
             type enumeration {
               enum "issu-in-progress" {
                 description "Terminated-id with default mapping to 10";
               }
               enum "session-access-interface-down" {
                 description "Terminated-id with default mapping to 8";
               }
               enum "session-administrative-close" {
                 description "Terminated-id with default mapping to 6";
               }
               enum "session-administrative-drain" {
                 description "Terminated-id with default mapping to 6";
               }
               enum "session-call-down" {
                 description "Terminated-id with default mapping to 10";
               }
               enum "session-call-failed" {
                 description "Terminated-id with default mapping to 15";
               }
               enum "session-create-failed-icrq-to-initiator-tunnel" {
                 description "Terminated-id with default mapping to 9";
               }
               enum "session-create-failed-invalid-config" {
                 description "Terminated-id with default mapping to 10";
               }
               enum "session-create-failed-limit-reached" {
                 description "Terminated-id with default mapping to 9";
               }
               enum "session-create-failed-no-resources" {
                 description "Terminated-id with default mapping to 9";
               }
               enum "session-create-failed-single-shot-tunnel-already-fired" {
                 description "Terminated-id with default mapping to 9";
               }
               enum "session-create-failed-too-busy" {
                 description "Terminated-id with default mapping to 9";
               }
               enum "session-failover-protocol-resync-disconnect" {
                 description "Terminated-id with default mapping to 6";
               }
               enum "session-hardware-unavailable" {
                 description "Terminated-id with default mapping to 8";
               }
               enum "session-no-resources-server-port" {
                 description "Terminated-id with default mapping to 9";
               }
               enum "session-not-ready" {
                 description "Terminated-id with default mapping to 9";
               }
               enum "session-receive-cdn" {
                 description "Terminated-id with default mapping to 10";
               }
               enum "session-receive-cdn-avp-bad-hidden" {
                 description "Terminated-id with default mapping to 10";
               }
               enum "session-receive-cdn-avp-bad-value-assigned-session-id" {
                 description "Terminated-id with default mapping to 10";
               }
               enum "session-receive-cdn-avp-duplicate-value-assigned-session-id" {
                 description "Terminated-id with default mapping to 10";
               }
               enum "session-receive-cdn-avp-malformed-bad-length" {
                 description "Terminated-id with default mapping to 10";
               }
               enum "session-receive-cdn-avp-malformed-truncated" {
                 description "Terminated-id with default mapping to 10";
               }
               enum "session-receive-cdn-avp-missing-mandatory-assigned-session-id" {
                 description "Terminated-id with default mapping to 10";
               }
               enum "session-receive-cdn-avp-missing-mandatory-result-code" {
                 description "Terminated-id with default mapping to 10";
               }
               enum "session-receive-cdn-avp-missing-random-vector" {
                 description "Terminated-id with default mapping to 10";
               }
               enum "session-receive-cdn-avp-missing-secret" {
                 description "Terminated-id with default mapping to 10";
               }
               enum "session-receive-cdn-avp-unknown" {
                 description "Terminated-id with default mapping to 10";
               }
               enum "session-receive-cdn-no-resources" {
                 description "Terminated-id with default mapping to 10";
               }
               enum "session-receive-iccn-avp-bad-hidden" {
                 description "Terminated-id with default mapping to 10";
               }
               enum "session-receive-iccn-avp-bad-value-framing-type" {
                 description "Terminated-id with default mapping to 10";
               }
               enum "session-receive-iccn-avp-bad-value-proxy-authen-type" {
                 description "Terminated-id with default mapping to 10";
               }
               enum "session-receive-iccn-avp-bad-value-unsupported-proxy-authen-type" {
                 description "Terminated-id with default mapping to 10";
               }
               enum "session-receive-iccn-avp-malformed-bad-length" {
                 description "Terminated-id with default mapping to 10";
               }
               enum "session-receive-iccn-avp-malformed-truncated" {
                 description "Terminated-id with default mapping to 10";
               }
               enum "session-receive-iccn-avp-missing-mandatory-connect-speed" {
                 description "Terminated-id with default mapping to 10";
               }
               enum "session-receive-iccn-avp-missing-mandatory-framing-type" {
                 description "Terminated-id with default mapping to 10";
               }
               enum "session-receive-iccn-avp-missing-mandatory-proxy-authen-challenge" {
                 description "Terminated-id with default mapping to 10";
               }
               enum "session-receive-iccn-avp-missing-mandatory-proxy-authen-id" {
                 description "Terminated-id with default mapping to 10";
               }
               enum "session-receive-iccn-avp-missing-mandatory-proxy-authen-name" {
                 description "Terminated-id with default mapping to 10";
               }
               enum "session-receive-iccn-avp-missing-mandatory-proxy-authen-response" {
                 description "Terminated-id with default mapping to 10";
               }
               enum "session-receive-iccn-avp-missing-random-vector" {
                 description "Terminated-id with default mapping to 10";
               }
               enum "session-receive-iccn-avp-missing-secret" {
                 description "Terminated-id with default mapping to 10";
               }
               enum "session-receive-iccn-avp-unknown" {
                 description "Terminated-id with default mapping to 10";
               }
               enum "session-receive-iccn-no-resources" {
                 description "Terminated-id with default mapping to 10";
               }
               enum "session-receive-iccn-unexpected" {
                 description "Terminated-id with default mapping to 10";
               }
               enum "session-receive-icrp-avp-bad-hidden" {
                 description "Terminated-id with default mapping to 10";
               }
               enum "session-receive-icrp-avp-bad-value-assigned-session-id" {
                 description "Terminated-id with default mapping to 10";
               }
               enum "session-receive-icrp-avp-duplicate-value-assigned-session-id" {
                 description "Terminated-id with default mapping to 10";
               }
               enum "session-receive-icrp-avp-malformed-bad-length" {
                 description "Terminated-id with default mapping to 10";
               }
               enum "session-receive-icrp-avp-malformed-truncated" {
                 description "Terminated-id with default mapping to 10";
               }
               enum "session-receive-icrp-avp-missing-mandatory-assigned-session-id" {
                 description "Terminated-id with default mapping to 10";
               }
               enum "session-receive-icrp-avp-missing-random-vector" {
                 description "Terminated-id with default mapping to 10";
               }
               enum "session-receive-icrp-avp-missing-secret" {
                 description "Terminated-id with default mapping to 10";
               }
               enum "session-receive-icrp-avp-unknown" {
                 description "Terminated-id with default mapping to 10";
               }
               enum "session-receive-icrp-no-resources" {
                 description "Terminated-id with default mapping to 10";
               }
               enum "session-receive-icrp-unexpected" {
                 description "Terminated-id with default mapping to 10";
               }
               enum "session-receive-icrq-administrative-close" {
                 description "Terminated-id with default mapping to 6";
               }
               enum "session-receive-icrq-authenticate-failed-host" {
                 description "Terminated-id with default mapping to 10";
               }
               enum "session-receive-icrq-avp-bad-hidden" {
                 description "Terminated-id with default mapping to 10";
               }
               enum "session-receive-icrq-avp-bad-value-assigned-session-id" {
                 description "Terminated-id with default mapping to 10";
               }
               enum "session-receive-icrq-avp-bad-value-bearer-type" {
                 description "Terminated-id with default mapping to 10";
               }
               enum "session-receive-icrq-avp-bad-value-cisco-nas-port" {
                 description "Terminated-id with default mapping to 10";
               }
               enum "session-receive-icrq-avp-duplicate-value-assigned-session-id" {
                 description "Terminated-id with default mapping to 10";
               }
               enum "session-receive-icrq-avp-malformed-bad-length" {
                 description "Terminated-id with default mapping to 10";
               }
               enum "session-receive-icrq-avp-malformed-truncated" {
                 description "Terminated-id with default mapping to 10";
               }
               enum "session-receive-icrq-avp-missing-mandatory-assigned-session-id" {
                 description "Terminated-id with default mapping to 10";
               }
               enum "session-receive-icrq-avp-missing-mandatory-call-serial-number" {
                 description "Terminated-id with default mapping to 10";
               }
               enum "session-receive-icrq-avp-missing-random-vector" {
                 description "Terminated-id with default mapping to 10";
               }
               enum "session-receive-icrq-avp-missing-secret" {
                 description "Terminated-id with default mapping to 10";
               }
               enum "session-receive-icrq-avp-unknown" {
                 description "Terminated-id with default mapping to 10";
               }
               enum "session-receive-icrq-no-resources" {
                 description "Terminated-id with default mapping to 10";
               }
               enum "session-receive-icrq-unexpected" {
                 description "Terminated-id with default mapping to 10";
               }
               enum "session-receive-occn-avp-bad-hidden" {
                 description "Terminated-id with default mapping to 10";
               }
               enum "session-receive-occn-avp-bad-value-framing-type" {
                 description "Terminated-id with default mapping to 10";
               }
               enum "session-receive-occn-avp-malformed-bad-length" {
                 description "Terminated-id with default mapping to 10";
               }
               enum "session-receive-occn-avp-malformed-truncated" {
                 description "Terminated-id with default mapping to 10";
               }
               enum "session-receive-occn-avp-missing-mandatory-connect-speed" {
                 description "Terminated-id with default mapping to 10";
               }
               enum "session-receive-occn-avp-missing-mandatory-framing-type" {
                 description "Terminated-id with default mapping to 10";
               }
               enum "session-receive-occn-avp-missing-random-vector" {
                 description "Terminated-id with default mapping to 10";
               }
               enum "session-receive-occn-avp-missing-secret" {
                 description "Terminated-id with default mapping to 10";
               }
               enum "session-receive-occn-avp-unknown" {
                 description "Terminated-id with default mapping to 10";
               }
               enum "session-receive-occn-no-resources" {
                 description "Terminated-id with default mapping to 10";
               }
               enum "session-receive-occn-unexpected" {
                 description "Terminated-id with default mapping to 10";
               }
               enum "session-receive-ocrp-avp-bad-hidden" {
                 description "Terminated-id with default mapping to 10";
               }
               enum "session-receive-ocrp-avp-bad-value-assigned-session-id" {
                 description "Terminated-id with default mapping to 10";
               }
               enum "session-receive-ocrp-avp-duplicate-value-assigned-session-id" {
                 description "Terminated-id with default mapping to 10";
               }
               enum "session-receive-ocrp-avp-malformed-bad-length" {
                 description "Terminated-id with default mapping to 10";
               }
               enum "session-receive-ocrp-avp-malformed-truncated" {
                 description "Terminated-id with default mapping to 10";
               }
               enum "session-receive-ocrp-avp-missing-mandatory-assigned-session-id" {
                 description "Terminated-id with default mapping to 10";
               }
               enum "session-receive-ocrp-avp-missing-random-vector" {
                 description "Terminated-id with default mapping to 10";
               }
               enum "session-receive-ocrp-avp-missing-secret" {
                 description "Terminated-id with default mapping to 10";
               }
               enum "session-receive-ocrp-avp-unknown" {
                 description "Terminated-id with default mapping to 10";
               }
               enum "session-receive-ocrp-no-resources" {
                 description "Terminated-id with default mapping to 10";
               }
               enum "session-receive-ocrp-unexpected" {
                 description "Terminated-id with default mapping to 10";
               }
               enum "session-receive-ocrq-administrative-close" {
                 description "Terminated-id with default mapping to 6";
               }
               enum "session-receive-ocrq-authenticate-failed-host" {
                 description "Terminated-id with default mapping to 10";
               }
               enum "session-receive-ocrq-avp-bad-hidden" {
                 description "Terminated-id with default mapping to 10";
               }
               enum "session-receive-ocrq-avp-bad-value-assigned-session-id" {
                 description "Terminated-id with default mapping to 10";
               }
               enum "session-receive-ocrq-avp-bad-value-bearer-type" {
                 description "Terminated-id with default mapping to 10";
               }
               enum "session-receive-ocrq-avp-bad-value-framing-type" {
                 description "Terminated-id with default mapping to 10";
               }
               enum "session-receive-ocrq-avp-duplicate-value-assigned-session-id" {
                 description "Terminated-id with default mapping to 10";
               }
               enum "session-receive-ocrq-avp-malformed-bad-length" {
                 description "Terminated-id with default mapping to 10";
               }
               enum "session-receive-ocrq-avp-malformed-truncated" {
                 description "Terminated-id with default mapping to 10";
               }
               enum "session-receive-ocrq-avp-missing-mandatory-assigned-session-id" {
                 description "Terminated-id with default mapping to 10";
               }
               enum "session-receive-ocrq-avp-missing-mandatory-bearer-type" {
                 description "Terminated-id with default mapping to 10";
               }
               enum "session-receive-ocrq-avp-missing-mandatory-call-serial-number" {
                 description "Terminated-id with default mapping to 10";
               }
               enum "session-receive-ocrq-avp-missing-mandatory-called-number" {
                 description "Terminated-id with default mapping to 10";
               }
               enum "session-receive-ocrq-avp-missing-mandatory-framing-type" {
                 description "Terminated-id with default mapping to 10";
               }
               enum "session-receive-ocrq-avp-missing-mandatory-maximum-bps" {
                 description "Terminated-id with default mapping to 10";
               }
               enum "session-receive-ocrq-avp-missing-mandatory-minimum-bps" {
                 description "Terminated-id with default mapping to 10";
               }
               enum "session-receive-ocrq-avp-missing-random-vector" {
                 description "Terminated-id with default mapping to 10";
               }
               enum "session-receive-ocrq-avp-missing-secret" {
                 description "Terminated-id with default mapping to 10";
               }
               enum "session-receive-ocrq-avp-unknown" {
                 description "Terminated-id with default mapping to 10";
               }
               enum "session-receive-ocrq-no-resources" {
                 description "Terminated-id with default mapping to 10";
               }
               enum "session-receive-ocrq-unexpected" {
                 description "Terminated-id with default mapping to 10";
               }
               enum "session-receive-ocrq-unsupported" {
                 description "Terminated-id with default mapping to 9";
               }
               enum "session-receive-sli-avp-bad-hidden" {
                 description "Terminated-id with default mapping to 10";
               }
               enum "session-receive-sli-avp-bad-value-accm" {
                 description "Terminated-id with default mapping to 10";
               }
               enum "session-receive-sli-avp-malformed-bad-length" {
                 description "Terminated-id with default mapping to 10";
               }
               enum "session-receive-sli-avp-malformed-truncated" {
                 description "Terminated-id with default mapping to 10";
               }
               enum "session-receive-sli-avp-missing-mandatory-accm" {
                 description "Terminated-id with default mapping to 10";
               }
               enum "session-receive-sli-avp-missing-random-vector" {
                 description "Terminated-id with default mapping to 10";
               }
               enum "session-receive-sli-avp-missing-secret" {
                 description "Terminated-id with default mapping to 10";
               }
               enum "session-receive-sli-avp-unknown" {
                 description "Terminated-id with default mapping to 10";
               }
               enum "session-receive-sli-no-resources" {
                 description "Terminated-id with default mapping to 10";
               }
               enum "session-receive-unexpected-packet-lac-incoming" {
                 description "Terminated-id with default mapping to 10";
               }
               enum "session-receive-unexpected-packet-lac-outgoing" {
                 description "Terminated-id with default mapping to 10";
               }
               enum "session-receive-unexpected-packet-lns-incoming" {
                 description "Terminated-id with default mapping to 10";
               }
               enum "session-receive-unexpected-packet-lns-outgoing" {
                 description "Terminated-id with default mapping to 10";
               }
               enum "session-receive-unknown-session-id" {
                 description "Terminated-id with default mapping to 10";
               }
               enum "session-receive-wen-avp-bad-hidden" {
                 description "Terminated-id with default mapping to 10";
               }
               enum "session-receive-wen-avp-malformed-bad-length" {
                 description "Terminated-id with default mapping to 10";
               }
               enum "session-receive-wen-avp-malformed-truncated" {
                 description "Terminated-id with default mapping to 10";
               }
               enum "session-receive-wen-avp-missing-mandatory-call-errors" {
                 description "Terminated-id with default mapping to 10";
               }
               enum "session-receive-wen-avp-missing-random-vector" {
                 description "Terminated-id with default mapping to 10";
               }
               enum "session-receive-wen-avp-missing-secret" {
                 description "Terminated-id with default mapping to 10";
               }
               enum "session-receive-wen-avp-unknown" {
                 description "Terminated-id with default mapping to 10";
               }
               enum "session-receive-wen-no-resources" {
                 description "Terminated-id with default mapping to 10";
               }
               enum "session-timeout-connection" {
                 description "Terminated-id with default mapping to 10";
               }
               enum "session-timeout-inactivity" {
                 description "Terminated-id with default mapping to 4";
               }
               enum "session-timeout-session" {
                 description "Terminated-id with default mapping to 5";
               }
               enum "session-timeout-upper-create" {
                 description "Terminated-id with default mapping to 9";
               }
               enum "session-transmit-speed-unavailable" {
                 description "Terminated-id with default mapping to 9";
               }
               enum "session-tunnel-down" {
                 description "Terminated-id with default mapping to 15";
               }
               enum "session-tunnel-failed" {
                 description "Terminated-id with default mapping to 15";
               }
               enum "session-tunnel-switch-profile-deleted" {
                 description "Terminated-id with default mapping to 6";
               }
               enum "session-tunneled-interface-down" {
                 description "Terminated-id with default mapping to 8";
               }
               enum "session-unknown-cause" {
                 description "Terminated-id with default mapping to 9";
               }
               enum "session-upper-create-failed" {
                 description "Terminated-id with default mapping to 9";
               }
               enum "session-upper-removed" {
                 description "Terminated-id with default mapping to 15";
               }
               enum "session-warmstart-not-operational" {
                 description "Terminated-id with default mapping to 15";
               }
               enum "session-warmstart-recovery-error" {
                 description "Terminated-id with default mapping to 15";
               }
               enum "session-warmstart-uppper-not-restacked" {
                 description "Terminated-id with default mapping to 10";
               }
               enum "session-eracheck-failed" {
                 description "Terminated-id with default mapping to 10";
               }
               enum "session-mappedswitchedsession-down" {
                 description "Terminated-id with default mapping to 10";
               }
               enum "session-rx-csurq-avp-unknown" {
                 description "Terminated-id with default mapping to 10";
               }
               enum "session-rx-icrq-issu-in-progress" {
                 description "Terminated-id with default mapping to 10";
               }
               enum "session-rx-ocrq-issu-in-progress" {
                 description "Terminated-id with default mapping to 10";
               }
               enum "session-sdb-release" {
                 description "Terminated-id with default mapping to 10";
               }
               enum "session-stray-ifl-association" {
                 description "Terminated-id with default mapping to 10";
               }
               enum "session-tunnelswitch-error" {
                 description "Terminated-id with default mapping to 10";
               }
               enum "session-uptimer-expiry" {
                 description "Terminated-id with default mapping to 10";
               }
               enum "tunnel-administrative-close" {
                 description "Terminated-id with default mapping to 6";
               }
               enum "tunnel-administrative-drain" {
                 description "Terminated-id with default mapping to 6";
               }
               enum "tunnel-control-channel-failed" {
                 description "Terminated-id with default mapping to 15";
               }
               enum "tunnel-created-no-sessions" {
                 description "Terminated-id with default mapping to 1";
               }
               enum "tunnel-destination-address-changed" {
                 description "Terminated-id with default mapping to 6";
               }
               enum "tunnel-destination-down" {
                 description "Terminated-id with default mapping to 10";
               }
               enum "tunnel-failover-protocol-no-resources-for-recovery-tunnel" {
                 description "Terminated-id with default mapping to 15";
               }
               enum "tunnel-failover-protocol-no-resources-for-session-resync" {
                 description "Terminated-id with default mapping to 15";
               }
               enum "tunnel-failover-protocol-not-supported" {
                 description "Terminated-id with default mapping to 15";
               }
               enum "tunnel-failover-protocol-not-supported-by-peer" {
                 description "Terminated-id with default mapping to 15";
               }
               enum "tunnel-failover-protocol-recovery-control-channel-failed" {
                 description "Terminated-id with default mapping to 15";
               }
               enum "tunnel-failover-protocol-recovery-tunnel-failed" {
                 description "Terminated-id with default mapping to 15";
               }
               enum "tunnel-failover-protocol-recovery-tunnel-finished" {
                 description "Terminated-id with default mapping to 1";
               }
               enum "tunnel-failover-protocol-recovery-tunnel-primary-down" {
                 description "Terminated-id with default mapping to 1";
               }
               enum "tunnel-failover-protocol-session-resync-failed" {
                 description "Terminated-id with default mapping to 15";
               }
               enum "tunnel-host-profile-changed" {
                 description "Terminated-id with default mapping to 6";
               }
               enum "tunnel-host-profile-deleted" {
                 description "Terminated-id with default mapping to 6";
               }
               enum "tunnel-receive-fsq-avp-bad-hidden" {
                 description "Terminated-id with default mapping to 15";
               }
               enum "tunnel-receive-fsq-avp-malformed-bad-length" {
                 description "Terminated-id with default mapping to 15";
               }
               enum "tunnel-receive-fsq-avp-malformed-truncated" {
                 description "Terminated-id with default mapping to 15";
               }
               enum "tunnel-receive-fsq-avp-missing-mandatory-failover-session-state" {
                 description "Terminated-id with default mapping to 15";
               }
               enum "tunnel-receive-fsq-avp-missing-random-vector" {
                 description "Terminated-id with default mapping to 15";
               }
               enum "tunnel-receive-fsq-avp-missing-secret" {
                 description "Terminated-id with default mapping to 15";
               }
               enum "tunnel-receive-fsq-avp-unknown" {
                 description "Terminated-id with default mapping to 15";
               }
               enum "tunnel-receive-fsq-no-resources" {
                 description "Terminated-id with default mapping to 15";
               }
               enum "tunnel-receive-fsq-session-id-not-null" {
                 description "Terminated-id with default mapping to 15";
               }
               enum "tunnel-receive-fsr-avp-bad-hidden" {
                 description "Terminated-id with default mapping to 15";
               }
               enum "tunnel-receive-fsr-avp-malformed-bad-length" {
                 description "Terminated-id with default mapping to 15";
               }
               enum "tunnel-receive-fsr-avp-malformed-truncated" {
                 description "Terminated-id with default mapping to 15";
               }
               enum "tunnel-receive-fsr-avp-missing-mandatory-failover-session-state" {
                 description "Terminated-id with default mapping to 15";
               }
               enum "tunnel-receive-fsr-avp-missing-random-vector" {
                 description "Terminated-id with default mapping to 15";
               }
               enum "tunnel-receive-fsr-avp-missing-secret" {
                 description "Terminated-id with default mapping to 15";
               }
               enum "tunnel-receive-fsr-avp-unknown" {
                 description "Terminated-id with default mapping to 15";
               }
               enum "tunnel-receive-fsr-no-resources" {
                 description "Terminated-id with default mapping to 15";
               }
               enum "tunnel-receive-fsr-session-id-not-null" {
                 description "Terminated-id with default mapping to 15";
               }
               enum "tunnel-receive-recovery-scccn-authenticate-failed-challenge" {
                 description "Terminated-id with default mapping to 17";
               }
               enum "tunnel-receive-recovery-scccn-avp-bad-hidden" {
                 description "Terminated-id with default mapping to 15";
               }
               enum "tunnel-receive-recovery-scccn-avp-bad-value-challenge-response" {
                 description "Terminated-id with default mapping to 15";
               }
               enum "tunnel-receive-recovery-scccn-avp-malformed-bad-length" {
                 description "Terminated-id with default mapping to 15";
               }
               enum "tunnel-receive-recovery-scccn-avp-malformed-truncated" {
                 description "Terminated-id with default mapping to 15";
               }
               enum "tunnel-receive-recovery-scccn-avp-missing-challenge-response" {
                 description "Terminated-id with default mapping to 17";
               }
               enum "tunnel-receive-recovery-scccn-avp-missing-random-vector" {
                 description "Terminated-id with default mapping to 15";
               }
               enum "tunnel-receive-recovery-scccn-avp-missing-secret" {
                 description "Terminated-id with default mapping to 15";
               }
               enum "tunnel-receive-recovery-scccn-avp-unexpected-challenge-response" {
                 description "Terminated-id with default mapping to 15";
               }
               enum "tunnel-receive-recovery-scccn-avp-unknown" {
                 description "Terminated-id with default mapping to 15";
               }
               enum "tunnel-receive-recovery-scccn-no-resources" {
                 description "Terminated-id with default mapping to 15";
               }
               enum "tunnel-receive-recovery-scccn-session-id-not-null" {
                 description "Terminated-id with default mapping to 15";
               }
               enum "tunnel-receive-recovery-scccp-avp-unexpected-challenge-response" {
                 description "Terminated-id with default mapping to 15";
               }
               enum "tunnel-receive-recovery-scccp-avp-bad-value-challenge-response" {
                 description "Terminated-id with default mapping to 15";
               }
               enum "tunnel-receive-recovery-scccp-avp-missing-challenge-response" {
                 description "Terminated-id with default mapping to 17";
               }
               enum "tunnel-receive-recovery-sccrp-authenticate-failed-challenge" {
                 description "Terminated-id with default mapping to 17";
               }
               enum "tunnel-receive-recovery-sccrp-avp-bad-hidden" {
                 description "Terminated-id with default mapping to 15";
               }
               enum "tunnel-receive-recovery-sccrp-avp-bad-value-assigned-tunnel-id" {
                 description "Terminated-id with default mapping to 15";
               }
               enum "tunnel-receive-recovery-sccrp-avp-bad-value-bearer-capabilities" {
                 description "Terminated-id with default mapping to 15";
               }
               enum "tunnel-receive-recovery-sccrp-avp-bad-value-challenge" {
                 description "Terminated-id with default mapping to 15";
               }
               enum "tunnel-receive-recovery-sccrp-avp-bad-value-framing-capabilities" {
                 description "Terminated-id with default mapping to 15";
               }
               enum "tunnel-receive-recovery-sccrp-avp-bad-value-protocol-version" {
                 description "Terminated-id with default mapping to 15";
               }
               enum "tunnel-receive-recovery-sccrp-avp-bad-value-receive-window-size" {
                 description "Terminated-id with default mapping to 15";
               }
               enum "tunnel-receive-recovery-sccrp-avp-bad-value-suggested-control-sequence" {
                 description "Terminated-id with default mapping to 15";
               }
               enum "tunnel-receive-recovery-sccrp-avp-duplicate-value-assigned-tunnel-id" {
                 description "Terminated-id with default mapping to 15";
               }
               enum "tunnel-receive-recovery-sccrp-avp-malformed-bad-length" {
                 description "Terminated-id with default mapping to 15";
               }
               enum "tunnel-receive-recovery-sccrp-avp-malformed-truncated" {
                 description "Terminated-id with default mapping to 15";
               }
               enum "tunnel-receive-recovery-sccrp-avp-mismatched-host-name" {
                 description "Terminated-id with default mapping to 15";
               }
               enum "tunnel-receive-recovery-sccrp-avp-mismatched-vendor-name" {
                 description "Terminated-id with default mapping to 15";
               }
               enum "tunnel-receive-recovery-sccrp-avp-missing-mandatory-assigned-tunnel-id" {
                 description "Terminated-id with default mapping to 15";
               }
               enum "tunnel-receive-recovery-sccrp-avp-missing-mandatory-framing-capabilities" {
                 description "Terminated-id with default mapping to 15";
               }
               enum "tunnel-receive-recovery-sccrp-avp-missing-mandatory-host-name" {
                 description "Terminated-id with default mapping to 15";
               }
               enum "tunnel-receive-recovery-sccrp-avp-missing-mandatory-protocol-version" {
                 description "Terminated-id with default mapping to 15";
               }
               enum "tunnel-receive-recovery-sccrp-avp-missing-random-vector" {
                 description "Terminated-id with default mapping to 15";
               }
               enum "tunnel-receive-recovery-sccrp-avp-missing-secret" {
                 description "Terminated-id with default mapping to 15";
               }
               enum "tunnel-receive-recovery-sccrp-avp-unexpected-challenge-without-secret" {
                 description "Terminated-id with default mapping to 15";
               }
               enum "tunnel-receive-recovery-sccrp-avp-unknown" {
                 description "Terminated-id with default mapping to 15";
               }
               enum "tunnel-receive-recovery-sccrp-no-resources" {
                 description "Terminated-id with default mapping to 15";
               }
               enum "tunnel-receive-recovery-sccrp-session-id-not-null" {
                 description "Terminated-id with default mapping to 15";
               }
               enum "tunnel-receive-recovery-sccrq-administrative-close" {
                 description "Terminated-id with default mapping to 6";
               }
               enum "tunnel-receive-recovery-sccrq-avp-bad-hidden" {
                 description "Terminated-id with default mapping to 15";
               }
               enum "tunnel-receive-recovery-sccrq-avp-bad-value-assigned-tunnel-id" {
                 description "Terminated-id with default mapping to 15";
               }
               enum "tunnel-receive-recovery-sccrq-avp-bad-value-bearer-capabilities" {
                 description "Terminated-id with default mapping to 15";
               }
               enum "tunnel-receive-recovery-sccrq-avp-bad-value-challenge" {
                 description "Terminated-id with default mapping to 15";
               }
               enum "tunnel-receive-recovery-sccrq-avp-bad-value-framing-capabilities" {
                 description "Terminated-id with default mapping to 15";
               }
               enum "tunnel-receive-recovery-sccrq-avp-bad-value-protocol-version" {
                 description "Terminated-id with default mapping to 15";
               }
               enum "tunnel-receive-recovery-sccrq-avp-bad-value-receive-window-size" {
                 description "Terminated-id with default mapping to 15";
               }
               enum "tunnel-receive-recovery-sccrq-avp-bad-value-tunnel-recovery" {
                 description "Terminated-id with default mapping to 15";
               }
               enum "tunnel-receive-recovery-sccrq-avp-duplicate-value-assigned-tunnel-id" {
                 description "Terminated-id with default mapping to 15";
               }
               enum "tunnel-receive-recovery-sccrq-avp-duplicate-value-tie-breaker" {
                 description "Terminated-id with default mapping to 15";
               }
               enum "tunnel-receive-recovery-sccrq-avp-malformed-bad-length" {
                 description "Terminated-id with default mapping to 15";
               }
               enum "tunnel-receive-recovery-sccrq-avp-malformed-truncated" {
                 description "Terminated-id with default mapping to 15";
               }
               enum "tunnel-receive-recovery-sccrq-avp-mismatched-host-name" {
                 description "Terminated-id with default mapping to 15";
               }
               enum "tunnel-receive-recovery-sccrq-avp-mismatched-vendor-name" {
                 description "Terminated-id with default mapping to 15";
               }
               enum "tunnel-receive-recovery-sccrq-avp-missing-mandatory-assigned-tunnel-id" {
                 description "Terminated-id with default mapping to 15";
               }
               enum "tunnel-receive-recovery-sccrq-avp-missing-mandatory-framing-capabilities" {
                 description "Terminated-id with default mapping to 15";
               }
               enum "tunnel-receive-recovery-sccrq-avp-missing-mandatory-host-name" {
                 description "Terminated-id with default mapping to 15";
               }
               enum "tunnel-receive-recovery-sccrq-avp-missing-mandatory-protocol-version" {
                 description "Terminated-id with default mapping to 15";
               }
               enum "tunnel-receive-recovery-sccrq-avp-missing-mandatory-tunnel-recovery" {
                 description "Terminated-id with default mapping to 15";
               }
               enum "tunnel-receive-recovery-sccrq-avp-missing-random-vector" {
                 description "Terminated-id with default mapping to 15";
               }
               enum "tunnel-receive-recovery-sccrq-avp-missing-secret" {
                 description "Terminated-id with default mapping to 15";
               }
               enum "tunnel-receive-recovery-sccrq-avp-missing-tie-breaker" {
                 description "Terminated-id with default mapping to 15";
               }
               enum "tunnel-receive-recovery-sccrq-avp-unexpected-challenge-without-secret" {
                 description "Terminated-id with default mapping to 15";
               }
               enum "tunnel-receive-recovery-sccrq-avp-unknown" {
                 description "Terminated-id with default mapping to 15";
               }
               enum "tunnel-receive-recovery-sccrq-no-resources-max-tunnels" {
                 description "Terminated-id with default mapping to 15";
               }
               enum "tunnel-receive-recovery-sccrq-session-id-not-null" {
                 description "Terminated-id with default mapping to 15";
               }
               enum "tunnel-receive-recovery-sccrq-tunnel-id-not-null" {
                 description "Terminated-id with default mapping to 15";
               }
               enum "tunnel-receive-recovery-stopccn-avp-bad-hidden" {
                 description "Terminated-id with default mapping to 15";
               }
               enum "tunnel-receive-recovery-stopccn-avp-bad-value-assigned-tunnel-id" {
                 description "Terminated-id with default mapping to 15";
               }
               enum "tunnel-receive-recovery-stopccn-avp-duplicate-value-assigned-tunnel-id" {
                 description "Terminated-id with default mapping to 15";
               }
               enum "tunnel-receive-recovery-stopccn-avp-malformed-bad-length" {
                 description "Terminated-id with default mapping to 15";
               }
               enum "tunnel-receive-recovery-stopccn-avp-malformed-truncated" {
                 description "Terminated-id with default mapping to 15";
               }
               enum "tunnel-receive-recovery-stopccn-avp-missing-mandatory-assigned-tunnel-id" {
                 description "Terminated-id with default mapping to 15";
               }
               enum "tunnel-receive-recovery-stopccn-avp-missing-mandatory-result-code" {
                 description "Terminated-id with default mapping to 15";
               }
               enum "tunnel-receive-recovery-stopccn-avp-missing-random-vector" {
                 description "Terminated-id with default mapping to 15";
               }
               enum "tunnel-receive-recovery-stopccn-avp-missing-secret" {
                 description "Terminated-id with default mapping to 15";
               }
               enum "tunnel-receive-recovery-stopccn-avp-unknown" {
                 description "Terminated-id with default mapping to 15";
               }
               enum "tunnel-receive-recovery-stopccn-no-resources" {
                 description "Terminated-id with default mapping to 15";
               }
               enum "tunnel-receive-recovery-stopccn-session-id-not-null" {
                 description "Terminated-id with default mapping to 15";
               }
               enum "tunnel-receive-recovery-unexpected-packet" {
                 description "Terminated-id with default mapping to 15";
               }
               enum "tunnel-receive-recovery-unknown-packet-message-type-indecipherable" {
                 description "Terminated-id with default mapping to 15";
               }
               enum "tunnel-receive-recovery-unknown-packet-message-type-unrecognized" {
                 description "Terminated-id with default mapping to 15";
               }
               enum "tunnel-receive-scccn-authenticate-failed-challenge" {
                 description "Terminated-id with default mapping to 17";
               }
               enum "tunnel-receive-scccn-avp-bad-hidden" {
                 description "Terminated-id with default mapping to 15";
               }
               enum "tunnel-receive-scccn-avp-bad-value-challenge-response" {
                 description "Terminated-id with default mapping to 15";
               }
               enum "tunnel-receive-scccn-avp-malformed-bad-length" {
                 description "Terminated-id with default mapping to 15";
               }
               enum "tunnel-receive-scccn-avp-malformed-truncated" {
                 description "Terminated-id with default mapping to 15";
               }
               enum "tunnel-receive-scccn-avp-missing-challenge-response" {
                 description "Terminated-id with default mapping to 17";
               }
               enum "tunnel-receive-scccn-avp-missing-random-vector" {
                 description "Terminated-id with default mapping to 15";
               }
               enum "tunnel-receive-scccn-avp-missing-secret" {
                 description "Terminated-id with default mapping to 15";
               }
               enum "tunnel-receive-scccn-avp-unexpected-challenge-response" {
                 description "Terminated-id with default mapping to 15";
               }
               enum "tunnel-receive-scccn-avp-unknown" {
                 description "Terminated-id with default mapping to 15";
               }
               enum "tunnel-receive-scccn-no-resources" {
                 description "Terminated-id with default mapping to 15";
               }
               enum "tunnel-receive-scccn-session-id-not-null" {
                 description "Terminated-id with default mapping to 15";
               }
               enum "tunnel-receive-scccn-unexpected" {
                 description "Terminated-id with default mapping to 15";
               }
               enum "tunnel-receive-sccrp-authenticate-failed-challenge" {
                 description "Terminated-id with default mapping to 17";
               }
               enum "tunnel-receive-sccrp-authenticate-failed-host" {
                 description "Terminated-id with default mapping to 17";
               }
               enum "tunnel-receive-sccrp-avp-bad-hidden" {
                 description "Terminated-id with default mapping to 15";
               }
               enum "tunnel-receive-sccrp-avp-bad-value-assigned-tunnel-id" {
                 description "Terminated-id with default mapping to 15";
               }
               enum "tunnel-receive-sccrp-avp-bad-value-bearer-capabilities" {
                 description "Terminated-id with default mapping to 15";
               }
               enum "tunnel-receive-sccrp-avp-bad-value-challenge" {
                 description "Terminated-id with default mapping to 15";
               }
               enum "tunnel-receive-sccrp-avp-bad-value-challenge-response" {
                 description "Terminated-id with default mapping to 15";
               }
               enum "tunnel-receive-sccrp-avp-bad-value-failover-capability" {
                 description "Terminated-id with default mapping to 15";
               }
               enum "tunnel-receive-sccrp-avp-bad-value-framing-capabilities" {
                 description "Terminated-id with default mapping to 15";
               }
               enum "tunnel-receive-sccrp-avp-bad-value-protocol-version" {
                 description "Terminated-id with default mapping to 15";
               }
               enum "tunnel-receive-sccrp-avp-bad-value-receive-window-size" {
                 description "Terminated-id with default mapping to 15";
               }
               enum "tunnel-receive-sccrp-avp-duplicate-value-assigned-tunnel-id" {
                 description "Terminated-id with default mapping to 15";
               }
               enum "tunnel-receive-sccrp-avp-malformed-bad-length" {
                 description "Terminated-id with default mapping to 15";
               }
               enum "tunnel-receive-sccrp-avp-malformed-truncated" {
                 description "Terminated-id with default mapping to 15";
               }
               enum "tunnel-receive-sccrp-avp-missing-challenge-response" {
                 description "Terminated-id with default mapping to 17";
               }
               enum "tunnel-receive-sccrp-avp-missing-mandatory-assigned-tunnel-id" {
                 description "Terminated-id with default mapping to 15";
               }
               enum "tunnel-receive-sccrp-avp-missing-mandatory-framing-capabilities" {
                 description "Terminated-id with default mapping to 15";
               }
               enum "tunnel-receive-sccrp-avp-missing-mandatory-host-name" {
                 description "Terminated-id with default mapping to 15";
               }
               enum "tunnel-receive-sccrp-avp-missing-mandatory-protocol-version" {
                 description "Terminated-id with default mapping to 15";
               }
               enum "tunnel-receive-sccrp-avp-missing-random-vector" {
                 description "Terminated-id with default mapping to 15";
               }
               enum "tunnel-receive-sccrp-avp-missing-secret" {
                 description "Terminated-id with default mapping to 15";
               }
               enum "tunnel-receive-sccrp-avp-unexpected-challenge-response" {
                 description "Terminated-id with default mapping to 15";
               }
               enum "tunnel-receive-sccrp-avp-unexpected-challenge-without-secret" {
                 description "Terminated-id with default mapping to 15";
               }
               enum "tunnel-receive-sccrp-avp-unknown" {
                 description "Terminated-id with default mapping to 15";
               }
               enum "tunnel-receive-sccrp-no-resources" {
                 description "Terminated-id with default mapping to 15";
               }
               enum "tunnel-receive-sccrp-session-id-not-null" {
                 description "Terminated-id with default mapping to 15";
               }
               enum "tunnel-receive-sccrp-unexpected" {
                 description "Terminated-id with default mapping to 15";
               }
               enum "tunnel-receive-sccrq-administrative-close" {
                 description "Terminated-id with default mapping to 6";
               }
               enum "tunnel-receive-sccrq-authenticate-failed-host" {
                 description "Terminated-id with default mapping to 17";
               }
               enum "tunnel-receive-sccrq-avp-bad-hidden" {
                 description "Terminated-id with default mapping to 15";
               }
               enum "tunnel-receive-sccrq-avp-bad-value-assigned-tunnel-id" {
                 description "Terminated-id with default mapping to 15";
               }
               enum "tunnel-receive-sccrq-avp-bad-value-bearer-capabilities" {
                 description "Terminated-id with default mapping to 15";
               }
               enum "tunnel-receive-sccrq-avp-bad-value-challenge" {
                 description "Terminated-id with default mapping to 15";
               }
               enum "tunnel-receive-sccrq-avp-bad-value-failover-capability" {
                 description "Terminated-id with default mapping to 15";
               }
               enum "tunnel-receive-sccrq-avp-bad-value-framing-capabilities" {
                 description "Terminated-id with default mapping to 15";
               }
               enum "tunnel-receive-sccrq-avp-bad-value-protocol-version" {
                 description "Terminated-id with default mapping to 15";
               }
               enum "tunnel-receive-sccrq-avp-bad-value-receive-window-size" {
                 description "Terminated-id with default mapping to 15";
               }
               enum "tunnel-receive-sccrq-avp-duplicate-value-assigned-tunnel-id" {
                 description "Terminated-id with default mapping to 15";
               }
               enum "tunnel-receive-sccrq-avp-malformed-bad-length" {
                 description "Terminated-id with default mapping to 15";
               }
               enum "tunnel-receive-sccrq-avp-malformed-truncated" {
                 description "Terminated-id with default mapping to 15";
               }
               enum "tunnel-receive-sccrq-avp-missing-mandatory-assigned-tunnel-id" {
                 description "Terminated-id with default mapping to 15";
               }
               enum "tunnel-receive-sccrq-avp-missing-mandatory-framing-capabilities" {
                 description "Terminated-id with default mapping to 15";
               }
               enum "tunnel-receive-sccrq-avp-missing-mandatory-host-name" {
                 description "Terminated-id with default mapping to 15";
               }
               enum "tunnel-receive-sccrq-avp-missing-mandatory-protocol-version" {
                 description "Terminated-id with default mapping to 15";
               }
               enum "tunnel-receive-sccrq-avp-missing-random-vector" {
                 description "Terminated-id with default mapping to 15";
               }
               enum "tunnel-receive-sccrq-avp-missing-secret" {
                 description "Terminated-id with default mapping to 15";
               }
               enum "tunnel-receive-sccrq-avp-unexpected-challenge-without-secret" {
                 description "Terminated-id with default mapping to 15";
               }
               enum "tunnel-receive-sccrq-avp-unknown" {
                 description "Terminated-id with default mapping to 15";
               }
               enum "tunnel-receive-sccrq-bad-address" {
                 description "Terminated-id with default mapping to 15";
               }
               enum "tunnel-receive-sccrq-invalid-ns" {
                 description "Terminated-id with default mapping to 10";
               }
               enum "tunnel-receive-sccrq-no-resources" {
                 description "Terminated-id with default mapping to 15";
               }
               enum "tunnel-receive-sccrq-no-resources-max-tunnels" {
                 description "Terminated-id with default mapping to 15";
               }
               enum "tunnel-receive-sccrq-session-id-not-null" {
                 description "Terminated-id with default mapping to 15";
               }
               enum "tunnel-receive-sccrq-unexpected" {
                 description "Terminated-id with default mapping to 15";
               }
               enum "tunnel-receive-session-packet-null-session-id-invalid" {
                 description "Terminated-id with default mapping to 15";
               }
               enum "tunnel-receive-session-packet-null-session-id-without-assigned-session-id" {
                 description "Terminated-id with default mapping to 15";
               }
               enum "tunnel-receive-stopccn" {
                 description "Terminated-id with default mapping to 1";
               }
               enum "tunnel-receive-stopccn-avp-bad-hidden" {
                 description "Terminated-id with default mapping to 15";
               }
               enum "tunnel-receive-stopccn-avp-bad-value-assigned-tunnel-id" {
                 description "Terminated-id with default mapping to 15";
               }
               enum "tunnel-receive-stopccn-avp-duplicate-value-assigned-tunnel-id" {
                 description "Terminated-id with default mapping to 15";
               }
               enum "tunnel-receive-stopccn-avp-malformed-bad-length" {
                 description "Terminated-id with default mapping to 15";
               }
               enum "tunnel-receive-stopccn-avp-malformed-truncated" {
                 description "Terminated-id with default mapping to 15";
               }
               enum "tunnel-receive-stopccn-avp-missing-mandatory-assigned-tunnel-id" {
                 description "Terminated-id with default mapping to 15";
               }
               enum "tunnel-receive-stopccn-avp-missing-mandatory-result-code" {
                 description "Terminated-id with default mapping to 15";
               }
               enum "tunnel-receive-stopccn-avp-missing-random-vector" {
                 description "Terminated-id with default mapping to 15";
               }
               enum "tunnel-receive-stopccn-avp-missing-secret" {
                 description "Terminated-id with default mapping to 15";
               }
               enum "tunnel-receive-stopccn-avp-unknown" {
                 description "Terminated-id with default mapping to 15";
               }
               enum "tunnel-receive-stopccn-no-resources" {
                 description "Terminated-id with default mapping to 15";
               }
               enum "tunnel-receive-stopccn-session-id-not-null" {
                 description "Terminated-id with default mapping to 15";
               }
               enum "tunnel-receive-unexpected-packet" {
                 description "Terminated-id with default mapping to 15";
               }
               enum "tunnel-receive-unexpected-packet-for-session" {
                 description "Terminated-id with default mapping to 15";
               }
               enum "tunnel-receive-unknown-packet-message-type-indecipherable" {
                 description "Terminated-id with default mapping to 15";
               }
               enum "tunnel-receive-unknown-packet-message-type-unrecognized" {
                 description "Terminated-id with default mapping to 15";
               }
               enum "tunnel-timeout-connection" {
                 description "Terminated-id with default mapping to 15";
               }
               enum "tunnel-timeout-connection-recovery-tunnel" {
                 description "Terminated-id with default mapping to 15";
               }
               enum "tunnel-timeout-idle" {
                 description "Terminated-id with default mapping to 1";
               }
               enum "tunnel-unknown-cause" {
                 description "Terminated-id with default mapping to 9";
               }
               enum "tunnel-warmstart-not-operational" {
                 description "Terminated-id with default mapping to 15";
               }
               enum "tunnel-warmstart-recovery-error" {
                 description "Terminated-id with default mapping to 15";
               }
             }
           }
         }
       }
     }
     output {
       container aaa-test-result {
         uses aaa-test-result-block;
       }
     }
   }
   rpc get-dhcp-user-aaa-test-result {
     description "Test the aaa servers for a dhcp user";
     junos:command "test aaa dhcp";
     input {
       leaf user {
         description "The username to test";
         type string;
         mandatory true;
       }
       leaf password {
         description "The password associated with username";
         type string;
       }
       leaf profile {
         description "Specify the access profile name which to use for user";
         type string;
       }
       leaf logical-system {
         description "Specify the logical-system in which to authenticate user";
         type string;
       }
       leaf routing-instance {
         description "Specify the routing-instance in which to authenticate user";
         type string;
       }
       leaf service-type {
         description "Service type ";
         type string;
       }
       leaf mac-address {
         description "Specify the Mac address of the DHCP client";
         type jt:mac-addr;
       }
       leaf option-82 {
         description "Specify the DHCP option 82";
         type string;
       }
       leaf agent-remote-id {
         description "DSL forum agent remote id ";
         type string {
           length "1 .. 63";
         }
       }
       leaf source-address {
         description "Use specified address as source address";
         type jt:ipv4addr;
       }
       leaf no-address-request {
         description "Request is for authentication without address-allocation";
         type empty;
       }
       leaf terminate-code {
         description "Specify DHCP terminate-code";
         type enumeration {
           enum "client-request" {
             description "Terminated-id with default mapping to 1";
           }
           enum "lost-carrier" {
             description "Terminated-id with default mapping to 2";
           }
           enum "nak" {
             description "Terminated-id with default mapping to 15";
           }
           enum "nas-logout" {
             description "Terminated-id with default mapping to 10";
           }
           enum "no-offers" {
             description "Terminated-id with default mapping to 4";
           }
         }
       }
     }
     output {
       container aaa-test-result {
         uses aaa-test-result-block;
       }
     }
   }
   rpc get-authdlite-user-aaa-test-result {
     description "Test the aaa servers for a authdlite user";
     junos:command "test aaa authd-lite";
     input {
       leaf user {
         description "The username to test";
         type string;
         mandatory true;
       }
       leaf password {
         description "The password associated with username";
         type string;
       }
       leaf profile {
         description "Specify the access profile name which to use for user";
         type string;
       }
       leaf port {
         description "Specify NAS-port to be used for test";
         type string;
       }
       leaf zero-stats {
         description "Specify that acct stats should be set to zero";
         type empty;
       }
       choice xauth_type {
         case xauth {
           leaf xauth {
             description "Emulate xauth client";
             type empty;
           }
         }
         case xauth-new {
           leaf xauth-new {
             description "Emulate xauth client using new opcodes (e.g. iked)";
             type empty;
           }
         }
       }
       leaf s6a {
         description "Emulate s6a client";
         type empty;
       }
     }
     output {
       container aaa-test-result {
         uses aaa-test-result-block;
       }
     }
   }
   rpc get-ocs-sftp-backup-test-result {
     description "Test aaa ocs sftp-backup";
     junos:command "test aaa ocs sftp-backup";
     output {
       container ocs-sftp-backup-test-result {
         uses ocs-sftp-backup-test-result-block;
       }
     }
   }
   rpc test-anti-spam-ip {
     description "Test anti-spam ip-check";
     junos:command "test security utm anti-spam ip-check";
     input {
       leaf test-ip {
         description "Anti-spam test IP address";
         junos:cli-feature "nokeyword";
         type jt:ipaddr;
         mandatory true;
       }
     }
     output {
       container anti-spam-test {
         uses anti-spam-test-block;
       }
     }
   }
   rpc test-web-filtering-profile {
     description "Test web-filtering";
     junos:command "test security utm web-filtering";
     input {
       leaf profile {
         description "Web-filtering profile name";
         type string {
           length "1 .. 29";
         }
         mandatory true;
       }
       leaf test-url {
         description "Web-filtering test URL";
         junos:cli-feature "nokeyword";
         type string {
           length "1 .. 249";
         }
         mandatory true;
       }
       choice lsys {
         case logical-system {
           leaf logical-system {
             description "Logical-system name";
             type string;
           }
         }
         case root-logical-system {
           leaf root-logical-system {
             description "Root logical-system (default)";
             type empty;
           }
         }
         case tenant {
           leaf tenant {
             description "Tenant name";
             type string;
           }
         }
         case all-logical-systems-tenants {
           leaf all-logical-systems-tenants {
             description "All multitenancy systems";
             type empty;
           }
         }
       }
     }
     output {
       container web-filtering-test {
         uses web-filtering-test-block;
       }
     }
   }
   rpc test-enhanced-web-filtering {
     description "Web-filtering url-check";
     junos:command "test security utm web-filtering url-check";
     input {
       leaf test-url {
         description "Web-filtering threat-check test URL";
         junos:cli-feature "nokeyword";
         type string {
           length "1 .. 249";
         }
         mandatory true;
       }
     }
     output {
       container enhanced-web-filtering-test {
         uses enhanced-web-filtering-test-block;
       }
     }
   }
   rpc rib-sharding-hash-route-to-shard {
     description "Test route with rib-sharding hash function";
     junos:command "test rib-sharding route";
     input {
       leaf destination {
         description "IP address and optional prefix length of destination";
         junos:cli-feature "nokeyword";
         type jt:ipprefix;
         mandatory true;
       }
     }
   }
   rpc rt-test-rt-proxy-register {
     description "Application";
     junos:command "test rt-proxy msg-srvc register app";
     input {
       choice daemon-select {
         case rib-sharding {
           leaf rib-sharding {
             description "Name of rib shard";
             type string {
               junos:posix-pattern "^[a-zA-Z0-9_-]{1,63}$";
               junos:pattern-message "Shard name is a string consisting of up to 63 letters, numbers, dashes and underscores";
             }
           }
         }
       }
       leaf app_name {
         description "Name";
         junos:cli-feature "nokeyword";
         type string;
         mandatory true;
       }
     }
     output {
       choice output_c {
         case output-tag {
           leaf output {
             type string;
           }
         }
         case multichassis-tag {
           anyxml multi-routing-engine-results;
         }
       }
     }
   }
   rpc rt-test-rt-proxy-deregister {
     description "Application";
     junos:command "test rt-proxy msg-srvc deregister app";
     input {
       choice daemon-select {
         case rib-sharding {
           leaf rib-sharding {
             description "Name of rib shard";
             type string {
               junos:posix-pattern "^[a-zA-Z0-9_-]{1,63}$";
               junos:pattern-message "Shard name is a string consisting of up to 63 letters, numbers, dashes and underscores";
             }
           }
         }
       }
       leaf app_name {
         description "Name";
         junos:cli-feature "nokeyword";
         type string;
         mandatory true;
       }
     }
     output {
       choice output_c {
         case output-tag {
           leaf output {
             type string;
           }
         }
         case multichassis-tag {
           anyxml multi-routing-engine-results;
         }
       }
     }
   }
   rpc rt-test-rt-proxy-send-req {
     description "Application";
     junos:command "test rt-proxy msg-srvc send-req app";
     input {
       choice daemon-select {
         case rib-sharding {
           leaf rib-sharding {
             description "Name of rib shard";
             type string {
               junos:posix-pattern "^[a-zA-Z0-9_-]{1,63}$";
               junos:pattern-message "Shard name is a string consisting of up to 63 letters, numbers, dashes and underscores";
             }
           }
         }
       }
       leaf app_name {
         description "Name";
         junos:cli-feature "nokeyword";
         type string;
         mandatory true;
       }
     }
     output {
       choice output_c {
         case output-tag {
           leaf output {
             type string;
           }
         }
         case multichassis-tag {
           anyxml multi-routing-engine-results;
         }
       }
     }
   }
   rpc rt-test-rt-proxy-send-resp {
     description "Application";
     junos:command "test rt-proxy msg-srvc send-resp app";
     input {
       choice daemon-select {
         case rib-sharding {
           leaf rib-sharding {
             description "Name of rib shard";
             type string {
               junos:posix-pattern "^[a-zA-Z0-9_-]{1,63}$";
               junos:pattern-message "Shard name is a string consisting of up to 63 letters, numbers, dashes and underscores";
             }
           }
         }
       }
       leaf app_name {
         description "Name";
         junos:cli-feature "nokeyword";
         type string;
         mandatory true;
       }
     }
     output {
       choice output_c {
         case output-tag {
           leaf output {
             type string;
           }
         }
         case multichassis-tag {
           anyxml multi-routing-engine-results;
         }
       }
     }
   }
   rpc test-msdp-dependent-peers {
     description "Find downstream dependent peers for a prefix";
     junos:command "test msdp dependent-peers";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf instance {
         description "Name of instance";
         type string;
       }
       leaf prefix {
         description "IPv4 address and optional prefix length";
         junos:cli-feature "nokeyword";
         type jt:ipv4prefix;
         mandatory true;
       }
     }
     output {
       choice output_c {
         case output-tag {
           leaf output {
             type string;
           }
         }
         case multichassis-tag {
           anyxml multi-routing-engine-results;
         }
       }
     }
   }
   rpc test-msdp-rpf-peers {
     description "Find MSDP reverse-path forwarding peer for an originator";
     junos:command "test msdp rpf-peer";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf instance {
         description "Name of instance";
         type string;
       }
       leaf originator {
         description "IPv4 address and optional prefix length of originator";
         junos:cli-feature "nokeyword";
         type jt:ipv4prefix;
         mandatory true;
       }
     }
     output {
       choice output_c {
         case output-tag {
           leaf output {
             type string;
           }
         }
         case multichassis-tag {
           anyxml multi-routing-engine-results;
         }
       }
     }
   }
   rpc test-routing-policy {
     description "Import and export policy evaluation";
     junos:command "test policy";
     input {
       leaf policy {
         description "Policy name";
         junos:cli-feature "nokeyword";
         type string;
       }
       leaf prefix {
         description "Destination prefix";
         junos:cli-feature "nokeyword";
         type string;
       }
     }
     output {
       container route-information {
         uses route-information-block;
       }
     }
   }
   rpc test-l2-learning {
     description "Layer 2 forwarding commands";
     junos:command "test l2-learning";
     input {
       leaf in-memory-debug {
         description "Enable or disable in-memory tracing";
         type enumeration {
           enum "disable" {
             description "Disable in-memory tracing";
           }
           enum "enable" {
             description "Enable in-memory tracing";
           }
         }
         mandatory true;
       }
     }
     output {
       choice output_c {
         case output-tag {
           leaf output {
             type string;
           }
         }
         case multichassis-tag {
           anyxml multi-routing-engine-results;
         }
       }
     }
   }
   rpc test-aaa-asm-ccr {
     description "Test commands to send CCR from diameter-asm";
     junos:command "test unified-edge ggsn-pgw diameter asm send-ccr-msg";
     input {
       leaf msg-type {
         description "Specify CCR Message type";
         junos:cli-feature "nokeyword";
         type enumeration {
           enum "ccri" {
             description "Trigger CCR-I message";
           }
           enum "ccru" {
             description "Trigger CCR-U message";
           }
           enum "ccrt" {
             description "Trigger CCR-T message";
           }
         }
         mandatory true;
       }
       leaf app-type {
         description "Specify Application type";
         junos:cli-feature "nokeyword";
         type enumeration {
           enum "app-gx" {
             description "Trigger Gx message";
           }
           enum "app-gy" {
             description "Trigger Gy message";
           }
         }
         mandatory true;
       }
       leaf message-length {
         description "Specify message length";
         junos:cli-feature "nokeyword";
         type enumeration {
           enum "short" {
             description "Short Gx message";
           }
           enum "long" {
             description "Long Gy message";
           }
         }
       }
       leaf te-id {
         description "TEID to be used in CCR";
         type union {
           type uint32;
           type string {
             pattern "<.*>|$.*";
           }
         }
         mandatory true;
       }
       leaf bearer-id {
         description "Bearer-id to be used in CCR";
         type union {
           type uint32;
           type string {
             pattern "<.*>|$.*";
           }
         }
         mandatory true;
       }
       leaf profile {
         description "Diameter application profile name";
         type string {
           length "1 .. 64";
         }
       }
       leaf count {
         description "Number of ccr messages, default is 1";
         type union {
           type uint32;
           type string {
             pattern "<.*>|$.*";
           }
         }
       }
       leaf rate {
         description "Number of ccr messages per 100msec, default is 100";
         type union {
           type uint32;
           type string {
             pattern "<.*>|$.*";
           }
         }
       }
     }
     output {
       choice output_c {
         case output-tag {
           leaf output {
             type string;
           }
         }
         case multichassis-tag {
           anyxml multi-routing-engine-results;
         }
       }
     }
   }
   rpc test-rfc2544-benchmarking {
     description "Rfc2544 test configuration";
     junos:command "test services rpm rfc2544-benchmarking";
     output {
       choice output_c {
         case output-tag {
           leaf output {
             type string;
           }
         }
         case multichassis-tag {
           anyxml multi-routing-engine-results;
         }
       }
     }
   }
   rpc test-rfc2544-benchmarking-test {
     description "Start/stop a rfc2544 test";
     junos:command "test services rpm rfc2544-benchmarking test";
     input {
       leaf test-name {
         description "Test name";
         junos:cli-feature "nokeyword";
         type string;
       }
       leaf test-start-stop-clear {
         junos:cli-feature "nokeyword";
         type enumeration {
           enum "start" {
             description "Start test";
           }
           enum "stop" {
             description "Stop test";
           }
           enum "clear-counters" {
             description "Clear test counters";
           }
         }
         mandatory true;
       }
       leaf routing-instance {
         description "Name of routing instance for rfc2544 test ";
         type string {
           junos:posix-pattern "!^((__.*__)|(all)|(.*[ ].*)|(\"\")|(.{129,}))$";
           junos:pattern-message "Must be a non-reserved string of 128 characters or less with no spaces.";
         }
       }
     }
     output {
       choice output_c {
         case output-tag {
           leaf output {
             type string;
           }
         }
         case multichassis-tag {
           anyxml multi-routing-engine-results;
         }
       }
     }
   }
   rpc test-rfc2544-benchmarking-test-id {
     description "Stop a rfc2544 test";
     junos:command "test services rpm rfc2544-benchmarking test-id";
     input {
       leaf test-id {
         description "Test id";
         junos:cli-feature "nokeyword";
         type union {
           type uint32;
           type string {
             pattern "<.*>|$.*";
           }
         }
       }
       leaf test-stop {
         junos:cli-feature "nokeyword";
         type enumeration {
           enum "stop" {
             description "Stop test";
           }
         }
       }
     }
     output {
       choice output_c {
         case output-tag {
           leaf output {
             type string;
           }
         }
         case multichassis-tag {
           anyxml multi-routing-engine-results;
         }
       }
     }
   }
   rpc get-test-services-l2tp-tunnel-result {
     description "Check L2TP tunnel configuration for a subscriber";
     junos:command "test services l2tp tunnel";
     input {
       leaf user {
         description "Name of the subscriber";
         type string;
         mandatory true;
       }
       leaf password {
         description "Password for the subscriber";
         type string;
       }
       leaf tunnel-name {
         description "Name of the L2TP tunnel";
         type string;
       }
       leaf up-name {
         description "Name of the User Plane";
         type string;
       }
     }
     output {
       container test-services-l2tp-tunnel-result {
         uses test-services-l2tp-tunnel-result-block;
       }
     }
   }
   rpc test-services-traffic-load-balance-code-coverage {
     description "Execute Traffic load balance code-coverage";
     junos:command "test services traffic-load-balance code-coverage";
     input {
       leaf database-id {
         description "Database identifier";
         junos:cli-feature "nokeyword";
         type enumeration {
           enum "all" {
             description "All databases";
           }
           enum "probe" {
             description "Probe database";
           }
           enum "firewall" {
             description "Firewall";
           }
           enum "ip-db" {
             description "Ip database";
           }
           enum "clear-db" {
             description "Clear all databases";
           }
           enum "stats" {
             description "Stats";
           }
           enum "group-db" {
             description "Group database";
           }
           enum "heap" {
             description "Heap";
           }
           enum "virtual-svc-db" {
             description "Virtual srv database";
           }
           enum "instance-db" {
             description "Instance database";
           }
           enum "real-svc-db" {
             description "Real srv database";
           }
           enum "group-real-svc-db" {
             description "Group real srv database";
           }
           enum "validation-db" {
             description "Validation database";
           }
           enum "pconn-db" {
             description "Pconn database";
           }
           enum "gencfg-db" {
             description "Gencfg database";
           }
           enum "main" {
             description "Main functions";
           }
           enum "snmp" {
             description "SNMP functions";
           }
           enum "ui" {
             description "UI functions";
           }
           enum "config-parse" {
             description "Config parse functions";
           }
           enum "filter-config" {
             description "Filter database";
           }
           enum "ssd" {
             description "SSD functions";
           }
           enum "commit-checks" {
             description "Commit checks";
           }
         }
       }
     }
     output {
       choice output_c {
         case output-tag {
           leaf output {
             type string;
           }
         }
         case multichassis-tag {
           anyxml multi-routing-engine-results;
         }
       }
     }
   }
   rpc test-services-traffic-load-balance-inject-error {
     description "Execute Traffic load balance error-injection";
     junos:command "test services traffic-load-balance inject-error";
     input {
       leaf error-id {
         description "Error identifier";
         type union {
           type uint32;
           type string {
             pattern "<.*>|$.*";
           }
         }
         mandatory true;
       }
       leaf always-fail {
         description "Fail always";
         type enumeration {
           enum "enable" {
             description "Enable failure";
           }
           enum "disable" {
             description "Disable failure";
           }
         }
         mandatory true;
       }
     }
     output {
       choice output_c {
         case output-tag {
           leaf output {
             type string;
           }
         }
         case multichassis-tag {
           anyxml multi-routing-engine-results;
         }
       }
     }
   }
   rpc test-services-url-filter-inject-error {
     description "Execute URL Filtering error-injection";
     junos:command "test services web-filter inject-error";
     input {
       leaf error-id {
         description "Error identifier";
         type union {
           type uint32;
           type string {
             pattern "<.*>|$.*";
           }
         }
         mandatory true;
       }
       leaf always-fail {
         description "Fail always";
         type enumeration {
           enum "enable" {
             description "Enable failure";
           }
           enum "disable" {
             description "Disable failure";
           }
         }
         mandatory true;
       }
     }
     output {
       choice output_c {
         case output-tag {
           leaf output {
             type string;
           }
         }
         case multichassis-tag {
           anyxml multi-routing-engine-results;
         }
       }
     }
   }
   rpc test-services-url-filter-add-cc-feed-file {
     description "Add a C&C feed file to web-filtering";
     junos:command "test services web-filter add-cc-feed-file";
     input {
       leaf filename {
         description "C&C feed file name";
         type string;
         mandatory true;
       }
     }
     output {
       choice output_c {
         case output-tag {
           leaf output {
             type string;
           }
         }
         case multichassis-tag {
           anyxml multi-routing-engine-results;
         }
       }
     }
   }
   rpc test-services-url-filter-add-gbl-wl-feed-file {
     description "Add a global whitelist feed file to web-filtering";
     junos:command "test services web-filter add-global-wl-feed-file";
     input {
       leaf wl-filename {
         description "Global whitelist feed file name";
         type string;
         mandatory true;
       }
     }
     output {
       choice output_c {
         case output-tag {
           leaf output {
             type string;
           }
         }
         case multichassis-tag {
           anyxml multi-routing-engine-results;
         }
       }
     }
   }
   rpc test-services-url-filter-add-gbl-bl-feed-file {
     description "Add a global blacklist feed file to web-filtering";
     junos:command "test services web-filter add-global-bl-feed-file";
     input {
       leaf bl-filename {
         description "Global blacklist feed file name";
         type string;
         mandatory true;
       }
     }
     output {
       choice output_c {
         case output-tag {
           leaf output {
             type string;
           }
         }
         case multichassis-tag {
           anyxml multi-routing-engine-results;
         }
       }
     }
   }
   rpc test-services-url-filter-add-geoip-group-json {
     description "Add GeoIP Group json to web-filtering";
     junos:command "test services web-filter add-geoip-group-json-file";
     input {
       leaf filename {
         description "GeoIP Group json file name";
         type string;
         mandatory true;
       }
     }
     output {
       choice output_c {
         case output-tag {
           leaf output {
             type string;
           }
         }
         case multichassis-tag {
           anyxml multi-routing-engine-results;
         }
       }
     }
   }
   rpc get-radius-server-access-test-result {
     description "Test user access to a radius server";
     junos:command "test access radius-server";
     input {
       leaf address {
         description "RADIUS server address";
         junos:cli-feature "nokeyword";
         type jt:ipv4addr;
         mandatory true;
       }
       leaf authentication-port {
         description "RADIUS server authentication port number";
         default "1812";
         type union {
           type string {
             pattern "<.*>|$.*";
           }
           type uint16 {
             range "1 .. 65535";
           }
         }
       }
       leaf secret {
         description "Shared secret with the RADIUS server";
         type string;
         mandatory true;
       }
       leaf user {
         description "User name to be authenticated to the RADIUS server";
         type string;
         mandatory true;
       }
       leaf password {
         description "Password for the user";
         type string;
         mandatory true;
       }
       leaf timeout {
         description "Request timeout period";
         default "3";
         units "seconds";
         type union {
           type string {
             pattern "<.*>|$.*";
           }
           type uint32 {
             range "1 .. 90";
           }
         }
       }
       leaf retry {
         description "Retry attempts";
         default "3";
         type union {
           type string {
             pattern "<.*>|$.*";
           }
           type uint32 {
             range "1 .. 10";
           }
         }
       }
       leaf source-address {
         description "Use specified address as source address";
         type jt:ipv4addr;
       }
     }
   }
   rpc get-radius-profile-access-test-result {
     description "Test user access to an access profile";
     junos:command "test access profile";
     input {
       leaf profile-name {
         description "Access profile name";
         junos:cli-feature "nokeyword";
         type string;
         mandatory true;
       }
       leaf user {
         description "User name to be authenticated to the RADIUS server";
         type string;
         mandatory true;
       }
       leaf password {
         description "Password for the user";
         type string;
         mandatory true;
       }
       leaf get-radius-profile-access-test-detail-result {
         description "Show radius attributes returned by the server";
         type empty;
       }
     }
     output {
       container radius-profile-access-test-result {
         uses radius-profile-access-test-result-block;
       }
     }
   }
   grouping command-forwarding {
     choice chassis-selector {
       case case_1 {
         leaf all-chassis {
           description "All chassis";
           type empty;
         }
       }
       case case_2 {
         leaf all-lcc {
           description "All LCC chassis";
           type empty;
         }
       }
       case case_3 {
         leaf scc {
           description "SCC";
           type empty;
         }
       }
       case case_4 {
         leaf sfc {
           description "SFC";
           type union {
             type string {
               pattern "<.*>|$.*";
             }
             type uint32;
           }
         }
       }
       case case_5 {
         leaf lcc {
           description "Specific LCC";
           type union {
             type string {
               pattern "<.*>|$.*";
             }
             type uint32;
           }
         }
       }
       case case_6 {
         leaf node {
           description "Specific node";
           type string;
         }
       }
       case case_7 {
         leaf bsys {
           description "Base system";
           type empty;
         }
       }
       case case_8 {
         leaf gnf {
           description "Specific guest network function";
           type union {
             type string {
               pattern "<.*>|$.*";
             }
             type uint32 {
               range "1 .. 10";
             }
           }
         }
       }
       case case_9 {
         leaf all-gnfs {
           description "All guest network functions";
           type empty;
         }
       }
       case case_10 {
         leaf all-system {
           description "All system (BSYS and GNFs)";
           type empty;
         }
       }
       case case_11 {
         leaf server {
           description "Specific server slot";
           type union {
             type string {
               pattern "<.*>|$.*";
             }
             type uint32 {
               range "0 .. 1";
             }
           }
         }
       }
       case case_12 {
         leaf all-servers {
           description "All servers";
           type empty;
         }
       }
       case case_13 {
         leaf vnf {
           description "Specific virtual-network-function";
           type string;
         }
       }
       case case_14 {
         leaf all-vnfs {
           description "All virtual-network-functions";
           type empty;
         }
       }
     }
     choice re-selector {
       case case_1 {
         leaf re0 {
           description "RE0";
           type empty;
         }
       }
       case case_2 {
         leaf re1 {
           description "RE1";
           type empty;
         }
       }
       case case_3 {
         leaf routing-engine {
           description "Specific routing engine";
           type enumeration {
             enum "local" {
               description "Local routing engine";
             }
             enum "other" {
               description "Other routing engine";
             }
             enum "master" {
               description "Master routing engine";
             }
             enum "backup" {
               description "Backup routing engine";
             }
             enum "both" {
               description "Both routing engines";
             }
           }
         }
       }
     }
     choice lr-selector {
       case case_1 {
         leaf logical-system {
           description "Name of logical system, or 'all'";
           type string;
         }
       }
     }
     choice tenant-selector {
       case case_1 {
         leaf tenant {
           description "Name of tenant, or 'all'";
           type string;
         }
       }
     }
     choice vc-selector {
       case case_1 {
         leaf local {
           description "Local virtual chassis member";
           type empty;
         }
       }
       case case_2 {
         leaf all-members {
           description "All virtual chassis members";
           type empty;
         }
       }
       case case_3 {
         leaf member {
           description "Specific virtual chassis member which is master";
           type union {
             type string {
               pattern "<.*>|$.*";
             }
             type uint32;
           }
         }
       }
     }
   }
   grouping aaa-test-result-block {
     leaf aaa-test-status {
       type string;
       description "Server status";
     }
     leaf terminate-attribute-name {
       type string;
       description "Client termination attribute name";
     }
     leaf terminate-attribute-value {
       type string;
       description "Client termination attribute value";
     }
     container radius-server-data {
       leaf radius-server-attribute-name {
         type string;
         description "Access radius attribute name";
       }
       leaf radius-server-attribute-value {
         type string;
         description "Access radius attribute value";
       }
     }
   }
   grouping ocs-sftp-backup-test-result-block {
     leaf-list ocs-sftp-backup-log-line {
       type string;
       description "Ocs sftp-backup log line";
     }
     leaf ocs-sftp-backup-test-status {
       type string;
       description "Ocs sftp-backup test status";
     }
   }
   grouping anti-spam-test-block {
     leaf anti-spam-test-result {
       type string;
       description "Test result string";
     }
     leaf anti-spam-name-server {
       type string;
       description "Name server string";
     }
     container anti-spam-test-output {
       leaf anti-spam-name-server {
         type string;
         description "Name server string";
       }
       leaf anti-spam-test-result {
         type string;
         description "Test result string";
       }
     }
   }
   grouping web-filtering-test-block {
     leaf web-filtering-test-status {
       type string;
       description "Test result string";
     }
     leaf wf-execute-action {
       type string;
       description "Test result execute action";
     }
     leaf match-category {
       type string;
       description "Test result match category";
     }
     container web-filtering-test-result {
       container web-filtering-test-full {
         leaf web-filtering-test-status {
           type string;
           description "Test result string";
         }
         leaf wf-execute-action {
           type string;
           description "Test result execute action";
         }
         leaf match-category {
           type string;
           description "Test result match category";
         }
       }
       container web-filtering-test-brief {
         leaf web-filtering-test-status {
           type string;
           description "Test result string";
         }
       }
     }
   }
   grouping enhanced-web-filtering-test-block {
     leaf enhanced-web-filtering-test-result {
       type string;
       description "Test result string";
     }
     leaf ewf-server-name {
       type string;
       description "EWF server name";
     }
     leaf wf-type {
       type string;
       description "WF type";
     }
     leaf ewf-category-name {
       type string;
       description "EWF category name";
     }
     leaf ewf-reputation {
       type uint32;
       description "EWF reputation value";
     }
     leaf ewf-reputation-level {
       type string;
       description "EWF reputation level";
     }
     container ewf-test-full {
       leaf ewf-server-name {
         type string;
         description "EWF server name";
       }
       leaf wf-type {
         type string;
         description "WF type";
       }
       leaf ewf-category-name {
         type string;
         description "EWF category name";
       }
       leaf ewf-reputation {
         type uint32;
         description "EWF reputation value";
       }
       leaf ewf-reputation-level {
         type string;
         description "EWF reputation level";
       }
     }
     container ewf-test-brief {
       leaf ewf-server-name {
         type string;
         description "EWF server name";
       }
       leaf enhanced-web-filtering-test-result {
         type string;
         description "Test result string";
       }
     }
   }
   grouping route-information-block {
     container ipv4-route-list {
       description "State of IPv4 route table";
       leaf-list ipv4-route-entry {
         type string;
       }
     }
     container ipv6-route-list {
       description "State of IPv6 route table";
       leaf-list ipv6-route-entry {
         type string;
       }
     }
     leaf as-number {
       type int32;
     }
     leaf router-id {
       type jt:ipaddr;
     }
     leaf maximum-ecmp {
       type int32;
     }
     leaf note-network-services-mode {
       type string;
     }
     list route-table {
       leaf table-name {
         type string;
         description "Unicast routing table";
       }
       leaf destination-count {
         type int32;
         description "Number of destinations in this rib";
       }
       leaf total-route-count {
         type int32;
       }
       leaf active-route-count {
         type int32;
         description "Active routes";
       }
       leaf holddown-route-count {
         type int32;
       }
       leaf hidden-route-count {
         type int32;
       }
       leaf restart-state {
         type string;
       }
       leaf prefix-max {
         type int32;
       }
       leaf prefix-threshold {
         type int32;
       }
       leaf prefix-label {
         type string;
       }
       leaf route-max {
         type int32;
       }
       leaf route-threshold {
         type int32;
       }
       leaf route-limit-label {
         type string;
       }
       list protocols {
         leaf protocol-name {
           type string;
         }
         leaf protocol-route-count {
           type int32;
           description "Total protocol routes";
         }
         leaf active-route-count {
           type int32;
           description "Active routes";
         }
       }
       container rib-origin-validation-statistics {
         description "RIB specific origin validation state information";
         leaf valid-routes {
           type uint32;
           description "Validation state Valid routes";
         }
         leaf invalid-origin-as-routes {
           type uint32;
           description "Routes invalid due to Origin-AS";
         }
         leaf invalid-max-length-routes {
           type uint32;
           description "Routes invalid due to Max-Length";
         }
         leaf unknown-routes {
           type uint32;
           description "Validation state Unknown routes";
         }
       }
       list rt {
         leaf rt-destination {
           type string;
           description "Route prefixes awaiting ACK";
         }
         leaf rt-prefix-length {
           type string;
         }
         list rt-entry {
           leaf active-tag {
             type string;
             description "Visual indication of active state of this route entry";
           }
           leaf validation-state {
             type string;
             description "Validation-state of a route";
           }
           leaf protocol-name {
             type string;
           }
           leaf preference {
             type int32;
             description "Preference for the route";
           }
           leaf metric {
             type int32;
           }
           leaf metric2 {
             type int32;
           }
           leaf nh-type {
             type string;
             description "Special next hop: Reject, Blackhole, Receive, Multicast, Local, or Unused";
           }
           leaf as-path {
             type string;
             description "Name of AS path regular expression (BGP only)";
           }
           leaf last-active {
             type empty;
             description "This route entry was the last active route entry";
           }
           leaf current-active {
             type empty;
             description "This route entry is currently active";
           }
           leaf bgp-rt-mult-nh-idx {
             type uint32;
             description "BGP multipath nexthop index";
           }
           leaf deleted {
             type empty;
           }
           leaf nh-erc-btid-id {
             type string;
             description "ERC Backtrace ID";
           }
           leaf nh-erc-btid-op {
             type string;
             description "ERC BTID Operation";
           }
           leaf nh-erc-btid-nreference {
             type int32;
             description "ERC Number of BTID References";
           }
           leaf nh-erc-btid-bt {
             type string;
             description "ERC BTID Backtrace ";
           }
           list route-record {
             leaf rt-recorded {
               type string;
             }
             leaf nh-address {
               type string;
               description "Address of next hop";
             }
             leaf as-index {
               type int32;
             }
             leaf as-recorded {
               type string;
             }
             leaf com-index {
               type int32;
             }
             leaf com-recorded {
               type string;
             }
           }
           list route-data-dcf {
             leaf trunk-id {
               type int32;
               description "Trunk Identifier associated with the LAG port";
             }
             leaf snmp-idx {
               type int32;
               description "IFD SNMP index";
             }
             leaf ts {
               type int32;
               description "Timestamp associated with the route";
             }
             leaf class-id {
               type int32;
               description "Class identifier associated with the route";
             }
             leaf rt-flags {
               type string;
               description "Flags associated with the route";
             }
             leaf rt-type {
               type string;
               description "Route type associated with the route";
             }
             leaf rt-proto {
               type string;
               description "Protocol associated with the route";
             }
             leaf rt-l2domain {
               type int32;
               description "L2domain associated with the route";
             }
             leaf rt-mac-addr {
               type jt:mac-addr;
               description "Mac address associated with the route";
             }
             list snpa {
               leaf snpa-type {
                 type string;
                 description "Type of SNPA";
               }
               list pfe-port-snpa {
                 leaf pfe-id {
                   type int32;
                 }
                 leaf port-id {
                   type int32;
                 }
               }
               list network-element-port-snpa {
                 leaf port-id {
                   type int32;
                 }
               }
               list mstp-root-snpa {
                 leaf mstp-root-id {
                   type int32;
                 }
               }
               list gateway-snpa {
                 leaf gateway-addr {
                   type jt:ipaddr;
                 }
               }
               list layer2-domain-port-snpa {
                 leaf port-id {
                   type int32;
                 }
               }
               list replication-block-snpa {
                 leaf replication-block-id {
                   type int32;
                 }
               }
               list replication-route-snpa {
                 leaf network-element-id {
                   type jt:ipaddr;
                 }
               }
               list layer2-multicast-port-snpa {
                 leaf layer2-multicast-port-id {
                   type int32;
                 }
               }
               list inh-snpa {
                 leaf inh-id {
                   type int32;
                 }
               }
             }
             leaf snpa-count {
               type int32;
               description "Number of SNPAs in this route";
             }
             leaf snpa-length {
               type int32;
               description "Total length of the SNPAs, in bytes";
             }
             container multicast-member-map-data {
               leaf multicast-root-hash {
                 type int32;
               }
               leaf multicast-core-hash {
                 type int32;
               }
               leaf multicast-edge-hash {
                 type int32;
               }
               leaf multicast-member-map {
                 type string;
               }
             }
             container layer3-multicast-data {
               leaf layer3-multicast-corekey {
                 type int32;
               }
             }
             container multicast-vsg-corekey-data {
               leaf multicast-vsg-corekey-key {
                 type int32;
               }
               leaf multicast-vsg-corekey-len {
                 type int32;
               }
             }
           }
           container rtd-flow-dep {
             leaf flow-dep-state {
               type string;
             }
             leaf flow-origin {
               type jt:ipaddr;
               description "Originator of the flow information";
             }
             leaf flow-next-as {
               type uint32;
               description "Neighbor AS of the flow information";
             }
             container flow-ucast-rt {
               leaf flow-rtn-dest {
                 type jt:ipaddr;
                 description "Destination address";
               }
               leaf flow-rtn-plen {
                 type int32;
                 description "Prefix length";
               }
               leaf flow-rtn-state {
                 type string;
                 description "Validation entry state";
               }
             }
           }
           container bgp-path-attributes {
             container attr-as-path {
               leaf attr-length {
                 type string;
               }
               leaf flags {
                 type string;
                 description "Enabled trace flags";
               }
               leaf path-length {
                 type string;
               }
               leaf attr-value {
                 type string;
               }
             }
             container attr-as4-path {
               leaf attr-length {
                 type string;
               }
               leaf path-length {
                 type string;
               }
               leaf flags {
                 type string;
                 description "Enabled trace flags";
               }
               leaf attr-value {
                 type string;
               }
             }
             container attr-as-path-effective {
               leaf attr-length {
                 type string;
               }
               leaf aspath-effective-string {
                 type string;
               }
               leaf path-length {
                 type string;
               }
               leaf attr-value {
                 type string;
               }
               leaf flags {
                 type string;
                 description "Enabled trace flags";
               }
             }
             container attr-aggregator {
               leaf attr-length {
                 type string;
               }
               leaf flags {
                 type string;
                 description "Enabled trace flags";
               }
               leaf aggr-as-number {
                 type string;
               }
               leaf aggr-router-id {
                 type string;
               }
             }
             container attr-aggregator4 {
               leaf attr-length {
                 type string;
               }
               leaf flags {
                 type string;
                 description "Enabled trace flags";
               }
               leaf aggr-as-number {
                 type string;
               }
               leaf aggr-router-id {
                 type string;
               }
             }
             container attr-cluster-list {
               leaf attr-length {
                 type string;
               }
               leaf attr-value {
                 type string;
               }
             }
             container attr-originator-id {
               leaf attr-length {
                 type string;
               }
               leaf attr-value {
                 type string;
               }
             }
             leaf domain-path {
               type string;
             }
             container attr-unrecognized {
               leaf attr-length {
                 type string;
               }
               leaf attr-flags {
                 type string;
               }
               leaf attr-code {
                 type string;
               }
               leaf attr-value {
                 type string;
               }
             }
           }
           container communities {
             leaf-list community {
               type string;
               description "Basic community";
             }
             leaf-list extended-community {
               type string;
               description "Extended community";
             }
             leaf-list ipv6-extended-community {
               type string;
               description "IPv6 extended community";
             }
           }
           list bgp-tunnel-attribute {
             leaf tunnel-attribute-type {
               type string;
             }
             leaf tunnel-attribute-rpf {
               type empty;
             }
             leaf tunnel-attribute-color {
               type uint32;
             }
             leaf tunnel-attribute-destination {
               type jt:ipaddr;
             }
           }
           container attrset {
             container bgp-prefix-sid-attr {
               container bgp-prefix-sid-attr-label-idx-tlv {
                 leaf bgp-prefix-sid-label-idx-index {
                   type int32;
                 }
                 leaf bgp-prefix-sid-attr-status {
                   type string;
                 }
               }
               container bgp-prefix-sid-attr-srgb-tlv {
                 list bgp-prefix-sid-srgb-block {
                   leaf bgp-prefix-sid-srgb-block-start-label {
                     type int32;
                   }
                   leaf bgp-prefix-sid-srgb-block-range {
                     type int32;
                   }
                 }
               }
               container bgp-prefix-sid-attr-service-tlv {
                 leaf bgp-prefix-sid-srv6-sid-value {
                   type jt:ipaddr;
                 }
                 leaf bgp-prefix-sid-attr-service-tlv-type {
                   type uint32;
                 }
                 leaf bgp-prefix-sid-srv6-sid-bh {
                   type uint32;
                 }
                 leaf bgp-prefix-sid-srv6-sid-bl {
                   type uint32;
                 }
                 leaf bgp-prefix-sid-srv6-sid-nl {
                   type uint32;
                 }
                 leaf bgp-prefix-sid-srv6-sid-fl {
                   type uint32;
                 }
                 leaf bgp-prefix-sid-srv6-sid-al {
                   type uint32;
                 }
                 leaf bgp-prefix-sid-srv6-sid-tl {
                   type uint32;
                 }
                 leaf bgp-prefix-sid-srv6-sid-to {
                   type uint32;
                 }
               }
               container bgp-prefix-sid-attr-unknown-tlvs {
                 list bgp-prefix-sid-attr-unknown-tlv {
                   leaf bgp-prefix-sid-unknown-tlv-type {
                     type uint32;
                   }
                   leaf bgp-prefix-sid-unknown-tlv-len {
                     type uint32;
                   }
                 }
               }
             }
             leaf attrset-as {
               type int32;
               description "Originator AS";
             }
             leaf med {
               type int32;
               description "Multiple exit discriminator";
             }
             leaf local-preference {
               type int32;
             }
             leaf as-path {
               type string;
               description "Name of AS path regular expression (BGP only)";
             }
             leaf pmsi {
               type string;
               description "P-multicast service interface";
             }
             leaf cluster-id {
               type string;
             }
             leaf originator {
               type string;
             }
             leaf connector {
               type string;
             }
             container communities {
               leaf-list community {
                 type string;
                 description "Basic community";
               }
               leaf-list extended-community {
                 type string;
                 description "Extended community";
               }
               leaf-list ipv6-extended-community {
                 type string;
                 description "IPv6 extended community";
               }
             }
             list bgp-tunnel-attribute {
               leaf tunnel-attribute-type {
                 type string;
               }
               leaf tunnel-attribute-rpf {
                 type empty;
               }
               leaf tunnel-attribute-color {
                 type uint32;
               }
               leaf tunnel-attribute-destination {
                 type jt:ipaddr;
               }
             }
           }
           container link-state-information {
             container link-state-link {
               leaf link-name {
                 type string;
               }
               leaf color {
                 type int32;
               }
               leaf metric {
                 type int32;
               }
               leaf te-metric {
                 type int32;
                 description "LSP TE metric";
               }
               leaf link-avg-delay {
                 type uint32;
               }
               leaf link-min-delay {
                 type uint32;
               }
               leaf link-max-delay {
                 type uint32;
               }
               leaf link-avg-delay-var {
                 type uint32;
               }
               leaf ldp-support {
                 type string;
               }
               leaf rsvpte-support {
                 type string;
               }
               leaf maximum-bw {
                 type uint64;
               }
               leaf reservable-bw {
                 type uint64;
               }
               container protections {
                 leaf-list protection-type {
                   type string;
                   description "LSP protection desired";
                 }
               }
               container link-srlgs {
                 leaf-list link-srlg {
                   type string;
                 }
               }
               container unreserved-bws {
                 list unreserved-bw {
                   leaf unreserved-bw-priority {
                     type uint32;
                   }
                   leaf unreserved-bw-value {
                     type string;
                   }
                 }
               }
               container link-state-link-opaque-attrs {
                 leaf link-state-link-opaque-attrs-length {
                   type uint32;
                 }
                 leaf link-state-link-opaque-attrs-bytes {
                   type string;
                 }
               }
               container link-adj-sids {
                 list link-lan-adj-sid {
                   leaf link-lan-adj-sid-af {
                     type string;
                   }
                   leaf link-lan-adj-sid-label {
                     type uint32;
                   }
                   leaf link-lan-adj-sid-flags {
                     type string;
                   }
                   leaf link-lan-adj-sid-weight {
                     type uint32;
                   }
                   leaf link-lan-adj-sid-neighbor {
                     type string;
                   }
                 }
                 list link-p2p-adj-sid {
                   leaf link-p2p-adj-sid-af {
                     type string;
                   }
                   leaf link-p2p-adj-sid-label {
                     type uint32;
                   }
                   leaf link-p2p-adj-sid-flags {
                     type string;
                   }
                   leaf link-p2p-adj-sid-weight {
                     type uint32;
                   }
                 }
               }
               container link-bgp-peer-sids {
                 list link-bgp-peer-sid {
                   leaf link-bgp-peer-sid-label {
                     type uint32;
                   }
                   leaf link-bgp-peer-sid-flags {
                     type string;
                   }
                   leaf link-bgp-peer-sid-weight {
                     type uint32;
                   }
                 }
               }
               container link-srv6-end-x-sids {
                 list link-srv6-end-x-sid {
                   leaf link-srv6-end-x-sid-type {
                     type string;
                   }
                   leaf link-srv6-end-x-sid-val {
                     type jt:ipv6addr;
                   }
                   leaf link-srv6-end-x-sid-flags {
                     type string;
                   }
                   leaf link-srv6-end-x-sid-weight {
                     type int32;
                   }
                   leaf link-srv6-end-x-sid-algo {
                     type int32;
                   }
                   leaf link-srv6-end-x-sid-func {
                     type string;
                   }
                   leaf link-srv6-end-x-sid-lan-neighbor-id {
                     type string;
                   }
                   container link-srv6-end-x-sid-sstlv {
                     leaf link-srv6-end-x-sid-sstlv-header {
                       type empty;
                     }
                     leaf link-srv6-end-x-sid-sstlv-blen {
                       type uint32;
                     }
                     leaf link-srv6-end-x-sid-sstlv-nlen {
                       type uint32;
                     }
                     leaf link-srv6-end-x-sid-sstlv-flen {
                       type uint32;
                     }
                     leaf link-srv6-end-x-sid-sstlv-alen {
                       type uint32;
                     }
                   }
                 }
               }
               container link-msd-types {
                 list link-msd-entry {
                   leaf link-msd-type {
                     type uint32;
                   }
                   leaf link-msd-value {
                     type uint32;
                   }
                 }
               }
             }
             container link-state-node {
               leaf node-name {
                 type string;
               }
               leaf area-border-router {
                 type string;
               }
               leaf external-router {
                 type string;
               }
               leaf attached {
                 type string;
               }
               leaf overload {
                 type string;
               }
               container node-areas {
                 leaf-list node-area {
                   type string;
                 }
               }
               container node-ipv4-router-ids {
                 leaf-list node-ipv4-router-id {
                   type jt:ipaddr;
                 }
               }
               container node-ipv6-router-ids {
                 leaf-list node-ipv6-router-id {
                   type jt:ipaddr;
                 }
               }
               container node-topologies {
                 list node-topology {
                   leaf id {
                     type uint32;
                   }
                 }
               }
               container link-state-node-opaque-attrs {
                 leaf link-state-node-opaque-attrs-length {
                   type uint32;
                 }
                 leaf link-state-node-opaque-attrs-bytes {
                   type string;
                 }
               }
               container node-spring-capability {
                 list node-spring-srgb-block {
                   leaf node-spring-srgb-block-start {
                     type uint32;
                   }
                   leaf node-spring-srgb-block-range {
                     type uint32;
                   }
                   leaf node-spring-srgb-block-flags {
                     type string;
                   }
                 }
               }
               container node-msd-types {
                 list node-msd-entry {
                   leaf node-msd-type {
                     type uint32;
                   }
                   leaf node-msd-value {
                     type uint32;
                   }
                 }
               }
               container node-srv6-capability {
                 leaf node-srv6-capability-flag {
                   type uint32;
                 }
               }
               container node-spring-algorithms {
                 list node-spring-algorithm {
                   leaf node-spring-algorithm-type {
                     type uint32;
                   }
                 }
               }
               container node-spring-falgo-defs {
                 list node-spring-falgo-def {
                   leaf node-spring-falgo-def-algo {
                     type uint32;
                   }
                   leaf node-spring-falgo-def-metric-type {
                     type uint32;
                   }
                   leaf node-spring-falgo-def-calculation-type {
                     type uint32;
                   }
                   leaf node-spring-falgo-def-priority {
                     type uint32;
                   }
                   leaf node-spring-falgo-def-flags {
                     type string;
                   }
                   leaf node-spring-falgo-def-include-any {
                     type string;
                   }
                   leaf node-spring-falgo-def-exclude {
                     type string;
                   }
                   leaf node-spring-falgo-def-include-all {
                     type string;
                   }
                 }
               }
             }
             list link-state-te-policy-cp-segment {
             }
             list link-state-te-policy-cp-segment-list {
               list link-state-te-policy-cp-segment {
                 leaf link-state-te-policy-cp-mpls-segment-id {
                   type uint32;
                 }
                 leaf link-state-te-policy-cp-srv6-segment-id {
                   type jt:ipv6addr;
                 }
                 leaf link-state-te-policy-cp-segment-descriptor {
                   type jt:ipaddr;
                 }
                 leaf link-state-te-policy-cp-segment-flags {
                   type string;
                 }
                 leaf link-state-te-policy-cp-segment-ep-bhv {
                   type string;
                 }
                 leaf link-state-te-policy-cp-segment-ep-bhv-flags {
                   type uint32;
                 }
                 leaf link-state-te-policy-cp-segment-ep-bhv-algo {
                   type uint32;
                 }
                 container link-state-te-policy-cp-segment-sstlv {
                   leaf link-state-te-policy-cp-segment-sstlv-header {
                     type empty;
                   }
                   leaf link-state-te-policy-cp-segment-sstlv-blen {
                     type uint32;
                   }
                   leaf link-state-te-policy-cp-segment-sstlv-nlen {
                     type uint32;
                   }
                   leaf link-state-te-policy-cp-segment-sstlv-flen {
                     type uint32;
                   }
                   leaf link-state-te-policy-cp-segment-sstlv-alen {
                     type uint32;
                   }
                 }
               }
             }
             container link-state-te-policy-cp {
               leaf link-state-te-policy-cp-name {
                 type string;
               }
               leaf link-state-te-policy-cp-flags {
                 type string;
               }
               leaf link-state-te-policy-cp-preference {
                 type uint32;
               }
               leaf link-state-te-policy-cp-priority {
                 type uint32;
               }
               leaf link-state-te-policy-cp-constraint-header {
                 type empty;
               }
               leaf link-state-te-policy-cp-constraint-flags {
                 type string;
               }
               leaf link-state-te-policy-cp-mtid {
                 type uint32;
               }
               leaf link-state-te-policy-cp-algo {
                 type uint32;
               }
               leaf link-state-te-policy-cp-exclude-any {
                 type string;
               }
               leaf link-state-te-policy-cp-include-any {
                 type string;
               }
               leaf link-state-te-policy-cp-include-all {
                 type string;
               }
               leaf link-state-te-policy-cp-bandwidth {
                 type uint32;
               }
               leaf link-state-te-policy-cp-bsid-flags {
                 type string;
               }
               leaf link-state-te-policy-cp-mpls-bsid {
                 type uint32;
               }
               leaf link-state-te-policy-cp-mpls-spec-bsid {
                 type uint32;
               }
               leaf link-state-te-policy-cp-srv6-bsid {
                 type jt:ipv6addr;
               }
               leaf link-state-te-policy-cp-srv6-spec-bsid {
                 type jt:ipv6addr;
               }
               leaf link-state-te-policy-cp-segment-list-count {
                 type int32;
               }
               list link-state-te-policy-cp-segment-list {
                 leaf link-state-te-policy-cp-segment-list-index {
                   type int32;
                 }
                 leaf link-state-te-policy-cp-segment-list-flags {
                   type string;
                 }
                 leaf link-state-te-policy-cp-segment-list-mtid {
                   type uint32;
                 }
                 leaf link-state-te-policy-cp-segment-list-weight {
                   type uint32;
                 }
                 leaf link-state-te-policy-cp-segment-list-algo {
                   type uint32;
                 }
                 leaf link-state-te-policy-cp-segment-list-metric-type {
                   type string;
                 }
                 leaf link-state-te-policy-cp-segment-list-metric-value {
                   type uint32;
                 }
                 leaf link-state-te-policy-cp-segment-count {
                   type int32;
                 }
                 leaf link-state-te-policy-cp-segment-header {
                   type empty;
                 }
                 list link-state-te-policy-cp-segment {
                   leaf link-state-te-policy-cp-mpls-segment-id {
                     type uint32;
                   }
                   leaf link-state-te-policy-cp-srv6-segment-id {
                     type jt:ipv6addr;
                   }
                   leaf link-state-te-policy-cp-segment-descriptor {
                     type jt:ipaddr;
                   }
                   leaf link-state-te-policy-cp-segment-flags {
                     type string;
                   }
                   leaf link-state-te-policy-cp-segment-ep-bhv {
                     type string;
                   }
                   leaf link-state-te-policy-cp-segment-ep-bhv-flags {
                     type uint32;
                   }
                   leaf link-state-te-policy-cp-segment-ep-bhv-algo {
                     type uint32;
                   }
                   container link-state-te-policy-cp-segment-sstlv {
                     leaf link-state-te-policy-cp-segment-sstlv-header {
                       type empty;
                     }
                     leaf link-state-te-policy-cp-segment-sstlv-blen {
                       type uint32;
                     }
                     leaf link-state-te-policy-cp-segment-sstlv-nlen {
                       type uint32;
                     }
                     leaf link-state-te-policy-cp-segment-sstlv-flen {
                       type uint32;
                     }
                     leaf link-state-te-policy-cp-segment-sstlv-alen {
                       type uint32;
                     }
                   }
                 }
               }
             }
             container link-state-prefix {
               leaf link-state-prefix-attr-flags {
                 type string;
               }
               leaf link-state-prefix-metric {
                 type uint32;
               }
               list link-state-prefix-sid {
                 leaf link-state-prefix-sid-index {
                   type uint32;
                 }
                 leaf link-state-prefix-sid-flags {
                   type string;
                 }
                 leaf link-state-prefix-sid-algo {
                   type string;
                 }
               }
               container link-state-prefix-srv6-locator {
                 leaf link-state-prefix-srv6-locator-flags {
                   type string;
                 }
                 leaf link-state-prefix-srv6-locator-algo {
                   type string;
                 }
                 leaf link-state-prefix-srv6-locator-metric {
                   type string;
                 }
               }
               list link-state-prefix-fapm {
                 leaf link-state-prefix-fapm-algo {
                   type uint32;
                 }
                 leaf link-state-prefix-fapm-metric {
                   type uint32;
                 }
               }
             }
             container link-state-srv6-endsid {
               container link-state-srv6-endsid-info {
                 leaf link-state-srv6-endsid-epb {
                   type string;
                 }
                 leaf link-state-srv6-endsid-flags {
                   type string;
                 }
                 leaf link-state-srv6-endsid-algo {
                   type string;
                 }
                 container link-state-srv6-endsid-sstlv {
                   leaf link-state-srv6-endsid-sstlv-header {
                     type empty;
                   }
                   leaf link-state-srv6-endsid-sstlv-blen {
                     type uint32;
                   }
                   leaf link-state-srv6-endsid-sstlv-nlen {
                     type uint32;
                   }
                   leaf link-state-srv6-endsid-sstlv-flen {
                     type uint32;
                   }
                   leaf link-state-srv6-endsid-sstlv-alen {
                     type uint32;
                   }
                 }
               }
             }
             container link-state-unknown-tlvs {
               list link-state-unknown-tlv {
                 leaf unknown-type {
                   type uint32;
                 }
                 leaf unknown-length {
                   type uint32;
                 }
                 leaf unknown-bytes {
                   type string;
                 }
               }
             }
           }
           container aggregate {
             container aggregate-as-path {
               container bgp-path-attributes {
                 container attr-as-path {
                   leaf attr-length {
                     type string;
                   }
                   leaf flags {
                     type string;
                     description "Enabled trace flags";
                   }
                 }
                 container attr-as4-path {
                   leaf attr-length {
                     type string;
                   }
                 }
                 container attr-as-path-effective {
                   leaf attr-length {
                     type string;
                   }
                 }
                 container attr-aggregator {
                   leaf attr-length {
                     type string;
                   }
                 }
                 container attr-aggregator4 {
                   leaf attr-length {
                     type string;
                   }
                 }
                 container attr-cluster-list {
                   leaf attr-length {
                     type string;
                   }
                 }
                 container attr-originator-id {
                   leaf attr-length {
                     type string;
                   }
                 }
               }
               leaf as-path {
                 type string;
                 description "Name of AS path regular expression (BGP only)";
               }
               leaf reference-count {
                 type int32;
                 description "Reference count";
               }
             }
             leaf aggregate-flags {
               type string;
               description "Flags on this aggregate route entry";
             }
             leaf aggregate-depth {
               type int32;
               description "Depth of this aggregate";
             }
             leaf aggregate-active {
               type empty;
               description "Present if this aggregate is active";
             }
             leaf aggregate-algo {
               type uint32;
               description "Algorithm number";
             }
             leaf contributing-route-count {
               type int32;
               description "Number of contributing routes in this aggregate";
             }
             list aggregated-route {
               leaf destination-prefix {
                 type string;
                 description "Destination prefix and mask";
               }
               leaf protocol-name {
                 type string;
               }
             }
           }
           list kern-nhexpand {
             container srv6-info {
               leaf srv6-info-srh-sid-mode {
                 type string;
                 description "Reduced/non-reduced mode for SRH";
               }
               leaf srv6-info-packet-mode {
                 type string;
                 description "Packet mode for SRV6-Tunnel";
               }
               leaf srv6-info-srh-last-sid {
                 type string;
                 description "Remove last sid for ACX";
               }
               leaf srv6-info-dyn-tunnel {
                 type string;
                 description "SRv6 tunnel created dynamically";
               }
               leaf srv6-source {
                 type jt:ipaddr;
                 description "Source IPv6 address";
               }
               leaf srv6-destination {
                 type jt:ipaddr;
                 description "Destination IPv6 address";
               }
               list srv6-segment-list {
                 leaf srv6-segment-list-index {
                   type uint32;
                   description "SRH segment list index";
                 }
                 leaf srv6-segment-list-addr {
                   type jt:ipaddr;
                   description "SRH segment address";
                 }
               }
             }
           }
           list nh {
             leaf selected-next-hop {
               type empty;
               description "Present if this next hop is selected";
             }
             leaf to {
               type string;
               description "Neighbor address to which to send (next-hop address)";
             }
             leaf nh-indirect-fnh-type {
               type string;
               description "Indirect pointing to a well-known nexthop";
             }
             leaf via {
               type string;
               description "Reachable via a local interface";
             }
             container vxlan-header-rewrite {
               leaf vxlan-header-rewrite-mtu {
                 type int32;
                 description "VXLAN tunnel MTU";
               }
               leaf vxlan-header-rewrite-flags {
                 type int32;
                 description "VXLAN tunnel flags";
               }
               leaf vxlan-header-rewrite-encap-rtb-id {
                 type int32;
                 description "VXLAN tunnel encapsulation table ID";
               }
               leaf vxlan-header-rewrite-decap-rtb-id {
                 type int32;
                 description "VXLAN tunnel decapsulation table ID";
               }
               leaf vxlan-header-rewrite-encap-vnid {
                 type int32;
                 description "VXLAN tunnel encapsulation VNI";
               }
               leaf vxlan-header-rewrite-decap-vnid {
                 type int32;
                 description "VXLAN tunnel decapsulation VNI";
               }
               leaf vxlan-header-rewrite-svtep {
                 type jt:ipaddr;
                 description "Source VTEP address";
               }
               leaf vxlan-header-rewrite-dvtep {
                 type jt:ipaddr;
                 description "Destination VTEP address";
               }
               leaf vxlan-header-rewrite-smac {
                 type string;
                 description "Source MAC address";
               }
               leaf vxlan-header-rewrite-dmac {
                 type string;
                 description "Destination MAC address";
               }
             }
             container srv6-info {
               leaf srv6-info-srh-sid-mode {
                 type string;
                 description "Reduced/non-reduced mode for SRH";
               }
               leaf srv6-info-packet-mode {
                 type string;
                 description "Packet mode for SRV6-Tunnel";
               }
               leaf srv6-info-srh-last-sid {
                 type string;
                 description "Remove last sid for ACX";
               }
               leaf srv6-info-dyn-tunnel {
                 type string;
                 description "SRv6 tunnel created dynamically";
               }
               leaf srv6-source {
                 type jt:ipaddr;
                 description "Source IPv6 address";
               }
               leaf srv6-destination {
                 type jt:ipaddr;
                 description "Destination IPv6 address";
               }
               list srv6-segment-list {
                 leaf srv6-segment-list-index {
                   type uint32;
                   description "SRH segment list index";
                 }
                 leaf srv6-segment-list-addr {
                   type jt:ipaddr;
                   description "SRH segment address";
                 }
               }
             }
             leaf nh-string {
               type string;
             }
             leaf nh-table-receive {
               type string;
               description "Destination is a local address";
             }
             leaf nh-table {
               type string;
               description "Indirect pointing to another table";
             }
             leaf nh-table-localized {
               type string;
               description "Indirect pointing to a localized table";
             }
             leaf nh-localized-ifl {
               type string;
               description "Indirect pointing to a localized ifl";
             }
             leaf lsp-name {
               type string;
               description "Tunneled into an RSVP LSP";
             }
             leaf mpls-label {
               type string;
               description "Label of MPLS packet";
             }
             leaf nh-local-interface {
               type string;
               description "Destination is a local interface";
             }
             leaf nh-service {
               type string;
               description "Next-hop service";
             }
             leaf nh-private-comp {
               type string;
               description "Private Composite Next-hop";
             }
             leaf srv6-prefix-sid {
               type jt:ipaddr;
               description "SRv6 prefixe sid value";
             }
             leaf srv6-encap-brief {
               type string;
               description "IPV6 SR-header encapsulation";
             }
             leaf elnh-address {
               type int32;
               description "Address of Element Next-hop";
             }
             leaf localized-table {
               type string;
               description "Name of localized table";
             }
             leaf ae-member-interface {
               type string;
               description "AE Member interface";
             }
             leaf weight {
               type int32;
               description "Next-hop weight";
             }
             leaf balance {
               type int32;
               description "Next-hop balance";
             }
             leaf uflags {
               type int32;
               description "Next-hop uflags";
             }
             leaf filter {
               type string;
               description "Next-hop firewall filter";
             }
             leaf session {
               type int32;
               description "Session ID Associated with this NH";
             }
             leaf statistics-id-group-terse {
               type string;
               description "Statistics ID Group Associated with this NH";
             }
             leaf app-specific-opaque {
               type string;
               description "Application specific opaque data dump";
             }
             leaf gw-opaque {
               type int32;
               description "Nexthops gateway opaque data handle";
             }
             leaf statistics-pkts-count {
               type int32;
               description "Statistics packet count Associated with this NH";
             }
             leaf statistics-bytes-count {
               type int32;
               description "Statistics bytes count Associated with this NH";
             }
             leaf ext-int-type {
               type string;
               description "Next-hop type of equal-external-internal multipath";
             }
             leaf fc {
               type int32;
               description "Forwarding-class";
             }
             leaf label-ttl-action {
               type string;
               description "TTL action associated with labels";
             }
             leaf load-balance-label {
               type string;
               description "Load balance action associated with labels";
             }
             leaf label-element {
               type string;
               description "Pointer to the tag label element";
             }
             leaf label-element-parent {
               type string;
               description "Pointer to the tag label element parent";
             }
             leaf label-element-refcount {
               type string;
               description "Number of references to the tag label element";
             }
             leaf label-element-childcount {
               type string;
               description "Number of child references to the tag label element";
             }
             leaf label-element-lspid {
               type string;
               description "LSP ID of the tag label element";
             }
             leaf nh-service-pkt-dist {
               type string;
               description "Multi services packet distribution type";
             }
             leaf nh-service-app-data {
               type string;
               description "Multi services application specific data";
             }
             leaf nh-index {
               type uint32;
               description "Next-hop index";
             }
             leaf nh-address {
               type string;
               description "Address of next hop";
             }
             leaf nh-reference-count {
               type int32;
               description "Number of references to this next hop";
             }
             leaf tunnel-composite-attr-type {
               type string;
               description "Tunnel-Type for tunnel-composite-nexthop";
             }
             leaf tunnel-composite-attr-subtype {
               type string;
               description "Tunnel-Subtype for tunnel-composite-nexthop";
             }
             leaf tunnel-composite-attr-reference-count {
               type int32;
               description "Tunnel-reference-count for tunnel-composite-nexthop";
             }
             leaf tunnel-composite-attr-nh-id {
               type int32;
               description "Tunnel-NextHop-Id for tunnel-composite-nexthop";
             }
             leaf tunnel-composite-attr-dest {
               type jt:ipaddr;
               description "Tunnel-Destination for tunnel-composite-nexthop";
             }
             leaf tunnel-composite-attr-src {
               type jt:ipaddr;
               description "Tunnel-Source for tunnel-composite-nexthop";
             }
             leaf tunnel-composite-attr-tunnel-endpoint {
               type jt:ipaddr;
               description "Tunnel-Endpoint for tunnel-composite-nexthop";
             }
             leaf tunnel-composite-anchor-pfe {
               type string;
               description "Anchor PFE name, if tunnel nexthop is localized";
             }
             leaf tunnel-composite-encap-rtb-id {
               type int32;
               description "Tunnel encap routing table index";
             }
             leaf tunnel-composite-decap-rtb-id {
               type int32;
               description "Tunnel decap routing table index";
             }
             leaf tunnel-composite-attr-ttl {
               type int32;
               description "Tunnel-TTL for tunnel-composite-nexthop";
             }
             leaf tunnel-composite-attr-udp-port {
               type int32;
               description "Tunnel-UDP-Destination port for tunnel-composite-nexthop";
             }
             leaf tunnel-composite-attr-fc-id {
               type int32;
               description "Tunnel-Forwarding-Class-ID for tunnel-composite-nexthop";
             }
             leaf tunnel-composite-attr-tid {
               type int32;
               description "Tunnel-Id for tunnel-composite-nexthop";
             }
             leaf tunnel-composite-attr-label {
               type string;
               description "Tunnel-VPN-Label for tunnel-composite-nexthop";
             }
             leaf tunnel-composite-attr-label-ttl {
               type string;
               description "Tunnel-VPN-Label-TTL for tunnel-composite-nexthop";
             }
             leaf tunnel-composite-attr-gre-key {
               type int32;
               description "GRE key for tunnel-composite-nexthop";
             }
             leaf-list tunnel-composite-attr-segment-addr {
               type jt:ipaddr;
               description "IPv6 segment-address";
             }
             leaf-list tunnel-composite-attr-sid {
               type int32;
               description "IPv6 segment-sid";
             }
             leaf tunnel-composite-attr-vni {
               type int32;
               description "Tunnel-VNI for tunnel-composite-nexthop in VxLAN";
             }
             leaf tunnel-composite-attr-dest-mac {
               type string;
               description "Tunnel-Dest-Mac for tunnel-composite-nexthop in VxLAN";
             }
             leaf translate-composite-attr-type {
               type string;
               description "Translation type for translate-composite-nexthop";
             }
             leaf translate-composite-attr-flags {
               type string;
               description "Flags for translate-composite-nexthop";
             }
             leaf translate-composite-attr-reference-count {
               type int32;
               description "Reference count for translate-composite-nexthop";
             }
             leaf translate-composite-attr-nh-id {
               type int32;
               description "NextHop id for translate-composite-nexthop";
             }
             leaf translate-composite-attr-dest {
               type jt:ipaddr;
               description "Translation destination for translate-composite-nexthop";
             }
             leaf translate-composite-attr-dest-plen {
               type int32;
               description "Translation destination prefix length for translate-composite-nexthop";
             }
             leaf translate-composite-attr-src {
               type jt:ipaddr;
               description "Translation source for translate-composite-nexthop";
             }
             leaf translate-composite-attr-src-plen {
               type int32;
               description "Translation source prefix length for translate-composite-nexthop";
             }
             leaf translate-composite-attr-dest-alg-type {
               type string;
               description "Destination algorithm type for translate-composite-nexthop";
             }
             leaf translate-composite-attr-src-alg-type {
               type string;
               description "Source algorithm type for translate-composite-nexthop";
             }
             leaf translate-composite-attr-dest-vrf-id {
               type int32;
               description "Destination vrf id for translate-composite-nexthop";
             }
             leaf translate-composite-attr-src-vrf-id {
               type int32;
               description "Source vrf id for translate-composite-nexthop";
             }
             leaf translate-composite-attr-hoplimit {
               type int32;
               description "Hoplimit for translate-composite-nexthop";
             }
             leaf translate-composite-attr-traffic-class {
               type int32;
               description "Traffic class for translate-composite-nexthop";
             }
             leaf translate-composite-attr-ttl {
               type int32;
               description "Ttl for translate-composite-nexthop";
             }
             leaf translate-composite-attr-tos {
               type int32;
               description "Tos for translate-composite-nexthop";
             }
           }
           container protocol-nh {
             list nh {
               container vxlan-header-rewrite {
                 leaf vxlan-header-rewrite-mtu {
                   type int32;
                   description "VXLAN tunnel MTU";
                 }
                 leaf vxlan-header-rewrite-flags {
                   type int32;
                   description "VXLAN tunnel flags";
                 }
                 leaf vxlan-header-rewrite-encap-rtb-id {
                   type int32;
                   description "VXLAN tunnel encapsulation table ID";
                 }
                 leaf vxlan-header-rewrite-decap-rtb-id {
                   type int32;
                   description "VXLAN tunnel decapsulation table ID";
                 }
                 leaf vxlan-header-rewrite-encap-vnid {
                   type int32;
                   description "VXLAN tunnel encapsulation VNI";
                 }
                 leaf vxlan-header-rewrite-decap-vnid {
                   type int32;
                   description "VXLAN tunnel decapsulation VNI";
                 }
                 leaf vxlan-header-rewrite-svtep {
                   type jt:ipaddr;
                   description "Source VTEP address";
                 }
                 leaf vxlan-header-rewrite-dvtep {
                   type jt:ipaddr;
                   description "Destination VTEP address";
                 }
                 leaf vxlan-header-rewrite-smac {
                   type string;
                   description "Source MAC address";
                 }
                 leaf vxlan-header-rewrite-dmac {
                   type string;
                   description "Destination MAC address";
                 }
               }
               container srv6-info {
                 leaf srv6-info-srh-sid-mode {
                   type string;
                   description "Reduced/non-reduced mode for SRH";
                 }
                 leaf srv6-info-packet-mode {
                   type string;
                   description "Packet mode for SRV6-Tunnel";
                 }
                 leaf srv6-info-srh-last-sid {
                   type string;
                   description "Remove last sid for ACX";
                 }
                 leaf srv6-info-dyn-tunnel {
                   type string;
                   description "SRv6 tunnel created dynamically";
                 }
                 leaf srv6-source {
                   type jt:ipaddr;
                   description "Source IPv6 address";
                 }
                 leaf srv6-destination {
                   type jt:ipaddr;
                   description "Destination IPv6 address";
                 }
                 list srv6-segment-list {
                   leaf srv6-segment-list-index {
                     type uint32;
                     description "SRH segment list index";
                   }
                   leaf srv6-segment-list-addr {
                     type jt:ipaddr;
                     description "SRH segment address";
                   }
                 }
               }
               leaf nh-string {
                 type string;
               }
               leaf elnh-address {
                 type int32;
                 description "Address of Element Next-hop";
               }
               leaf to {
                 type string;
                 description "Neighbor address to which to send (next-hop address)";
               }
               leaf via {
                 type string;
                 description "Reachable via a local interface";
               }
               leaf localized-table {
                 type string;
                 description "Name of localized table";
               }
               leaf ae-member-interface {
                 type string;
                 description "AE Member interface";
               }
               leaf weight {
                 type int32;
                 description "Next-hop weight";
               }
               leaf balance {
                 type int32;
                 description "Next-hop balance";
               }
               leaf uflags {
                 type int32;
                 description "Next-hop uflags";
               }
               leaf filter {
                 type string;
                 description "Next-hop firewall filter";
               }
               leaf selected-next-hop {
                 type empty;
                 description "Present if this next hop is selected";
               }
               leaf session {
                 type int32;
                 description "Session ID Associated with this NH";
               }
               leaf statistics-id-group-terse {
                 type string;
                 description "Statistics ID Group Associated with this NH";
               }
               leaf app-specific-opaque {
                 type string;
                 description "Application specific opaque data dump";
               }
               leaf gw-opaque {
                 type int32;
                 description "Nexthops gateway opaque data handle";
               }
               leaf statistics-pkts-count {
                 type int32;
                 description "Statistics packet count Associated with this NH";
               }
               leaf statistics-bytes-count {
                 type int32;
                 description "Statistics bytes count Associated with this NH";
               }
               leaf ext-int-type {
                 type string;
                 description "Next-hop type of equal-external-internal multipath";
               }
               leaf fc {
                 type int32;
                 description "Forwarding-class";
               }
               leaf lsp-name {
                 type string;
                 description "Tunneled into an RSVP LSP";
               }
               leaf mpls-label {
                 type string;
                 description "Label of MPLS packet";
               }
               leaf label-ttl-action {
                 type string;
                 description "TTL action associated with labels";
               }
               leaf load-balance-label {
                 type string;
                 description "Load balance action associated with labels";
               }
               leaf label-element {
                 type string;
                 description "Pointer to the tag label element";
               }
               leaf label-element-parent {
                 type string;
                 description "Pointer to the tag label element parent";
               }
               leaf label-element-refcount {
                 type string;
                 description "Number of references to the tag label element";
               }
               leaf label-element-childcount {
                 type string;
                 description "Number of child references to the tag label element";
               }
               leaf label-element-lspid {
                 type string;
                 description "LSP ID of the tag label element";
               }
               leaf nh-table-receive {
                 type string;
                 description "Destination is a local address";
               }
               leaf nh-table {
                 type string;
                 description "Indirect pointing to another table";
               }
               leaf nh-localized-ifl {
                 type string;
                 description "Indirect pointing to a localized ifl";
               }
               leaf nh-local-interface {
                 type string;
                 description "Destination is a local interface";
               }
               leaf nh-service {
                 type string;
                 description "Next-hop service";
               }
               leaf nh-service-pkt-dist {
                 type string;
                 description "Multi services packet distribution type";
               }
               leaf nh-service-app-data {
                 type string;
                 description "Multi services application specific data";
               }
               leaf nh-private-comp {
                 type string;
                 description "Private Composite Next-hop";
               }
               leaf nh-index {
                 type uint32;
                 description "Next-hop index";
               }
               leaf nh-address {
                 type string;
                 description "Address of next hop";
               }
               leaf nh-reference-count {
                 type int32;
                 description "Number of references to this next hop";
               }
               leaf tunnel-composite-attr-type {
                 type string;
                 description "Tunnel-Type for tunnel-composite-nexthop";
               }
               leaf tunnel-composite-attr-subtype {
                 type string;
                 description "Tunnel-Subtype for tunnel-composite-nexthop";
               }
               leaf tunnel-composite-attr-reference-count {
                 type int32;
                 description "Tunnel-reference-count for tunnel-composite-nexthop";
               }
               leaf tunnel-composite-attr-nh-id {
                 type int32;
                 description "Tunnel-NextHop-Id for tunnel-composite-nexthop";
               }
               leaf tunnel-composite-attr-dest {
                 type jt:ipaddr;
                 description "Tunnel-Destination for tunnel-composite-nexthop";
               }
               leaf tunnel-composite-attr-src {
                 type jt:ipaddr;
                 description "Tunnel-Source for tunnel-composite-nexthop";
               }
               leaf tunnel-composite-attr-tunnel-endpoint {
                 type jt:ipaddr;
                 description "Tunnel-Endpoint for tunnel-composite-nexthop";
               }
               leaf tunnel-composite-anchor-pfe {
                 type string;
                 description "Anchor PFE name, if tunnel nexthop is localized";
               }
               leaf tunnel-composite-encap-rtb-id {
                 type int32;
                 description "Tunnel encap routing table index";
               }
               leaf tunnel-composite-decap-rtb-id {
                 type int32;
                 description "Tunnel decap routing table index";
               }
               leaf tunnel-composite-attr-ttl {
                 type int32;
                 description "Tunnel-TTL for tunnel-composite-nexthop";
               }
               leaf tunnel-composite-attr-udp-port {
                 type int32;
                 description "Tunnel-UDP-Destination port for tunnel-composite-nexthop";
               }
               leaf tunnel-composite-attr-fc-id {
                 type int32;
                 description "Tunnel-Forwarding-Class-ID for tunnel-composite-nexthop";
               }
               leaf tunnel-composite-attr-tid {
                 type int32;
                 description "Tunnel-Id for tunnel-composite-nexthop";
               }
               leaf tunnel-composite-attr-label {
                 type string;
                 description "Tunnel-VPN-Label for tunnel-composite-nexthop";
               }
               leaf tunnel-composite-attr-label-ttl {
                 type string;
                 description "Tunnel-VPN-Label-TTL for tunnel-composite-nexthop";
               }
               leaf tunnel-composite-attr-gre-key {
                 type int32;
                 description "GRE key for tunnel-composite-nexthop";
               }
               leaf-list tunnel-composite-attr-segment-addr {
                 type jt:ipaddr;
                 description "IPv6 segment-address";
               }
               leaf-list tunnel-composite-attr-sid {
                 type int32;
                 description "IPv6 segment-sid";
               }
               leaf tunnel-composite-attr-vni {
                 type int32;
                 description "Tunnel-VNI for tunnel-composite-nexthop in VxLAN";
               }
               leaf tunnel-composite-attr-dest-mac {
                 type string;
                 description "Tunnel-Dest-Mac for tunnel-composite-nexthop in VxLAN";
               }
               leaf translate-composite-attr-type {
                 type string;
                 description "Translation type for translate-composite-nexthop";
               }
               leaf translate-composite-attr-flags {
                 type string;
                 description "Flags for translate-composite-nexthop";
               }
               leaf translate-composite-attr-reference-count {
                 type int32;
                 description "Reference count for translate-composite-nexthop";
               }
               leaf translate-composite-attr-nh-id {
                 type int32;
                 description "NextHop id for translate-composite-nexthop";
               }
               leaf translate-composite-attr-dest {
                 type jt:ipaddr;
                 description "Translation destination for translate-composite-nexthop";
               }
               leaf translate-composite-attr-dest-plen {
                 type int32;
                 description "Translation destination prefix length for translate-composite-nexthop";
               }
               leaf translate-composite-attr-src {
                 type jt:ipaddr;
                 description "Translation source for translate-composite-nexthop";
               }
               leaf translate-composite-attr-src-plen {
                 type int32;
                 description "Translation source prefix length for translate-composite-nexthop";
               }
               leaf translate-composite-attr-dest-alg-type {
                 type string;
                 description "Destination algorithm type for translate-composite-nexthop";
               }
               leaf translate-composite-attr-src-alg-type {
                 type string;
                 description "Source algorithm type for translate-composite-nexthop";
               }
               leaf translate-composite-attr-dest-vrf-id {
                 type int32;
                 description "Destination vrf id for translate-composite-nexthop";
               }
               leaf translate-composite-attr-src-vrf-id {
                 type int32;
                 description "Source vrf id for translate-composite-nexthop";
               }
               leaf translate-composite-attr-hoplimit {
                 type int32;
                 description "Hoplimit for translate-composite-nexthop";
               }
               leaf translate-composite-attr-traffic-class {
                 type int32;
                 description "Traffic class for translate-composite-nexthop";
               }
               leaf translate-composite-attr-ttl {
                 type int32;
                 description "Ttl for translate-composite-nexthop";
               }
               leaf translate-composite-attr-tos {
                 type int32;
                 description "Tos for translate-composite-nexthop";
               }
             }
             leaf to {
               type string;
               description "Neighbor address to which to send (next-hop address)";
             }
             leaf metric {
               type int32;
             }
             leaf aigp {
               type string;
               description "AIGP";
             }
             leaf balance {
               type int32;
               description "Next-hop balance";
             }
             leaf flags {
               type string;
               description "Enabled trace flags";
             }
             leaf res-state {
               type string;
               description "Status of route resolution";
             }
             leaf-list res-path-aux {
               type string;
             }
             leaf-list res-path-aux-type {
               type string;
             }
             leaf-list res-path-aux-flags {
               type string;
             }
             leaf-list res-path-aux-rs-name {
               type string;
             }
             leaf-list res-path-aux-rs-ribs {
               type string;
             }
             leaf-list res-path-inode-flags {
               type string;
             }
             leaf-list res-path-flags {
               type string;
             }
             leaf-list res-path-fnh-link {
               type string;
             }
             leaf-list res-path-inh-link {
               type string;
             }
             leaf mpls-label {
               type string;
               description "Label of MPLS packet";
             }
             leaf label-ttl-action {
               type string;
               description "TTL action associated with labels";
             }
             leaf load-balance-label {
               type string;
               description "Load balance action associated with labels";
             }
             leaf-list composite-nh {
               type string;
             }
             leaf-list pnh-statistics-id-group {
               type string;
               description "Statistics ID Group Associated with this protocol NH";
             }
             leaf-list vpnlabel-nh {
               type string;
             }
             leaf-list indirect-nh {
               type string;
             }
             leaf ext-int-type {
               type string;
               description "Next-hop type of equal-external-internal multipath";
             }
             leaf gw-opaque {
               type int32;
               description "Nexthops gateway opaque data handle";
             }
             leaf-list forwarding-nh-count {
               type int32;
               description "Number of indirect path forwarding next hops";
             }
             leaf-list merged-forwarding-nh-count {
               type int32;
               description "Number of indirect path forwarding next hops (Merged)";
             }
             leaf nh-type {
               type string;
               description "Special next hop: Reject, Blackhole, Receive, Multicast, Local, or Unused";
             }
             leaf-list node-prefix {
               type string;
             }
             leaf-list node-prefix-length {
               type int32;
             }
             leaf-list originating-rib {
               type string;
               description "Routing table from which this route was learned";
             }
             leaf-list node-metric {
               type int32;
             }
             leaf-list node-path-count {
               type int32;
               description "Number of paths for this node";
             }
             leaf node-flags {
               type int32;
               description "Flags for this node";
             }
             leaf-list node-forwarding-nh-count {
               type int32;
             }
             leaf-list nh-subtype {
               type string;
               description "Specified nexthop subtype";
             }
             leaf indirect-nh-count {
               type int32;
               description "Number of indirect next hops";
             }
             leaf composite-nh-count {
               type int32;
               description "Number of composite next hops";
             }
             container eth-header-rewrite {
               leaf eth-header-rewrite-smac {
                 type string;
                 description "Source MAC address";
               }
               leaf eth-header-rewrite-dmac {
                 type string;
                 description "Destination MAC address";
               }
               leaf eth-header-rewrite-tpid {
                 type int32;
                 description "Ethernet header TPID";
               }
               leaf eth-header-rewrite-tci {
                 type int32;
                 description "Ethernet header TCI";
               }
               leaf eth-header-rewrite-vlan-id {
                 type int32;
                 description "Ethernet header VLAN ID";
               }
               leaf eth-header-rewrite-ethertype {
                 type int32;
                 description "Ethernet header ethertype";
               }
             }
             container vxlan-header-rewrite {
               leaf vxlan-header-rewrite-mtu {
                 type int32;
                 description "VXLAN tunnel MTU";
               }
               leaf vxlan-header-rewrite-flags {
                 type int32;
                 description "VXLAN tunnel flags";
               }
               leaf vxlan-header-rewrite-encap-rtb-id {
                 type int32;
                 description "VXLAN tunnel encapsulation table ID";
               }
               leaf vxlan-header-rewrite-decap-rtb-id {
                 type int32;
                 description "VXLAN tunnel decapsulation table ID";
               }
               leaf vxlan-header-rewrite-encap-vnid {
                 type int32;
                 description "VXLAN tunnel encapsulation VNI";
               }
               leaf vxlan-header-rewrite-decap-vnid {
                 type int32;
                 description "VXLAN tunnel decapsulation VNI";
               }
               leaf vxlan-header-rewrite-svtep {
                 type jt:ipaddr;
                 description "Source VTEP address";
               }
               leaf vxlan-header-rewrite-dvtep {
                 type jt:ipaddr;
                 description "Destination VTEP address";
               }
               leaf vxlan-header-rewrite-smac {
                 type string;
                 description "Source MAC address";
               }
               leaf vxlan-header-rewrite-dmac {
                 type string;
                 description "Destination MAC address";
               }
             }
             container fully-resolved-tunnel {
               leaf fully-resolved-tunnel-type {
                 type string;
                 description "Tunnel type";
               }
               leaf fully-resolved-tunnel-dest {
                 type jt:ipaddr;
                 description "Tunnel Destination";
               }
               leaf fully-resolved-tunnel-src {
                 type jt:ipaddr;
                 description "Tunnel Source";
               }
               leaf fully-resolved-tunnel-ep-addr {
                 type jt:ipaddr;
                 description "Tunnel endpoint address";
               }
               leaf fully-resolved-tunnel-encap-rtb-id {
                 type int32;
                 description "Tunnel encap routing table id";
               }
               leaf fully-resolved-tunnel-decap-rtb-id {
                 type int32;
                 description "Tunnel decap routing table id";
               }
             }
           }
           container srte-policy-state {
             leaf sr-source {
               type string;
             }
             leaf sr-origin {
               type string;
             }
             leaf sr-preference {
               type uint32;
             }
             leaf sr-preference-override {
               type uint32;
             }
             leaf sr-route-distinguisher {
               type uint32;
             }
           }
           container srte-policy-information {
             container srte-policy {
               leaf srte-path-preference {
                 type uint32;
               }
               leaf srte-binding-sid {
                 type string;
               }
               leaf srte-adv-policy-name {
                 type string;
               }
               leaf srte-priority {
                 type uint32;
               }
               leaf srte-enlp {
                 type uint32;
               }
               leaf srte-tlv-recv-flags {
                 type string;
               }
               leaf srte-binding-sid-label-encoding {
                 type string;
               }
               list srte-segment-list {
                 leaf srte-segment-list-weight {
                   type uint32;
                 }
                 list srte-segment {
                   leaf srte-segment-label {
                     type uint32;
                   }
                   leaf srte-segment-label-ttl {
                     type string;
                     description "SR Policy segment label ttl";
                   }
                   leaf srte-segment-type {
                     type string;
                     description "SR Policy segment type";
                   }
                   leaf srte-segment-label-class {
                     type uint32;
                     description "SR Policy segment label traffic-class";
                   }
                 }
               }
             }
           }
           container bgp-prefix-sid-attr {
             container bgp-prefix-sid-attr-label-idx-tlv {
               leaf bgp-prefix-sid-label-idx-index {
                 type int32;
               }
               leaf bgp-prefix-sid-attr-status {
                 type string;
               }
             }
             container bgp-prefix-sid-attr-srgb-tlv {
               list bgp-prefix-sid-srgb-block {
                 leaf bgp-prefix-sid-srgb-block-start-label {
                   type int32;
                 }
                 leaf bgp-prefix-sid-srgb-block-range {
                   type int32;
                 }
               }
             }
             container bgp-prefix-sid-attr-service-tlv {
               leaf bgp-prefix-sid-srv6-sid-value {
                 type jt:ipaddr;
               }
               leaf bgp-prefix-sid-attr-service-tlv-type {
                 type uint32;
               }
               leaf bgp-prefix-sid-srv6-sid-bh {
                 type uint32;
               }
               leaf bgp-prefix-sid-srv6-sid-bl {
                 type uint32;
               }
               leaf bgp-prefix-sid-srv6-sid-nl {
                 type uint32;
               }
               leaf bgp-prefix-sid-srv6-sid-fl {
                 type uint32;
               }
               leaf bgp-prefix-sid-srv6-sid-al {
                 type uint32;
               }
               leaf bgp-prefix-sid-srv6-sid-tl {
                 type uint32;
               }
               leaf bgp-prefix-sid-srv6-sid-to {
                 type uint32;
               }
             }
             container bgp-prefix-sid-attr-unknown-tlvs {
               list bgp-prefix-sid-attr-unknown-tlv {
                 leaf bgp-prefix-sid-unknown-tlv-type {
                   type uint32;
                 }
                 leaf bgp-prefix-sid-unknown-tlv-len {
                   type uint32;
                 }
               }
             }
           }
           container srte-policy-telemetry-statistics-state {
             leaf srte-policy-telemetry-statistics-state.heading {
               type string;
             }
             container srte-policy-telemetry-statistics-config {
               leaf ingress {
                 type empty;
                 description "Flag indicating ingress statistics is configured";
               }
               leaf transit {
                 type empty;
                 description "Flag indicating transit statistics is configured";
               }
             }
             list srte-policy-telemetry-statistics-sensor-information {
               leaf sensor-type {
                 type string;
               }
               leaf sensor-status {
                 type string;
               }
               leaf sensor-id {
                 type int32;
                 description "Unique identifier for the sensor";
               }
             }
           }
           leaf preference2 {
             type int32;
           }
           leaf age {
             type string;
           }
           leaf med {
             type int32;
             description "Multiple exit discriminator";
           }
           leaf local-preference {
             type int32;
           }
           leaf rt-tag {
             type int32;
           }
           leaf rt-tag2 {
             type int32;
           }
           leaf learned-from {
             type jt:ipaddr;
             description "Peer address from which this route was learned";
           }
           leaf peer-as {
             type int32;
             description "Peer AS number";
           }
           leaf evpn-remote-mes {
             type jt:ipaddr;
             description "Remote PE";
           }
           leaf evpn-routing-instance-name {
             type string;
             description "Routing Instance";
           }
           leaf evpn-tag-rt-type {
             type string;
             description "Route Type";
           }
           leaf evpn-vlan-id {
             type int32;
             description "VLAN-ID";
           }
           leaf evpn-vpws-service-id {
             type int32;
             description "VPWS Service-Id";
           }
           leaf rt-evpn-esi {
             type string;
             description "ESI";
           }
           leaf evpn-isid {
             type int32;
             description "ISID";
           }
           leaf rt-evpn-bmac {
             type string;
             description "BMAC";
           }
           leaf bgp-rtarget-type {
             type string;
             description "BGP RT-Constrain route type";
           }
           leaf bgp-rtarget-generation {
             type uint32;
             description "BGP RT-Constrain generation";
           }
           leaf bgp-rtarget-for {
             type string;
             description "BGP RT-Constrain member";
           }
           leaf nh-index {
             type uint32;
             description "Next-hop index";
           }
           leaf transport-class {
             type string;
             description "Transport class name";
           }
           leaf nh-address {
             type string;
             description "Address of next hop";
           }
           leaf nh-reference-count {
             type int32;
             description "Number of references to this next hop";
           }
           leaf ext-int-intf-index {
             type int32;
             description "Interface index of equal-external-internal multipath";
           }
           leaf nh-session-id {
             type uint32;
             description "Nexthop session id";
           }
           leaf nh-key-opaque {
             type int32;
             description "Nexthop key opaque handle";
           }
           leaf nh-non-key-opaque {
             type int32;
             description "Nexthop non-key opaque handle";
           }
           leaf nh-key-opaque-dump {
             type string;
             description "Nexthop key opaque app dump";
           }
           leaf nh-non-key-opaque-dump {
             type string;
             description "Nexthop non-key opaque app dump";
           }
           leaf nh-flood-overflow {
             type empty;
             description "Flood nexthop exceeds maximum branches";
           }
           leaf nh-kernel-id {
             type int32;
             description "Table Id for this next hop";
           }
           leaf client-data {
             type string;
             description "Route server client details";
           }
           leaf route-distinguisher {
             type string;
             description "Name of the route-distinguisher";
           }
           leaf reason-for-invalid {
             type string;
           }
           leaf thread-name {
             type string;
           }
           leaf pmsi {
             type string;
             description "P-multicast service interface";
           }
           leaf connector {
             type string;
           }
           leaf color {
             type int32;
           }
           leaf color2 {
             type int32;
           }
           leaf prefix-segment-index {
             type int32;
           }
           leaf rt-isis-level {
             type int32;
           }
           leaf rt-isis-downbit {
             type int32;
           }
           leaf rt-entry-state {
             type string;
             description "State of this route entry";
           }
           leaf rt-fib-install-priority {
             type string;
             description "Route FIB installation priority";
           }
           leaf rt-ack-state {
             type string;
             description "Route acknowledgement state";
           }
           leaf rt-ack-ll-flag {
             type string;
             description "Status of route ACK flags";
           }
           leaf rt-ack-req-ts {
             type string;
             description "Time when ack request is sent";
           }
           leaf rt-ack-res-time {
             type uint32;
             description "Ack route response time";
           }
           leaf rt-ack-re-flash-time {
             type string;
             description "Time when ack is re flashed to protocols";
           }
           leaf rt-ack-re-flash-status {
             type string;
             description "Status of ACK re-flash to protocols";
           }
           leaf rt-ack-guid {
             type uint64;
             description "Ack route global identifier";
           }
           leaf rt-ack-olc {
             type uint64;
             description "Ack route global version";
           }
           leaf rt-ack-local-ver {
             type uint32;
             description "Ack route global version";
           }
           leaf rt-ack-and-err-flag {
             type uint32;
             description "Route ack and error flag";
           }
           leaf pfe-err-state {
             type string;
             description "Route error state from PFE";
           }
           leaf pfe-err-time {
             type uint32;
             description "Route error receive time";
           }
           leaf rt-ver-id {
             type uint32;
             description "Route version ID";
           }
           leaf rt-entry-pim-state {
             type string;
             description "PIM state of this route entry";
           }
           leaf inactive-reason {
             type string;
             description "HFRR profile Inactive reason (if any)";
           }
           leaf local-as {
             type int32;
             description "Local AS number";
           }
           leaf med-plus-igp {
             type int32;
           }
           leaf rt-aigp {
             type uint64;
           }
           leaf rt-effective-aigp {
             type uint64;
             description "Effective AIGP value used by route selection";
           }
           leaf rt-effective-aigp-reason {
             type string;
             description "Reason why the effective AIGP value was selected";
           }
           leaf rt-resolving-aigp {
             type uint64;
           }
           leaf rt-effective-metric {
             type uint64;
             description "Effective metric value used by route selection";
           }
           leaf rt-effective-metric-reason {
             type string;
             description "Reason why the effective metric value was selected";
           }
           leaf rt-orr {
             type uint32;
           }
           leaf rt-actual-igp-metric {
             type uint32;
           }
           leaf rt-ospf-area {
             type string;
           }
           leaf task-name {
             type string;
             description "Name of this task";
           }
           leaf announce-bits {
             type int32;
           }
           leaf announce-tasks {
             type string;
           }
           leaf flow-id {
             type int32;
           }
           leaf bgp-rt-flag {
             type string;
             description "BGP route flag";
           }
           leaf label-base {
             type int32;
             description "Label base for l2vpn";
           }
           leaf label-range {
             type int32;
             description "Label range for l2vpn";
           }
           leaf l2vpn-status-vector {
             type string;
           }
           leaf label-offset {
             type int32;
             description "Label offset for l2vpn";
           }
           leaf remote-site {
             type int32;
             description "Remote site id";
           }
           leaf l2vpn-mesh-group {
             type string;
           }
           leaf vc-label {
             type int32;
             description "VC label";
           }
           leaf context-id {
             type jt:ipaddr;
             description "Context Identifier";
           }
           leaf route-control-word {
             type string;
             description "Control Word";
           }
           leaf mtu {
             type int32;
             description "MTU along an interface";
           }
           leaf cell-bundle-size {
             type int32;
             description "Cell bundle size";
           }
           leaf vlan-id {
             type int32;
           }
           leaf flow-label-transmit {
             type int32;
           }
           leaf flow-label-receive {
             type int32;
           }
           leaf tdm-payload-size {
             type int32;
           }
           leaf tdm-bitrate {
             type int32;
           }
           leaf pw-status-code {
             type int32;
           }
           leaf cac-bandwidth-failure {
             type empty;
             description "Call admission control failure due to insufficient bandwidth";
           }
           leaf vpn-label {
             type int32;
             description "VPN label";
           }
           leaf route-label {
             type int32;
             description "Route label";
           }
           leaf route-labels {
             type string;
             description "Route label";
           }
           leaf mac-route-esi {
             type string;
             description "ESI";
           }
           leaf evpn-igmp-flags {
             type int32;
             description "IGMP flags";
           }
           leaf evpn-mld-flags {
             type int32;
             description "MLD flags";
           }
           leaf evpn-leave-reserved {
             type int32;
             description "IGMP Leave Reserved Field";
           }
           leaf evpn-leave-mrt {
             type int32;
             description "IGMP Leave Max Response Time";
           }
           leaf overlay-gateway-address {
             type jt:ipaddr;
             description "Overlay gateway address";
           }
           leaf reroute-address {
             type jt:ipaddr;
             description "Reroute address";
           }
           leaf peer-id {
             type jt:ipaddr;
           }
           leaf rt-entry-ext-pfx-attr-flags {
             type string;
             description "Route entry extended prefix attribute flags";
           }
           leaf rt-entry-ext-pfx-source-rtrid {
             type string;
             description "Route entry extended prefix source rtr id";
           }
           leaf path-id {
             type string;
           }
           leaf gateway {
             type string;
             description "Sourcing gateway";
           }
           leaf rtrib-primary {
             type string;
             description "Primary routing table";
           }
           leaf rtrib-secondary {
             type string;
             description "Secondary routing table";
           }
           leaf indirect-nh-count {
             type int32;
             description "Number of indirect next hops";
           }
           leaf composite-nh-count {
             type int32;
             description "Number of composite next hops";
           }
           leaf helper-nhid {
             type uint32;
             description "Helper nexthop index";
           }
           leaf helper-refcount {
             type int32;
             description "Reference count of those needing helper route";
           }
           leaf backup-pe-group-name {
             type string;
             description "Name of the backup PE group";
           }
           leaf designated-forwarder {
             type string;
             description "Indicates if we are the designated forwarder for this route";
           }
           leaf rt-entry-opaque-data {
             type string;
             description "Opaque data associated with the route entry";
           }
           leaf rt-stats-id-grp-single-line {
             type string;
             description "Stats-id-group associated with the route entry";
           }
           leaf rt-entry-ext-pfx-sid-data {
             type string;
             description "Route entry extended prefix sid data";
           }
           leaf hidden-reason {
             type string;
             description "Protocol's reason for hiding the route";
           }
           leaf bgp-bmp-send-flag-start {
             type string;
           }
           leaf bgp-bmp-send-flag-pre {
             type string;
           }
           leaf bgp-bmp-send-flag-post {
             type string;
           }
           leaf bgp-bmp-send-flag-ribout-prepolicy {
             type string;
           }
           leaf bgp-bmp-send-flag-ribout-postpolicy {
             type string;
           }
           leaf bgp-bmp-send-flag-station {
             type string;
           }
           leaf bgp-nnh-nodes {
             type string;
             description "Next-next-hop nodes";
           }
           leaf bgp-nh-nnh-map {
             type string;
             description "Next-hop to next-next-hop map";
           }
           leaf bgp-nh-nnh-entry {
             type string;
             description "Next-hop to next-next-hop entry";
           }
           leaf glb-profile {
             type string;
             description "GLB Profile";
           }
           leaf glb-profile-id {
             type uint32;
             description "GLB Profile ID";
           }
           leaf rt-entry-stats {
             type string;
             description "Route entry statistics data";
           }
           container connection-bandwidth {
             leaf connection-bandwidth.heading {
               type string;
               description "Bandwidth of a layer 2 connection";
             }
             leaf bandwidth {
               type int32;
             }
             leaf class-type {
               type int32;
             }
             leaf class-bandwidth {
               type int32;
             }
           }
           container route-flap-damping {
             leaf last-merit {
               type int32;
               description "Last merit value";
             }
             leaf merit {
               type int32;
               description "Current merit value";
             }
             leaf damping-parameters {
               type string;
             }
             leaf default-damping-parameters {
               type empty;
               description "Default damping parameters used";
             }
             leaf last-update {
               type string;
             }
             leaf first-update {
               type string;
             }
             leaf route-flap-count {
               type int32;
               description "Number of times this route has flapped";
             }
             leaf suppressed {
               type empty;
               description "This route is suppressed";
             }
             leaf reuse-time {
               type string;
               description "Time until this route is reusable";
             }
             leaf reuse-preference {
               type int32;
               description "Preference to use when this route is reused";
             }
             leaf expire-time {
               type string;
               description "Time when this damping entry expires";
             }
           }
           container nhh {
             leaf nh-type {
               type string;
               description "Special next hop: Reject, Blackhole, Receive, Multicast, Local, or Unused";
             }
             leaf nh-index {
               type uint32;
               description "Next-hop index";
             }
             leaf transport-class {
               type string;
               description "Transport class name";
             }
             leaf nh-address {
               type string;
               description "Address of next hop";
             }
             leaf nh-reference-count {
               type int32;
               description "Number of references to this next hop";
             }
             leaf ext-int-intf-index {
               type int32;
               description "Interface index of equal-external-internal multipath";
             }
             leaf nh-session-id {
               type uint32;
               description "Nexthop session id";
             }
             leaf nh-key-opaque {
               type int32;
               description "Nexthop key opaque handle";
             }
             leaf nh-non-key-opaque {
               type int32;
               description "Nexthop non-key opaque handle";
             }
             leaf nh-key-opaque-dump {
               type string;
               description "Nexthop key opaque app dump";
             }
             leaf nh-non-key-opaque-dump {
               type string;
               description "Nexthop non-key opaque app dump";
             }
             leaf nh-flood-overflow {
               type empty;
               description "Flood nexthop exceeds maximum branches";
             }
             leaf nh-kernel-id {
               type int32;
               description "Table Id for this next hop";
             }
           }
           list nh-expand {
             leaf nhe-name {
               type string;
               description "Name of next-hop";
             }
             leaf nhe-handle {
               type int32;
               description "Nexthop pointer";
             }
             leaf nhe-index {
               type int32;
               description "Next-hop index";
             }
             leaf nhe-to {
               type string;
               description "Nexthop address";
             }
             leaf nhe-mbr-count {
               type int32;
               description "Number of child nexhops";
             }
             leaf nhe-mpls-label {
               type string;
               description "Label of MPLS packet";
             }
           }
           list rt-session-id {
             leaf rt-session-id-value {
               type int32;
               description "Value of session-id";
             }
             leaf rt-session-id-version {
               type int32;
               description "Version of session-id";
             }
           }
           container flex-rt-statistics {
             leaf flex-rt-statistics-pkts-count {
               type int32;
               description "Packet count";
             }
             leaf flex-rt-statistics-pps {
               type int32;
               description "Pps";
             }
             leaf flex-rt-statistics-bytes-count {
               type int32;
               description "Byte count";
             }
             leaf flex-rt-statistics-bps {
               type int32;
               description "Bps";
             }
           }
           leaf bgp-group-name {
             type string;
           }
           leaf bgp-no-label-reason {
             type string;
           }
           leaf sr-policy-distinguisher {
             type uint32;
           }
           leaf sr-policy-color {
             type uint32;
           }
           leaf sr-policy-endpoint {
             type jt:ipaddr;
           }
           leaf bgp-metric-flags {
             type string;
             description "BGP metrics flags";
           }
           leaf bgp-output-queue-class {
             type string;
             description "BGP output queue class";
           }
           leaf cluster-id {
             type string;
           }
           leaf originator {
             type string;
           }
           leaf bgp-aigp {
             type string;
             description "Accumulated IGP Metric";
           }
           leaf bgp-elc {
             type empty;
             description "Entropy label capable";
           }
           leaf bgp-elc-v2 {
             type empty;
             description "Entropy label capable version 2";
           }
           leaf bgp-elc-v3 {
             type empty;
             description "Entropy label capable version 3";
           }
           leaf bgp-elc-nh-valid {
             type string;
             description "Whether next hop field matches route next hop";
           }
           leaf bgp-rca-unknown-capabilities-len {
             type uint32;
             description "Total length of RCA unknown capabilities";
           }
           leaf bgp-rca-capability-code {
             type uint32;
             description "RCA capability code";
           }
           leaf bgp-rca-capability-len {
             type uint32;
             description "RCA capability length";
           }
           leaf bgp-rca-capability-val {
             type string;
             description "RCA capability value";
           }
         }
         list kern-nhexpand {
           container srv6-info {
             leaf srv6-info-srh-sid-mode {
               type string;
               description "Reduced/non-reduced mode for SRH";
             }
             leaf srv6-info-packet-mode {
               type string;
               description "Packet mode for SRV6-Tunnel";
             }
             leaf srv6-info-srh-last-sid {
               type string;
               description "Remove last sid for ACX";
             }
             leaf srv6-info-dyn-tunnel {
               type string;
               description "SRv6 tunnel created dynamically";
             }
             leaf srv6-source {
               type jt:ipaddr;
               description "Source IPv6 address";
             }
             leaf srv6-destination {
               type jt:ipaddr;
               description "Destination IPv6 address";
             }
             list srv6-segment-list {
               leaf srv6-segment-list-index {
                 type uint32;
                 description "SRH segment list index";
               }
               leaf srv6-segment-list-addr {
                 type jt:ipaddr;
                 description "SRH segment address";
               }
             }
           }
           leaf kern-nhe-platform-layer-input {
             type empty;
             description "Platform layer input nexthop";
           }
           leaf kern-nhe-in-kernel {
             type empty;
             description "Nexthoo install in kernel";
           }
           leaf kern-nhe-name {
             type string;
             description "Name of next-hop";
           }
           leaf kern-nhe-subtype {
             type string;
             description "Nexthop Subtype";
           }
           leaf kern-nhe-handle {
             type int32;
             description "Nexthop pointer";
           }
           leaf kern-nhe-index {
             type int32;
             description "Next-hop index";
           }
           leaf kern-gw-opaque {
             type int32;
             description "Nexthop gateway opaque data handle";
           }
           leaf kern-key-opaque {
             type int32;
             description "Nexthop key opaque data handle";
           }
           leaf kern-nhe-to {
             type string;
             description "Nexthop address";
           }
           leaf kern-nhe-mbr-count {
             type int32;
             description "Number of child nexhops";
           }
           leaf kern-nhe-mpls-label {
             type string;
             description "Label of MPLS packet";
           }
           leaf kern-nhe-pnh {
             type string;
             description "Protocol Nexthop address";
           }
           leaf kern-nhe-sessionid {
             type int32;
             description "Session ID";
           }
           leaf kern-nhe-tunnel-type {
             type string;
             description "Tunnel type";
           }
           leaf kern-nhe-tunnel-src {
             type string;
             description "Tunnel Source address";
           }
           leaf kern-nhe-tunnel-dest {
             type string;
             description "Tunnel Destination address";
           }
           leaf kern-nhe-tunnel-ep {
             type string;
             description "Tunnel Endpoint address";
           }
           leaf kern-nhe-tunnel-vxlan-encap-vni {
             type int32;
             description "VxLAN tunnel encap vni";
           }
           leaf kern-nhe-tunnel-vxlan-decap-vni {
             type int32;
             description "VxLAN tunnel decap vni";
           }
           leaf kern-nhe-translate-type {
             type string;
             description "Translation type";
           }
           leaf kern-nhe-translate-src {
             type string;
             description "Translation Source address";
           }
           leaf kern-nhe-translate-src-plen {
             type int32;
             description "Translation Source address prefix length";
           }
           leaf kern-nhe-translate-dest {
             type string;
             description "Translation Destination address";
           }
           leaf kern-nhe-translate-dest-plen {
             type int32;
             description "Translation Destination address prefix length";
           }
           leaf kern-nhe-tunnel-encap-rtb-id {
             type int32;
             description "Tunnel encap routing table id";
           }
           leaf kern-nhe-tunnel-decap-rtb-id {
             type int32;
             description "Tunnel decap routing table id";
           }
           leaf kern-nhe-interface {
             type string;
             description "Interface";
           }
           leaf kern-nhe-slice-gencfg-id {
             type int32;
             description "Slice-Gencfg ID";
           }
           leaf kern-nhe-sliceid {
             type int32;
             description "Slice ID";
           }
           leaf kern-nhe-fwf {
             type string;
             description "Filter Name";
           }
           leaf kern-nhe-flex-tunnel-info {
             type string;
             description "Flex-tunnel information of nexthop";
           }
           leaf kern-nhe-flags {
             type string;
             description "Nexthop flags";
           }
           leaf kern-nhe-reference-count {
             type int32;
             description "Nexthop reference count";
           }
           leaf kern-elnh-address {
             type int32;
             description "Address of Element Next-hop";
           }
         }
         leaf rt-entry-count {
           type int32;
           description "Number of route entries in this route";
         }
         leaf rt-announced-count {
           type int32;
           description "Number of announced route entries";
         }
         leaf rt-state {
           type string;
           description "State of this route";
         }
         leaf-list tsi {
           type string;
           description "Task-specific information";
         }
         container communities {
           leaf-list community {
             type string;
             description "Basic community";
           }
           leaf-list extended-community {
             type string;
             description "Extended community";
           }
           leaf-list ipv6-extended-community {
             type string;
             description "IPv6 extended community";
           }
         }
         list bgp-tunnel-attribute {
           leaf tunnel-attribute-type {
             type string;
           }
           leaf tunnel-attribute-rpf {
             type empty;
           }
           leaf tunnel-attribute-color {
             type uint32;
           }
           leaf tunnel-attribute-destination {
             type jt:ipaddr;
           }
         }
       }
     }
     list rt-martians {
       leaf rt-martian-table-name {
         type string;
         description "Name of the martian table, for example, inet.0";
       }
       list route-filter {
         description "Entries in martian table";
         leaf address {
           type jt:ipaddr;
         }
         leaf flags {
           type string;
           description "Enabled trace flags";
         }
         leaf extended-information {
           type string;
         }
         leaf match-count {
           type uint64;
         }
         container policy-extended-information {
           leaf account {
             type empty;
             description "Account";
           }
           leaf accept {
             type empty;
             description "Accept a route";
           }
           leaf advertise-locator {
             type empty;
             description "Advertise SRv6 locator";
           }
           leaf advertise-locator-internal {
             type empty;
             description "Advertise SRv6 locator internal";
           }
           leaf aggregate-bandwidth {
             type int32;
             description "Aggregate bandwidth";
           }
           leaf auto-link-bandwidth {
             type empty;
             description "Auto link bandwidth";
           }
           leaf analyze {
             type empty;
             description "Send to registered controllers for analysis";
           }
           leaf as-path-prepend {
             type uint32;
             description "Prepend AS numbers to an AS path (BGP only)";
           }
           leaf cos-next-hop-map {
             type string;
             description "The CoS-based next-hop map in forwarding table";
           }
           leaf damping {
             type string;
             description "Define BGP route flap damping parameters";
           }
           leaf default-action {
             type string;
             description "The default policy action";
           }
           leaf destination-class {
             type string;
             description "The destination class in forwarding table";
           }
           leaf dynamic-tunnel-attributes {
             type string;
             description "The dynamic tunnel attributes used for forwarding";
           }
           leaf fib-install-priority {
             type string;
             description "FIB install priority";
           }
           leaf filter {
             type string;
             description "Next-hop firewall filter";
           }
           leaf get-route-range {
             type empty;
             description "Get route range";
           }
           leaf ignore-service-label {
             type string;
             description "Ignore service labels";
           }
           leaf install-to-fib {
             type string;
             description "Install to FIB";
           }
           leaf ipv4-source-router-id {
             type empty;
           }
           leaf ipv4-source-router-id-address {
             type string;
             description "IPV4 source router id address";
           }
           leaf ipv6-source-router-id {
             type empty;
           }
           leaf ipv6-source-router-id-address {
             type string;
             description "IPV6 source router id address";
           }
           leaf label-allocation {
             type string;
             description "Label allocation mode";
           }
           leaf label-allocation-fallback-reject {
             type string;
             description "Suppress prefix export when label allocation fails";
           }
           leaf limit-bandwidth {
             type uint64;
             description "Limit advertised aggregate outbound link bandwidth";
           }
           leaf load-balance {
             type string;
             description "Load-balancing algorithm chosen";
           }
           leaf mhop-bfd-port {
             type uint32;
             description "Use port number 4784 for MPLS-BFD as per RFC5884";
           }
           leaf multipath-resolve {
             type string;
             description "Use all paths for resolution over this prefix";
           }
           leaf next {
             type string;
             description "Skip to next policy or term";
           }
           leaf no-backup {
             type empty;
             description "This prefix should not have backup";
           }
           leaf no-entropy-label-capability {
             type empty;
             description "Don't advertise entropy label capability";
           }
           leaf no-route-localize {
             type empty;
             description "No route localize";
           }
           leaf origin {
             type string;
             description "BGP origin attribute";
           }
           leaf p2mp-lsp-root {
             type jt:ipaddr;
             description "P2mp lsp root address";
           }
           leaf policy-priority {
             type string;
           }
           leaf reject {
             type empty;
             description "Reject a route";
           }
           leaf request-long-lived-ack {
             type empty;
             description "Advertise route after forwarding is programmed";
           }
           leaf resolution-map {
             type string;
             description "Resolution map";
           }
           leaf resolution-map-mode {
             type string;
             description "Resolution map modes";
           }
           leaf selected-mldp-egress {
             type string;
             description "This node should act as egress node for MLDP inband signalling";
           }
           leaf send-withdrawal-on-route-change {
             type empty;
             description "Withdrawn route as change is not ack'd from forwarding";
           }
           leaf set-down-bit {
             type empty;
             description "Set down bit";
           }
           leaf slice {
             type string;
             description "Slice name";
           }
           leaf source-class {
             type string;
             description "The source class in forwarding table";
           }
           leaf sr-te-template {
             type string;
             description "SR TE template to apply";
           }
           leaf ssm-source {
             type jt:ipaddr;
             description "List of Sources for SSM mapping";
           }
           leaf trace {
             type empty;
             description "Log matches to a trace file";
           }
           leaf tunnel-end-point-address {
             type string;
             description "Set tunnel end-point address of tunnel";
           }
           leaf validation-state {
             type string;
             description "Validation-state of a route";
           }
           container install-nexthop {
             description "The next hop to be used for forwarding";
             container except {
               leaf lsp {
                 type string;
                 description "Label switched path name";
               }
               leaf lsp-regex {
                 type string;
                 description "Label switched path name regular expression";
               }
               leaf non-labelled-nexthop {
                 type empty;
               }
               leaf non-lsp-nexthop {
                 type empty;
               }
               leaf static-lsp {
                 type string;
               }
               leaf static-lsp-regex {
                 type string;
               }
               leaf overlay-vxlan-interfaces {
                 type empty;
               }
             }
             container fallback {
               leaf lsp {
                 type string;
                 description "Label switched path name";
               }
               leaf lsp-regex {
                 type string;
                 description "Label switched path name regular expression";
               }
               leaf non-labelled-nexthop {
                 type empty;
               }
               leaf non-lsp-nexthop {
                 type empty;
               }
               leaf static-lsp {
                 type string;
               }
               leaf static-lsp-regex {
                 type string;
               }
               leaf overlay-vxlan-interfaces {
                 type empty;
               }
             }
           }
           container map-to-interface {
             description "Set output logical interface";
             list interface {
               description "Interface name or address";
               leaf interface-name {
                 type string;
                 description "Name of interface";
               }
               leaf interface-flags {
                 type int32;
               }
             }
           }
           container then-metric {
           }
           container prefix-segment {
             description "The prefix segment attributes";
             leaf redistribute {
               type empty;
             }
             container algorithm {
               leaf prefix-segment-index-value {
                 type uint32;
               }
               leaf algorithm-name {
                 type uint32;
               }
               leaf node-segment {
                 type empty;
               }
               leaf redistribute {
                 type empty;
               }
             }
           }
           list tunnel-attribute {
             description "Tunnel attribute information";
             leaf tunnel-type {
               type string;
               description "Tunnel type";
             }
             leaf reference-count {
               type int32;
               description "Reference count";
             }
             leaf tunnel-data {
               type string;
               description "Tunnel Data";
             }
           }
           container source-based-forwarding {
             container sbf-attributes {
               leaf sbf-next-table {
                 type string;
               }
             }
           }
           container policy-label {
           }
         }
       }
     }
     list rt-ribgroup {
       leaf rt-ribgroup-name {
         type string;
         description "Rib-group name";
       }
       leaf rt-ribgroup-address {
         type string;
         description "Rib-group address";
       }
       leaf rt-ribgroup-address-family {
         type string;
         description "Rib-group address family";
       }
       leaf rt-ribgroup-flags {
         type string;
         description "Rib-group flags";
       }
       leaf rt-ribgroup-refcount {
         type uint32;
         description "Rib-group refcount";
       }
       leaf rt-ribgroup-export-name {
         type string;
         description "Export RIB name";
       }
       leaf rt-ribgroup-import-name {
         type string;
         description "Import RIB name";
       }
       leaf rt-ribgroup-import-policy-name {
         type string;
         description "Import policy name";
       }
       leaf-list rt-ribgroup-import-secondary-name {
         type string;
         description "Import secondary RIB name";
       }
       leaf rt-ribgroup-union-head-name {
         type string;
         description "Rib-group union head name";
       }
       leaf rt-ribgroup-union-child-name {
         type string;
         description "Rib-group union child name";
       }
       leaf rt-ribgroup-deleted {
         type empty;
         description "Ribgroup deleted. Display of ribgroups will end here.";
       }
     }
     container rt-test-policy-prefix {
       leaf rt-policy-name {
         type string;
       }
       leaf rt-destination {
         type string;
         description "Route prefixes awaiting ACK";
       }
       leaf rt-prefix-length {
         type string;
       }
       container rt-test-policy-term {
         leaf rt-policy-term-name {
           type string;
         }
         leaf rt-policy-term-result {
           type string;
         }
         leaf rt-policy-term-action {
           type string;
         }
       }
     }
     container rt-test-policy {
       leaf rt-policy-name {
         type string;
       }
       leaf rt-route-accepted {
         type int32;
       }
       leaf rt-route-rejected {
         type int32;
       }
     }
     container rt-test-rib-sharding {
       leaf rt-destination {
         type string;
         description "Route prefixes awaiting ACK";
       }
       leaf rt-hash-prefix-to-shard {
         type string;
       }
     }
     list route-entry {
       leaf destination-address {
         type string;
       }
       leaf route-flags {
         type string;
       }
       leaf route-state {
         type string;
       }
       list nh-entry {
         leaf nexthop-address {
           type string;
         }
         leaf nexthop-type {
           type string;
         }
         leaf nexthop-index {
           type int32;
         }
         leaf nexthop-interface {
           type string;
         }
         leaf nexthop-local-address {
           type string;
         }
         list event-history {
           leaf event-timestamp {
             type string;
           }
           leaf event-id {
             type string;
           }
           leaf event-action {
             type string;
           }
           leaf event-information {
             type string;
           }
         }
       }
     }
   }
   grouping test-services-l2tp-tunnel-result-block {
     container l2tp-tunnel-test-subscriber-information {
       description "Subscriber information obtained from tunnel verification";
       leaf subscriber-name {
         type string;
         description "Name of the subscriber";
       }
       leaf subscriber-authentication-status {
         type string;
         description "Status of the subscriber authentication";
       }
       leaf subscriber-tunneling-status {
         type string;
         description "Status of the subscriber tunneling";
       }
     }
     container l2tp-tunnel-test-result-table {
       description "Table of tunnel verification result";
       list l2tp-tunnel-test-result-entry {
         description "Result information for one tunnel's verification";
         leaf tunnel-name {
           type string;
           description "Name of the tunnel";
         }
         leaf tunnel-peer {
           type jt:ipaddr;
           description "IP address of the tunnel peer";
         }
         leaf tunnel-logical-system {
           type string;
           description "Logical system of the tunnel";
         }
         leaf tunnel-routing-instance {
           type string;
           description "Routing instance of the tunnel";
         }
         leaf tunnel-status {
           type string;
           description "Status of tunnel establishment";
         }
       }
     }
   }
   grouping radius-profile-access-test-result-block {
     leaf radius-profile-name {
       type string;
       description "Access profile name";
     }
     leaf radius-client-user-name {
       type string;
       description "Session user name";
     }
     leaf radius-client-password {
       type string;
       description "Session password";
     }
     leaf radius-profile-num-servers {
       type int32;
       description "Access profile num servers";
     }
     leaf radius-server-ip-address {
       type jt:ipaddr;
       description "Server IP address";
     }
     leaf radius-server-udp-port {
       type uint32;
       description "Server UDP port";
     }
     leaf radius-server-source-address {
       type jt:ipaddr;
       description "Source IP address";
     }
     leaf radius-server-timeout {
       type uint32;
       description "Server timeout value in seconds";
     }
     leaf radius-server-retry-count {
       type uint32;
       description "Server retry count";
     }
     leaf radius-server-secret {
       type string;
       description "Radius shared secret";
     }
     leaf radius-server-status {
       type string;
       description "Server status";
     }
     leaf radius-server-attempts {
       type int32;
       description "Access profile connection attemps";
     }
   }
 }
