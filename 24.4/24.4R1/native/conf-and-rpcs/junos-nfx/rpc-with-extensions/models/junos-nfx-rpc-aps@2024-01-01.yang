/*
 * Copyright (c) 2025 Juniper Networks, Inc.
 * All rights reserved.
 */
 module junos-nfx-rpc-aps {
   namespace "http://yang.juniper.net/junos-nfx/rpc/aps";

   prefix aps;

   import junos-common-ddl-extensions {
     prefix junos;
     revision-date 2024-01-01;
   }

   import junos-common-types {
     prefix jt;
     revision-date 2024-01-01;
   }

   organization "Juniper Networks, Inc.";

   contact "yang-support@juniper.net";

   description "Junos RPC YANG module for aps command(s)";

   revision 2024-01-01 {
     description "Junos: 24.4R1.11";
   }

   rpc get-aps-information {
     description "Show Automatic Protection Switching information";
     junos:command "show aps";
     input {
       leaf level {
         junos:cli-feature "nokeyword";
         default "brief";
         type enumeration {
           enum "brief" {
             description "Display brief output (default)";
           }
           enum "detail" {
             description "Display detailed output";
           }
           enum "extensive" {
             description "Display extensive output";
           }
           enum "summary" {
             description "Display summary output";
           }
         }
       }
     }
     output {
       container aps-interface-information {
         uses aps-interface-information-block;
       }
     }
   }
   rpc get-aps-interface-information {
     description "Show an APS interface";
     junos:command "show aps interface";
     input {
       leaf intf_name {
         description "Interface name";
         junos:cli-feature "nokeyword";
         type string;
         mandatory true;
       }
     }
     output {
       container aps-interface-information {
         uses aps-interface-information-block;
       }
     }
   }
   rpc get-aps-group-information {
     description "Show an APS group";
     junos:command "show aps group";
     input {
       leaf group_name {
         description "Group name";
         junos:cli-feature "nokeyword";
         type string;
         mandatory true;
       }
     }
     output {
       container aps-interface-information {
         uses aps-interface-information-block;
       }
     }
   }
   grouping command-forwarding {
     choice chassis-selector {
       case case_1 {
         leaf all-chassis {
           description "All chassis";
           type empty;
         }
       }
       case case_2 {
         leaf all-lcc {
           description "All LCC chassis";
           type empty;
         }
       }
       case case_3 {
         leaf scc {
           description "SCC";
           type empty;
         }
       }
       case case_4 {
         leaf sfc {
           description "SFC";
           type union {
             type string {
               pattern "<.*>|$.*";
             }
             type uint32;
           }
         }
       }
       case case_5 {
         leaf lcc {
           description "Specific LCC";
           type union {
             type string {
               pattern "<.*>|$.*";
             }
             type uint32;
           }
         }
       }
       case case_6 {
         leaf node {
           description "Specific node";
           type string;
         }
       }
       case case_7 {
         leaf bsys {
           description "Base system";
           type empty;
         }
       }
       case case_8 {
         leaf gnf {
           description "Specific guest network function";
           type union {
             type string {
               pattern "<.*>|$.*";
             }
             type uint32 {
               range "1 .. 10";
             }
           }
         }
       }
       case case_9 {
         leaf all-gnfs {
           description "All guest network functions";
           type empty;
         }
       }
       case case_10 {
         leaf all-system {
           description "All system (BSYS and GNFs)";
           type empty;
         }
       }
       case case_11 {
         leaf server {
           description "Specific server slot";
           type union {
             type string {
               pattern "<.*>|$.*";
             }
             type uint32 {
               range "0 .. 1";
             }
           }
         }
       }
       case case_12 {
         leaf all-servers {
           description "All servers";
           type empty;
         }
       }
       case case_13 {
         leaf vnf {
           description "Specific virtual-network-function";
           type string;
         }
       }
       case case_14 {
         leaf all-vnfs {
           description "All virtual-network-functions";
           type empty;
         }
       }
     }
     choice re-selector {
       case case_1 {
         leaf re0 {
           description "RE0";
           type empty;
         }
       }
       case case_2 {
         leaf re1 {
           description "RE1";
           type empty;
         }
       }
       case case_3 {
         leaf routing-engine {
           description "Specific routing engine";
           type enumeration {
             enum "local" {
               description "Local routing engine";
             }
             enum "other" {
               description "Other routing engine";
             }
             enum "master" {
               description "Master routing engine";
             }
             enum "backup" {
               description "Backup routing engine";
             }
             enum "both" {
               description "Both routing engines";
             }
           }
         }
       }
     }
     choice lr-selector {
       case case_1 {
         leaf logical-system {
           description "Name of logical system, or 'all'";
           type string;
         }
       }
     }
     choice tenant-selector {
       case case_1 {
         leaf tenant {
           description "Name of tenant, or 'all'";
           type string;
         }
       }
     }
     choice vc-selector {
       case case_1 {
         leaf local {
           description "Local virtual chassis member";
           type empty;
         }
       }
       case case_2 {
         leaf all-members {
           description "All virtual chassis members";
           type empty;
         }
       }
       case case_3 {
         leaf member {
           description "Specific virtual chassis member which is master";
           type union {
             type string {
               pattern "<.*>|$.*";
             }
             type uint32;
           }
         }
       }
     }
   }
   grouping aps-interface-information-block {
     container aps-interface {
       description "Information about an Automatic Protection Switching interface";
       leaf aps-interface-name {
         type string;
         description "Name of the interface";
       }
       leaf aps-interface-group {
         type string;
         description "Name of the interface group";
       }
       leaf aps-interface-circuit-type {
         type string;
         description "Type of the circuit";
       }
       leaf aps-interface-circuit-state {
         type string;
         description "State of the circuit";
       }
       leaf aps-interface-state {
         type string;
         description "State of the interface";
       }
       leaf aps-config-state {
         type string;
         description "State of config";
       }
       leaf aps-config-state-circuit {
         type string;
         description "State of circuit config";
       }
       leaf aps-neighbor {
         type string;
         description "Neighbor address";
       }
       leaf aps-adjacent-state {
         type string;
         description "Adjacent state";
       }
       leaf aps-neighbor-select-state {
         type string;
         description "Neighbor interface state";
       }
       leaf aps-time-remaining {
         type string;
         description "Remaining time";
       }
       leaf aps-channel-state {
         type string;
         description "State of the channel";
       }
       leaf aps-annex-b {
         type string;
         description "Annex-b mode";
       }
       leaf aps-loop-circuit-type {
         type string;
         description "Loop circuit type";
       }
       leaf aps-loop-circuit-name {
         type string;
         description "Loop circuit name";
       }
       leaf aps-pair-interface-name {
         type string;
         description "Paired interface name";
       }
       leaf aps-pair-group-name {
         type string;
         description "Paired group name";
       }
       leaf aps-local-mode {
         type string;
         description "APS local mode";
       }
       leaf aps-neighbor-mode {
         type string;
         description "APS neighbor mode";
       }
       leaf aps-request-k1 {
         type string;
         description "Request K1 value";
       }
       leaf aps-receive-k1 {
         type string;
         description "Receive K1 value";
       }
       leaf aps-transmit-k1 {
         type string;
         description "Transmit K1 value";
       }
       leaf aps-neighbor-k1 {
         type string;
         description "Neighbor K1 value";
       }
       leaf aps-request-k2 {
         type string;
         description "Request K2 value";
       }
       leaf aps-receive-k2 {
         type string;
         description "Receive K2 value";
       }
       leaf aps-transmit-k2 {
         type string;
         description "Transmit K2 value";
       }
       leaf aps-neighbor-paired-request {
         type string;
         description "Neighbor paired switch request";
       }
       leaf aps-revert-time {
         type string;
         description "APS revert time";
       }
       leaf aps-neighbor-revert-time {
         type string;
         description "Neighbor revert time";
       }
       leaf aps-wait-to-restore-time {
         type string;
         description "APS annex-b wait to restore time";
       }
       leaf aps-neighbor-wait-to-restore-time {
         type string;
         description "APS annex-b neighbor wait to restore time";
       }
       leaf aps-remaining-revert-time {
         type string;
         description "Remaining revert time";
       }
       leaf aps-remaining-wait-to-restore-time {
         type string;
         description "Remaining wait to restore time";
       }
       leaf aps-remaining-forced-revert-time {
         type string;
         description "Remaining forced revert time";
       }
       leaf aps-remaining-hello-timer {
         type string;
         description "Remaining hello timer";
       }
       leaf aps-remaining-update-timer {
         type string;
         description "Remaining update timer";
       }
       leaf aps-remaining-holddown-timer {
         type string;
         description "Remaining holddown timer";
       }
     }
   }
 }
