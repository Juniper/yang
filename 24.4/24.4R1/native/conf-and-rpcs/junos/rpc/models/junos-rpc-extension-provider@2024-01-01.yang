/*
 * Copyright (c) 2025 Juniper Networks, Inc.
 * All rights reserved.
 */
 module junos-rpc-extension-provider {
   namespace "http://yang.juniper.net/junos/rpc/extension-provider";

   prefix extension-provider;

   import junos-common-types {
     prefix jt;
     revision-date 2024-01-01;
   }

   organization "Juniper Networks, Inc.";

   contact "yang-support@juniper.net";

   description "Junos RPC YANG module for extension-provider command(s)";

   revision 2024-01-01 {
     description "Junos: 24.4R1.11";
   }

   rpc get-mspinfo-packages {
     description "Show packages loaded on the extension provider PIC";
     input {
       leaf detail {
         type empty;
       }
       leaf interface {
         description "Name of extension provider interface";
         type string;
       }
     }
     output {
       container mspinfo-raw-output {
         uses mspinfo-raw-output-block;
       }
     }
   }
   rpc get-mspinfo-processes {
     description "Show system process table on the extension provider PIC";
     input {
       leaf detail {
         description "Display detailed output";
         type empty;
       }
       leaf wide {
         description "Display information even if wider than 80 columns";
         type empty;
       }
       leaf interface {
         description "Name of extension provider interface";
         type string;
       }
     }
     output {
       container mspinfo-raw-output {
         uses mspinfo-raw-output-block;
       }
     }
   }
   rpc get-mspinfo-processes-brief {
     description "Display brief output";
     input {
       leaf interface {
         description "Name of extension provider interface";
         type string;
       }
     }
     output {
       container mspinfo-raw-output {
         uses mspinfo-raw-output-block;
       }
     }
   }
   rpc get-mspinfo-processes-extensive {
     description "Display brief output";
     input {
       leaf interface {
         description "Name of extension provider interface";
         type string;
       }
     }
     output {
       container mspinfo-raw-output {
         uses mspinfo-raw-output-block;
       }
     }
   }
   rpc get-mspinfo-connections {
     description "Show connection activity on the extension provider PIC";
     input {
       leaf protocol {
         type enumeration {
           enum "inet" {
             description "Display IPv4 connections";
           }
           enum "inet6" {
             description "Display IPv6 connections";
           }
         }
       }
       leaf extensive {
         description "Display extensive output";
         type empty;
       }
       leaf show-routing-instances {
         description "Display routing instances";
         type empty;
       }
       leaf interface {
         description "Name of extension provider interface";
         type string;
       }
     }
     output {
       container mspinfo-raw-output {
         uses mspinfo-raw-output-block;
       }
     }
   }
   rpc get-mspinfo-virtual-memory {
     description "Show kernel dynamic memory usage on the extension provider PIC";
     input {
       leaf interface {
         description "Name of extension provider interface";
         type string;
       }
     }
     output {
       container mspinfo-raw-output {
         uses mspinfo-raw-output-block;
       }
     }
   }
   rpc get-mspinfo-uptime {
     description "Show uptime on the extension provider PIC";
     input {
       leaf interface {
         description "Name of extension provider interface";
         type string;
       }
     }
     output {
       container mspinfo-raw-output {
         uses mspinfo-raw-output-block;
       }
     }
   }
   grouping command-forwarding {
     leaf no-forwarding {
       description "No forwarding";
       type empty;
     }
     choice chassis-selector {
       case case_1 {
         leaf all-chassis {
           description "All chassis";
           type empty;
         }
       }
       case case_2 {
         leaf all-lcc {
           description "All LCC chassis";
           type empty;
         }
       }
       case case_3 {
         leaf scc {
           description "SCC";
           type empty;
         }
       }
       case case_4 {
         leaf sfc {
           description "SFC";
           type union {
             type string {
               pattern "<.*>|$.*";
             }
             type uint32;
           }
         }
       }
       case case_5 {
         leaf lcc {
           description "Specific LCC";
           type union {
             type string {
               pattern "<.*>|$.*";
             }
             type uint32;
           }
         }
       }
       case case_6 {
         leaf node {
           description "Specific node";
           type string;
         }
       }
       case case_7 {
         leaf bsys {
           description "Base system";
           type empty;
         }
       }
       case case_8 {
         leaf gnf {
           description "Specific guest network function";
           type union {
             type string {
               pattern "<.*>|$.*";
             }
             type uint32 {
               range "1 .. 10";
             }
           }
         }
       }
       case case_9 {
         leaf all-gnfs {
           description "All guest network functions";
           type empty;
         }
       }
       case case_10 {
         leaf all-system {
           description "All system (BSYS and GNFs)";
           type empty;
         }
       }
       case case_11 {
         leaf server {
           description "Specific server slot";
           type union {
             type string {
               pattern "<.*>|$.*";
             }
             type uint32 {
               range "0 .. 1";
             }
           }
         }
       }
       case case_12 {
         leaf all-servers {
           description "All servers";
           type empty;
         }
       }
       case case_13 {
         leaf vnf {
           description "Specific virtual-network-function";
           type string;
         }
       }
       case case_14 {
         leaf all-vnfs {
           description "All virtual-network-functions";
           type empty;
         }
       }
     }
     choice re-selector {
       case case_1 {
         leaf re0 {
           description "RE0";
           type empty;
         }
       }
       case case_2 {
         leaf re1 {
           description "RE1";
           type empty;
         }
       }
       case case_3 {
         leaf routing-engine {
           description "Specific routing engine";
           type enumeration {
             enum "local" {
               description "Local routing engine";
             }
             enum "other" {
               description "Other routing engine";
             }
             enum "master" {
               description "Master routing engine";
             }
             enum "backup" {
               description "Backup routing engine";
             }
             enum "both" {
               description "Both routing engines";
             }
           }
         }
       }
     }
     choice lr-selector {
       case case_1 {
         leaf logical-system {
           description "Name of logical system, or 'all'";
           type string;
         }
       }
     }
     choice tenant-selector {
       case case_1 {
         leaf tenant {
           description "Name of tenant, or 'all'";
           type string;
         }
       }
     }
     choice vc-selector {
       case case_1 {
         leaf local {
           description "Local virtual chassis member";
           type empty;
         }
       }
       case case_2 {
         leaf all-members {
           description "All virtual chassis members";
           type empty;
         }
       }
       case case_3 {
         leaf member {
           description "Specific virtual chassis member which is master";
           type union {
             type string {
               pattern "<.*>|$.*";
             }
             type uint32;
           }
         }
       }
     }
   }
   grouping mspinfo-raw-output-block {
     leaf interface-name {
       type string;
       description "Name of the adaptive services interface";
     }
     leaf raw-output {
       type string;
       description "Raw Output Field";
     }
   }
 }
