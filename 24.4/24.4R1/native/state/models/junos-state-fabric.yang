module junos-state-fabric {
  yang-version 1.1;
  namespace "http://yang.juniper.net/junos/state/fabric";
  prefix js-fab;

  import junos-base-extensions {
    prefix junos-base;
  }

  import junos-state {
    prefix js;
  }

  import junos-types {
    prefix jt;
  }

  organization
    "Juniper Networks, Inc.";

  contact
    "Juniper Networks, Inc.

     1133 Innovation Way
     Sunnyvale, CA 94089

     +1 888 314-5822

     E-mail: yang-support@juniper.net";

  description
    "This module contains a collection of top level nodes for JUNOS
     fabric state data.

     Copyright (c) 2023 Juniper Networks, Inc.
     All rights reserved.";

  revision 2023-12-08 {
    description
      "Initial revision";
    reference "0.1.0";
  }

  junos-base:version "0.1.0";

  grouping fabric-path {
    description
      "Grouping for the list of fabric paths in system";

    container fabric-paths {
      description
        "Encapsulating container for the list of fabric path
         references";

      list fabric-path {
        key plane-id;
        description
          "List of fabric path references";

        leaf plane-id {
          type uint32;
          description
            "Represents fabric plane number";
        }

        leaf plane-state {
          type enumeration {
            enum offline {
              value 1;
              description
                "Plane state is offline";
            }

            enum online {
              value 2;
              description
                "Plane state is online";
            }

            enum fault {
              value 3;
              description
                "Plane state is fault";
            }

            enum offline-transition {
              value 4;
              description
                "Plane state is offline transition";
            }
          }
          description
            "Represents fabric plane state";
        }

        leaf link-error {
          type boolean;
          description
            "Represents link error on fabric plane";
        }

        leaf link-training-failure {
          type boolean;
          description
            "Represents link training failure on fabric plane";
        }

        leaf reachability-error-local {
          type boolean;
          description
           "Represents local reachability errors on fabric plane";
        }

        leaf reachability-error-remote {
          type boolean;
          description
            "Represents remote reachability errors on fabric plane";
        }

        leaf plane-uptime {
          type jt:absolute-time-seconds;
          description
            "Represents fabric plane uptime in seconds";
        }
      }
    }
  }

  grouping fabric-link {
    description
      "Grouping for the list of fabric links in system";

    container fabric-links {
      description
        "Encapsulating container for the list of fabric link
         references";

      list fabric-link {
        key name;
        description
          "List of fabric link references";

        leaf name {
          type string;
          description
            "Represents an unique fabric link in the system";
        }

        leaf link-direction {
          type enumeration {
            enum in-link {
              value 1;
              description
                "Fabric in-link";
            }

            enum out-link {
              value 2;
              description
                "Fabric out-link";
            }
          }
          description
            "Represents fabric link direction in the system";
        }

        leaf operational-state {
          type enumeration {
            enum offline {
              value 1;
              description
                "Link state is offline";
            }

            enum online {
              value 2;
              description
                "Link state is online";
            }

            enum fault {
              value 3;
              description
                "Link state is fault";
            }

            enum offline-transition {
              value 4;
              description
                "Link state is offline transition";
            }

            enum online-transition {
              value 5;
              description
                "Link state is online transition";
            }
          }
          description
            "Represents fabric link operational state in the system";
        }

        leaf self-link-name {
          type string;
          description
            "Represents Fabric (Self) link name in the system";
        }

        leaf peer-link-name {
          type string;
          description
            "Represents Fabric (Peer) link name in the system";
        }

        leaf self-asic-name {
          type string;
          description
            "Represents Fabric (Self) ASIC name in the system";
        }

        leaf peer-asic-name {
          type string;
          description
            "Represents Fabric (Peer) ASIC name in the system";
        }
      }
    }
  }

  grouping fabric-top {
    description
      "Top-level grouping for fabric state data";

    container fabric {
      description
        "Container for fabric state";

      uses fabric-path;
      uses fabric-link;
    }
  }

  augment "/js:state" {
    description
      "Adds fabric domain to system state";

    uses fabric-top;
  }
}
