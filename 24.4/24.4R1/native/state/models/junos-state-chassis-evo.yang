module junos-state-chassis-evo {
  yang-version 1.1;
  namespace "http://yang.juniper.net/junos/state/chassis/evo";
  prefix js-chas-evo;

  import junos-extensions {
    prefix jx;
  }

  import junos-state {
    prefix js;
  }

  import ietf-yang-types {
    prefix yang;
  }

  import junos-state-chassis {
    prefix js-chas;
  }

  organization
    "Juniper Networks, Inc.";

  contact
    "Juniper Networks, Inc.

     1133 Innovation Way
     Sunnyvale, CA 94089

     +1 888 314-5822

     E-mail: yang-support@juniper.net";

  description
    "This module contains a collection of top level nodes for JUNOS
     evolved chassis state data.

     Copyright (c) 2024 Juniper Networks, Inc.
     All rights reserved.";

  revision 2024-08-02 {
    description
      "Initial revision";
    reference "0.1.0";
  }

  jx:version "0.1.0";

  grouping chassis-evo-top {
    description
      "Top-level grouping for chassis state data in Junos evolved";

    container inotify {
      description
        "Container for inotify data in a given node. This is
         Linux specific.";

      container user-watches {
        description
          "Container for per node inotify user watches";

        leaf used {
          type yang:gauge32;
          description
            "Number of user watches being used in this node";
        }

        leaf max {
          type uint32;
          description
            "Maximum number of user watches in this node";
        }
      }
    }
  }

  grouping chassis-process-evo-top {
    description
      "Grouping for per-process inotify state data";

    container inotify {
      description
        "Container for per process file system notification data";

      container user-watches {
        description
          "Container for per process inotify user watches";

        leaf used {
          type yang:gauge32;
          description
            "Number of user watches in use by this process";
        }
      }
    }
  }

  augment "/js:state/js-chas:chassis/js-chas:modules/js-chas:module" +
          "/js-chas:kernel" {
    description
      "Augments kernel container with Junos evolved specific data";

    uses chassis-evo-top;
  }

  augment "/js:state/js-chas:chassis/js-chas:modules/js-chas:module" +
          "/js-chas:processes/js-chas:process" {
    description
      "Augments process container with Junos evolved specific data";

    uses chassis-process-evo-top;
  }
}
