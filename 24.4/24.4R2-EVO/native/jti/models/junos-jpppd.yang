module junos-jpppd {
  yang-version 1;
  namespace "http://juniper.net/yang/jpppd";
  prefix junos-jpppd;

  organization
    "Juniper Networks Inc.";
  contact
    "Juniper Networks, Inc.

     1133 Innovation Way
     Sunnyvale, CA

     +1 888 314-5822

     E-mail: yang-support@juniper.net";
  description
    "Juniper Networks definition of Junos native jpppd yang model";

  revision 2017-01-01 {
    description
      "Initial revision";
  }

  grouping ppp-stats-group {
    description
      "The set of statistics associated with the PPP module";
    leaf ppp-stats-total-subscriber-sessions {
      description
        "The total number of subscriber sessions on an interface";
      type uint32;
    }
    leaf ppp-stats-sessions-disable-phase {
      description
        "Number of PPP sessions disabled where the link is either administratively or physically down";
      type uint32;
    }
    leaf ppp-stats-sessions-establish-phase {
      description
        "Number of PPP sessions in establish phase";
      type uint32;
    }
    leaf ppp-stats-sessions-network-phase {
      description
        "Number of PPP sessions in the network phase";
      type uint32;
    }
    leaf ppp-stats-sessions-authenticate-phase {
      description
        "Number of PPP sessions in authenticate phase";
      type uint32;
    }
  }

  grouping jpppd-top {
    description
      "Juniper Networks native jpppd statistics collection";
    container junos {
      description
        "All native jpppd statistics for Junos";
      config false;
      container system {
        description
          "Container for system";
        container subscriber-management {
          description
            "Subscriber management collection";
          container client-protocols {
            description
              "Protocol collection";
            container ppp {
              description
                "PPP Protocol";
              container statistics {
                description
                  "Container for statistics";
                uses ppp-stats-group;
              }
            }
          }
        }
      }
    }
  }

  uses jpppd-top;
}
