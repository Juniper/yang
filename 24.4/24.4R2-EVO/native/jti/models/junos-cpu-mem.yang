module junos-cpu-mem {

    yang-version "1";

    // namespace
    namespace "http://juniper.net/yang/junos-cpu-mem";

    prefix "junos-cpu-mem";

    // meta
    organization "Juniper Networks";

    contact
      "Juniper Networks, Inc.

       1133 Innovation Way
       Sunnyvale, CA 94089

       +1 888 314-5822

       E-mail: yang-support@juniper.net";

    description
        "This module provides data definitions for exporting cpu mem Stats
        ";

    revision 2023-08-08 {
      description
        "Initial revision.";
      reference "0.1.0";
    }

    container junos {
        config false;
        description "JunOS OS";

        container system {
            description "Junos System";

            list linecard {
                description "Contains PFE resources";

                container cpu {
                    description "cpu sensor data";

                    container memory {
                        description "cpu memory data";
                    }
                }
            }
        }
    }
}
