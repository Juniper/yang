/*
 * Copyright (c) 2025 Juniper Networks, Inc.
 * All rights reserved.
 */
 module junos-conf-bridge-domains {
   namespace "http://yang.juniper.net/junos/conf/bridge-domains";

   prefix jc-bridge-domains;

   import junos-common-types {
     prefix jt;
     revision-date 2024-01-01;
   }

   import junos-conf-root {
     prefix jc;
     revision-date 2024-01-01;
   }

   organization "Juniper Networks, Inc.";

   contact "yang-support@juniper.net";

   description "Junos bridge-domains configuration module";

   revision 2024-01-01 {
     description "Junos: 24.4R2.16-EVO";
   }

   augment /jc:configuration {
     uses bridge-domains-group;
   }
   augment /jc:configuration/jc:groups {
     uses bridge-domains-group;
   }
   grouping bridge-domains-group {
     container bridge-domains {
       description "Bridge domain configuration";
       uses apply-advanced;
       list domain {
         key name;
         uses juniper-bridge-domains;
       }
     }
   }
   grouping apply-advanced {
     description "Apply advanced configuration logic";
     leaf-list apply-groups {
       ordered-by user;
       description "Groups from which to inherit configuration data";
       type string;
     }
     leaf-list apply-groups-except {
       ordered-by user;
       description "Don't inherit configuration data from these groups";
       type string;
     }
     list apply-macro {
       key name;
       ordered-by user;
       description "Macro and parameters for commit script expansion";
       uses apply-macro-type;
     }
   }
   grouping apply-macro-type {
     description "Macro data for commit-script expansion";
     leaf name {
       description "Name of the macro to be expanded";
       type string;
     }
     list data {
       key name;
       uses macro-data-type;
     }
   }
   grouping juniper-bridge-domains {
     description "Bridge domains";
     leaf name {
       description "Bridge domain name";
       type string {
       }
     }
     uses apply-advanced;
     leaf description {
       description "Text description of bridge domain";
       type string {
       }
     }
     leaf domain-type {
       description "Type of bridge domain";
       type enumeration {
         enum "bridge" {
           description "Forwarding instance";
         }
       }
     }
     choice vlan_choice {
       case case_1 {
         leaf vlan-id {
           description "IEEE 802.1q VLAN identifier for bridging domain";
           type string;
         }
       }
       case case_2 {
         container vlan-tags {
           presence "enable vlan-tags";
           description "IEEE 802.1q VLAN tags for bridging domain";
           leaf outer {
             description "[tpid.]vlan-id, tpid format is 0xNNNN and is optional";
             type string {
             }
           }
           leaf inner {
             description "[tpid.]vlan-id, tpid format is 0xNNNN and is optional";
             type string {
             }
           }
         }
       }
       case case_3 {
         leaf-list vlan-id-list {
           description "Create bridge-domain for each of the vlan-id specified in the vlan-id-list";
           type jt:vlan-range;
         }
       }
     }
     leaf-list isid-list {
       ordered-by user;
       description "Create bridge-domain for isid (Valid isid:256..16777214)";
       type string;
     }
     leaf vlan-id-scope-local {
       description "Enable the scope of vlan-id local to avoid transmitting vlan tagged packets";
       type empty;
     }
     leaf service-id {
       description "Service id required if bridge-domain is of type MC-AE and vlan-id all or vlan-id none or vlan-tags";
       type union {
         type string {
           pattern "<.*>|$.*";
         }
         type uint32 {
           range "1 .. 65535";
         }
       }
     }
     leaf domain-id {
       description "Domain-id for auto derived Route Target";
       type union {
         type string {
           pattern "<.*>|$.*";
         }
         type uint32 {
           range "1 .. 15";
         }
       }
     }
     leaf no-local-switching {
       description "Disable local switching within CE-facing interfaces";
       type empty;
     }
     leaf mcae-mac-synchronize {
       description "Enable IRB MAC synchronization in this bridge domain";
       type empty;
     }
     leaf mcae-mac-flush {
       description "Enable MCAE MAC flush in a/s mode for a bridge domain on MCAE link up";
       type empty;
     }
     leaf irb-enhanced-scale {
       description "Enhanced IRB ARP and ND scale";
       type empty;
     }
     leaf no-irb-layer-2-copy {
       description "Disable transmission of layer-2 copy of packets of irb routing-interface";
       type empty;
     }
     leaf enable-mac-move-action {
       description "Enable blocking action due to mac-move in this Bridge Domain";
       type empty;
     }
     list interface {
       key name;
       ordered-by user;
       description "Interface name for this bridge domain";
       leaf name {
         type string;
       }
       uses apply-advanced;
       leaf protect-interface {
         description "Name of protect interface";
         type union {
           type jt:interface-name;
           type string {
             pattern "<.*>|$.*";
           }
         }
       }
     }
     leaf routing-interface {
       description "Routing interface name for this bridge-domain";
       type union {
         type jt:interface-unit;
         type string {
           pattern "<.*>|$.*";
         }
       }
     }
     container forwarding-options {
       description "Forwarding options configuration";
       uses juniper-bridge-forwarding-options;
     }
     container bridge-options {
       description "Bridge domain configuration";
       uses juniper-protocols-bd;
     }
     container protocols {
       presence "enable protocols";
       uses apply-advanced;
       container igmp-snooping {
         description "IGMP snooping configuration";
         presence "enable igmp-snooping";
         uses juniper-bd-protocols-igmp-snooping;
       }
       container mld-snooping {
         description "MLD snooping configuration";
         presence "enable mld-snooping";
         uses juniper-bd-protocols-mld-snooping;
       }
     }
     container vxlan {
       description "VXLAN options";
       uses apply-advanced;
       leaf ovsdb-managed {
         description "Bridge-domain is managed remotely via VXLAN OVSDB Controller";
         type empty;
       }
       leaf vni {
         description "VXLAN identifier";
         type union {
           type string {
             pattern "<.*>|$.*";
           }
           type uint32 {
             range "0 .. 16777214";
           }
         }
       }
       leaf translation-vni {
         description "Translated VXLAN identifier";
         type union {
           type string {
             pattern "<.*>|$.*";
           }
           type uint32 {
             range "1 .. 16777214";
           }
         }
       }
       leaf multicast-group {
         description "Multicast group registered for VXLAN segment";
         type jt:ipv4addr;
       }
       leaf encapsulate-inner-vlan {
         description "Retain inner VLAN in the packet";
         type empty;
       }
       leaf decapsulate-accept-inner-vlan {
         description "Accept VXLAN packets with inner VLAN";
         type empty;
       }
       leaf unreachable-vtep-aging-timer {
         description "Unreachable VXLAN tunnel endpoint removal timer";
         units "seconds";
         type union {
           type string {
             pattern "<.*>|$.*";
           }
           type uint16 {
             range "300 .. 1800";
           }
         }
       }
       leaf destination-udp-port {
         description "VXLAN destination UDP port";
         default "4789";
         type union {
           type string {
             pattern "<.*>|$.*";
           }
           type uint16 {
             range "4789 .. 65535";
           }
         }
       }
       leaf ingress-node-replication {
         description "Enable ingress node replication";
         type empty;
       }
       leaf-list static-remote-vtep-list {
         description "Configure bridge domain specific static remote VXLAN tunnel endpoints";
         type jt:ipaddr;
         max-elements 1024;
       }
     }
     leaf isolated-vlan {
       description "Isolated VLAN ID for private vlan bridge domain";
       type union {
         type string {
           pattern "<.*>|$.*";
         }
         type uint32 {
           range "1 .. 4094";
         }
       }
     }
     leaf-list community-vlans {
       description "List of Community VLANs for private vlan bridge domain";
       type jt:vlan-range;
     }
     container proxy-mac {
       description "Proxy MAC settings";
       uses apply-advanced;
       leaf irb {
         description "Reply with virtual-gateway MAC or IRB MAC";
         type empty;
       }
       leaf proxy-mac-address {
         description "Reply with configured MAC for all requests";
         type jt:mac-unicast;
       }
     }
     container multicast-snooping-options {
       description "Multicast snooping option configuration";
       uses juniper-multicast-snooping-options;
     }
   }
   grouping juniper-bd-protocols-igmp-snooping {
     description "IGMP snooping options";
     uses apply-advanced;
     container traceoptions {
       description "Trace options for IGMP Snooping";
       uses apply-advanced;
       container file {
         description "Trace file options";
         leaf filename {
           description "Name of file in which to write trace information";
           type string {
             length "1 .. 1024";
           }
         }
         leaf replace {
           description "Replace trace file rather than appending to it";
           status deprecated;
           type empty;
         }
         leaf size {
           description "Maximum trace file size";
           type string;
         }
         leaf files {
           description "Maximum number of trace files";
           default "10";
           type union {
             type string {
               pattern "<.*>|$.*";
             }
             type uint32 {
               range "2 .. 1000";
             }
           }
         }
         leaf no-stamp {
           description "Do not timestamp trace file";
           status deprecated;
           type empty;
         }
         choice world-readable-choice {
           leaf world-readable {
             description "Allow any user to read the log file";
             type empty;
           }
           leaf no-world-readable {
             description "Don't allow any user to read the log file";
             type empty;
           }
         }
       }
       list flag {
         key name;
         ordered-by user;
         description "Tracing parameters";
         leaf name {
           type enumeration {
             enum "packets" {
               description "Trace all IGMP packets";
             }
             enum "query" {
               description "Trace IGMP membership query messages";
             }
             enum "report" {
               description "Trace membership report messages";
             }
             enum "leave" {
               description "Trace leave group messages (IGMPv2 only)";
             }
             enum "group" {
               description "Trace group operations";
             }
             enum "client-notification" {
               description "Trace notifications";
             }
             enum "host-notification" {
               description "Trace host notifications";
             }
             enum "route" {
               description "Trace routing information";
             }
             enum "normal" {
               description "Trace normal events";
             }
             enum "general" {
               description "Trace general events";
             }
             enum "state" {
               description "Trace state transitions";
             }
             enum "policy" {
               description "Trace policy processing";
             }
             enum "task" {
               description "Trace routing protocol task processing";
             }
             enum "timer" {
               description "Trace routing protocol timer processing";
             }
             enum "all" {
               description "Trace everything";
             }
           }
         }
         leaf send {
           description "Trace transmitted packets";
           type empty;
         }
         leaf receive {
           description "Trace received packets";
           type empty;
         }
         leaf detail {
           description "Trace detailed information";
           type empty;
         }
         leaf disable {
           description "Disable this trace flag";
           type empty;
         }
       }
     }
     leaf query-interval {
       description "When to send host query messages";
       default "125";
       units "seconds";
       type union {
         type string {
           pattern "<.*>|$.*";
         }
         type uint32 {
           range "1 .. 1024";
         }
       }
     }
     container l2-querier {
       description "Enable L2 querier mode";
       uses apply-advanced;
       leaf source-address {
         description "Source IP address to use for L2 querier";
         type jt:ipv4addr;
       }
     }
     leaf query-response-interval {
       description "How long to wait for a host query response";
       default "10";
       units "seconds";
       type string {
       }
     }
     leaf query-last-member-interval {
       description "When to send group query messages";
       default "1";
       units "seconds";
       type string {
       }
     }
     leaf robust-count {
       description "Expected packet loss on a subnet";
       default "2";
       type union {
         type string {
           pattern "<.*>|$.*";
         }
         type uint32 {
           range "2 .. 10";
         }
       }
     }
     leaf learn-pim-router {
       description "Learn PIM router interfaces from PIM hellos";
       type empty;
     }
     leaf immediate-leave {
       description "Enable immediate group leave on interfaces";
       type empty;
     }
     leaf evpn-ssm-reports-only {
       description "Accept and process only <s,g> reports of SSM groups";
       type empty;
     }
     leaf version {
       description "Set IGMP snooping version number";
       type union {
         type string {
           pattern "<.*>|$.*";
         }
         type uint8 {
           range "2 .. 3";
         }
       }
     }
     container proxy {
       presence "enable proxy";
       description "Enable proxy mode";
       uses apply-advanced;
       leaf source-address {
         description "Source IP address to use for proxy";
         type jt:ipv4addr;
       }
       leaf irb {
         description "Proxy IGMP reports to IRB";
         type empty;
       }
     }
     list interface {
       key name;
       ordered-by user;
       description "Interface options for IGMP";
       leaf name {
         description "Interface name";
         type union {
           type jt:interface-name;
           type string {
             pattern "<.*>|$.*";
           }
         }
       }
       uses apply-advanced;
       leaf multicast-router-interface {
         description "Enabling multicast-router-interface on the interface";
         type empty;
       }
       leaf immediate-leave {
         description "Enable immediate group leave on interfaces";
         type empty;
       }
       leaf host-only-interface {
         description "Enable interfaces to be treated as host-side interfaces";
         type empty;
       }
       leaf group-limit {
         description "Maximum number of (source,group) per interface";
         type union {
           type string {
             pattern "<.*>|$.*";
           }
           type uint16 {
             range "1 .. 65535";
           }
         }
       }
       container static {
         description "Static group or source membership";
         uses apply-advanced;
         list group {
           key name;
           ordered-by user;
           description "IP multicast group address";
           leaf name {
             description "IP multicast group address";
             type jt:ipv4addr;
           }
           uses apply-advanced;
           list source {
             key name;
             ordered-by user;
             description "IP multicast source address";
             leaf name {
               description "Source address of IP multicast data";
               type jt:ipv4addr;
             }
             uses apply-advanced;
           }
         }
       }
     }
     list pseudowire-remote-address {
       key name;
       ordered-by user;
       description "Pseudowire interface options for IGMP";
       leaf name {
         description "Pseudowire endpoint address";
         type jt:ipv4addr;
       }
       uses apply-advanced;
       leaf multicast-router-interface {
         description "Enabling multicast-router-interface on the interface";
         type empty;
       }
       leaf immediate-leave {
         description "Enable immediate group leave on interfaces";
         type empty;
       }
     }
     list vlan {
       key name;
       ordered-by user;
       description "Vlan options";
       leaf name {
         description "VLAN name";
         type string;
       }
       uses apply-advanced;
       leaf query-interval {
         description "When to send host query messages";
         units "seconds";
         type union {
           type string {
             pattern "<.*>|$.*";
           }
           type uint32 {
             range "1 .. 1024";
           }
         }
       }
       leaf query-response-interval {
         description "How long to wait for a host query response";
         units "seconds";
         type string {
         }
       }
       leaf query-last-member-interval {
         description "When to send group query messages";
         units "seconds";
         type string {
         }
       }
       leaf robust-count {
         description "Expected packet loss on a subnet";
         type union {
           type string {
             pattern "<.*>|$.*";
           }
           type uint32 {
             range "2 .. 10";
           }
         }
       }
       leaf immediate-leave {
         description "Enable immediate group leave on interfaces";
         type empty;
       }
       container proxy {
         presence "enable proxy";
         description "Enable proxy mode";
         uses apply-advanced;
         leaf source-address {
           description "Source IP address to use for proxy";
           type jt:ipv4addr;
         }
       }
       container l2-querier {
         description "Enable L2 querier mode";
         uses apply-advanced;
         leaf source-address {
           description "Source IP address to use for L2 querier";
           type jt:ipv4addr;
         }
       }
       leaf evpn-ssm-reports-only {
         description "Accept and process only <s,g> reports of SSM groups";
         type empty;
       }
       list interface {
         key name;
         ordered-by user;
         description "Interface options for IGMP";
         leaf name {
           description "Interface name";
           type union {
             type jt:interface-name;
             type string {
               pattern "<.*>|$.*";
             }
           }
         }
         uses apply-advanced;
         leaf multicast-router-interface {
           description "Enabling multicast-router-interface on the interface";
           type empty;
         }
         leaf immediate-leave {
           description "Enable immediate group leave on interfaces";
           type empty;
         }
         leaf host-only-interface {
           description "Enable interfaces to be treated as host-side interfaces";
           type empty;
         }
         leaf group-limit {
           description "Maximum number of (source,group) per interface";
           type union {
             type string {
               pattern "<.*>|$.*";
             }
             type uint16 {
               range "1 .. 65535";
             }
           }
         }
         container static {
           description "Static group or source membership";
           uses apply-advanced;
           list group {
             key name;
             ordered-by user;
             description "IP multicast group address";
             leaf name {
               description "IP multicast group address";
               type jt:ipv4addr;
             }
             uses apply-advanced;
             list source {
               key name;
               ordered-by user;
               description "IP multicast source address";
               leaf name {
                 description "Source address of IP multicast data";
                 type jt:ipv4addr;
               }
               uses apply-advanced;
             }
           }
         }
       }
       list pseudowire-remote-address {
         key name;
         ordered-by user;
         description "Pseudowire interface options for IGMP";
         leaf name {
           description "Pseudowire endpoint address";
           type jt:ipv4addr;
         }
         uses apply-advanced;
         leaf multicast-router-interface {
           description "Enabling multicast-router-interface on the interface";
           type empty;
         }
         leaf immediate-leave {
           description "Enable immediate group leave on interfaces";
           type empty;
         }
       }
       list qualified-vlan {
         key name;
         ordered-by user;
         description "VLAN options for qualified-learning";
         leaf name {
           description "VLAN ID of the learning-domain";
           type union {
             type string {
               pattern "<.*>|$.*";
             }
             type uint32 {
               range "0 .. 1023";
             }
           }
         }
         uses apply-advanced;
         leaf query-interval {
           description "When to send host query messages";
           units "seconds";
           type union {
             type string {
               pattern "<.*>|$.*";
             }
             type uint32 {
               range "1 .. 1024";
             }
           }
         }
         leaf query-response-interval {
           description "How long to wait for a host query response";
           units "seconds";
           type string {
           }
         }
         leaf query-last-member-interval {
           description "When to send group query messages";
           units "seconds";
           type string {
           }
         }
         leaf robust-count {
           description "Expected packet loss on a subnet";
           type union {
             type string {
               pattern "<.*>|$.*";
             }
             type uint32 {
               range "2 .. 10";
             }
           }
         }
         leaf immediate-leave {
           description "Enable immediate group leave on interfaces";
           type empty;
         }
         container proxy {
           presence "enable proxy";
           description "Enable proxy mode";
           uses apply-advanced;
           leaf source-address {
             description "Source IP address to use for proxy";
             type jt:ipv4addr;
           }
         }
         leaf evpn-ssm-reports-only {
           description "Accept and process only <s,g> reports of SSM groups";
           type empty;
         }
         list interface {
           key name;
           ordered-by user;
           description "Interface options for IGMP";
           leaf name {
             description "Interface name";
             type union {
               type jt:interface-name;
               type string {
                 pattern "<.*>|$.*";
               }
             }
           }
           uses apply-advanced;
           leaf multicast-router-interface {
             description "Enabling multicast-router-interface on the interface";
             type empty;
           }
           leaf immediate-leave {
             description "Enable immediate group leave on interfaces";
             type empty;
           }
           leaf host-only-interface {
             description "Enable interfaces to be treated as host-side interfaces";
             type empty;
           }
           leaf group-limit {
             description "Maximum number of (source,group) per interface";
             type union {
               type string {
                 pattern "<.*>|$.*";
               }
               type uint16 {
                 range "1 .. 65535";
               }
             }
           }
           container static {
             description "Static group or source membership";
             uses apply-advanced;
             list group {
               key name;
               ordered-by user;
               description "IP multicast group address";
               leaf name {
                 description "IP multicast group address";
                 type jt:ipv4addr;
               }
               uses apply-advanced;
               list source {
                 key name;
                 ordered-by user;
                 description "IP multicast source address";
                 leaf name {
                   description "Source address of IP multicast data";
                   type jt:ipv4addr;
                 }
                 uses apply-advanced;
               }
             }
           }
         }
         list pseudowire-remote-address {
           key name;
           ordered-by user;
           description "Pseudowire interface options for IGMP";
           leaf name {
             description "Pseudowire endpoint address";
             type jt:ipv4addr;
           }
           uses apply-advanced;
           leaf multicast-router-interface {
             description "Enabling multicast-router-interface on the interface";
             type empty;
           }
           leaf immediate-leave {
             description "Enable immediate group leave on interfaces";
             type empty;
           }
         }
       }
       leaf version {
         description "Set IGMP snooping version number";
         type union {
           type string {
             pattern "<.*>|$.*";
           }
           type uint8 {
             range "2 .. 3";
           }
         }
       }
       container traceoptions {
         description "Trace options for IGMP Snooping";
         uses apply-advanced;
         container file {
           description "Trace file options";
           leaf filename {
             description "Name of file in which to write trace information";
             type string {
               length "1 .. 1024";
             }
           }
           leaf replace {
             description "Replace trace file rather than appending to it";
             status deprecated;
             type empty;
           }
           leaf size {
             description "Maximum trace file size";
             type string;
           }
           leaf files {
             description "Maximum number of trace files";
             default "10";
             type union {
               type string {
                 pattern "<.*>|$.*";
               }
               type uint32 {
                 range "2 .. 1000";
               }
             }
           }
           leaf no-stamp {
             description "Do not timestamp trace file";
             status deprecated;
             type empty;
           }
           choice world-readable-choice {
             leaf world-readable {
               description "Allow any user to read the log file";
               type empty;
             }
             leaf no-world-readable {
               description "Don't allow any user to read the log file";
               type empty;
             }
           }
         }
         list flag {
           key name;
           ordered-by user;
           description "Tracing parameters";
           leaf name {
             type enumeration {
               enum "packets" {
                 description "Trace all IGMP packets";
               }
               enum "query" {
                 description "Trace IGMP membership query messages";
               }
               enum "report" {
                 description "Trace membership report messages";
               }
               enum "leave" {
                 description "Trace leave group messages (IGMPv2 only)";
               }
               enum "group" {
                 description "Trace group operations";
               }
               enum "client-notification" {
                 description "Trace notifications";
               }
               enum "route" {
                 description "Trace routing information";
               }
               enum "normal" {
                 description "Trace normal events";
               }
               enum "general" {
                 description "Trace general events";
               }
               enum "state" {
                 description "Trace state transitions";
               }
               enum "policy" {
                 description "Trace policy processing";
               }
               enum "task" {
                 description "Trace routing protocol task processing";
               }
               enum "timer" {
                 description "Trace routing protocol timer processing";
               }
               enum "all" {
                 description "Trace everything";
               }
             }
           }
           leaf send {
             description "Trace transmitted packets";
             type empty;
           }
           leaf receive {
             description "Trace received packets";
             type empty;
           }
           leaf detail {
             description "Trace detailed information";
             type empty;
           }
           leaf disable {
             description "Disable this trace flag";
             type empty;
           }
         }
       }
       leaf no-flood-to-multicast-router-interfaces {
         description "Don't flood multicast traffic to router interfaces";
         type empty;
       }
     }
     leaf no-flood-to-multicast-router-interfaces {
       description "Don't flood multicast traffic to router interfaces";
       type empty;
     }
   }
   grouping juniper-bd-protocols-mld-snooping {
     description "MLD snooping options";
     uses apply-advanced;
     container traceoptions {
       description "Trace options for MLD Snooping";
       uses apply-advanced;
       container file {
         description "Trace file options";
         leaf filename {
           description "Name of file in which to write trace information";
           type string {
             length "1 .. 1024";
           }
         }
         leaf replace {
           description "Replace trace file rather than appending to it";
           status deprecated;
           type empty;
         }
         leaf size {
           description "Maximum trace file size";
           type string;
         }
         leaf files {
           description "Maximum number of trace files";
           default "10";
           type union {
             type string {
               pattern "<.*>|$.*";
             }
             type uint32 {
               range "2 .. 1000";
             }
           }
         }
         leaf no-stamp {
           description "Do not timestamp trace file";
           status deprecated;
           type empty;
         }
         choice world-readable-choice {
           leaf world-readable {
             description "Allow any user to read the log file";
             type empty;
           }
           leaf no-world-readable {
             description "Don't allow any user to read the log file";
             type empty;
           }
         }
       }
       list flag {
         key name;
         ordered-by user;
         description "Tracing parameters";
         leaf name {
           type enumeration {
             enum "packets" {
               description "Trace all MLD packets";
             }
             enum "query" {
               description "Trace MLD membership query messages";
             }
             enum "report" {
               description "Trace membership report messages";
             }
             enum "leave" {
               description "Trace leave group messages (MLDv2 only)";
             }
             enum "group" {
               description "Trace group operations";
             }
             enum "client-notification" {
               description "Trace notifications";
             }
             enum "host-notification" {
               description "Trace host notifications";
             }
             enum "route" {
               description "Trace routing information";
             }
             enum "normal" {
               description "Trace normal events";
             }
             enum "general" {
               description "Trace general events";
             }
             enum "state" {
               description "Trace state transitions";
             }
             enum "policy" {
               description "Trace policy processing";
             }
             enum "task" {
               description "Trace routing protocol task processing";
             }
             enum "timer" {
               description "Trace routing protocol timer processing";
             }
             enum "all" {
               description "Trace everything";
             }
           }
         }
         leaf send {
           description "Trace transmitted packets";
           type empty;
         }
         leaf receive {
           description "Trace received packets";
           type empty;
         }
         leaf detail {
           description "Trace detailed information";
           type empty;
         }
         leaf disable {
           description "Disable this trace flag";
           type empty;
         }
       }
     }
     leaf query-interval {
       description "When to send host query messages";
       default "125";
       units "seconds";
       type union {
         type string {
           pattern "<.*>|$.*";
         }
         type uint32 {
           range "1 .. 1024";
         }
       }
     }
     container l2-querier {
       description "Enable L2 querier mode";
       uses apply-advanced;
       leaf source-address {
         description "Source IPv6 link local address to use for L2 querier";
         type jt:ipv6addr;
       }
     }
     leaf query-response-interval {
       description "How long to wait for a host query response";
       default "10";
       units "seconds";
       type string {
       }
     }
     leaf query-last-member-interval {
       description "When to send group query messages";
       default "1";
       units "seconds";
       type string {
       }
     }
     leaf robust-count {
       description "Expected packet loss on a subnet";
       default "2";
       type union {
         type string {
           pattern "<.*>|$.*";
         }
         type uint32 {
           range "2 .. 10";
         }
       }
     }
     leaf immediate-leave {
       description "Enable immediate group leave on interfaces";
       type empty;
     }
     leaf evpn-ssm-reports-only {
       description "Accept and process only <s,g> reports of SSM groups";
       type empty;
     }
     leaf version {
       description "Set MLD snooping version number";
       type union {
         type string {
           pattern "<.*>|$.*";
         }
         type uint8 {
           range "1 .. 2";
         }
       }
     }
     container proxy {
       description "Enable proxy mode";
       uses apply-advanced;
       leaf source-address {
         description "Source IPv6 link local address to use for proxy";
         type jt:ipv6addr;
       }
       leaf irb {
         description "Proxy IGMP reports to IRB";
         type empty;
       }
     }
     list interface {
       key name;
       ordered-by user;
       description "Interface options for MLD";
       leaf name {
         description "Interface name";
         type union {
           type jt:interface-name;
           type string {
             pattern "<.*>|$.*";
           }
         }
       }
       uses apply-advanced;
       leaf multicast-router-interface {
         description "Enabling multicast-router-interface on the interface";
         type empty;
       }
       leaf immediate-leave {
         description "Enable immediate group leave on interfaces";
         type empty;
       }
       leaf host-only-interface {
         description "Enable interfaces to be treated as host-side interfaces";
         type empty;
       }
       leaf group-limit {
         description "Maximum number of (source,group) per interface";
         type union {
           type string {
             pattern "<.*>|$.*";
           }
           type uint16 {
             range "1 .. 65535";
           }
         }
       }
       container static {
         description "Static group or source membership";
         uses apply-advanced;
         list group {
           key name;
           ordered-by user;
           description "IP multicast group address";
           leaf name {
             description "IP multicast group address";
             type jt:ipv6addr;
           }
           uses apply-advanced;
           list source {
             key name;
             ordered-by user;
             description "IP multicast source address";
             leaf name {
               description "Source address of IP multicast data";
               type jt:ipv6addr;
             }
             uses apply-advanced;
           }
         }
       }
     }
     list pseudowire-remote-address {
       key name;
       ordered-by user;
       description "Pseudowire interface options for MLD";
       leaf name {
         description "Pseudowire endpoint address";
         type jt:ipv4addr;
       }
       uses apply-advanced;
       leaf multicast-router-interface {
         description "Enabling multicast-router-interface on the interface";
         type empty;
       }
       leaf immediate-leave {
         description "Enable immediate group leave on interfaces";
         type empty;
       }
     }
     list vlan {
       key name;
       ordered-by user;
       description "Vlan options";
       leaf name {
         description "Vlan of the bridge-domain";
         type string;
       }
       uses apply-advanced;
       leaf query-interval {
         description "When to send host query messages";
         units "seconds";
         type union {
           type string {
             pattern "<.*>|$.*";
           }
           type uint32 {
             range "1 .. 1024";
           }
         }
       }
       leaf query-response-interval {
         description "How long to wait for a host query response";
         units "seconds";
         type string {
         }
       }
       leaf query-last-member-interval {
         description "When to send group query messages";
         units "seconds";
         type string {
         }
       }
       leaf robust-count {
         description "Expected packet loss on a subnet";
         type union {
           type string {
             pattern "<.*>|$.*";
           }
           type uint32 {
             range "2 .. 10";
           }
         }
       }
       leaf immediate-leave {
         description "Enable immediate group leave on interfaces";
         type empty;
       }
       container proxy {
         description "Enable proxy mode";
         uses apply-advanced;
         leaf source-address {
           description "Source IPv6 link local address to use for proxy";
           type jt:ipv6addr;
         }
       }
       container l2-querier {
         description "Enable L2 querier mode";
         uses apply-advanced;
         leaf source-address {
           description "Source IPv6 link local address to use for L2 querier";
           type jt:ipv6addr;
         }
       }
       leaf evpn-ssm-reports-only {
         description "Accept and process only <s,g> reports of SSM groups";
         type empty;
       }
       list interface {
         key name;
         ordered-by user;
         description "Interface options for MLD";
         leaf name {
           description "Interface name";
           type union {
             type jt:interface-name;
             type string {
               pattern "<.*>|$.*";
             }
           }
         }
         uses apply-advanced;
         leaf multicast-router-interface {
           description "Enabling multicast-router-interface on the interface";
           type empty;
         }
         leaf immediate-leave {
           description "Enable immediate group leave on interfaces";
           type empty;
         }
         leaf host-only-interface {
           description "Enable interfaces to be treated as host-side interfaces";
           type empty;
         }
         leaf group-limit {
           description "Maximum number of (source,group) per interface";
           type union {
             type string {
               pattern "<.*>|$.*";
             }
             type uint16 {
               range "1 .. 65535";
             }
           }
         }
         container static {
           description "Static group or source membership";
           uses apply-advanced;
           list group {
             key name;
             ordered-by user;
             description "IP multicast group address";
             leaf name {
               description "IP multicast group address";
               type jt:ipv6addr;
             }
             uses apply-advanced;
             list source {
               key name;
               ordered-by user;
               description "IP multicast source address";
               leaf name {
                 description "Source address of IP multicast data";
                 type jt:ipv6addr;
               }
               uses apply-advanced;
             }
           }
         }
       }
       list pseudowire-remote-address {
         key name;
         ordered-by user;
         description "Pseudowire interface options for MLD";
         leaf name {
           description "Pseudowire endpoint address";
           type jt:ipv4addr;
         }
         uses apply-advanced;
         leaf multicast-router-interface {
           description "Enabling multicast-router-interface on the interface";
           type empty;
         }
         leaf immediate-leave {
           description "Enable immediate group leave on interfaces";
           type empty;
         }
       }
       list qualified-vlan {
         key name;
         ordered-by user;
         description "VLAN options for qualified-learning";
         leaf name {
           description "VLAN ID of the learning-domain";
           type union {
             type string {
               pattern "<.*>|$.*";
             }
             type uint32 {
               range "0 .. 1023";
             }
           }
         }
         uses apply-advanced;
         leaf query-interval {
           description "When to send host query messages";
           units "seconds";
           type union {
             type string {
               pattern "<.*>|$.*";
             }
             type uint32 {
               range "1 .. 1024";
             }
           }
         }
         leaf query-response-interval {
           description "How long to wait for a host query response";
           units "seconds";
           type string {
           }
         }
         leaf query-last-member-interval {
           description "When to send group query messages";
           units "seconds";
           type string {
           }
         }
         leaf robust-count {
           description "Expected packet loss on a subnet";
           type union {
             type string {
               pattern "<.*>|$.*";
             }
             type uint32 {
               range "2 .. 10";
             }
           }
         }
         leaf immediate-leave {
           description "Enable immediate group leave on interfaces";
           type empty;
         }
         container proxy {
           description "Enable proxy mode";
           uses apply-advanced;
           leaf source-address {
             description "Source IPv6 link local address to use for proxy";
             type jt:ipv6addr;
           }
         }
         leaf evpn-ssm-reports-only {
           description "Accept and process only <s,g> reports of SSM groups";
           type empty;
         }
         list interface {
           key name;
           ordered-by user;
           description "Interface options for MLD";
           leaf name {
             description "Interface name";
             type union {
               type jt:interface-name;
               type string {
                 pattern "<.*>|$.*";
               }
             }
           }
           uses apply-advanced;
           leaf multicast-router-interface {
             description "Enabling multicast-router-interface on the interface";
             type empty;
           }
           leaf immediate-leave {
             description "Enable immediate group leave on interfaces";
             type empty;
           }
           leaf host-only-interface {
             description "Enable interfaces to be treated as host-side interfaces";
             type empty;
           }
           leaf group-limit {
             description "Maximum number of (source,group) per interface";
             type union {
               type string {
                 pattern "<.*>|$.*";
               }
               type uint16 {
                 range "1 .. 65535";
               }
             }
           }
           container static {
             description "Static group or source membership";
             uses apply-advanced;
             list group {
               key name;
               ordered-by user;
               description "IP multicast group address";
               leaf name {
                 description "IP multicast group address";
                 type jt:ipv6addr;
               }
               uses apply-advanced;
               list source {
                 key name;
                 ordered-by user;
                 description "IP multicast source address";
                 leaf name {
                   description "Source address of IP multicast data";
                   type jt:ipv6addr;
                 }
                 uses apply-advanced;
               }
             }
           }
         }
         list pseudowire-remote-address {
           key name;
           ordered-by user;
           description "Pseudowire interface options for MLD";
           leaf name {
             description "Pseudowire endpoint address";
             type jt:ipv4addr;
           }
           uses apply-advanced;
           leaf multicast-router-interface {
             description "Enabling multicast-router-interface on the interface";
             type empty;
           }
           leaf immediate-leave {
             description "Enable immediate group leave on interfaces";
             type empty;
           }
         }
       }
       leaf version {
         description "Set MLD snooping version number";
         type union {
           type string {
             pattern "<.*>|$.*";
           }
           type uint8 {
             range "1 .. 2";
           }
         }
       }
       leaf no-flood-to-multicast-router-interfaces {
         description "Don't flood multicast traffic to router interfaces";
         type empty;
       }
       container traceoptions {
         description "Trace options for MLD Snooping";
         uses apply-advanced;
         container file {
           description "Trace file options";
           leaf filename {
             description "Name of file in which to write trace information";
             type string {
               length "1 .. 1024";
             }
           }
           leaf replace {
             description "Replace trace file rather than appending to it";
             status deprecated;
             type empty;
           }
           leaf size {
             description "Maximum trace file size";
             type string;
           }
           leaf files {
             description "Maximum number of trace files";
             default "10";
             type union {
               type string {
                 pattern "<.*>|$.*";
               }
               type uint32 {
                 range "2 .. 1000";
               }
             }
           }
           leaf no-stamp {
             description "Do not timestamp trace file";
             status deprecated;
             type empty;
           }
           choice world-readable-choice {
             leaf world-readable {
               description "Allow any user to read the log file";
               type empty;
             }
             leaf no-world-readable {
               description "Don't allow any user to read the log file";
               type empty;
             }
           }
         }
         list flag {
           key name;
           ordered-by user;
           description "Tracing parameters";
           leaf name {
             type enumeration {
               enum "packets" {
                 description "Trace all MLD packets";
               }
               enum "query" {
                 description "Trace MLD membership query messages";
               }
               enum "report" {
                 description "Trace membership report messages";
               }
               enum "leave" {
                 description "Trace leave group messages (MLDv1 only)";
               }
               enum "group" {
                 description "Trace group operations";
               }
               enum "client-notification" {
                 description "Trace notifications";
               }
               enum "host-notification" {
                 description "Trace host notifications";
               }
               enum "route" {
                 description "Trace routing information";
               }
               enum "normal" {
                 description "Trace normal events";
               }
               enum "general" {
                 description "Trace general events";
               }
               enum "state" {
                 description "Trace state transitions";
               }
               enum "policy" {
                 description "Trace policy processing";
               }
               enum "task" {
                 description "Trace routing protocol task processing";
               }
               enum "timer" {
                 description "Trace routing protocol timer processing";
               }
               enum "all" {
                 description "Trace everything";
               }
             }
           }
           leaf send {
             description "Trace transmitted packets";
             type empty;
           }
           leaf receive {
             description "Trace received packets";
             type empty;
           }
           leaf detail {
             description "Trace detailed information";
             type empty;
           }
           leaf disable {
             description "Disable this trace flag";
             type empty;
           }
         }
       }
     }
     leaf no-flood-to-multicast-router-interfaces {
       description "Don't flood multicast traffic to router interfaces";
       type empty;
     }
   }
   grouping juniper-bridge-forwarding-options {
     uses apply-advanced;
     container filter {
       description "Filtering for bridge forwarding table";
       uses apply-advanced;
       leaf input {
         description "Name of input filter to apply for forwarded packets";
         type string;
       }
       leaf output {
         description "Name of output filter to apply for forwarded packets";
         type string;
       }
     }
     container flood {
       description "Filtering for bridge flood table";
       uses apply-advanced;
       leaf input {
         description "Name of input filter to apply for bridge flood packets";
         type string;
       }
     }
     container dhcp-relay {
       description "Dynamic Host Configuration Protocol relay configuration";
       status deprecated;
       uses jdhcp-relay-type;
     }
     container dhcp-security {
       description "Dynamic ARP Inspection configuration";
       presence "enable dhcp-security";
       uses jdhcp-security-type;
     }
   }
   grouping jdhcp-relay-type {
     description "Dynamic Host Configuration Protocol relay configuration";
     uses apply-advanced;
     container traceoptions {
       description "DHCP relay trace options";
       status deprecated;
       uses jdhcp-traceoptions-type;
     }
     container persistent-storage {
       description "Trigger to enable flat file storage";
       leaf automatic {
         description "Trigger automatically";
         type empty;
       }
     }
     leaf duplicate-clients-on-interface {
       description "Allow duplicate clients on different interfaces in a subnet";
       status deprecated;
       type empty;
     }
     container duplicate-clients-in-subnet {
       description "Allow duplicate clients in a subnet";
       uses jdhcp-duplicate-clients-in-subnet-type;
     }
     container interface-traceoptions {
       description "DHCP relay interface trace options";
       status deprecated;
       uses jdhcp-interface-traceoptions-type;
     }
     container dhcpv6 {
       description "DHCPv6 configuration";
       uses dhcpv6-relay-type;
     }
     leaf arp-inspection {
       description "Enable Dynamic ARP Inspection";
       type empty;
     }
     container forward-snooped-clients {
       description "Forward snooped (unicast) packets";
       choice interface-type {
         case case_1 {
           leaf configured-interfaces {
             description "Forward snooped (unicast) packets on configured interfaces";
             type empty;
           }
         }
         case case_2 {
           leaf non-configured-interfaces {
             description "Forward snooped (unicast) packets on non-configured interfaces";
             type empty;
           }
         }
         case case_3 {
           leaf all-interfaces {
             description "Forward snooped (unicast) packets on configured and non-configured interfaces";
             type empty;
           }
         }
       }
     }
     container authentication {
       description "DHCP authentication";
       uses authentication-type;
     }
     container liveness-detection {
       description "DHCP client liveness detection processing";
       uses dhcp-liveness-detection-type;
     }
     container dynamic-profile {
       description "Dynamic profile to use";
       uses dynamic-profile-type;
     }
     leaf service-profile {
       description "Dynamic profile to use for default service activation";
       type string {
         length "1 .. 128";
       }
     }
     leaf access-profile {
       description "Access profile to use for AAA services";
       type string {
         length "1 .. 128";
       }
     }
     container short-cycle-protection {
       description "Short cycle lockout configuration";
       leaf lockout-min-time {
         description "Short cycle lockout time in seconds";
         type union {
           type string {
             pattern "<.*>|$.*";
           }
           type uint32 {
             range "1 .. 86400";
           }
         }
       }
       leaf lockout-max-time {
         description "Short cycle lockout time in seconds";
         type union {
           type string {
             pattern "<.*>|$.*";
           }
           type uint32 {
             range "1 .. 86400";
           }
         }
       }
     }
     container overrides {
       description "DHCP override processing";
       presence "enable overrides";
       uses override-type;
     }
     container relay-option {
       description "DHCP option processing";
       presence "enable relay-option";
       uses dhcp-generic-v4-option;
     }
     container server-match {
       description "Server match processing";
       uses apply-advanced;
       container default-action {
         description "Server match default action";
         presence "enable default-action";
         uses server-match-action-choice;
       }
       list address {
         key name;
         description "Server address";
         leaf name {
           description "Server address for matching";
           type jt:ipv4prefix;
         }
         uses apply-advanced;
         choice server-match-action-choice {
           case case_1 {
             leaf forward-only {
               description "Forward without subscriber services when a match is made";
               type empty;
             }
           }
           case case_2 {
             leaf create-relay-entry {
               description "Create relay entry and allow subscriber services";
               type empty;
             }
           }
         }
       }
     }
     container relay-option-60 {
       description "DHCP option-60 processing";
       presence "enable relay-option-60";
       status deprecated;
       uses relay-option-60-type-top;
     }
     container relay-option-82 {
       description "DHCP option-82 processing";
       presence "enable relay-option-82";
       uses relay-option-82-type;
     }
     container forward-only {
       description "Forward DHCP packets without creating binding";
       presence "enable forward-only";
       uses forward-only-to-rc-type;
     }
     leaf description {
       description "Text description of servers";
       type string;
     }
     leaf maximum-hop-count {
       description "Maximum number of hops per packet";
       type union {
         type string {
           pattern "<.*>|$.*";
         }
         type uint32 {
           range "1 .. 16";
         }
       }
     }
     leaf minimum-wait-time {
       description "Minimum number of seconds before requests are forwarded";
       type union {
         type string {
           pattern "<.*>|$.*";
         }
         type uint32 {
           range "0 .. 30000";
         }
       }
     }
     leaf client-response-ttl {
       description "IP time-to-live value to set in responses to client";
       type union {
         type string {
           pattern "<.*>|$.*";
         }
         type uint32 {
           range "1 .. 255";
         }
       }
     }
     leaf source-ip-change {
       description "Use address of egress interface as source ip";
       type empty;
     }
     leaf forward-only-replies {
       description "Forward-only replies from server to appropriate logical-system:routing-instance based on options";
       type empty;
     }
     container server-group {
       description "Define a DHCP server group";
       uses server-group-type;
     }
     container active-server-group {
       description "Name of DHCP server group";
       uses dhcpv4-gbl-active-sg-type;
     }
     container route-suppression {
       description "Suppress access-internal and/or destination route addition";
       uses dhcp-route-suppression-type;
     }
     list group {
       key name;
       description "Define a DHCP group";
       uses dhcp-group;
     }
     list dual-stack-group {
       key name;
       description "Define a DHCP dual stack group";
       uses dhcp-dual-stack-group;
     }
     leaf no-snoop {
       description "Do not snoop DHCP packets";
       type empty;
     }
     leaf server-response-time {
       description "Number of seconds in a period of activity between the last server response and an unaswered request";
       default "0";
       type union {
         type uint32;
         type string {
           pattern "<.*>|$.*";
         }
       }
     }
     container lease-time-validation {
       presence "enable lease-time-validation";
       description "Configure lease time violation validation";
       uses apply-advanced;
       leaf lease-time-threshold {
         description "Threshold for lease time violation in seconds";
         units "seconds";
         type union {
           type string {
             pattern "<.*>|$.*";
           }
           type uint32 {
             range "60 .. 2147483647";
           }
         }
       }
       container violation-action {
         description "Lease time validation violation action";
         leaf drop {
           description "Drop dhcpv4 offer and ack packets";
           type empty;
         }
       }
     }
     container leasequery {
       description "DHCP leasequery configuration";
       presence "enable leasequery";
       uses relay-leasequery-type;
     }
     container bulk-leasequery {
       description "DHCP bulk leasequery configuration";
       presence "enable bulk-leasequery";
       uses relay-bulk-leasequery-v4-type;
     }
     container active-leasequery {
       description "DHCPv4 active leasequery configuration";
       presence "enable active-leasequery";
       uses active-leasequery-v4-type;
     }
     container remote-id-mismatch {
       description "DHCP client remote-id mismatch";
       presence "enable remote-id-mismatch";
       uses dhcp-remote-id-mismatch-type;
     }
   }
   grouping active-leasequery-v4-type {
     description "Configure active leasequery";
     uses apply-advanced;
     leaf topology-discover {
       description "Topology discovery";
       type empty;
     }
     list peer-address {
       key name;
       description "Server ip address";
       leaf name {
         description "Peer ip address";
         type jt:ipaddr;
       }
       uses apply-advanced;
     }
     list exclude-interface {
       key name;
       ordered-by user;
       description "Exclude interface participating in active leasequery";
       leaf name {
         description "Interface name";
         type union {
           type jt:interface-name;
           type string {
             pattern "<.*>|$.*";
           }
         }
       }
       uses apply-advanced;
     }
     leaf timeout {
       description "Read/write timeout in seconds";
       default "120";
       units "seconds";
       type union {
         type string {
           pattern "<.*>|$.*";
         }
         type uint32 {
           range "10 .. 3600";
         }
       }
     }
     leaf idle-timeout {
       description "Idle timeout in seconds";
       default "60";
       units "seconds";
       type union {
         type string {
           pattern "<.*>|$.*";
         }
         type uint32 {
           range "10 .. 3600";
         }
       }
     }
   }
   grouping authentication-type {
     description "DHCP authentication";
     uses apply-advanced;
     leaf password {
       description "Username password to use";
       type string {
         length "1 .. 64";
       }
     }
     container username-include {
       description "Add username options";
       uses apply-advanced;
       leaf delimiter {
         description "Change delimiter/separator character";
         type string {
           length 1;
         }
       }
       leaf domain-name {
         description "Add domain name";
         type string {
           length "1 .. 64";
         }
       }
       leaf user-prefix {
         description "Add user defined prefix";
         type string {
           length "1 .. 64";
         }
       }
       leaf mac-address {
         description "Include MAC address";
         type empty;
       }
       container option-82 {
         presence "enable option-82";
         description "Include option 82";
         leaf circuit-id {
           description "Include option 82 circuit-id (sub option 1)";
           type empty;
         }
         leaf remote-id {
           description "Include option 82 remote-id (sub option 2)";
           type empty;
         }
       }
       leaf logical-system-name {
         description "Include logical system name";
         type empty;
       }
       leaf routing-instance-name {
         description "Include routing instance name";
         type empty;
       }
       container client-id {
         presence "enable client-id";
         description "Include client ID";
         leaf exclude-headers {
           description "Exclude all the headers";
           type empty;
         }
         leaf use-automatic-ascii-hex-encoding {
           description "Use automatic ascii hex username encoding";
           type empty;
         }
       }
       leaf option-60 {
         description "Include option 60";
         type empty;
       }
       leaf circuit-type {
         description "Include circuit type";
         type empty;
       }
       leaf interface-name {
         description "Include interface name";
         type empty;
       }
       leaf interface-description {
         description "Include interface description";
         type enumeration {
           enum "device" {
             description "Add the device interface description";
           }
           enum "logical" {
             description "Add the logical interface description";
           }
         }
       }
       leaf vlan-tags {
         description "Include the vlan tag(s)";
         type empty;
       }
     }
   }
   grouping dhcp-dual-stack-group {
     description "DHCP dual stack groups";
     leaf name {
       description "Dual stack group name";
       type string {
         length "1 .. 64";
       }
     }
     uses apply-advanced;
     container authentication {
       description "DHCP authentication";
       uses dual-stack-authentication-type;
     }
     leaf service-profile {
       description "Dynamic profile to use for default service activation";
       type string {
         length "1 .. 128";
       }
     }
     leaf access-profile {
       description "Access profile to be used for jdhcpd";
       type string {
         length "1 .. 128";
       }
     }
     container dynamic-profile {
       description "Dynamic profile to use";
       uses dynamic-profile-type;
     }
     container liveness-detection {
       description "DHCP client liveness detection processing";
       uses dhcp-liveness-detection-dualstack-type;
     }
     container relay-agent-interface-id {
       description "Interface-id option processing";
       presence "enable relay-agent-interface-id";
       uses v6-relay-option-interface-id-type;
     }
     container relay-agent-remote-id {
       description "Remote-id option processing";
       presence "enable relay-agent-remote-id";
       uses v6-relay-option-remote-id-type;
     }
     container classification-key {
       description "Classification key for identifying dual stack household";
       uses classification-types;
     }
     leaf dual-stack-interface-client-limit {
       description "Limit the number of client allowed on an interface";
       type union {
         type string {
           pattern "<.*>|$.*";
         }
         type uint32 {
           range "1 .. 500000";
         }
       }
     }
     container protocol-master {
       description "Select family as protocol master";
       uses jdhcp-dual-stack-protocol-mstr-type;
     }
     container short-cycle-protection {
       description "Short cycle lockout configuration";
       leaf lockout-min-time {
         description "Short cycle lockout time in seconds";
         type union {
           type string {
             pattern "<.*>|$.*";
           }
           type uint32 {
             range "1 .. 86400";
           }
         }
       }
       leaf lockout-max-time {
         description "Short cycle lockout time in seconds";
         type union {
           type string {
             pattern "<.*>|$.*";
           }
           type uint32 {
             range "1 .. 86400";
           }
         }
       }
     }
   }
   grouping classification-types {
     description "Different mechanisms to identify a single household";
     uses apply-advanced;
     leaf mac-address {
       description "MAC address of client";
       type empty;
     }
     leaf circuit-id {
       description "Circuit-id as key";
       type empty;
     }
     leaf remote-id {
       description "Remote-id as key";
       type empty;
     }
   }
   grouping dhcp-generic-v4-option {
     description "Generic DHCP options processing";
     uses apply-advanced;
     leaf option-number {
       description "Option number";
       status deprecated;
       type enumeration {
         enum "60" {
           description "Option 60";
           status deprecated;
         }
         enum "77" {
           description "Option 77";
           status deprecated;
         }
       }
     }
     container equals {
       description "Generic option equals";
       status deprecated;
       uses relay-v4-option-ascii-hex;
     }
     container default-action {
       description "Generic option default action";
       status deprecated;
       uses dhcp-v4-option-default-action;
     }
     container starts-with {
       description "Generic option starts with";
       status deprecated;
       uses relay-v4-option-ascii-hex;
     }
     container option-60 {
       description "Add option 60 processing";
       presence "enable option-60";
       uses dhcp-generic-v4-option-type;
     }
     container option-77 {
       description "Add option 77 processing";
       presence "enable option-77";
       uses dhcp-generic-v4-option-type;
     }
     list option-order {
       key name;
       ordered-by user;
       description "Options precedence order";
       leaf name {
         description "Option number";
         type enumeration {
           enum "60" {
             description "Option 60";
           }
           enum "77" {
             description "Option 77";
           }
         }
       }
       uses apply-advanced;
     }
   }
   grouping dhcp-generic-v4-option-type {
     uses apply-advanced;
     container equals {
       description "Generic option equals";
       uses relay-v4-option-ascii-hex;
     }
     container default-action {
       description "Generic option default action";
       uses dhcp-v4-option-default-action;
     }
     container starts-with {
       description "Generic option starts with";
       uses relay-v4-option-ascii-hex;
     }
   }
   grouping dhcp-group {
     description "DHCP groups";
     leaf name {
       description "Group name";
       type string {
         length "1 .. 64";
       }
     }
     uses apply-advanced;
     container active-server-group {
       description "Name of DHCP server group";
       uses dhcpv4-gp-active-sg-type;
     }
     container authentication {
       description "DHCP authentication";
       uses authentication-type;
     }
     container liveness-detection {
       description "DHCP client liveness detection processing";
       uses dhcp-liveness-detection-type;
     }
     container dynamic-profile {
       description "Dynamic profile to use";
       uses dynamic-profile-type;
     }
     leaf service-profile {
       description "Dynamic profile to use for default service activation";
       type string {
         length "1 .. 128";
       }
     }
     leaf access-profile {
       description "Access profile to use for AAA services";
       type string {
         length "1 .. 128";
       }
     }
     container overrides {
       description "DHCP override processing";
       presence "enable overrides";
       uses override-type;
     }
     container short-cycle-protection {
       description "Short cycle lockout configuration";
       leaf lockout-min-time {
         description "Short cycle lockout time in seconds";
         type union {
           type string {
             pattern "<.*>|$.*";
           }
           type uint32 {
             range "1 .. 86400";
           }
         }
       }
       leaf lockout-max-time {
         description "Short cycle lockout time in seconds";
         type union {
           type string {
             pattern "<.*>|$.*";
           }
           type uint32 {
             range "1 .. 86400";
           }
         }
       }
     }
     container server-match {
       description "Server match processing";
       uses apply-advanced;
       container default-action {
         description "Server match default action";
         presence "enable default-action";
         uses server-match-action-choice;
       }
       list address {
         key name;
         description "Server address";
         leaf name {
           description "Server address for matching";
           type jt:ipv4prefix;
         }
         uses apply-advanced;
         choice server-match-action-choice {
           case case_1 {
             leaf forward-only {
               description "Forward without subscriber services when a match is made";
               type empty;
             }
           }
           case case_2 {
             leaf create-relay-entry {
               description "Create relay entry and allow subscriber services";
               type empty;
             }
           }
         }
       }
     }
     container relay-option {
       description "DHCP option processing";
       presence "enable relay-option";
       uses dhcp-generic-v4-option;
     }
     container relay-option-60 {
       description "DHCP option-60 processing";
       presence "enable relay-option-60";
       status deprecated;
       uses relay-option-60-type-group;
     }
     container relay-option-82 {
       description "DHCP option-82 processing";
       presence "enable relay-option-82";
       uses relay-option-82-type;
     }
     container forward-only {
       description "Forward DHCP packets without creating binding";
       presence "enable forward-only";
       uses forward-only-to-rc-type;
     }
     container route-suppression {
       description "Suppress access-internal and/or destination route addition";
       uses dhcp-route-suppression-type;
     }
     leaf description {
       description "Text description of servers";
       type string;
     }
     leaf maximum-hop-count {
       description "Maximum number of hops per packet";
       type union {
         type string {
           pattern "<.*>|$.*";
         }
         type uint32 {
           range "1 .. 16";
         }
       }
     }
     leaf minimum-wait-time {
       description "Minimum number of seconds before requests are forwarded";
       type union {
         type string {
           pattern "<.*>|$.*";
         }
         type uint32 {
           range "0 .. 30000";
         }
       }
     }
     leaf client-response-ttl {
       description "IP time-to-live value to set in responses to client";
       type union {
         type string {
           pattern "<.*>|$.*";
         }
         type uint32 {
           range "1 .. 255";
         }
       }
     }
     leaf source-ip-change {
       description "Use address of egress interface as source ip";
       type empty;
     }
     list interface {
       key name;
       description "One or more interfaces";
       leaf name {
         description "Interface name";
         type union {
           type jt:interface-name;
           type string {
             pattern "<.*>|$.*";
           }
         }
       }
       uses apply-advanced;
       leaf upto {
         description "Interface up to";
         type union {
           type jt:interface-name;
           type string {
             pattern "<.*>|$.*";
           }
         }
       }
       leaf exclude {
         description "Exclude this interface range";
         type empty;
       }
       leaf trace {
         description "Enable tracing for this interface";
         type empty;
       }
       container overrides {
         description "DHCP override processing";
         uses override-type;
       }
       container dynamic-profile {
         description "Dynamic profile to use";
         uses dynamic-profile-type;
       }
       leaf service-profile {
         description "Dynamic profile to use for default service activation";
         type string {
           length "1 .. 128";
         }
       }
       leaf access-profile {
         description "Access profile to use for AAA services";
         type string {
           length "1 .. 128";
         }
       }
       container short-cycle-protection {
         description "Short cycle lockout configuration";
         leaf lockout-min-time {
           description "Short cycle lockout time in seconds";
           type union {
             type string {
               pattern "<.*>|$.*";
             }
             type uint32 {
               range "1 .. 86400";
             }
           }
         }
         leaf lockout-max-time {
           description "Short cycle lockout time in seconds";
           type union {
             type string {
               pattern "<.*>|$.*";
             }
             type uint32 {
               range "1 .. 86400";
             }
           }
         }
       }
     }
     list interface-tag {
       key name;
       description "Interfae tag configuration";
       leaf name {
         description "Interface tag name";
         type string {
           length "1 .. 64";
         }
       }
       uses apply-advanced;
       container overrides {
         description "DHCP override processing";
         uses override-type;
       }
       container dynamic-profile {
         description "Dynamic profile to use";
         uses dynamic-profile-type;
       }
       leaf service-profile {
         description "Dynamic profile to use for default service activation";
         type string {
           length "1 .. 128";
         }
       }
       leaf access-profile {
         description "Access profile to use for AAA services";
         type string {
           length "1 .. 128";
         }
       }
       container short-cycle-protection {
         description "Short cycle lockout configuration";
         leaf lockout-min-time {
           description "Short cycle lockout time in seconds";
           type union {
             type string {
               pattern "<.*>|$.*";
             }
             type uint32 {
               range "1 .. 86400";
             }
           }
         }
         leaf lockout-max-time {
           description "Short cycle lockout time in seconds";
           type union {
             type string {
               pattern "<.*>|$.*";
             }
             type uint32 {
               range "1 .. 86400";
             }
           }
         }
       }
     }
     container remote-id-mismatch {
       description "DHCP client remote-id mismatch";
       presence "enable remote-id-mismatch";
       uses dhcp-remote-id-mismatch-type;
     }
     container lease-time-validation {
       presence "enable lease-time-validation";
       description "Configure lease time violation validation";
       uses apply-advanced;
       leaf lease-time-threshold {
         description "Threshold for lease time violation in seconds";
         units "seconds";
         type union {
           type string {
             pattern "<.*>|$.*";
           }
           type uint32 {
             range "60 .. 2147483647";
           }
         }
       }
       container violation-action {
         description "Lease time validation violation action";
         leaf drop {
           description "Drop dhcpv4 offer and ack packets";
           type empty;
         }
       }
     }
   }
   grouping dhcp-liveness-detection-dualstack-type {
     description "DHCP client liveness detection processing";
     uses apply-advanced;
     container failure-action {
       description "Liveness detection failure action options";
       uses dhcp-liveness-detection-failure-action-type;
     }
     container method {
       description "Liveness detection method options";
       uses apply-advanced;
       choice method-choice {
         case case_1 {
           container layer2-liveness-detection {
             description "Address resolution options";
             uses dhcp-arp-nud-liveness-detection-type;
           }
         }
       }
     }
   }
   grouping dhcp-arp-nud-liveness-detection-type {
     description "Address Resolution detection options";
     uses apply-advanced;
     leaf transmit-interval {
       description "Transmit interval for address resolution";
       default "300";
       units "seconds";
       type union {
         type string {
           pattern "<.*>|$.*";
         }
         type uint32 {
           range "300 .. 1800";
         }
       }
     }
     leaf max-consecutive-retries {
       description "Retry attempts";
       default "3";
       type union {
         type string {
           pattern "<.*>|$.*";
         }
         type uint32 {
           range "3 .. 6";
         }
       }
     }
   }
   grouping dhcp-liveness-detection-failure-action-type {
     description "Liveness detection failure action options";
     uses apply-advanced;
     choice failure-action-type {
       case case_1 {
         leaf clear-binding {
           description "Clear the client binding";
           type empty;
         }
       }
       case case_2 {
         leaf clear-binding-if-interface-up {
           description "Clear the client binding only if the incoming interface is up";
           type empty;
         }
       }
       case case_3 {
         leaf log-only {
           description "Maintain the client binding and log the failure event";
           type empty;
         }
       }
     }
   }
   grouping dhcp-liveness-detection-type {
     description "DHCP client liveness detection processing";
     uses apply-advanced;
     container failure-action {
       description "Liveness detection failure action options";
       uses dhcp-liveness-detection-failure-action-type;
     }
     container method {
       description "Liveness detection method options";
       uses apply-advanced;
       choice method-choice {
         case case_1 {
           container bfd {
             description "Bidirectional Forwarding Detection (BFD) options";
             uses dhcp-bfd-liveness-detection-type;
           }
         }
         case case_2 {
           container layer2-liveness-detection {
             description "Address resolution options";
             uses dhcp-arp-nud-liveness-detection-type;
           }
         }
       }
     }
   }
   grouping dhcp-bfd-liveness-detection-type {
     description "Bidirectional Forwarding Detection (BFD) options";
     uses apply-advanced;
     leaf version {
       description "BFD protocol version number";
       default "automatic";
       type enumeration {
         enum "0" {
           description "BFD version 0 (deprecated)";
         }
         enum "1" {
           description "BFD version 1";
         }
         enum "automatic" {
           description "Choose BFD version automatically";
         }
       }
     }
     leaf minimum-interval {
       description "Minimum transmit and receive interval";
       units "milliseconds";
       type union {
         type string {
           pattern "<.*>|$.*";
         }
         type uint32 {
           range "30000 .. 255000";
         }
       }
     }
     leaf minimum-transmit-interval {
       description "Minimum transmit interval";
       status deprecated;
       units "milliseconds";
       type union {
         type string {
           pattern "<.*>|$.*";
         }
         type uint32 {
           range "30000 .. 255000";
         }
       }
     }
     leaf minimum-receive-interval {
       description "Minimum receive interval";
       units "milliseconds";
       type union {
         type string {
           pattern "<.*>|$.*";
         }
         type uint32 {
           range "30000 .. 255000";
         }
       }
     }
     leaf multiplier {
       description "Detection time multiplier";
       default "3";
       type union {
         type string {
           pattern "<.*>|$.*";
         }
         type uint32 {
           range "1 .. 255";
         }
       }
     }
     leaf inline-disable {
       description "Disable inline mode for this BFD session";
       type empty;
     }
     leaf pdu-size {
       description "BFD transport protocol payload size";
       default "24";
       type union {
         type string {
           pattern "<.*>|$.*";
         }
         type uint32 {
           range "24 .. 16000";
         }
       }
     }
     choice adaptation-choice {
       case case_1 {
         leaf no-adaptation {
           description "Disable adaptation";
           type empty;
         }
       }
     }
     container transmit-interval {
       description "Transmit-interval options";
       uses apply-advanced;
       leaf minimum-interval {
         description "Minimum transmit interval";
         units "milliseconds";
         type union {
           type string {
             pattern "<.*>|$.*";
           }
           type uint32 {
             range "30000 .. 255000";
           }
         }
       }
       leaf threshold {
         description "High transmit interval triggering a trap";
         units "milliseconds";
         type union {
           type uint32;
           type string {
             pattern "<.*>|$.*";
           }
         }
       }
     }
     container detection-time {
       description "Detection-time options";
       uses apply-advanced;
       leaf threshold {
         description "High detection-time triggering a trap";
         units "milliseconds";
         type union {
           type uint32;
           type string {
             pattern "<.*>|$.*";
           }
         }
       }
     }
     leaf session-mode {
       description "BFD single-hop or multihop session-mode";
       default "automatic";
       type enumeration {
         enum "automatic" {
           description "Choose session-mode automatically";
         }
         enum "single-hop" {
           description "Use single-hop";
         }
         enum "multihop" {
           description "Use multihop";
         }
       }
     }
     leaf holddown-interval {
       description "Time to hold the session-UP notification to the client";
       default "0";
       units "milliseconds";
       type union {
         type string {
           pattern "<.*>|$.*";
         }
         type uint32 {
           range "0 .. 255000";
         }
       }
     }
   }
   grouping dhcp-remote-id-mismatch-type {
     description "DHCP client remote-id-mismatch processing";
     uses apply-advanced;
     leaf disconnect {
       description "Disconnect session on remote-id mismatch";
       type empty;
     }
   }
   grouping dhcp-route-suppression-type {
     uses apply-advanced;
     choice dhcp-route-suppression-choice {
       case case_1 {
         leaf access-internal {
           description "Suppress access-internal and destination route addition";
           type empty;
         }
       }
       case case_2 {
         leaf destination {
           description "Suppress destination route addition";
           type empty;
         }
       }
     }
   }
   grouping dhcp-v4-option-default-action {
     description "Default action";
     uses apply-advanced;
     choice server-group-choice {
       case case_1 {
         leaf relay-server-group {
           description "Name of DHCP relay server group when match is made";
           type string {
             length "1 .. 64";
           }
         }
       }
       case case_2 {
         leaf local-server-group {
           description "Name of DHCP local server group when match is made";
           type string {
             length "1 .. 64";
           }
         }
       }
       case case_3 {
         leaf drop {
           description "Discard when a match is made";
           type empty;
         }
       }
       case case_4 {
         leaf forward-only {
           description "Forward without subscriber services when a match is made";
           type empty;
         }
       }
     }
   }
   grouping dhcpv4-gbl-active-sg-type {
     leaf active-server-group {
       description "Name of DHCP server group";
       type string {
         length "1 .. 64";
       }
     }
     leaf allow-server-change {
       description "Accept DHCP-ACK from any server in this group";
       type empty;
     }
   }
   grouping dhcpv4-gp-active-sg-type {
     leaf active-server-group {
       description "Name of DHCP server group";
       type string {
         length "1 .. 64";
       }
     }
     leaf allow-server-change {
       description "Accept DHCP-ACK from any server in this group";
       type empty;
     }
   }
   grouping dhcpv6-relay-type {
     description "DHCPv6 relay configuration";
     uses apply-advanced;
     container authentication {
       description "DHCPv6 authentication";
       uses dhcpv6-authentication-type;
     }
     container persistent-storage {
       description "Trigger to enable flat file storage";
       leaf automatic {
         description "Trigger automatically";
         type empty;
       }
     }
     container liveness-detection {
       description "DHCPv6 client liveness detection processing";
       uses dhcpv6-liveness-detection-type;
     }
     container dynamic-profile {
       description "Dynamic profile to use";
       uses dynamic-profile-type;
     }
     leaf service-profile {
       description "Dynamic profile to use for default service activation";
       type string {
         length "1 .. 128";
       }
     }
     leaf access-profile {
       description "Access profile to use for AAA services";
       type string {
         length "1 .. 128";
       }
     }
     container short-cycle-protection {
       description "Short cycle lockout configuration";
       leaf lockout-min-time {
         description "Short cycle lockout time in seconds";
         type union {
           type string {
             pattern "<.*>|$.*";
           }
           type uint32 {
             range "1 .. 86400";
           }
         }
       }
       leaf lockout-max-time {
         description "Short cycle lockout time in seconds";
         type union {
           type string {
             pattern "<.*>|$.*";
           }
           type uint32 {
             range "1 .. 86400";
           }
         }
       }
     }
     container overrides {
       description "DHCPv6 override processing";
       presence "enable overrides";
       uses dhcpv6-override-relay-type;
     }
     container relay-option {
       description "DHCPv6 option processing";
       presence "enable relay-option";
       uses dhcp-generic-v6-option;
     }
     leaf exclude-relay-agent-identifier {
       description "Exclude relay agent identifier from packets to server";
       type empty;
     }
     container server-match {
       description "Server match processing";
       uses apply-advanced;
       container default-action {
         description "Server match default action";
         uses server-match-action-choice;
       }
       container duid {
         description "Match duid processing";
         uses apply-advanced;
         container equals {
           description "Duid equals";
           uses server-match-v6-ascii-hex;
         }
         container starts-with {
           description "Duid starts with";
           uses server-match-v6-ascii-hex;
         }
       }
       list address {
         key name;
         description "Server ipv6 address";
         leaf name {
           description "Server ipv6 address for matching";
           type jt:ipv6prefix;
         }
         uses apply-advanced;
         choice server-match-action-choice {
           case case_1 {
             leaf forward-only {
               description "Forward without subscriber services when a match is made";
               type empty;
             }
           }
           case case_2 {
             leaf create-relay-entry {
               description "Create relay entry and allow subscriber services";
               type empty;
             }
           }
         }
       }
     }
     leaf relay-agent-option-79 {
       description "Add the client MAC address to the Relay Forward header.";
       type empty;
     }
     container vendor-specific-information {
       description "DHCPv6 option 17 vendor-specific processing";
       uses jdhcp-vendor-specific-type;
     }
     container forward-only {
       description "Forward DHCPv6 packets without creating binding";
       presence "enable forward-only";
       uses forward-only-to-rc-type;
     }
     leaf forward-only-replies {
       description "Forward-only replies from server to appropriate logical-system:routing-instance based on options";
       type empty;
     }
     container forward-snooped-clients {
       description "Forward snooped (unicast) packets";
       choice interface-type {
         case case_1 {
           leaf configured-interfaces {
             description "Forward snooped (unicast) packets on configured interfaces";
             type empty;
           }
         }
         case case_2 {
           leaf non-configured-interfaces {
             description "Forward snooped (unicast) packets on non-configured interfaces";
             type empty;
           }
         }
         case case_3 {
           leaf all-interfaces {
             description "Forward snooped (unicast) packets on configured and non-configured interfaces";
             type empty;
           }
         }
       }
     }
     container route-suppression {
       description "Suppress access-internal and/or access route addition";
       uses dhcpv6-route-suppression-type;
     }
     list group {
       key name;
       description "Define a DHCPv6 relay group";
       uses dhcpv6-relay-group;
     }
     container relay-agent-interface-id {
       description "DHCPv6 interface-id option processing";
       presence "enable relay-agent-interface-id";
       uses v6-relay-option-interface-id-type;
     }
     container relay-agent-remote-id {
       description "DHCPv6 remote-id option processing";
       presence "enable relay-agent-remote-id";
       uses v6-relay-option-remote-id-type;
     }
     container server-group {
       description "Define a DHCPv6 server group";
       uses v6-server-group-type;
     }
     container active-server-group {
       description "Name of DHCPv6 server group";
       uses dhcpv6-gbl-active-sg-type;
     }
     leaf server-response-time {
       description "Number of seconds in a period of activity between the last server response and an unaswered request";
       default "0";
       type union {
         type uint32;
         type string {
           pattern "<.*>|$.*";
         }
       }
     }
     container lease-time-validation {
       presence "enable lease-time-validation";
       description "Configure lease time violation validation";
       uses apply-advanced;
       leaf lease-time-threshold {
         description "Threshold for lease time violation in seconds";
         units "seconds";
         type union {
           type string {
             pattern "<.*>|$.*";
           }
           type uint32 {
             range "60 .. 2147483647";
           }
         }
       }
       container violation-action {
         description "Lease time validation violation action";
         leaf drop {
           description "Drop dhcpv6 advertise and reply packets";
           type empty;
         }
       }
     }
     leaf no-snoop {
       description "Do not snoop DHCPV6 packets";
       type empty;
     }
     container leasequery {
       description "DHCPv6 leasequery configuration";
       presence "enable leasequery";
       uses relay-leasequery-type;
     }
     container bulk-leasequery {
       description "DHCPv6 bulk leasequery configuration";
       presence "enable bulk-leasequery";
       uses relay-bulk-leasequery-v6-type;
     }
     container active-leasequery {
       description "DHCPv6 active leasequery configuration";
       presence "enable active-leasequery";
       uses active-leasequery-v6-type;
     }
     container remote-id-mismatch {
       description "DHCP client remote-id mismatch";
       presence "enable remote-id-mismatch";
       uses dhcp-remote-id-mismatch-type;
     }
     container duplicate-clients {
       description "Allow duplicate clients";
       uses dhcpv6-duplicate-clients-type;
     }
   }
   grouping active-leasequery-v6-type {
     description "Configure active leasequery";
     uses apply-advanced;
     leaf topology-discover {
       description "Topology discovery";
       type empty;
     }
     list exclude-interface {
       key name;
       ordered-by user;
       description "Exclude interface participating in active leasequery";
       leaf name {
         description "Interface name";
         type union {
           type jt:interface-name;
           type string {
             pattern "<.*>|$.*";
           }
         }
       }
       uses apply-advanced;
     }
     leaf timeout {
       description "Read/write timeout in seconds";
       default "120";
       units "seconds";
       type union {
         type string {
           pattern "<.*>|$.*";
         }
         type uint32 {
           range "10 .. 3600";
         }
       }
     }
     leaf idle-timeout {
       description "Idle timeout in seconds";
       default "60";
       units "seconds";
       type union {
         type string {
           pattern "<.*>|$.*";
         }
         type uint32 {
           range "10 .. 3600";
         }
       }
     }
     list peer-address {
       key name;
       description "Peer ipv6 address";
       leaf name {
         description "Peer ipv6 address";
         type jt:ipv6addr;
       }
       uses apply-advanced;
     }
   }
   grouping dhcp-generic-v6-option {
     description "Generic DHCPv6 options processing";
     uses apply-advanced;
     leaf option-number {
       description "Option number";
       status deprecated;
       type enumeration {
         enum "15" {
           description "Option 15";
           status deprecated;
         }
         enum "16" {
           description "Option 16";
           status deprecated;
         }
       }
     }
     container equals {
       description "Generic option equals";
       status deprecated;
       uses relay-v6-option-ascii-hex;
     }
     container default-action {
       description "Generic option default action";
       status deprecated;
       uses dhcp-v6-option-default-action;
     }
     container starts-with {
       description "Generic option starts with";
       status deprecated;
       uses relay-v6-option-ascii-hex;
     }
     container option-15 {
       description "Add option 15 processing";
       presence "enable option-15";
       uses dhcp-generic-v6-option-type;
     }
     container option-16 {
       description "Add option 16 processing";
       presence "enable option-16";
       uses dhcp-generic-v6-option-type;
     }
     list option-order {
       key name;
       ordered-by user;
       description "Options precedence order";
       leaf name {
         description "Option number";
         type enumeration {
           enum "15" {
             description "Option 15";
           }
           enum "16" {
             description "Option 16";
           }
         }
       }
       uses apply-advanced;
     }
   }
   grouping dhcp-generic-v6-option-type {
     uses apply-advanced;
     container equals {
       description "Generic option equals";
       uses relay-v6-option-ascii-hex;
     }
     container default-action {
       description "Generic option default action";
       uses dhcp-v6-option-default-action;
     }
     container starts-with {
       description "Generic option starts with";
       uses relay-v6-option-ascii-hex;
     }
   }
   grouping dhcp-v6-option-default-action {
     description "Default action";
     uses apply-advanced;
     choice server-group-choice {
       case case_1 {
         leaf relay-server-group {
           description "Name of DHCP relay server group when match is made";
           type string {
             length "1 .. 64";
           }
         }
       }
       case case_2 {
         leaf drop {
           description "Discard when a match is made";
           type empty;
         }
       }
       case case_3 {
         leaf forward-only {
           description "Forward without subscriber services when a match is made";
           type empty;
         }
       }
     }
   }
   grouping dhcpv6-authentication-type {
     description "DHCPv6 authentication";
     uses apply-advanced;
     leaf password {
       description "Username password to use";
       type string {
         length "1 .. 64";
       }
     }
     container username-include {
       description "Add username options";
       uses apply-advanced;
       leaf delimiter {
         description "Change delimiter/separator character";
         type string {
           length 1;
         }
       }
       leaf domain-name {
         description "Add domain name";
         type string {
           length "1 .. 64";
         }
       }
       leaf user-prefix {
         description "Add user defined prefix";
         type string {
           length "1 .. 64";
         }
       }
       leaf mac-address {
         description "Include MAC address";
         type empty;
       }
       container client-id {
         presence "enable client-id";
         description "Include client ID";
         leaf exclude-headers {
           description "Exclude all the headers";
           type empty;
         }
         leaf use-automatic-ascii-hex-encoding {
           description "Use automatic ascii hex username encoding";
           type empty;
         }
       }
       container relay-agent-remote-id {
         presence "enable relay-agent-remote-id";
         description "Include the relay agent remote ID";
         uses apply-advanced;
         choice relay-agent-remote-id-choice {
           case case_1 {
             leaf enterprise-id {
               description "Only use enterprise-id portion of option-37";
               status deprecated;
               type empty;
             }
           }
           case case_2 {
             leaf remote-id {
               description "Only use remote-id portion of option-37";
               status deprecated;
               type empty;
             }
           }
         }
       }
       leaf logical-system-name {
         description "Include logical system name";
         type empty;
       }
       leaf routing-instance-name {
         description "Include routing instance name";
         type empty;
       }
       leaf relay-agent-subscriber-id {
         description "Include the relay agent subscriber ID";
         type empty;
       }
       leaf relay-agent-interface-id {
         description "Include the relay agent interface ID";
         type empty;
       }
       leaf circuit-type {
         description "Include circuit type";
         type empty;
       }
       leaf interface-name {
         description "Include interface name";
         type empty;
       }
       leaf interface-description {
         description "Include interface description";
         type enumeration {
           enum "device" {
             description "Add the device interface description";
           }
           enum "logical" {
             description "Add the logical interface description";
           }
         }
       }
       leaf vlan-tags {
         description "Include the vlan tag(s)";
         type empty;
       }
     }
   }
   grouping dhcpv6-duplicate-clients-type {
     description "Allow duplicate clients";
     choice distinguish-with {
       case case_1 {
         leaf incoming-interface {
           description "Allow duplicate clients on different underlying interfaces";
           type empty;
         }
       }
     }
   }
   grouping dhcpv6-gbl-active-sg-type {
     uses apply-advanced;
     leaf active-server-group {
       description "Name of DHCPv6 server group";
       type string {
         length "1 .. 64";
       }
     }
   }
   grouping dhcpv6-liveness-detection-type {
     description "DHCPv6 client liveness detection processing";
     uses apply-advanced;
     container failure-action {
       description "Liveness detection failure action options";
       uses dhcp-liveness-detection-failure-action-type;
     }
     container method {
       description "Liveness detection method options";
       uses apply-advanced;
       choice method-choice {
         case case_1 {
           container bfd {
             description "Bidirectional Forwarding Detection (BFD) options";
             uses dhcp-bfd-liveness-detection-type;
           }
         }
         case case_2 {
           container layer2-liveness-detection {
             description "Neighbor discovery options";
             uses dhcp-arp-nud-liveness-detection-type;
           }
         }
       }
     }
   }
   grouping dhcpv6-override-relay-type {
     description "DHCPv6 relay override processing";
     uses apply-advanced;
     choice allow-snooped-clients-choice {
       leaf allow-snooped-clients {
         description "Allow client creation from snooped PDUs";
         type empty;
       }
       leaf no-allow-snooped-clients {
         description "Don't allow client creation from snooped PDUs";
         type empty;
       }
     }
     leaf delay-authentication {
       description "Delay subscriber authentication in DHCP protocol processing until request packet";
       type empty;
     }
     leaf interface-client-limit {
       description "Limit the number of clients allowed on an interface";
       type union {
         type string {
           pattern "<.*>|$.*";
         }
         type uint32 {
           range "1 .. 500000";
         }
       }
     }
     leaf dual-stack {
       description "Dual stack group to use.";
       type string {
         length "1 .. 64";
       }
     }
     leaf no-bind-on-request {
       description "Do not bind if stray DHCPv6 RENEW, REBIND is received";
       type empty;
     }
     container client-negotiation-match {
       description "Use secondary match criteria for SOLICIT PDU";
       choice match-with {
         case case_1 {
           leaf incoming-interface {
             description "Use incoming interface";
             type empty;
           }
         }
       }
     }
     leaf send-release-on-delete {
       description "Always send RELEASE to the server when a binding is deleted";
       type empty;
     }
     leaf always-process-option-request-option {
       description "Always process option even after address allocation failure";
       type empty;
     }
     leaf relay-source {
       description "Interface for relay source";
       type union {
         type jt:interface-name;
         type string {
           pattern "<.*>|$.*";
         }
       }
     }
     leaf delete-binding-on-renegotiation {
       description "Delete binding on renegotiation";
       type empty;
     }
     leaf asymmetric-lease-time {
       description "Use a reduced lease time for the client. In seconds";
       units "seconds";
       type union {
         type string {
           pattern "<.*>|$.*";
         }
         type uint32 {
           range "600 .. 86400";
         }
       }
     }
     leaf asymmetric-prefix-lease-time {
       description "Use a reduced prefix lease time for the client. In seconds";
       units "seconds";
       type union {
         type string {
           pattern "<.*>|$.*";
         }
         type uint32 {
           range "600 .. 86400";
         }
       }
     }
   }
   grouping dhcpv6-relay-group {
     description "DHCPv6 groups";
     leaf name {
       description "Group name";
       type string {
         length "1 .. 64";
       }
     }
     uses apply-advanced;
     container active-server-group {
       description "Name of DHCPv6 server group";
       uses dhcpv6-gp-active-sg-type;
     }
     list dual-stack-group {
       key name;
       description "Define a DHCP dual stack group";
       uses dhcp-dual-stack-group;
     }
     container authentication {
       description "DHCPv6 authentication";
       uses dhcpv6-authentication-type;
     }
     container liveness-detection {
       description "DHCPv6 client liveness detection processing";
       uses dhcpv6-liveness-detection-type;
     }
     container dynamic-profile {
       description "Dynamic profile to use";
       uses dynamic-profile-type;
     }
     leaf service-profile {
       description "Dynamic profile to use for default service activation";
       type string {
         length "1 .. 128";
       }
     }
     leaf access-profile {
       description "Access profile to use for AAA services";
       type string {
         length "1 .. 128";
       }
     }
     container short-cycle-protection {
       description "Short cycle lockout configuration";
       leaf lockout-min-time {
         description "Short cycle lockout time in seconds";
         type union {
           type string {
             pattern "<.*>|$.*";
           }
           type uint32 {
             range "1 .. 86400";
           }
         }
       }
       leaf lockout-max-time {
         description "Short cycle lockout time in seconds";
         type union {
           type string {
             pattern "<.*>|$.*";
           }
           type uint32 {
             range "1 .. 86400";
           }
         }
       }
     }
     container overrides {
       description "DHCPv6 override processing";
       presence "enable overrides";
       uses dhcpv6-override-relay-type;
     }
     container relay-option {
       description "DHCPv6 option processing";
       presence "enable relay-option";
       uses dhcp-generic-v6-option;
     }
     container vendor-specific-information {
       description "DHCPv6 option 17 vendor-specific processing";
       uses jdhcp-vendor-specific-type;
     }
     container forward-only {
       description "Forward DHCPv6 packets without creating binding";
       presence "enable forward-only";
       uses forward-only-to-rc-type;
     }
     container relay-agent-interface-id {
       description "DHCPv6 interface-id option processing";
       presence "enable relay-agent-interface-id";
       uses v6-relay-option-interface-id-type;
     }
     container relay-agent-remote-id {
       description "DHCPv6 remote-id option processing";
       presence "enable relay-agent-remote-id";
       uses v6-relay-option-remote-id-type;
     }
     container route-suppression {
       description "Suppress access-internal and/or access route addition";
       uses dhcpv6-route-suppression-type;
     }
     leaf relay-agent-option-79 {
       description "Add the client MAC address to the Relay Forward header.";
       type empty;
     }
     list interface {
       key name;
       description "One or more interfaces";
       leaf name {
         description "Interface name";
         type union {
           type jt:interface-name;
           type string {
             pattern "<.*>|$.*";
           }
         }
       }
       uses apply-advanced;
       leaf upto {
         description "Interface up to";
         type union {
           type jt:interface-name;
           type string {
             pattern "<.*>|$.*";
           }
         }
       }
       leaf exclude {
         description "Exclude this interface range";
         type empty;
       }
       leaf trace {
         description "Enable tracing for this interface";
         type empty;
       }
       container overrides {
         description "DHCPv6 override processing";
         uses dhcpv6-override-relay-type;
       }
       container dynamic-profile {
         description "Dynamic profile to use";
         uses dynamic-profile-type;
       }
       leaf service-profile {
         description "Dynamic profile to use for default service activation";
         type string {
           length "1 .. 128";
         }
       }
       leaf access-profile {
         description "Access profile to use for AAA services";
         type string {
           length "1 .. 128";
         }
       }
       container short-cycle-protection {
         description "Short cycle lockout configuration";
         leaf lockout-min-time {
           description "Short cycle lockout time in seconds";
           type union {
             type string {
               pattern "<.*>|$.*";
             }
             type uint32 {
               range "1 .. 86400";
             }
           }
         }
         leaf lockout-max-time {
           description "Short cycle lockout time in seconds";
           type union {
             type string {
               pattern "<.*>|$.*";
             }
             type uint32 {
               range "1 .. 86400";
             }
           }
         }
       }
     }
     list interface-tag {
       key name;
       description "Interface tag configurations";
       leaf name {
         description "Interface tag name";
         type string {
           length "1 .. 64";
         }
       }
       uses apply-advanced;
       container overrides {
         description "DHCPv6 override processing";
         uses dhcpv6-override-relay-type;
       }
       container dynamic-profile {
         description "Dynamic profile to use";
         uses dynamic-profile-type;
       }
       leaf service-profile {
         description "Dynamic profile to use for default service activation";
         type string {
           length "1 .. 128";
         }
       }
       leaf access-profile {
         description "Access profile to use for AAA services";
         type string {
           length "1 .. 128";
         }
       }
       container short-cycle-protection {
         description "Short cycle lockout configuration";
         leaf lockout-min-time {
           description "Short cycle lockout time in seconds";
           type union {
             type string {
               pattern "<.*>|$.*";
             }
             type uint32 {
               range "1 .. 86400";
             }
           }
         }
         leaf lockout-max-time {
           description "Short cycle lockout time in seconds";
           type union {
             type string {
               pattern "<.*>|$.*";
             }
             type uint32 {
               range "1 .. 86400";
             }
           }
         }
       }
     }
     container lease-time-validation {
       presence "enable lease-time-validation";
       description "Configure lease time violation validation";
       uses apply-advanced;
       leaf lease-time-threshold {
         description "Threshold for lease time violation in seconds";
         units "seconds";
         type union {
           type string {
             pattern "<.*>|$.*";
           }
           type uint32 {
             range "60 .. 2147483647";
           }
         }
       }
       container violation-action {
         description "Lease time validation violation action";
         leaf drop {
           description "Drop dhcpv6 advertise and reply packets";
           type empty;
         }
       }
     }
     container remote-id-mismatch {
       description "DHCP client remote-id mismatch";
       presence "enable remote-id-mismatch";
       uses dhcp-remote-id-mismatch-type;
     }
     container server-match {
       description "Server match processing";
       uses apply-advanced;
       container default-action {
         description "Server match default action";
         uses server-match-action-choice;
       }
       container duid {
         description "Match duid processing";
         uses apply-advanced;
         container equals {
           description "Duid equals";
           uses server-match-v6-ascii-hex;
         }
         container starts-with {
           description "Duid starts with";
           uses server-match-v6-ascii-hex;
         }
       }
       list address {
         key name;
         description "Server ipv6 address";
         leaf name {
           description "Server ipv6 address for matching";
           type jt:ipv6prefix;
         }
         uses apply-advanced;
         choice server-match-action-choice {
           case case_1 {
             leaf forward-only {
               description "Forward without subscriber services when a match is made";
               type empty;
             }
           }
           case case_2 {
             leaf create-relay-entry {
               description "Create relay entry and allow subscriber services";
               type empty;
             }
           }
         }
       }
     }
   }
   grouping dhcpv6-gp-active-sg-type {
     uses apply-advanced;
     leaf active-server-group {
       description "Name of DHCPv6 server group";
       type string {
         length "1 .. 64";
       }
     }
   }
   grouping dhcpv6-route-suppression-type {
     description "Suppress access-internal and/or access route addition";
     leaf access {
       description "Suppress access route addition";
       type empty;
     }
     leaf access-internal {
       description "Suppress access-internal route addition";
       type empty;
     }
   }
   grouping dual-stack-authentication-type {
     description "DHCP dual stack authentication";
     uses apply-advanced;
     leaf password {
       description "Username password to use";
       type string {
         length "1 .. 64";
       }
     }
     container username-include {
       description "Add username options";
       uses apply-advanced;
       leaf delimiter {
         description "Change delimiter/separator character";
         type string {
           length 1;
         }
       }
       leaf domain-name {
         description "Add domain name";
         type string {
           length "1 .. 64";
         }
       }
       leaf user-prefix {
         description "Add user defined prefix";
         type string {
           length "1 .. 64";
         }
       }
       leaf mac-address {
         description "Include MAC address";
         type empty;
       }
       container client-id {
         presence "enable client-id";
         description "Include client ID";
         leaf exclude-headers {
           description "Exclude all the headers";
           type empty;
         }
         leaf use-automatic-ascii-hex-encoding {
           description "Use automatic ascii hex username encoding";
           type empty;
         }
       }
       leaf relay-agent-remote-id {
         description "Include the relay agent remote ID";
         type empty;
       }
       leaf logical-system-name {
         description "Include logical system name";
         type empty;
       }
       leaf routing-instance-name {
         description "Include routing instance name";
         type empty;
       }
       leaf relay-agent-interface-id {
         description "Include the relay agent interface ID";
         type empty;
       }
       leaf interface-name {
         description "Include interface name";
         type empty;
       }
       leaf interface-description {
         description "Include interface description";
         type enumeration {
           enum "device" {
             description "Add the device interface description";
           }
           enum "logical" {
             description "Add the logical interface description";
           }
         }
       }
       leaf circuit-type {
         description "Include circuit type";
         type empty;
       }
       leaf vlan-tags {
         description "Include the vlan tag(s)";
         type empty;
       }
     }
   }
   grouping dynamic-profile-type {
     description "Dynamic profile to use";
     uses apply-advanced;
     leaf dynamic-profile {
       description "Dynamic profile to use";
       type string {
         length "1 .. 80";
       }
     }
     choice dynamic-profile-type-choice {
       case case_1 {
         leaf use-primary {
           description "Dynamic profile to use on the primary interface";
           type string {
             length "1 .. 80";
           }
         }
       }
       case case_2 {
         container aggregate-clients {
           presence "enable aggregate-clients";
           description "Aggregate client profiles";
           uses apply-advanced;
           choice aggregate-type {
             case case_1 {
               leaf merge {
                 description "Merge the client dynamic profiles";
                 type empty;
               }
             }
             case case_2 {
               leaf replace {
                 description "Replace client dynamic profiles";
                 type empty;
               }
             }
           }
         }
       }
     }
   }
   grouping forward-only-to-rc-type {
     description "Forward DHCP packets without creating binding";
     uses apply-advanced;
     leaf logical-system {
       default "current";
       type string;
     }
     leaf routing-instance {
       default "current";
       type string;
     }
   }
   grouping jdhcp-dual-stack-protocol-mstr-type {
     description "Select family as protocol master";
     choice addr-fam {
       case case_1 {
         leaf inet {
           description "INET family has protocol master behavior";
           type empty;
         }
       }
       case case_2 {
         leaf inet6 {
           description "INET6 family has protocol master behavior";
           type empty;
         }
       }
     }
   }
   grouping jdhcp-duplicate-clients-in-subnet-type {
     description "Allow duplicate clients in a subnet";
     choice distinguish-with {
       case case_1 {
         leaf incoming-interface {
           description "Allow duplicate clients on different interfaces in a subnet";
           type empty;
         }
       }
       case case_2 {
         leaf option-82 {
           description "Allow duplicate clients using different option-82 options in a subnet";
           type empty;
         }
       }
     }
   }
   grouping jdhcp-interface-traceoptions-type {
     description "Interface trace options for DHCP";
     uses apply-advanced;
     leaf no-remote-trace {
       description "Disable remote tracing";
       type empty;
     }
     container file {
       description "Trace file information";
       leaf filename {
         description "Name of file in which to write trace information";
         type string {
           length "1 .. 1024";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     list flag {
       key name;
       ordered-by user;
       description "Interface trace categories";
       leaf name {
         type enumeration {
           enum "state" {
             description "State-transition operations";
           }
           enum "packet" {
             description "Packet-decoding operations";
           }
           enum "flow" {
             description "Flow-decoding operations";
           }
           enum "packet-option" {
             description "DHCP option-decoding operations";
           }
           enum "dhcpv6-state" {
             description "State-transition operations for dhcpv6";
           }
           enum "dhcpv6-packet" {
             description "Packet-decoding operations for dhcpv6";
           }
           enum "dhcpv6-packet-option" {
             description "DHCP option-decoding operations for dhcpv6";
           }
           enum "all" {
             description "All operations";
           }
         }
       }
     }
   }
   grouping jdhcp-security-type {
     description "DHCP access security configuration";
     uses apply-advanced;
     leaf no-dhcp-snooping {
       description "Disable dhcp snooping";
       type empty;
     }
     leaf arp-inspection {
       description "Enable dynamic ARP inspection";
       type empty;
     }
     leaf ip-source-guard {
       description "Enable IP source guard";
       type empty;
     }
     leaf no-dhcpv6-snooping {
       description "Disable DHCPv6 snooping";
       type empty;
     }
     leaf neighbor-discovery-inspection {
       description "Enable neighbor discovery inspection";
       type empty;
     }
     leaf ipv6-source-guard {
       description "Enable IPv6 source guard";
       type empty;
     }
     leaf light-weight-dhcpv6-relay {
       description "Enable light weight dhcpv6 relay";
       type empty;
     }
     list group {
       key name;
       description "Define a DHCP security group for overriding defaults";
       uses ds-group;
     }
     container option-82 {
       description "DHCP option-82 processing for snooped packets";
       presence "enable option-82";
       uses security-option-82-type;
     }
     container dhcpv6-options {
       description "DHCPv6 option processing for snooped packets";
       presence "enable dhcpv6-options";
       uses security-dhcpv6-options-type;
     }
     leaf mine-dhcp-client-options {
       description "Start storing incoming DHCP client options";
       type empty;
     }
     leaf mine-dhcpv6-client-options {
       description "Start storing incoming DHCPv6 client options";
       type empty;
     }
     leaf trust-all {
       description "Mark all ports as trusted for dhcp security";
       type empty;
     }
   }
   grouping ds-group {
     description "DHCP security groups";
     leaf name {
       description "Group name";
       type string {
         length "1 .. 64";
       }
     }
     uses apply-advanced;
     container overrides {
       description "DHCP override processing";
       presence "enable overrides";
       uses ds-override-type;
     }
     list interface {
       key name;
       description "One or more interfaces";
       leaf name {
         description "Interface name";
         type union {
           type jt:interface-name;
           type string {
             pattern "<.*>|$.*";
           }
         }
       }
       uses apply-advanced;
       list static-ip {
         key name;
         ordered-by user;
         description "Static IP address configuration";
         uses ip-mac-static;
       }
       list static-ipv6 {
         key name;
         ordered-by user;
         description "Static IPv6 address configuration";
         uses ipv6-mac-static;
       }
     }
   }
   grouping ds-override-type {
     description "Dynamic ARP Inspection override processing";
     uses apply-advanced;
     leaf trusted {
       description "Make this trusted group of interfaces";
       type empty;
     }
     leaf untrusted {
       description "Make this untrusted group of interfaces";
       type empty;
     }
     leaf no-option82 {
       description "Make this group of interfaces not to add option82";
       type empty;
     }
     leaf no-option37 {
       description "Make this group of interfaces not to add option37";
       type empty;
     }
     leaf no-option18 {
       description "Make this group of interfaces not to add option18";
       type empty;
     }
     leaf no-option16 {
       description "Make this group of interfaces not to add option16";
       type empty;
     }
     leaf no-option79 {
       description "Make this group of interfaces not to add option79";
       type empty;
     }
     leaf no-dhcpv6-options {
       description "Make this group of interfaces not to add any DHCPv6 options";
       type empty;
     }
   }
   grouping ip-mac-static {
     leaf name {
       description "IP address";
       type jt:ipaddr;
     }
     leaf mac {
       description "MAC address";
       type jt:mac-addr;
     }
   }
   grouping ipv6-mac-static {
     leaf name {
       description "IP address";
       type jt:ipv6addr;
     }
     leaf mac {
       description "MAC address";
       type jt:mac-addr;
     }
   }
   grouping jdhcp-traceoptions-type {
     description "Trace options for DHCP";
     uses apply-advanced;
     leaf no-remote-trace {
       description "Disable remote tracing";
       type empty;
     }
     container file {
       description "Trace file information";
       leaf filename {
         description "Name of file in which to write trace information";
         type string {
           length "1 .. 1024";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     list flag {
       key name;
       ordered-by user;
       description "DHCP operations to include in debugging trace";
       leaf name {
         type enumeration {
           enum "state" {
             description "State-transition operations";
           }
           enum "packet" {
             description "Packet-decoding operations";
           }
           enum "flow" {
             description "Flow-decoding operations";
           }
           enum "packet-option" {
             description "DHCP option-decoding operations";
           }
           enum "dhcpv6-state" {
             description "State-transition operations for dhcpv6";
           }
           enum "dhcpv6-packet" {
             description "Packet-decoding operations for dhcpv6";
           }
           enum "dhcpv6-packet-option" {
             description "DHCP option-decoding operations for dhcpv6";
           }
           enum "all" {
             description "All operations";
           }
           enum "database" {
             description "Database operations";
           }
           enum "persistent" {
             description "Persitent file operations";
           }
           enum "lockout-db" {
             description "Lockout database operations";
           }
           enum "interface" {
             description "Interface operations";
           }
           enum "rtsock" {
             description "Routing socket operations";
           }
           enum "flow-notify" {
             description "Flow notification operations";
           }
           enum "io" {
             description "I/O operations";
           }
           enum "ha" {
             description "High Availability-related operations";
           }
           enum "ui" {
             description "User Interface operations";
           }
           enum "general" {
             description "Miscellaneous operations";
           }
           enum "fwd" {
             description "Firewall process operations";
           }
           enum "rpd" {
             description "Routing Protocol process operations";
           }
           enum "auth" {
             description "Authentication operations";
           }
           enum "profile" {
             description "Profile operations";
           }
           enum "session-db" {
             description "Session database operations";
           }
           enum "performance" {
             description "Performance measurement operations";
           }
           enum "statistics" {
             description "Baseline statistics operations";
           }
           enum "dhcpv6-io" {
             description "I/O operations for dhcpv6";
           }
           enum "dhcpv6-rpd" {
             description "Routing Protocol process operations for dhcpv6";
           }
           enum "dhcpv6-session-db" {
             description "Session database operations for dhcpv6";
           }
           enum "dhcpv6-general" {
             description "Miscellaneous operations for dhcpv6";
           }
           enum "liveness-detection" {
             description "Liveness detection operations";
           }
           enum "security-persistence" {
             description "Liveness detection operations";
           }
           enum "mclag" {
             description "Multichassis LAG";
           }
           enum "ra-guard" {
             description "DHCP RA guard option for dhcpv6";
           }
           enum "era" {
             description "DHCP ERA logging option dhcp";
           }
           enum "telemetry" {
             description "Telemetry operation";
           }
         }
       }
     }
   }
   grouping jdhcp-vendor-specific-type {
     description "Add vendor-specific option processing";
     uses apply-advanced;
     leaf host-name {
       description "Add router host name";
       type empty;
     }
     leaf location {
       description "Add location information expressed as interface name format";
       type empty;
     }
   }
   grouping juniper-multicast-snooping-options {
     uses apply-advanced;
     container options {
       description "Miscellaneous options";
       uses apply-advanced;
       container syslog {
         description "Set system logging level";
         uses apply-advanced;
         container level {
           description "Logging level";
           leaf emergency {
             description "Emergency level";
             type empty;
           }
           leaf alert {
             description "Alert level";
             type empty;
           }
           leaf critical {
             description "Critical level";
             type empty;
           }
           leaf error {
             description "Error level";
             type empty;
           }
           leaf warning {
             description "Warning level";
             type empty;
           }
           leaf notice {
             description "Notice level";
             type empty;
           }
           leaf info {
             description "Informational level";
             type empty;
           }
           leaf debug {
             description "Debugging level";
             type empty;
           }
         }
         leaf upto {
           description "Log up to a particular logging level";
           type enumeration {
             enum "emergency" {
               description "Emergency level";
             }
             enum "alert" {
               description "Alert level";
             }
             enum "critical" {
               description "Critical level";
             }
             enum "error" {
               description "Error level";
             }
             enum "warning" {
               description "Warning level";
             }
             enum "notice" {
               description "Notice level";
             }
             enum "info" {
               description "Informational level";
             }
             enum "debug" {
               description "Debugging level";
             }
           }
         }
         leaf mark {
           description "Periodically mark the trace file";
           units "seconds";
           type union {
             type int32;
             type string {
               pattern "<.*>|$.*";
             }
           }
         }
       }
     }
     container traceoptions {
       description "Multicast snooping trace options";
       uses apply-advanced;
       container file {
         description "Trace file options";
         leaf filename {
           description "Name of file in which to write trace information";
           type string {
             length "1 .. 1024";
           }
         }
         leaf replace {
           description "Replace trace file rather than appending to it";
           status deprecated;
           type empty;
         }
         leaf size {
           description "Maximum trace file size";
           type string;
         }
         leaf files {
           description "Maximum number of trace files";
           default "10";
           type union {
             type string {
               pattern "<.*>|$.*";
             }
             type uint32 {
               range "2 .. 1000";
             }
           }
         }
         leaf no-stamp {
           description "Do not timestamp trace file";
           status deprecated;
           type empty;
         }
         choice world-readable-choice {
           leaf world-readable {
             description "Allow any user to read the log file";
             type empty;
           }
           leaf no-world-readable {
             description "Don't allow any user to read the log file";
             type empty;
           }
         }
       }
       list flag {
         key name;
         ordered-by user;
         description "Tracing parameters";
         leaf name {
           type enumeration {
             enum "parse" {
               description "Trace configuration parsing";
             }
             enum "config-internal" {
               description "Trace configuration internals";
             }
             enum "route" {
               description "Trace routing information";
             }
             enum "normal" {
               description "Trace normal events";
             }
             enum "general" {
               description "Trace general events";
             }
             enum "state" {
               description "Trace state transitions";
             }
             enum "policy" {
               description "Trace policy processing";
             }
             enum "task" {
               description "Trace routing protocol task processing";
             }
             enum "timer" {
               description "Trace routing protocol timer processing";
             }
             enum "all" {
               description "Trace everything";
             }
           }
         }
         leaf disable {
           description "Disable this trace flag";
           type empty;
         }
       }
     }
     container forwarding-cache {
       description "Multicast forwarding cache";
       uses apply-advanced;
       container threshold {
         description "Threshold";
         uses apply-advanced;
         leaf suppress {
           description "Suppress threshold";
           type union {
             type string {
               pattern "<.*>|$.*";
             }
             type uint32 {
               range "1 .. 200000";
             }
           }
         }
         leaf reuse {
           description "Reuse threshold";
           type union {
             type string {
               pattern "<.*>|$.*";
             }
             type uint32 {
               range "1 .. 200000";
             }
           }
         }
       }
     }
     leaf-list flood-groups {
       ordered-by user;
       description "Groups for which the traffic will be flooded";
       type jt:ipaddr;
     }
     container host-outbound-traffic {
       description "Host generated protocol packets";
       uses apply-advanced;
       leaf forwarding-class {
         description "Forwarding class name";
         type string {
         }
       }
       leaf dot1p {
         description "Dot1p bits";
         type union {
           type string {
             pattern "<.*>|$.*";
           }
           type uint32 {
             range "0 .. 7";
           }
         }
       }
     }
     container graceful-restart {
       description "Configure graceful restart attributes";
       uses apply-advanced;
       choice enable-disable {
         case case_1 {
           leaf disable {
             description "Disable graceful restart";
             type empty;
           }
         }
       }
       leaf restart-duration {
         description "Maximum time for graceful restart to finish";
         default "180";
         units "seconds";
         type union {
           type string {
             pattern "<.*>|$.*";
           }
           type uint32 {
             range "0 .. 300";
           }
         }
       }
     }
     leaf ignore-stp-topology-change {
       description "Don't process stp topology change";
       type empty;
     }
     container multichassis-lag-replicate-state {
       presence "enable multichassis-lag-replicate-state";
       description "Enable multichassis lag replication";
       uses apply-advanced;
       leaf suppress-report {
         description "Enable mclag report suppression";
         type empty;
       }
     }
     container oism {
       description "Optimized inter subnet multicast options";
       uses apply-advanced;
       leaf install-star-g-routes {
         description "Install (*,G) multicast routes in data plane";
         type empty;
       }
       leaf conserve-mcast-routes-in-pfe {
         description "Don't install snooping routes in forwarding plane";
         type empty;
       }
     }
     leaf nexthop-hold-time {
       description "Nexthop hold time in milliseconds";
       units "milliseconds";
       type union {
         type string {
           pattern "<.*>|$.*";
         }
         type uint32 {
           range "1 .. 1000";
         }
       }
     }
     leaf multicast-router-job-pause {
       description "Pause multicast router handling job";
       type empty;
     }
     leaf multicast-router-no-flood-job-pause {
       description "Pause multicast router no-flood handling job";
       type empty;
     }
   }
   grouping juniper-protocols-bd {
     description "Bridging configuration";
     uses apply-advanced;
     container mac-table-size {
       description "Size of MAC address forwarding table";
       uses apply-advanced;
       leaf limit {
         description "Maximum number of MAC addresses";
         type union {
           type string {
             pattern "<.*>|$.*";
           }
           type uint32;
         }
       }
       leaf packet-action {
         description "Action when MAC limit is reached";
         type enumeration {
           enum "none" {
             description "Forward the packet";
           }
           enum "drop" {
             description "Drop packets and do not learn. Default is forward";
           }
         }
       }
     }
     container mac-ip-table-size {
       description "Size of MAC+IP bindings table";
       uses apply-advanced;
       leaf limit {
         description "Maximum number of MAC+IP bindings";
         type union {
           type string {
             pattern "<.*>|$.*";
           }
           type uint32;
         }
       }
     }
     container interface-mac-limit {
       description "Maximum MAC address learned per interface";
       uses apply-advanced;
       leaf limit {
         description "Maximum number of MAC addresses per interface";
         type union {
           type string {
             pattern "<.*>|$.*";
           }
           type uint32;
         }
       }
       leaf packet-action {
         description "Action when MAC limit is reached";
         type enumeration {
           enum "none" {
             description "Forward the packet";
           }
           enum "drop" {
             description "Drop packets and do not learn. Default is forward";
           }
           enum "log" {
             description "Do not drop the packet but generate an alarm, an SNMP trap or a system log entry";
           }
           enum "shutdown" {
             description "Disable the interface and generate an alarm, an SNMP trap or a system log entry";
           }
           enum "drop-and-log" {
             description "Drop the packet and generate an alarm, an SNMP trap or a system log entry";
           }
         }
       }
     }
     container interface-mac-ip-limit {
       description "Maximum MAC+IP bindings learned per interface";
       uses apply-advanced;
       leaf limit {
         description "Maximum number of MAC+IP bindings per interface";
         type union {
           type string {
             pattern "<.*>|$.*";
           }
           type uint32;
         }
       }
     }
     container mac-move-limit {
       presence "enable mac-move-limit";
       description "Number of MAC movements allowed on this VLAN";
       uses apply-advanced;
       choice limit-choice {
         case case_1 {
           leaf none {
             description "Disable mac-move-limit for this VLAN";
             type empty;
           }
         }
         case case_2 {
           leaf limit {
             description "Number of MAC movements allowed on this VLAN";
             type union {
               type string {
                 pattern "<.*>|$.*";
               }
               type uint32 {
                 range "1 .. 4294967295";
               }
             }
           }
         }
       }
       leaf packet-action {
         description "Action to be taken in case the MAC movement limit is exceeded";
         default "drop";
         type enumeration {
           enum "none" {
             description "Take no action";
           }
           enum "drop" {
             description "Drop the packet and do not generate an alarm";
           }
           enum "log" {
             description "Do not drop the packet but generate an alarm, an SNMP trap, or a system log entry.";
           }
           enum "shutdown" {
             description "Disable the interface and generate an alarm, an SNMP trap, or a system log entry.";
           }
           enum "drop-and-log" {
             description "Drop the packet and generate an alarm, an SNMP trap, or a system log entry.";
           }
           enum "vlan-member-shutdown" {
             description "Disable the interface of this VLAN";
           }
         }
       }
       list interface {
         key name;
         description "Interface that connect this site to the VPN";
         leaf name {
           description "Interface name";
           type union {
             type jt:interface-name;
             type string {
               pattern "<.*>|$.*";
             }
           }
         }
         uses apply-advanced;
         leaf action-priority {
           description "Blocking priority of this interface on mac move detection";
           type union {
             type string {
               pattern "<.*>|$.*";
             }
             type uint32 {
               range "0 .. 7";
             }
           }
         }
       }
     }
     container mac-notification {
       presence "enable mac-notification";
       description "MAC notification options";
       uses apply-advanced;
       leaf notification-interval {
         description "Interval for sending MAC notifications";
         default "30";
         units "seconds";
         type union {
           type string {
             pattern "<.*>|$.*";
           }
           type uint32 {
             range "1 .. 60";
           }
         }
       }
     }
     leaf mac-table-aging-time {
       description "Delay for discarding MAC address if no updates are received";
       units "seconds";
       type union {
         type string {
           pattern "<.*>|$.*";
         }
         type uint32;
       }
     }
     leaf no-mac-learning {
       description "Disable dynamic MAC address learning";
       type empty;
     }
     leaf no-normalization {
       description "Disable vlan id normalization for interfaces";
       type empty;
     }
     leaf drop-unknown-mac-ip {
       description "Drop unknown MAC-IP traffic";
       type empty;
     }
     leaf mac-statistics {
       description "Enable MAC address statistics";
       type empty;
     }
     container mib {
       presence "enable mib";
       description "Snmp mib options";
       uses apply-advanced;
       container dot1q-mib {
         presence "enable dot1q-mib";
         description "Dot1q MIB configuration options";
         uses apply-advanced;
         leaf port-list {
           description "Port list for staticegressports and staticuntaggedports MIB";
           type enumeration {
             enum "bit-map" {
               description "Port list is represented in bit-map format";
             }
             enum "string" {
               description "Port list is represented in string format";
             }
           }
         }
       }
     }
     container static-rvtep-mac {
       description "Configure Static MAC and remote VxLAN tunnel endpoint entries";
       uses apply-advanced;
       list mac {
         key "mac_addr remote-vtep";
         description "Unicast MAC address";
         leaf mac_addr {
           type jt:mac-unicast;
         }
         leaf remote-vtep {
           description "Configure static remote VXLAN tunnel endpoints";
           type jt:ipaddr;
         }
       }
     }
     container network-isolation-profile {
       description "Network isolation configuration";
       uses apply-advanced;
       list group {
         key name;
         description "Network isolation group";
         leaf name {
           description "Group name";
           type string;
         }
         uses apply-advanced;
       }
     }
     list interface {
       key name;
       description "Interface that connect this site to the VPN";
       leaf name {
         description "Interface name";
         type union {
           type jt:interface-name;
           type string {
             pattern "<.*>|$.*";
           }
         }
       }
       uses apply-advanced;
       container mac-learning-priority {
         description "MAC learning priority for the interface";
         uses apply-advanced;
         leaf priority {
           description "Mac learning priority for the interface";
           type union {
             type string {
               pattern "<.*>|$.*";
             }
             type uint32 {
               range "1 .. 65535";
             }
           }
         }
         leaf packet-action {
           default "discard";
           type enumeration {
             enum "discard" {
               description "Discard the packets and do not learn. Default is forward";
             }
             enum "forward" {
               description "Forward the packet";
             }
           }
         }
       }
       container interface-mac-limit {
         description "Maximum number of MAC addresses learned on the interface";
         uses apply-advanced;
         leaf limit {
           description "Maximum number of MAC addresses per interface";
           type union {
             type string {
               pattern "<.*>|$.*";
             }
             type uint32;
           }
         }
         leaf disable {
           description "Disable interface for interface-mac-limit";
           type empty;
         }
         leaf packet-action {
           description "Action when MAC limit is reached";
           type enumeration {
             enum "none" {
               description "Forward the packet";
             }
             enum "drop" {
               description "Drop packets and do not learn. Default is forward";
             }
             enum "log" {
               description "Do not drop the packet but generate an alarm, an SNMP trap or a system log entry";
             }
             enum "shutdown" {
               description "Disable the interface and generate an alarm, an SNMP trap or a system log entry";
             }
             enum "drop-and-log" {
               description "Drop the packet and generate an alarm, an SNMP trap or a system log entry";
             }
           }
         }
       }
       leaf action-priority {
         description "Blocking priority of this interface on mac move detection";
         type union {
           type string {
             pattern "<.*>|$.*";
           }
           type uint32 {
             range "0 .. 8";
           }
         }
       }
       list static-mac {
         key name;
         ordered-by user;
         description "Static MAC addresses assigned to this interface";
         leaf name {
           description "MAC address";
           type jt:mac-addr;
         }
         uses apply-advanced;
         list vlan-id {
           key name;
           ordered-by user;
           description "VLAN ID of learning VLAN";
           leaf name {
             description "Learning VLAN";
             type union {
               type string {
                 pattern "<.*>|$.*";
               }
               type uint32 {
                 range "0 .. 4094";
               }
             }
           }
           uses apply-advanced;
         }
       }
       list static-mac-ip {
         key name;
         ordered-by user;
         description "Static MAC-IP address bindings";
         leaf name {
           description "IP address";
           type jt:ipaddr;
         }
         uses apply-advanced;
         leaf-list mac-address {
           ordered-by user;
           description "MAC address";
           type jt:mac-unicast;
           max-elements 8;
         }
         leaf router {
           description "Router flag for ipv6 addresses";
           type empty;
         }
       }
       container interface-mac-ip-limit {
         description "Maximum number of MAC+IP bindings learned on the interface";
         uses apply-advanced;
         leaf limit {
           description "Maximum number of MAC+IP bindings per interface";
           type union {
             type string {
               pattern "<.*>|$.*";
             }
             type uint32;
           }
         }
       }
       leaf no-mac-learning {
         description "Disable dynamic MAC address learning";
         type empty;
       }
       leaf mac-pinning {
         description "Enable MAC pinning";
         type empty;
       }
     }
   }
   grouping macro-data-type {
     leaf name {
       description "Keyword part of the keyword-value pair";
       type string;
     }
     leaf value {
       description "Value part of the keyword-value pair";
       type string;
     }
   }
   grouping override-type {
     description "DHCP override processing";
     uses apply-advanced;
     leaf no-unicast-replies {
       description "Overwrite unicast bit in incoming packet, when present";
       type empty;
     }
     choice allow-snooped-clients-choice {
       leaf allow-snooped-clients {
         description "Allow client creation from snooped PDUs";
         type empty;
       }
       leaf no-allow-snooped-clients {
         description "Don't allow client creation from snooped PDUs";
         type empty;
       }
     }
     leaf allow-no-end-option {
       description "Allow packets without end-of-option";
       type empty;
     }
     leaf always-write-giaddr {
       description "Overwrite existing 'giaddr' field, when present";
       type empty;
     }
     container always-write-option-82 {
       description "Overwrite existing value of option 82, when present";
       presence "enable always-write-option-82";
       uses write-option-82-type;
     }
     leaf user-defined-option-82 {
       description "Set user defined description for option-82";
       status deprecated;
       type string {
         length "1 .. 252";
       }
     }
     leaf include-option-82-in-vsa {
       description "Include option 82 in Dhcp-Options RADIUS VSA";
       type empty;
     }
     leaf layer2-unicast-replies {
       description "Do not broadcast client responses";
       type empty;
     }
     leaf trust-option-82 {
       description "Trust options-82 option";
       type empty;
     }
     leaf delay-authentication {
       description "Delay subscriber authentication in DHCP protocol processing until request packet";
       type empty;
     }
     leaf disable-relay {
       description "Disable DHCP relay processing";
       type empty;
     }
     leaf no-bind-on-request {
       description "Do not bind if stray DHCP request is received";
       type empty;
     }
     leaf interface-client-limit {
       description "Limit the number of client allowed on an interface";
       type union {
         type string {
           pattern "<.*>|$.*";
         }
         type uint32 {
           range "1 .. 500000";
         }
       }
     }
     leaf no-arp {
       description "Disable DHCP ARP table population";
       status deprecated;
       type empty;
     }
     leaf bootp-support {
       description "Allows relay of bootp req and reply";
       type empty;
     }
     leaf dual-stack {
       description "Dual stack group to use.";
       type string {
         length "1 .. 64";
       }
     }
     container client-discover-match {
       presence "enable client-discover-match";
       description "Use secondary match criteria for DISCOVER PDU";
       choice match-with {
         case case_1 {
           leaf option60-and-option82 {
             description "Use option 60 and option 82";
             type empty;
           }
         }
         case case_2 {
           leaf incoming-interface {
             description "Use incoming interface";
             type empty;
           }
         }
       }
     }
     container proxy-mode {
       presence "enable proxy-mode";
       description "Put the relay in proxy mode";
     }
     leaf asymmetric-lease-time {
       description "Use a reduced lease time for the client. In seconds";
       units "seconds";
       type union {
         type string {
           pattern "<.*>|$.*";
         }
         type uint32 {
           range "600 .. 86400";
         }
       }
     }
     container replace-ip-source-with {
       description "Replace IP source address in request and release packets";
       choice replacement-type {
         case case_1 {
           leaf giaddr {
             description "Replace IP source address with giaddr";
             type empty;
           }
         }
       }
     }
     leaf send-release-on-delete {
       description "Always send RELEASE to the server when a binding is deleted";
       type empty;
     }
     leaf relay-source {
       description "Interface for relay source";
       type union {
         type jt:interface-name;
         type string {
           pattern "<.*>|$.*";
         }
       }
     }
     leaf delete-binding-on-renegotiation {
       description "Delete binding on rengotiation";
       type empty;
     }
   }
   grouping relay-bulk-leasequery-v4-type {
     description "Configure bulk leasequery";
     uses apply-advanced;
     leaf attempts {
       description "Number of retry attempts";
       default "360";
       type union {
         type string {
           pattern "<.*>|$.*";
         }
         type uint32 {
           range "1 .. 720";
         }
       }
     }
     leaf timeout {
       description "Number of seconds";
       default "10";
       units "seconds";
       type union {
         type string {
           pattern "<.*>|$.*";
         }
         type uint32 {
           range "1 .. 10";
         }
       }
     }
   }
   grouping relay-bulk-leasequery-v6-type {
     description "Configure bulk leasequery";
     uses apply-advanced;
     leaf attempts {
       description "Number of retry attempts";
       default "6";
       type union {
         type string {
           pattern "<.*>|$.*";
         }
         type uint32 {
           range "1 .. 10";
         }
       }
     }
     leaf timeout {
       description "Number of seconds";
       default "10";
       units "seconds";
       type union {
         type string {
           pattern "<.*>|$.*";
         }
         type uint32 {
           range "1 .. 10";
         }
       }
     }
     container trigger {
       description "Trigger for bulk leasequery";
       leaf automatic {
         description "Trigger automatically";
         type empty;
       }
     }
   }
   grouping relay-leasequery-type {
     description "Configure leasequery";
     uses apply-advanced;
     leaf attempts {
       description "Number of retry attempts";
       default "6";
       type union {
         type string {
           pattern "<.*>|$.*";
         }
         type uint32 {
           range "1 .. 10";
         }
       }
     }
     leaf timeout {
       description "Number of seconds";
       default "10";
       units "seconds";
       type union {
         type string {
           pattern "<.*>|$.*";
         }
         type uint32 {
           range "1 .. 10";
         }
       }
     }
   }
   grouping relay-option-60-type-group {
     description "DHCP option-60 processing";
     uses apply-advanced;
     container vendor-option {
       description "Add vendor option";
       uses apply-advanced;
       container equals {
         description "Option 60 equals";
         uses relay-option-60-match-group;
       }
       container not-equals {
         description "Option 60 does not equal";
         status deprecated;
         uses relay-option-60-match-group;
       }
       container starts-with {
         description "Option 60 starts with";
         uses relay-option-60-match-group;
       }
       choice server-group-choice {
         case case_1 {
           leaf default-relay-server-group {
             description "Name of DHCP relay server group when match is not made";
             type string {
               length "1 .. 64";
             }
           }
         }
         case case_2 {
           leaf default-local-server-group {
             description "Name of DHCP local server group when match is not made";
             type string {
               length "1 .. 64";
             }
           }
         }
         case case_3 {
           leaf drop {
             description "Discard when a match is not made";
             type empty;
           }
         }
         case case_4 {
           leaf forward-only {
             description "Forward without subscriber services when a match is not made";
             type empty;
           }
         }
       }
     }
   }
   grouping relay-option-60-match-group {
     uses apply-advanced;
     list ascii {
       key name;
       description "ASCII string";
       leaf name {
         description "ASCII string";
         type string {
           length "1 .. 256";
         }
       }
       uses apply-advanced;
       choice server-group-choice {
         case case_1 {
           leaf relay-server-group {
             description "Name of DHCP relay server group when match is made";
             type string {
               length "1 .. 64";
             }
           }
         }
         case case_2 {
           leaf local-server-group {
             description "Name of DHCP local server group when match is made";
             type string {
               length "1 .. 64";
             }
           }
         }
         case case_3 {
           leaf drop {
             description "Discard when a match is made";
             type empty;
           }
         }
         case case_4 {
           leaf forward-only {
             description "Forward without subscriber services when a match is made";
             type empty;
           }
         }
       }
     }
     list hexadecimal {
       key name;
       description "Hexadecimal string";
       leaf name {
         description "Hexadecimal string";
         type string {
           length "1 .. 512";
         }
       }
       uses apply-advanced;
       choice server-group-choice {
         case case_1 {
           leaf relay-server-group {
             description "Name of DHCP relay server group when match is made";
             type string {
               length "1 .. 64";
             }
           }
         }
         case case_2 {
           leaf local-server-group {
             description "Name of DHCP local server group when match is made";
             type string {
               length "1 .. 64";
             }
           }
         }
         case case_3 {
           leaf drop {
             description "Discard when a match is made";
             type empty;
           }
         }
         case case_4 {
           leaf forward-only {
             description "Forward without subscriber services when a match is made";
             type empty;
           }
         }
       }
     }
   }
   grouping relay-option-60-type-top {
     description "DHCP option-60 processing";
     uses apply-advanced;
     container vendor-option {
       description "Add vendor option";
       uses apply-advanced;
       container equals {
         description "Option 60 equals";
         uses relay-option-60-match-top;
       }
       container not-equals {
         description "Option 60 does not equal";
         status deprecated;
         uses relay-option-60-match-top;
       }
       container starts-with {
         description "Option 60 starts with";
         uses relay-option-60-match-top;
       }
       choice server-group-choice {
         case case_1 {
           leaf default-relay-server-group {
             description "Name of DHCP relay server group when match is not made";
             type string {
               length "1 .. 64";
             }
           }
         }
         case case_2 {
           leaf default-local-server-group {
             description "Name of DHCP local server group when match is not made";
             type string {
               length "1 .. 64";
             }
           }
         }
         case case_3 {
           leaf drop {
             description "Discard when a match is not made";
             type empty;
           }
         }
         case case_4 {
           leaf forward-only {
             description "Forward without subscriber services when a match is not made";
             type empty;
           }
         }
       }
     }
   }
   grouping relay-option-60-match-top {
     uses apply-advanced;
     list ascii {
       key name;
       description "ASCII string";
       leaf name {
         description "ASCII string";
         type string {
           length "1 .. 256";
         }
       }
       uses apply-advanced;
       choice server-group-choice {
         case case_1 {
           leaf relay-server-group {
             description "Name of DHCP relay server group when match is made";
             type string {
               length "1 .. 64";
             }
           }
         }
         case case_2 {
           leaf local-server-group {
             description "Name of DHCP local server group when match is made";
             type string {
               length "1 .. 64";
             }
           }
         }
         case case_3 {
           leaf drop {
             description "Discard when a match is made";
             type empty;
           }
         }
         case case_4 {
           leaf forward-only {
             description "Forward without subscriber services when a match is made";
             type empty;
           }
         }
       }
     }
     list hexadecimal {
       key name;
       description "Hexadecimal string";
       leaf name {
         description "Hexadecimal string";
         type string {
           length "1 .. 512";
         }
       }
       uses apply-advanced;
       choice server-group-choice {
         case case_1 {
           leaf relay-server-group {
             description "Name of DHCP relay server group when match is made";
             type string {
               length "1 .. 64";
             }
           }
         }
         case case_2 {
           leaf local-server-group {
             description "Name of DHCP local server group when match is made";
             type string {
               length "1 .. 64";
             }
           }
         }
         case case_3 {
           leaf drop {
             description "Discard when a match is made";
             type empty;
           }
         }
         case case_4 {
           leaf forward-only {
             description "Forward without subscriber services when a match is made";
             type empty;
           }
         }
       }
     }
   }
   grouping relay-option-82-type {
     description "DHCP option-82 processing";
     uses apply-advanced;
     container circuit-id {
       presence "enable circuit-id";
       description "Add circuit identifier";
       uses apply-advanced;
       container prefix {
         description "Add prefix to circuit/interface-id or remote-id";
         uses apply-advanced;
         leaf host-name {
           description "Add router host name to circuit / interface-id or remote-id";
           type empty;
         }
         leaf logical-system-name {
           description "Add logical system name to circuit / interface-id or remote-id";
           type empty;
         }
         leaf routing-instance-name {
           description "Add routing instance name to circuit / interface-id or remote-id";
           type empty;
         }
       }
       leaf use-interface-description {
         description "Use interface description instead of circuit identifier";
         type enumeration {
           enum "logical" {
             description "Use the logical interface description";
           }
           enum "device" {
             description "Use the device interface description";
           }
         }
       }
       leaf use-vlan-id {
         description "Use VLAN id instead of name";
         type empty;
       }
       container vlan-id-only {
         presence "enable vlan-id-only";
         description "Use only VLAN id";
         uses apply-advanced;
       }
       leaf no-vlan-interface-name {
         description "Not include vlan or interface name";
         type empty;
       }
       leaf include-irb-and-l2 {
         description "Include IRB and L2 interface name";
         type empty;
       }
       container user-defined {
         presence "enable user-defined";
         description "Include user defined string";
         uses apply-advanced;
         leaf string {
           description "Set user-defined character string description";
           type string {
             length "1 .. 252";
           }
         }
         leaf hex-string {
           description "Set user-defined hexadecimal string description";
           type string {
             length "1 .. 510";
           }
         }
       }
       leaf keep-incoming-circuit-id {
         description "Keep incoming circuit identifier";
         type empty;
       }
     }
     container remote-id {
       presence "enable remote-id";
       description "Add remote identifier";
       uses apply-advanced;
       container prefix {
         description "Add prefix to circuit/interface-id or remote-id";
         uses apply-advanced;
         leaf host-name {
           description "Add router host name to circuit / interface-id or remote-id";
           type empty;
         }
         leaf logical-system-name {
           description "Add logical system name to circuit / interface-id or remote-id";
           type empty;
         }
         leaf routing-instance-name {
           description "Add routing instance name to circuit / interface-id or remote-id";
           type empty;
         }
       }
       leaf use-interface-description {
         description "Use interface description instead of circuit identifier";
         type enumeration {
           enum "logical" {
             description "Use the logical interface description";
           }
           enum "device" {
             description "Use the device interface description";
           }
         }
       }
       leaf use-vlan-id {
         description "Use VLAN id instead of name";
         type empty;
       }
       leaf no-vlan-interface-name {
         description "Not include vlan or interface name";
         type empty;
       }
       leaf include-irb-and-l2 {
         description "Include IRB and L2 interface name";
         type empty;
       }
       container hostname-only {
         presence "enable hostname-only";
         description "Include hostname only";
         uses apply-advanced;
       }
       container user-defined {
         presence "enable user-defined";
         description "Include user defined string";
         uses apply-advanced;
         leaf string {
           description "Set user-defined character string description";
           type string {
             length "1 .. 252";
           }
         }
         leaf hex-string {
           description "Set user-defined hexadecimal string description";
           type string {
             length "1 .. 510";
           }
         }
       }
       leaf keep-incoming-remote-id {
         description "Keep incoming remote identifier";
         type empty;
       }
       leaf use-string {
         description "Use raw string instead of the default remote id";
         status deprecated;
         type string;
       }
     }
     leaf server-id-override {
       description "Add link-selection and server-id sub-options on packets to server";
       type empty;
     }
     leaf link-selection {
       description "Add link-selection suboption on packets to server";
       type empty;
     }
     leaf exclude-relay-agent-identifier {
       description "Exclude relay agent identifier from packets to server";
       type empty;
     }
     container vendor-specific {
       description "Add vendor-specific information";
       uses jdhcp-vendor-specific-type;
     }
   }
   grouping relay-v4-option-ascii-hex {
     uses apply-advanced;
     list ascii {
       key name;
       description "ASCII string";
       leaf name {
         description "ASCII string";
         type string {
           length "1 .. 256";
         }
       }
       uses apply-advanced;
       choice server-group-choice {
         case case_1 {
           leaf relay-server-group {
             description "Name of DHCP relay server group when match is made";
             type string {
               length "1 .. 64";
             }
           }
         }
         case case_2 {
           leaf local-server-group {
             description "Name of DHCP local server group when match is made";
             type string {
               length "1 .. 64";
             }
           }
         }
         case case_3 {
           leaf drop {
             description "Discard when a match is made";
             type empty;
           }
         }
         case case_4 {
           leaf forward-only {
             description "Forward without subscriber services when a match is made";
             type empty;
           }
         }
       }
     }
     list hexadecimal {
       key name;
       description "Hexadecimal string";
       leaf name {
         description "Hexadecimal string";
         type string {
           length "1 .. 512";
         }
       }
       uses apply-advanced;
       choice server-group-choice {
         case case_1 {
           leaf relay-server-group {
             description "Name of DHCP relay server group when match is made";
             type string {
               length "1 .. 64";
             }
           }
         }
         case case_2 {
           leaf local-server-group {
             description "Name of DHCP local server group when match is made";
             type string {
               length "1 .. 64";
             }
           }
         }
         case case_3 {
           leaf drop {
             description "Discard when a match is made";
             type empty;
           }
         }
         case case_4 {
           leaf forward-only {
             description "Forward without subscriber services when a match is made";
             type empty;
           }
         }
       }
     }
   }
   grouping relay-v6-option-ascii-hex {
     uses apply-advanced;
     list ascii {
       key name;
       description "ASCII string";
       leaf name {
         description "ASCII string";
         type string {
           length "1 .. 256";
         }
       }
       uses apply-advanced;
       choice server-group-choice {
         case case_1 {
           leaf relay-server-group {
             description "Name of DHCP relay server group when match is made";
             type string {
               length "1 .. 64";
             }
           }
         }
         case case_2 {
           leaf drop {
             description "Discard when a match is made";
             type empty;
           }
         }
         case case_3 {
           leaf forward-only {
             description "Forward without subscriber services when a match is made";
             type empty;
           }
         }
       }
     }
     list hexadecimal {
       key name;
       description "Hexadecimal string";
       leaf name {
         description "Hexadecimal string";
         type string {
           length "1 .. 512";
         }
       }
       uses apply-advanced;
       choice server-group-choice {
         case case_1 {
           leaf relay-server-group {
             description "Name of DHCP relay server group when match is made";
             type string {
               length "1 .. 64";
             }
           }
         }
         case case_2 {
           leaf drop {
             description "Discard when a match is made";
             type empty;
           }
         }
         case case_3 {
           leaf forward-only {
             description "Forward without subscriber services when a match is made";
             type empty;
           }
         }
       }
     }
   }
   grouping security-dhcpv6-options-type {
     description "Configure DHCPv6 options";
     uses apply-advanced;
     container option-37 {
       presence "enable option-37";
       description "Configure DHCPv6 remote identifier option";
       uses apply-advanced;
       container prefix {
         description "Configure DHCPv6 remote identifier prefix";
         uses apply-advanced;
         leaf host-name {
           description "Prefix router host name to DHCPv6 remote identifier";
           type empty;
         }
         leaf logical-system-name {
           description "Prefix logical system name to DHCPv6 remote identifier";
           type empty;
         }
         leaf routing-instance-name {
           description "Prefix routing instance name to DHCPv6 remote identifier";
           type empty;
         }
         leaf vlan-name {
           description "Prefix vlan name to DHCPv6 remote identifier";
           type empty;
         }
         leaf vlan-id {
           description "Prefix vlan tag to DHCPv6 remote identifier";
           type empty;
         }
       }
       leaf use-interface-mac {
         description "Add incoming interface's MAC address to DHCPv6 remote identifier";
         type empty;
       }
       leaf use-interface-index {
         description "Add interface index to DHCPv6 remote identifier";
         type enumeration {
           enum "logical" {
             description "Use the logical interface index";
           }
           enum "device" {
             description "Use the device interface index";
           }
         }
       }
       leaf use-interface-name {
         description "Add interface name to DHCPv6 remote identifier";
         type enumeration {
           enum "logical" {
             description "Use the logical interface name";
           }
           enum "device" {
             description "Use the device interface name";
           }
         }
       }
       leaf use-interface-description {
         description "Add interface description to DHCPv6 remote identifier";
         type enumeration {
           enum "logical" {
             description "Use the logical interface description";
           }
           enum "device" {
             description "Use the device interface description";
           }
         }
       }
       leaf use-string {
         description "Add custom string to DHCPv6 remote identifier";
         type string;
       }
     }
     container option-18 {
       presence "enable option-18";
       description "Configure DHCPv6 interface identifier option";
       uses apply-advanced;
       container prefix {
         description "Configure DHCPv6 interface identifier prefix";
         uses apply-advanced;
         leaf host-name {
           description "Prefix router host name to DHCPv6 interface identifier";
           type empty;
         }
         leaf logical-system-name {
           description "Prefix logical system name to DHCPv6 interface identifier";
           type empty;
         }
         leaf routing-instance-name {
           description "Prefix routing instance name to DHCPv6 interface identifier";
           type empty;
         }
         leaf vlan-name {
           description "Prefix vlan name to DHCPv6 interface identifier";
           type empty;
         }
         leaf vlan-id {
           description "Prefix vlan tag to DHCPv6 interface identifier";
           type empty;
         }
       }
       leaf use-interface-mac {
         description "Add incoming interface's MAC address to DHCPv6 circuit identifier";
         type empty;
       }
       leaf use-interface-index {
         description "Add interface index to DHCPv6 interface identifier";
         type enumeration {
           enum "logical" {
             description "Use the logical interface index";
           }
           enum "device" {
             description "Use the device interface index";
           }
         }
       }
       leaf use-interface-name {
         description "Add interface name to DHCPv6 remote identifier";
         type enumeration {
           enum "logical" {
             description "Use the logical interface name";
           }
           enum "device" {
             description "Use the device interface name";
           }
         }
       }
       leaf use-interface-description {
         description "Add interface description to DHCPv6 interface identifier";
         type enumeration {
           enum "logical" {
             description "Use the logical interface description";
           }
           enum "device" {
             description "Use the device interface description";
           }
         }
       }
       leaf use-string {
         description "Add custom string to DHCPv6 interface identifier";
         type string;
       }
     }
     container option-16 {
       presence "enable option-16";
       description "Configure DHCPv6 vendor class identifier option. Overwrite if exists";
       uses apply-advanced;
       leaf use-string {
         description "Add custom string to DHCPv6 vendor identifier";
         type string;
       }
     }
     leaf option-79 {
       description "Configure DHCPv6 client link layer address option";
       type empty;
     }
   }
   grouping security-option-82-type {
     description "DHCP option-82 processing";
     uses apply-advanced;
     container circuit-id {
       presence "enable circuit-id";
       description "Configure DHCP option 82 circuit id";
       uses apply-advanced;
       container prefix {
         description "Configure DHCP option 82 circuit id prefix";
         uses apply-advanced;
         leaf host-name {
           description "Add router host name to DHCP option-82 circuit id";
           type empty;
         }
         leaf logical-system-name {
           description "Add logical system name to DHCP option-82 circuit id";
           type empty;
         }
         leaf routing-instance-name {
           description "Add routing instance name to DHCP option-82 circuit id";
           type empty;
         }
       }
       leaf use-interface-description {
         description "Use interface description instead of circuit identifier";
         type enumeration {
           enum "logical" {
             description "Use the logical interface description";
           }
           enum "device" {
             description "Use the device interface description";
           }
         }
       }
       leaf use-vlan-id {
         description "Use VLAN id instead of name";
         type empty;
       }
     }
     container remote-id {
       presence "enable remote-id";
       description "Configure DHCP option 82 remote id";
       uses apply-advanced;
       leaf host-name {
         description "Add router host name to DHCP option-82 remote id";
         type empty;
       }
       leaf use-interface-description {
         description "Use interface description instead of interface name";
         type enumeration {
           enum "logical" {
             description "Use the logical interface description";
           }
           enum "device" {
             description "Use the device interface description";
           }
         }
       }
       leaf use-string {
         description "Use raw string instead of the default remote id";
         type string;
       }
       leaf mac {
         description "Add chassis MAC Address to DHCP option-82 remote id";
         type empty;
       }
     }
     container vendor-id {
       presence "enable vendor-id";
       description "Configure DHCP option 82 vendor id";
       uses apply-advanced;
       leaf use-string {
         description "Use raw string instead of the default vendor id";
         default "Juniper Networks";
         type string;
       }
     }
   }
   grouping server-group-type {
     uses apply-advanced;
     list server-group {
       key name;
       description "One or more server groups";
       leaf name {
         description "Server group name";
         type string {
           length "1 .. 64";
         }
       }
       uses apply-advanced;
       list address {
         key name;
         description "IP Address of one or more DHCP servers";
         max-elements 32;
         leaf name {
           description "IP Address of DHCP server";
           type jt:ipaddr;
         }
         uses apply-advanced;
       }
     }
   }
   grouping server-match-action-choice {
     uses apply-advanced;
     choice v4-action-choice {
       case case_1 {
         leaf forward-only {
           description "Forward without subscriber services";
           type empty;
         }
       }
       case case_2 {
         leaf create-relay-entry {
           description "Create relay entry and allow subscriber services";
           type empty;
         }
       }
     }
   }
   grouping server-match-v6-ascii-hex {
     uses apply-advanced;
     list ascii {
       key name;
       description "ASCII string";
       leaf name {
         description "ASCII string";
         type string {
           length "1 .. 256";
         }
       }
       uses apply-advanced;
       choice server-match-action-choice {
         case case_1 {
           leaf forward-only {
             description "Forward without subscriber services when a match is made";
             type empty;
           }
         }
         case case_2 {
           leaf create-relay-entry {
             description "Create relay entry and allow subscriber services";
             type empty;
           }
         }
       }
     }
     list hexadecimal {
       key name;
       description "Hexadecimal string";
       leaf name {
         description "Hexadecimal string";
         type string {
           length "1 .. 512";
         }
       }
       uses apply-advanced;
       choice server-match-action-choice {
         case case_1 {
           leaf forward-only {
             description "Forward without subscriber services when a match is made";
             type empty;
           }
         }
         case case_2 {
           leaf create-relay-entry {
             description "Create relay entry and allow subscriber services";
             type empty;
           }
         }
       }
     }
   }
   grouping v6-relay-option-interface-id-type {
     description "Interface ID processing";
     uses apply-advanced;
     container prefix {
       description "Add prefix to circuit/interface-id or remote-id";
       uses apply-advanced;
       leaf host-name {
         description "Add router host name to circuit / interface-id or remote-id";
         type empty;
       }
       leaf logical-system-name {
         description "Add logical system name to circuit / interface-id or remote-id";
         type empty;
       }
       leaf routing-instance-name {
         description "Add routing instance name to circuit / interface-id or remote-id";
         type empty;
       }
     }
     leaf use-interface-description {
       description "Use interface description instead of circuit identifier";
       type enumeration {
         enum "logical" {
           description "Use the logical interface description";
         }
         enum "device" {
           description "Use the device interface description";
         }
       }
     }
     leaf use-vlan-id {
       description "Use VLAN id instead of name";
       type empty;
     }
     leaf no-vlan-interface-name {
       description "Not include vlan or interface name";
       type empty;
     }
     leaf include-irb-and-l2 {
       description "Include IRB and L2 interface name";
       type empty;
     }
     container user-defined {
       presence "enable user-defined";
       description "Include user defined string";
       uses apply-advanced;
       leaf string {
         description "Set user-defined character string description";
         type string {
           length "1 .. 252";
         }
       }
       leaf hex-string {
         description "Set user-defined hexadecimal string description";
         type string {
           length "1 .. 510";
         }
       }
     }
     container use-option-82 {
       description "Use option-82 circuit-id for interface-id";
       presence "enable use-option-82";
       uses v6-relay-option-cid-rid-action;
     }
     container keep-incoming-interface-id {
       description "Keep incoming interface identifier";
       presence "enable keep-incoming-interface-id";
       uses v6-relay-option-cid-rid-action;
     }
   }
   grouping v6-relay-option-cid-rid-action {
     uses apply-advanced;
     leaf strict {
       description "Drop packet if id not present";
       type empty;
     }
   }
   grouping v6-relay-option-remote-id-type {
     description "Remote ID processing";
     uses apply-advanced;
     container prefix {
       description "Add prefix to circuit/interface-id or remote-id";
       uses apply-advanced;
       leaf host-name {
         description "Add router host name to circuit / interface-id or remote-id";
         type empty;
       }
       leaf logical-system-name {
         description "Add logical system name to circuit / interface-id or remote-id";
         type empty;
       }
       leaf routing-instance-name {
         description "Add routing instance name to circuit / interface-id or remote-id";
         type empty;
       }
     }
     leaf use-interface-description {
       description "Use interface description instead of circuit identifier";
       type enumeration {
         enum "logical" {
           description "Use the logical interface description";
         }
         enum "device" {
           description "Use the device interface description";
         }
       }
     }
     leaf use-vlan-id {
       description "Use VLAN id instead of name";
       type empty;
     }
     leaf no-vlan-interface-name {
       description "Not include vlan or interface name";
       type empty;
     }
     leaf include-irb-and-l2 {
       description "Include IRB and L2 interface name";
       type empty;
     }
     container user-defined {
       presence "enable user-defined";
       description "Include user defined string";
       uses apply-advanced;
       leaf string {
         description "Set user-defined character string description";
         type string {
           length "1 .. 252";
         }
       }
       leaf hex-string {
         description "Set user-defined hexadecimal string description";
         type string {
           length "1 .. 510";
         }
       }
     }
     container use-option-82 {
       description "Use option-82 remote-id for v6 remote-id";
       presence "enable use-option-82";
       uses v6-relay-option-cid-rid-action;
     }
     leaf keep-incoming-remote-id {
       description "Keep incoming remote identifier";
       type empty;
     }
   }
   grouping v6-server-group-type {
     uses apply-advanced;
     list server-group {
       key name;
       description "One or more server groups";
       leaf name {
         description "DHCPv6 Server group name";
         type string {
           length "1 .. 64";
         }
       }
       uses apply-advanced;
       list address {
         key name;
         description "IP Address of one or more DHCP servers";
         max-elements 32;
         leaf name {
           description "IP Address of DHCP server";
           type jt:ipaddr;
         }
         uses apply-advanced;
       }
     }
   }
   grouping write-option-82-type {
     uses apply-advanced;
   }
 }
