module junos-genstate-statistics {
   yang-version 1;
   namespace "http://yang.juniper.net/junos/genstate/statistics";
   prefix jgss;

   import junos-genstate {
     prefix jgs;
     revision-date 2024-01-01;
   }

   import junos-common-types {
     prefix jt;
     revision-date 2024-01-01;
   }

   organization
     "Juniper Networks, Inc.";

   contact
     "Juniper Networks, Inc.

      1133 Innovation Way
      Sunnyvale, CA 94089

      +1 888 314-5822

      E-mail: yang-support@juniper.net";

   description "Junos genstate data model for statistics";

   revision 2024-01-01 {
     description "Junos: 24.4R2.16-EVO";
   }

   grouping statistics-top {
     description "Top-level grouping";
     container statistics {
       description "Top-level container";
       container tcp {
         leaf packets-sent {
           type uint32;
           description "Packets sent";
         }
         leaf sent-data-packets {
           type uint32;
           description "Data packets";
         }
         leaf data-packets-bytes {
           type uint32;
           description "In terms of bytes";
         }
         leaf sent-data-packets-retransmitted {
           type uint32;
           description "Data packets retransmitted";
         }
         leaf retransmitted-bytes {
           type uint32;
           description "In terms of bytes";
         }
         leaf sent-data-unnecessary-retransmitted {
           type uint32;
           description "Data unnecessary retransmitted";
         }
         leaf sent-resends-by-mtu-discovery {
           type uint32;
           description "Resends initiated by MTU discovery";
         }
         leaf sent-ack-only-packets {
           type uint32;
           description "Ack-only packets";
         }
         leaf sent-packets-delayed {
           type uint32;
           description "Number of packets delayed";
         }
         leaf sent-urg-only-packets {
           type uint32;
           description "URG only packets";
         }
         leaf sent-window-probe-packets {
           type uint32;
           description "Window probe packets";
         }
         leaf sent-window-update-packets {
           type uint32;
           description "Window update packets";
         }
         leaf sent-control-packets {
           type uint32;
           description "Control packets";
         }
         leaf packets-received {
           type uint32;
           description "Packets received";
         }
         leaf received-acks {
           type uint32;
           description "Acks";
         }
         leaf acks-bytes {
           type uint32;
           description "Number of bytes";
         }
         leaf received-duplicate-acks {
           type uint32;
           description "Dupliacte acks";
         }
         leaf received-acks-for-unsent-data {
           type uint32;
           description "Acks for unsent data";
         }
         leaf packets-received-in-sequence {
           type uint32;
           description "Packets received in-sequence";
         }
         leaf in-sequence-bytes {
           type uint32;
           description "Packets received in-sequence in bytes";
         }
         leaf received-completely-duplicate-packet {
           type uint32;
           description "Completely duplicate packets";
         }
         leaf duplicate-in-bytes {
           type uint32;
           description "Completely duplicate packets in bytes";
         }
         leaf received-old-duplicate-packets {
           type uint32;
           description "Old duplicate packets";
         }
         leaf received-packets-with-some-dupliacte-data {
           type uint32;
           description "Packets with some duplicate data";
         }
         leaf some-duplicate-in-bytes {
           type uint32;
           description "Packets with some duplicate data in bytes";
         }
         leaf received-out-of-order-packets {
           type uint32;
           description "Out-of-order packets";
         }
         leaf out-of-order-in-bytes {
           type uint32;
           description "Out-of-order packets in bytes";
         }
         leaf received-packets-of-data-after-window {
           type uint32;
           description "Packets of data after window";
         }
         leaf bytes {
           type uint32;
           description "Packets of data after window in bytes";
         }
         leaf received-window-probes {
           type uint32;
           description "Window probes";
         }
         leaf received-window-update-packets {
           type uint32;
         }
         leaf packets-received-after-close {
           type uint32;
           description "Packets received after close";
         }
         leaf received-discarded-for-bad-checksum {
           type uint32;
           description "Discarded for bad checksum";
         }
         leaf received-discarded-for-bad-header-offset {
           type uint32;
           description "Discarded for bad header offset fields";
         }
         leaf received-discarded-because-packet-too-short {
           type uint32;
           description "Discarded because packet too short";
         }
         leaf connection-requests {
           type uint32;
           description "Connection requests";
         }
         leaf connection-accepts {
           type uint32;
           description "Connection accepts";
         }
         leaf bad-connection-attempts {
           type uint32;
           description "Bad connection attempts";
         }
         leaf listen-queue-overflows {
           type uint32;
           description "Listen queue overflows";
         }
         leaf bad-rst-window {
           type uint32;
           description "Ignored RSTs in the windows";
         }
         leaf connections-established {
           type uint32;
           description "Connections established";
         }
         leaf connections-closed {
           type uint32;
           description "Connections closed";
         }
         leaf drops {
           type uint32;
           description "Drops";
         }
         leaf connections-updated-rtt-on-close {
           type uint32;
           description "Connections updated cached RTT on close";
         }
         leaf connections-updated-variance-on-close {
           type uint32;
           description "Connections updated cached RTT variance on close";
         }
         leaf connections-updated-ssthresh-on-close {
           type uint32;
           description "Connections updated cached ssthresh on close";
         }
         leaf embryonic-connections-dropped {
           type uint32;
           description "Embryonic connections dropped";
         }
         leaf segments-updated-rtt {
           type uint32;
           description "Segments updated RTT";
         }
         leaf attempts {
           type uint32;
           description "Attempts";
         }
         leaf retransmit-timeouts {
           type uint32;
           description "Retransmit timeouts";
         }
         leaf connections-dropped-by-retransmit-timeout {
           type uint32;
           description "Connections dropped";
         }
         leaf persist-timeouts {
           type uint32;
           description "Persist timeouts";
         }
         leaf connections-dropped-by-persist-timeout {
           type uint32;
         }
         leaf keepalive-timeouts {
           type uint32;
           description "Keepalive timeouts";
         }
         leaf keepalive-probes-sent {
           type uint32;
           description "Keepalive probes sent";
         }
         leaf keepalive-connections-dropped {
           type uint32;
           description "Keepalive connections dropped";
         }
         leaf ack-header-predictions {
           type uint32;
           description "Correct ACK header predictions";
         }
         leaf data-packet-header-predictions {
           type uint32;
           description "Correct data packet header predictions";
         }
         leaf syncache-entries-added {
           type uint32;
           description "Syncache entries added";
         }
         leaf retransmitted {
           type uint32;
           description "Retransmitted in syncache entries added";
         }
         leaf dupsyn {
           type uint32;
           description "Dupsyn in syncache entries added";
         }
         leaf dropped {
           type uint32;
           description "Dropped in syncache entries added";
         }
         leaf completed {
           type uint32;
           description "Completed in syncache entries added";
         }
         leaf bucket-overflow {
           type uint32;
           description "Bucket overflow in syncache entries added";
         }
         leaf cache-overflow {
           type uint32;
           description "Cache overflow in syncache entries added";
         }
         leaf reset {
           type uint32;
           description "Reset in syncache entries added";
         }
         leaf stale {
           type uint32;
           description "Stale in syncache entries added";
         }
         leaf aborted {
           type uint32;
           description "Aborted in syncache entries added";
         }
         leaf badack {
           type uint32;
           description "Bad ACK in syncache entries added";
         }
         leaf unreach {
           type uint32;
           description "Unreach in syncache entries added";
         }
         leaf zone-failures {
           type uint32;
           description "Zone failures in syncache entries added";
         }
         leaf cookies-sent {
           type uint32;
           description "Cookies sent";
         }
         leaf cookies-received {
           type uint32;
           description "Cookies received";
         }
         leaf sack-recovery-episodes {
           type uint32;
           description "SACK recovery episodes";
         }
         leaf segment-retransmits {
           type uint32;
           description "Segment retransmits in SACK recovery episodes";
         }
         leaf byte-retransmits {
           type uint32;
           description "Byte retransmits in SACK recovery episodes";
         }
         leaf sack-options-received {
           type uint32;
           description "SACK options (SACK blocks) received";
         }
         leaf sack-opitions-sent {
           type uint32;
           description "SACK options (SACK blocks) sent";
         }
         leaf sack-scoreboard-overflow {
           type uint32;
           description "SACK scoreboard overflow";
         }
         leaf acks-sent-in-response-but-not-exact-rsts {
           type uint32;
           description "ACKs sent in response to in-window but not exact RSTs";
         }
         leaf acks-sent-in-response-to-syns-on-established-connections {
           type uint32;
           description "ACKs sent in response to in-window SYNs on established connections";
         }
         leaf rcv-packets-dropped-due-to-bad-address {
           type uint32;
           description "Rcv packets dropped dropped by TCP due to bad address";
         }
         leaf out-of-sequence-segment-drops {
           type uint32;
           description "Out-of-sequence segment drops due to insufficient memory";
         }
         leaf rst-packets {
           type uint32;
           description "RST packets";
         }
         leaf icmp-packets-ignored {
           type uint32;
           description "ICMP packets ignored by TCP";
         }
         leaf send-packets-dropped {
           type uint32;
           description "Send packets dropped by TCP due to auth errors";
         }
         leaf rcv-packets-dropped {
           type uint32;
         }
         leaf outgoing-segments-dropped {
           type uint32;
           description "Outgoing segments dropped due to policing";
         }
         leaf received-synfin-dropped {
           type uint32;
           description "SYN,FIN packets dropped";
         }
         leaf received-ipsec-dropped {
           type uint32;
           description "Packets dropped due to IPSEC validation failed";
         }
         leaf received-mac-dropped {
           type uint32;
           description "Packets dropped due to MAC validation failed";
         }
         leaf received-minttl-exceeded {
           type uint32;
           description "Packets dropped as TTL exceed min TTL";
         }
         leaf listenstate-badflags-dropped {
           type uint32;
           description "Packets dropped due to non expected TCP flags in listen state";
         }
         leaf finwaitstate-badflags-dropped {
           type uint32;
           description "Packets dropped as TCP flags other than FIN/RST not expected in FIN wait state";
         }
         leaf received-dos-attack {
           type uint32;
           description "Packets dropped as part of DoS Attack";
         }
         leaf received-bad-synack {
           type uint32;
           description "Packets dropped due to bad SYN,ACK in SYN sent or received state";
         }
         leaf syncache-zone-full {
           type uint32;
           description "Packets dropped as sc zone full";
         }
         leaf received-rst-firewallfilter {
           type uint32;
           description "Received RST during reset send from firewall";
         }
         leaf received-noack-timewait {
           type uint32;
           description "Packets dropped as this is not ACK in timewait check";
         }
         leaf received-no-timewait-state {
           type uint32;
           description "Packets dropped as no timewait state";
         }
         leaf received-rst-timewait-state {
           type uint32;
           description "Packets dropped as reset received in timewait check";
         }
         leaf received-timewait-drops {
           type uint32;
           description "Packets dropped during timewait check";
         }
         leaf received-badaddr-timewait-state {
           type uint32;
           description "Packets dropped due as broadcast/multicast address in timewait";
         }
         leaf received-ackoff-in-syn-sentrcvd {
           type uint32;
           description "Packets dropped as no ack received when other than SYN sent or received state";
         }
         leaf received-badaddr-firewall {
           type uint32;
           description "Packets dropped broadcast/multicast address in firewall match";
         }
         leaf received-nosyn-syn-sent {
           type uint32;
           description "Packets dropped as no SYN received in SYN sent state";
         }
         leaf received-badrst-syn-sent {
           type uint32;
           description "Packets dropped as reset packet received in SYN sent state";
         }
         leaf received-badrst-listen-state {
           type uint32;
           description "Packets dropped as reset packet received in listen state";
         }
         leaf option-maxsegment-length {
           type uint32;
           description "TCP option max segment length is invalid";
         }
         leaf option-window-length {
           type uint32;
           description "TCP option window length is invalid";
         }
         leaf option-timestamp-length {
           type uint32;
           description "TCP option timestamp length is invalid";
         }
         leaf option-md5-length {
           type uint32;
           description "Packets TCP option MD5 length is invalid";
         }
         leaf option-auth-length {
           type uint32;
           description "TCP option authentication length is invalid";
         }
         leaf option-sackpermitted-length {
           type uint32;
           description "TCP option sack permitted length is invalid";
         }
         leaf option-sack-length {
           type uint32;
           description "TCP option selective acknowledgement length is invalid";
         }
         leaf option-authoption-length {
           type uint32;
           description "TCP option authentication option length is invalid";
         }
       }
       container sctp {
         leaf input-packets {
           type uint64;
           description "Input packets";
         }
         leaf datagrams {
           type uint32;
           description "Datagrams";
         }
         leaf packets-that-had-data {
           type uint32;
           description "Packets that had data";
         }
         leaf input-sack-chunks {
           type uint32;
           description "Input SACK chunks";
         }
         leaf input-data-chunks {
           type uint32;
           description "Input DATA chunks";
         }
         leaf duplicate-data-chunks {
           type uint32;
           description "Duplicate DATA chunks";
         }
         leaf input-hb-chunks {
           type uint32;
           description "Input HB chunks";
         }
         leaf hb-ack-chunks {
           type uint32;
           description "HB-ACK_CHUNKS";
         }
         leaf input-ecne-chunks {
           type uint32;
           description "Input ECNE chunks";
         }
         leaf input-auth-chunks {
           type uint32;
           description "Input AUTH-chunks";
         }
         leaf chunks-missing-auth {
           type uint32;
           description "Chunks-missing-AUTH";
         }
         leaf invalid-hmac-ids-received {
           type uint32;
           description "Invalid HMAC ids received";
         }
         leaf invalid-secret-ids-received {
           type uint32;
           description "Invalid secrete ids received";
         }
         leaf auth-failed {
           type uint32;
           description "Auth failed";
         }
         leaf fast-path-receives-all-one-chunk {
           type uint32;
           description "Fast path receives all one chunk";
         }
         leaf fast-path-multi-part-data {
           type uint32;
           description "Fast path multi part data";
         }
         leaf output-packets {
           type uint64;
           description "Output packets";
         }
         leaf output-sacks {
           type uint32;
           description "Output SACKs";
         }
         leaf output-data-chunks {
           type uint32;
           description "Output DATA chunks";
         }
         leaf retransmitted-data-chunks {
           type uint32;
           description "Retransmitted DATA chunks";
         }
         leaf fast-retransmitted-data-chunks {
           type uint32;
           description "Fast retransmitted DATA chunks";
         }
         leaf frs-that-happened-more-than-once-to-same-chunk {
           type uint32;
           description "FRs that happened more than once to same chunk";
         }
         leaf output-hb-chunks {
           type uint32;
           description "Ouput HB chunks";
         }
         leaf output-ecne-chunks {
           type uint32;
           description "Output ECNE chunks";
         }
         leaf output-auth-chunks {
           type uint32;
           description "Output AUTH chunks";
         }
         leaf ip-output-error-counter {
           type uint32;
           description "Ip output error counter";
         }
         leaf packet-drop-statistics {
           type string;
           description "Packet drop statistics";
         }
         leaf from-middle-box {
           type uint32;
           description "From middle box";
         }
         leaf from-end-host {
           type uint32;
           description "From end host";
         }
         leaf with-data {
           type uint32;
           description "With data";
         }
         leaf non-data-non-endhost {
           type uint32;
           description "Non-data, non-endhost";
         }
         leaf non-endhost-bandwidth-rep-only {
           type uint32;
           description "Non-endhost, bandwidth rep only";
         }
         leaf not-enough-for-chunk-header {
           type uint32;
           description "Not enough for chunk header";
         }
         leaf not-enough-data-to-confirm {
           type uint32;
           description "Not enough data to confirm";
         }
         leaf where-process-chunk-drop-said-break {
           type uint32;
           description "Where process_chunk_drop said break";
         }
         leaf failed-to-find-tsn {
           type uint32;
           description "Failed to find TSN";
         }
         leaf attempt-reverse-tsn-lookup {
           type uint32;
           description "Attempt reverse TSN lookup";
         }
         leaf e-host-confirms-zero-rwnd {
           type uint32;
           description "E-host confirms zero-rwnd";
         }
         leaf midbox-confirms-no-space {
           type uint32;
           description "Midbox confirms no space";
         }
         leaf data-did-not-match-tsn {
           type uint32;
           description "Data did not match TSN";
         }
         leaf tsns-marked-for-fast-retran {
           type uint32;
           description "TSN's marked for Fast Retran";
         }
         leaf timeouts {
           type string;
           description "Timeouts";
         }
         leaf iterator-timers-fired {
           type uint32;
           description "Iterator timers fired";
         }
         leaf t3-data-time-outs {
           type uint32;
           description "T3 data time outs";
         }
         leaf window-probe-t3-timers-fired {
           type uint32;
           description "Window probe (T3) timers fired";
         }
         leaf init-timers-fired {
           type uint32;
           description "INIT timers fired";
         }
         leaf sack-timers-fired {
           type uint32;
           description "Sack timers fired";
         }
         leaf shutdown-timers-fired {
           type uint32;
           description "Shutdown timers fired";
         }
         leaf heartbeat-timers-fired {
           type uint32;
           description "Heartbeat timers fired";
         }
         leaf a-cookie-timeout-fired {
           type uint32;
           description "A cookie timeout fired";
         }
         leaf an-endpoint-changed-its-cookiesecret {
           type uint32;
           description "An endpoint changed its cookiesecret";
         }
         leaf pmtu-timers-fired {
           type uint32;
           description "PMTU timers fired";
         }
         leaf shutdown-ack-timers-fired {
           type uint32;
           description "Shutdown ack timers fired";
         }
         leaf shutdown-guard-timers-fired {
           type uint32;
           description "Shutdown guard timers fired";
         }
         leaf stream-reset-timers-fired {
           type uint32;
           description "Stream reset timers fired";
         }
         leaf early-fr-timers-fired {
           type uint32;
           description "Early FR timers fired";
         }
         leaf an-asconf-timer-fired {
           type uint32;
           description "An asconf timer fired";
         }
         leaf auto-close-timer-fired {
           type uint32;
           description "Auto close timer fired";
         }
         leaf asoc-free-timers-expired {
           type uint32;
           description "Asoc free timers expired";
         }
         leaf inp-free-timers-expired {
           type uint32;
           description "Inp free timers expired";
         }
         leaf packet-shorter-than-header {
           type uint32;
           description "Packet shorter than header";
         }
         leaf checksum-error {
           type uint32;
           description "Checksum error";
         }
         leaf no-endpoint-for-port {
           type uint32;
           description "No endpoint for port";
         }
         leaf bad-v-tag {
           type uint32;
           description "Bad v-tag";
         }
         leaf bad-sid {
           type uint32;
           description "Bad SID";
         }
         leaf no-memory {
           type uint32;
           description "No memory";
         }
         leaf number-of-multiple-fr-in-a-rtt-window {
           type uint32;
           description "Number of multiple FR in a RTT window";
         }
         leaf rfc813-allowed-sending {
           type uint32;
           description "RFC813 allowed sending";
         }
         leaf rfc813-does-not-allow-sending {
           type uint32;
           description "RFC813 does not allow sending";
         }
         leaf times-max-burst-prohibited-sending {
           type uint32;
           description "Times max burst prohibited sending";
         }
         leaf look-ahead-tells-us-no-memory-in-interface {
           type uint32;
           description "Look ahead tells us no memory in interface";
         }
         leaf numbers-of-window-probes-sent {
           type uint32;
           description "Numbers of window probes sent";
         }
         leaf times-an-output-error-to-clamp-down-on-next-user-send {
           type uint32;
           description "Times an output error to clamp down on next user send";
         }
         leaf times-sctpsenderrors-were-caused-from-a-user {
           type uint32;
           description "Times sctp_senderrors were caused from a user";
         }
         leaf number-of-in-data-drops-due-to-chunk-limit-reached {
           type uint32;
           description "Number of in data drops due to chunk limit reached";
         }
         leaf number-of-in-data-drops-due-to-rwnd-limit-reached {
           type uint32;
           description "Number of in data drops due to rwnd limit reached";
         }
         leaf times-a-ecn-reduced-the-cwnd {
           type uint32;
           description "Times a ECN reduced the cwnd";
         }
         leaf used-express-lookup-via-vtag {
           type uint32;
           description "Used express lookup via vtag";
         }
         leaf collision-in-express-lookup {
           type uint32;
           description "Collision in express lookup";
         }
         leaf times-the-sender-ran-dry-of-user-data-on-primary {
           type uint32;
           description "Times the sender ran dry of user data on primary";
         }
         leaf sacks-the-slow-way {
           type uint32;
           description "Sacks the slow way";
         }
         leaf window-update-only-sacks-sent {
           type uint32;
           description "Window update only sacks sent";
         }
         leaf sends-with-sinfoflags-notzero {
           type uint32;
           description "Sends with sinfo_flags !=0";
         }
         leaf unordered-sends {
           type uint32;
           description "Unordered sends";
         }
         leaf sends-with-eof-flag-set {
           type uint32;
           description "Sends with EOF flag set";
         }
         leaf sends-with-abort-flag-set {
           type uint32;
           description "Sends with ABORT flag set";
         }
         leaf sctp-aborted {
           type uint32;
           description "ABORTED sctps";
         }
         leaf times-protocol-drain-called {
           type uint32;
           description "Times protocol drain called";
         }
         leaf times-we-did-a-protocol-drain {
           type uint32;
           description "Times we did a protocol drain";
         }
         leaf times-recv-was-called-with-peek {
           type uint32;
           description "Times recv was called with peek";
         }
         leaf cached-chunks-used {
           type uint32;
           description "Cached chunks used";
         }
         leaf cached-stream-oqs-used {
           type uint32;
           description "Cached stream oq's used";
         }
         leaf unread-messages-abandonded-by-close {
           type uint32;
           description "Unread messages abandonded by close";
         }
         leaf send-burst-avoidance-already-max-burst-inflight-to-net {
           type uint32;
           description "Send burst avoidance, already max burst inflight to net";
         }
         leaf send-cwnd-full-avoidance-already-max-burst-inflight-to-net {
           type uint32;
           description "Send cwnd full avoidance, already max burst inflight to net";
         }
         leaf number-of-map-array-over-runs-via-fwd-tsns {
           type uint32;
           description "Number of map array over-runs via fwd-tsn's";
         }
         leaf same-for-above {
           type uint32;
           description "Same for above";
         }
       }
       container udp {
         leaf datagrams-received {
           type uint32;
           description "Datagrams received";
         }
         leaf datagrams-with-incomplete-header {
           type uint32;
           description "Datagrams with incomplete header";
         }
         leaf datagrams-with-bad-datalength-field {
           type uint32;
           description "Datagrams with bad data length field";
         }
         leaf datagrams-with-bad-checksum {
           type uint32;
           description "Datagrams with bad checksum";
         }
         leaf datagrams-dropped-due-to-no-socket {
           type uint32;
           description "Datagrams dropped due to no socket";
         }
         leaf broadcast-or-multicast-datagrams-dropped-due-to-no-socket {
           type uint32;
           description "Broadcast/multicast datagrams dropped due to no socket";
         }
         leaf datagrams-dropped-due-to-full-socket-buffers {
           type uint32;
           description "Datagrams dropped due to full socket buffers";
         }
         leaf datagrams-not-for-hashed-pcb {
           type uint32;
           description "Datagrams not for hashed pcb";
         }
         leaf datagrams-delivered {
           type uint32;
           description "Datagrams delivered";
         }
         leaf datagrams-output {
           type uint32;
           description "Datagrams output";
         }
       }
       container ip {
         leaf packets-received {
           type uint32;
           description "Packets received";
         }
         leaf bad-header-checksums {
           type uint32;
           description "Bad header checksums";
         }
         leaf packets-with-size-smaller-than-minimum {
           type uint32;
           description "Packets with size smaller than minimum";
         }
         leaf packets-with-data-size-less-than-datalength {
           type uint32;
           description "Packets with data size < data length";
         }
         leaf packets-with-header-length-less-than-data-size {
           type uint32;
           description "Packets with header length < data size";
         }
         leaf packets-with-data-length-less-than-headerlength {
           type uint32;
           description "Packets with data length < header length";
         }
         leaf packets-with-incorrect-version-number {
           type uint32;
           description "Packets with incorrect version number";
         }
         leaf packets-destined-to-dead-next-hop {
           type uint32;
           description "Packets destined to dead nexthop";
         }
         leaf fragments-received {
           type uint32;
           description "Fragments received";
         }
         leaf fragments-dropped-due-to-outofspace-or-dup {
           type uint32;
           description "Fragments dropped due to out of space/dup";
         }
         leaf fragments-dropped-due-to-queueoverflow {
           type uint32;
           description "Fragment sessions dropped due to queue overflow";
         }
         leaf fragments-dropped-after-timeout {
           type uint32;
           description "Fragments dropped after timeout";
         }
         leaf packets-reassembled-ok {
           type uint32;
           description "Packets reassembled ok";
         }
         leaf packets-for-this-host {
           type uint32;
           description "Packets-for-this-host";
         }
         leaf packets-for-unknown-or-unsupported-protocol {
           type uint32;
           description "Packets for unknown/unsupported protocol";
         }
         leaf packets-forwarded {
           type uint32;
           description "Packets forwarded";
         }
         leaf packets-not-forwardable {
           type uint32;
           description "Packets not forwardable";
         }
         leaf redirects-sent {
           type uint32;
           description "Redirects sent";
         }
         leaf packets-sent-from-this-host {
           type uint32;
           description "Packets sent from this host";
         }
         leaf packets-sent-with-fabricated-ip-header {
           type uint32;
           description "Packets sent with fabricated ip header";
         }
         leaf output-packets-dropped-due-to-no-bufs {
           type uint32;
           description "Output packets dropped due to no bufs";
         }
         leaf output-packets-discarded-due-to-no-route {
           type uint32;
           description "Output packets discarded due to no route";
         }
         leaf output-datagrams-fragmented {
           type uint32;
           description "Output datagrams fragmented";
         }
         leaf fragments-created {
           type uint32;
           description "Fragments created";
         }
         leaf datagrams-that-can-not-be-fragmented {
           type uint32;
           description "Datagrams that can't be fragmented";
         }
         leaf packets-with-bad-options {
           type uint32;
           description "Packets with bad options";
         }
         leaf packets-with-options-handled-without-error {
           type uint32;
           description "Packets with options handled without error";
         }
         leaf strict-source-and-record-route-options {
           type uint32;
           description "Strict source and record route options";
         }
         leaf loose-source-and-record-route-options {
           type uint32;
           description "Loose source and record route options";
         }
         leaf record-route-options {
           type uint32;
           description "Record route options";
         }
         leaf timestamp-options {
           type uint32;
           description "Timestamp options";
         }
         leaf timestamp-and-address-options {
           type uint32;
           description "Timestamp and address options";
         }
         leaf timestamp-and-prespecified-address-options {
           type uint32;
           description "Timestamp and prespecified address options";
         }
         leaf option-packets-dropped-due-to-rate-limit {
           type uint32;
           description "Option packets dropped due to rate limit";
         }
         leaf router-alert-options {
           type uint32;
           description "Router alert options";
         }
         leaf multicast-packets-dropped {
           type uint32;
           description "Multicast packets dropped (no iflist)";
         }
         leaf packets-dropped {
           type uint32;
           description "Packets dropped (src and int don't match)";
         }
         leaf transit-re-packets-dropped-on-mgmt-interface {
           type uint32;
           description "Transit RE packets dropped on mgmt interface";
         }
         leaf packets-used-first-nexthop-in-ecmp-unilist {
           type uint32;
           description "Packets used first nexthop in ecmp unilist";
         }
         leaf incoming-ttpoip-packets-received {
           type uint32;
           description "Incoming TTPoIP packets received";
         }
         leaf incoming-ttpoip-packets-dropped {
           type uint32;
           description "Incoming TTPoIP packets dropped";
         }
         leaf outgoing-ttpoip-packets-sent {
           type uint32;
           description "Outgoing TTPoIP packets sent";
         }
         leaf outgoing-ttpoip-packets-dropped {
           type uint32;
           description "Outgoing TTPoIP packets dropped";
         }
         leaf incoming-rawip-packets-dropped-no-socket-buffer {
           type uint32;
           description "Incoming raw ip packets dropped. No space in recv socket buffer";
         }
         leaf incoming-virtual-node-packets-delivered {
           type uint32;
           description "Incoming packets consumed by virtual-node processing";
         }
       }
       container icmp {
         leaf drops-due-to-rate-limit {
           type uint32;
           description "Drops due to rate limit";
         }
         leaf drops-at-server-ine {
           type uint32;
           description "Drops at server INE";
         }
         leaf calls-to-icmp-error {
           type uint32;
           description "Calls to icmp_error";
         }
         leaf errors-not-generated-because-old-message-was-icmp {
           type uint32;
           description "Errors not generated because old message was icmp";
         }
         leaf messages-with-bad-code-fields {
           type uint32;
           description "Messages with bad code fields";
         }
         leaf messages-less-than-the-minimum-length {
           type uint32;
           description "Messages less than the minimum length";
         }
         leaf messages-with-bad-checksum {
           type uint32;
           description "Messages with bad checksum";
         }
         leaf messages-with-bad-source-address {
           type uint32;
           description "Messages with bad source address";
         }
         leaf messages-with-bad-length {
           type uint32;
           description "Messages with bad length";
         }
         leaf echo-drops-with-broadcast-or-multicast-destinaton-address {
           type uint32;
           description "Echo drops with broadcast or multicast destination address";
         }
         leaf timestamp-drops-with-broadcast-or-multicast-destination-address {
           type uint32;
           description "Timestamp drops with broadcast or multicast destination address";
         }
         leaf message-responses-generated {
           type uint32;
           description "Message responses generated";
         }
         list histogram {
           leaf type-of-histogram {
             type string;
             description "Input/ouput histogram";
           }
           leaf icmp-echo-reply {
             type uint32;
             description "Echo reply";
           }
           leaf icmp-ext-echo-reply {
             type uint32;
             description "Extended Echo reply";
           }
           leaf destination-unreachable {
             type uint32;
             description "Destination unreachable";
           }
           leaf source-quench {
             type uint32;
             description "Source-quench";
           }
           leaf routing-redirect {
             type uint32;
             description "Routing redirect";
           }
           leaf alternate-host-address {
             type uint32;
             description "Alternate host address";
           }
           leaf icmp-echo {
             type uint32;
             description "Echo";
           }
           leaf icmp-ext-echo {
             type uint32;
             description "Extended Echo";
           }
           leaf router-advertisement {
             type uint32;
             description "Router advertisement";
           }
           leaf router-solicitation {
             type uint32;
             description "Router solicitation";
           }
           leaf time-exceeded {
             type uint32;
             description "Time exceeded";
           }
           leaf parameter-problem {
             type uint32;
             description "Parameter problem";
           }
           leaf time-stamp {
             type uint32;
             description "Time stamp";
           }
           leaf time-stamp-reply {
             type uint32;
             description "Time stamp reply";
           }
           leaf information-request {
             type uint32;
             description "Information request";
           }
           leaf information-request-reply {
             type uint32;
             description "Information request reply";
           }
           leaf address-mask-request {
             type uint32;
             description "Address mask request";
           }
           leaf address-mask-reply {
             type uint32;
             description "Address mask reply";
           }
           leaf traceroute {
             type uint32;
             description "Traceroute";
           }
           leaf data-conversion-error {
             type uint32;
             description "Data conversion error";
           }
           leaf mobile-host-redirect {
             type uint32;
             description "Mobile host redirect";
           }
           leaf ipv6-where-are-you {
             type uint32;
             description "IPv6 where-are-you";
           }
           leaf ipv6-i-am-here {
             type uint32;
             description "IPv6 i-am-here";
           }
           leaf mobile-registration-request {
             type uint32;
             description "Mobile registration request";
           }
           leaf mobile-registration-reply {
             type uint32;
             description "Mobile registration reply";
           }
           leaf skip {
             type uint32;
             description "Skip";
           }
           leaf photuris {
             type uint32;
             description "Photuris";
           }
         }
       }
       container arp {
         leaf datagrams-received {
           type uint32;
           description "Datagrams received";
         }
         leaf arp-requests-received {
           type uint32;
           description "ARP requests received";
         }
         leaf arp-replies-received {
           type uint32;
           description "ARP replies received";
         }
         leaf resolution-request-received {
           type uint32;
           description "Resolution request received";
         }
         leaf resolution-request-dropped {
           type uint32;
           description "Resolution request dropped";
         }
         leaf unrestricted-proxy-requests {
           type uint32;
           description "Unrestricted proxy requests";
         }
         leaf restricted-proxy-requests {
           type uint32;
           description "Restricted proxy requests";
         }
         leaf received-proxy-requests {
           type uint32;
           description "Received proxy requests";
         }
         leaf proxy-requests-not-proxied {
           type uint32;
           description "Unrestricted proxy requests not proxied";
         }
         leaf restricted-proxy-requests-not-proxied {
           type uint32;
           description "Restricted proxy requests not proxied";
         }
         leaf datagrams-with-bogus-interface {
           type uint32;
           description "Datagrams with bogus interface";
         }
         leaf datagrams-with-incorrect-length {
           type uint32;
           description "Datagrams with incorrect length";
         }
         leaf datagrams-for-non-ip-protocol {
           type uint32;
           description "Datagrams for non-IP protocol";
         }
         leaf datagrams-with-unsupported-opcode {
           type uint32;
           description "Datagrams with unsupported op code";
         }
         leaf datagrams-with-bad-protocol-address-length {
           type uint32;
           description "Datagrams with bad protocol address length";
         }
         leaf datagrams-with-bad-hardware-address-length {
           type uint32;
           description "Datagrams with bad hardware address length";
         }
         leaf datagrams-with-multicast-source-address {
           type uint32;
           description "Datagrams with multicast source address";
         }
         leaf datagrams-with-multicast-target-address {
           type uint32;
           description "Datagrams with multicast target address";
         }
         leaf datagrams-with-my-own-hardware-address {
           type uint32;
           description "Datagrams with my own hardware address";
         }
         leaf datagrams-for-an-address-not-on-the-interface {
           type uint32;
           description "Datagrams for an address not on the interface";
         }
         leaf datagrams-with-a-broadcast-source-address {
           type uint32;
           description "Datagrams with a broadcast source address";
         }
         leaf datagrams-with-source-address-duplicate-to-mine {
           type uint32;
           description "Datagrams with source address duplicate to mine";
         }
         leaf datagrams-which-were-not-for-me {
           type uint32;
           description "Datagrams which were not for me";
         }
         leaf packets-discarded-waiting-for-resolution {
           type uint32;
           description "Packets discarded waiting for resolution";
         }
         leaf packets-sent-after-waiting-for-resolution {
           type uint32;
           description "Packets sent after waiting for resolution";
         }
         leaf arp-requests-sent {
           type uint32;
           description "ARP requests sent";
         }
         leaf arp-replies-sent {
           type uint32;
           description "ARP replies sent";
         }
         leaf requests-for-memory-denied {
           type uint32;
           description "Requests for memory denied";
         }
         leaf requests-dropped-on-entry {
           type uint32;
           description "Requests dropped on entry";
         }
         leaf requests-dropped-during-retry {
           type uint32;
           description "Requests dropped during retry";
         }
         leaf requests-dropped-due-to-interface-deletion {
           type uint32;
           description "Requests dropped due to interface deletion";
         }
         leaf requests-on-unnumbered-interfaces {
           type uint32;
           description "Requests on unnumbered interfaces";
         }
         leaf new-requests-on-unnumbered-interfaces {
           type uint32;
           description "New requests on unnumbered interfaces";
         }
         leaf replies-from-unnumbered-interfaces {
           type uint32;
           description "Replies for from unnumbered interfaces";
         }
         leaf requests-on-unnumbered-interface-with-non-subnetted-donor {
           type uint32;
           description "Requests on unnumbered interface with non-subnetted donor";
         }
         leaf replies-from-unnumbered-interface-with-non-subnetted-donor {
           type uint32;
           description "Replies from unnumbered interface with non-subnetted donor";
         }
         leaf arp-packets-rejected-as-family-is-configured-with-deny-arp {
           type uint32;
           description "Arp packets rejected as family is configured with deny arp";
         }
         leaf arp-response-packets-are-rejected-on-mc-ae-icl-interface {
           type uint32;
           description "Arp response packets are rejected on mc-ae icl interface";
         }
         leaf arp-replies-are-rejected-as-source-and-destination-is-same {
           type uint32;
           description "Arp replies are rejected as source and destination is same";
         }
         leaf arp-probe-for-proxy-address-reachable-from-the-incoming-interface {
           type uint32;
           description "Arp probe for proxy address reachable from the incoming interface";
         }
         leaf arp-request-discarded-for-vrrp-source-address {
           type uint32;
           description "Arp request discarded for vrrp source address";
         }
         leaf self-arp-request-packet-received-on-irb-interface {
           type uint32;
           description "Self arp request packet received on irb interface";
         }
         leaf proxy-arp-request-discarded-as-source-ip-is-a-proxy-target {
           type uint32;
           description "Proxy arp request discarded as source ip is a proxy target";
         }
         leaf arp-packets-are-dropped-as-nexthop-allocation-failed {
           type uint32;
           description "Arp packets are dropped as nexthop allocation failed";
         }
         leaf arp-packets-received-from-peer-vrrp-router-and-discarded {
           type uint32;
           description "Arp packets received from peer vrrp router and discarded";
         }
         leaf arp-packets-are-rejected-as-target-ip-arp-resolve-is-in-progress {
           type uint32;
           description "Arp packets are rejected as target ip arp resolve is in progress";
         }
         leaf grat-arp-packets-are-ignored-as-mac-address-is-not-changed {
           type uint32;
           description "Grat arp packets are ignored as mac address is not changed";
         }
         leaf arp-packets-are-dropped-from-peer-vrrp {
           type uint32;
           description "Arp packets are dropped from peer vrrp";
         }
         leaf arp-packets-are-dropped-as-driver-call-failed {
           type uint32;
           description "Arp packets are dropped as driver call failed";
         }
         leaf arp-packets-are-dropped-as-source-is-not-validated {
           type uint32;
           description "Arp packets are dropped as source is not validated";
         }
         leaf arp-system-max {
           type uint64;
           description "Max ARP NH system cache";
         }
         leaf arp-public-max {
           type uint64;
           description "Max public ARP NH cache";
         }
         leaf arp-iri-max {
           type uint64;
           description "Max iri ARP NH cache";
         }
         leaf arp-mgt-max {
           type uint64;
           description "Max mgt intf ARP NH cache";
         }
         leaf arp-public-cnt {
           type uint64;
           description "Current public ARP NH count";
         }
         leaf arp-iri-cnt {
           type uint64;
           description "Current iri ARP NH count";
         }
         leaf arp-mgt-cnt {
           type uint64;
           description "Current management ARP NH count";
         }
         leaf arp-system-drop {
           type uint64;
           description "System ARP NH drops";
         }
         leaf arp-public-drop {
           type uint64;
           description "Public ARP NH drops";
         }
         leaf arp-iri-drop {
           type uint64;
           description "IRI ARP NH drops";
         }
         leaf arp-mgt-drop {
           type uint64;
           description "Management intf ARP NH drops";
         }
         leaf arp-cache-count {
           type uint32;
           description "Number of entries present in ARP cache";
         }
       }
       container ip6 {
         leaf total-packets-received {
           type uint64;
           description "Total packets received";
         }
         leaf ip6-packets-with-size-smaller-than-minimum {
           type uint64;
           description "Ip6 packets with size smaller than minimum";
         }
         leaf packets-with-datasize-less-than-data-length {
           type uint64;
           description "Packets with data size < data length";
         }
         leaf ip6-packets-with-bad-options {
           type uint64;
           description "Ip6 packets with bad options";
         }
         leaf ip6-packets-with-incorrect-version-number {
           type uint64;
           description "Ip6 packets with incorrect version number";
         }
         leaf ip6-fragments-received {
           type uint64;
           description "Ip6 fragments received";
         }
         leaf duplicate-or-out-of-space-fragments-dropped {
           type uint64;
           description "Fragments dropped (dup or out of space)";
         }
         leaf ip6-fragments-dropped-after-timeout {
           type uint64;
           description "Ip6 fragments dropped after timeout";
         }
         leaf fragments-that-exceeded-limit {
           type uint64;
           description "Fragment sessions dropped due to queue overflow";
         }
         leaf ip6-packets-reassembled-ok {
           type uint64;
           description "Ip6 packets reassembled ok";
         }
         leaf ip6-packets-for-this-host {
           type uint64;
           description "Ip6 packets for this host";
         }
         leaf ip6-packets-forwarded {
           type uint64;
           description "Ip6 packets forwarded";
         }
         leaf ip6-packets-not-forwardable {
           type uint64;
           description "Ip6 packets not forwardable";
         }
         leaf ip6-redirects-sent {
           type uint64;
           description "Ip6 redirects sent";
         }
         leaf ip6-packets-sent-from-this-host {
           type uint64;
           description "Ip6 packets sent from this host";
         }
         leaf ip6-packets-sent-with-fabricated-ip-header {
           type uint64;
           description "Ip6 packets sent with fabricated ip header";
         }
         leaf ip6-output-packets-dropped-due-to-no-bufs {
           type uint64;
           description "Ip6 output packets dropped due to no bufs";
         }
         leaf ip6-output-packets-discarded-due-to-no-route {
           type uint64;
           description "Ip6 output packets discarded due to no route";
         }
         leaf ip6-output-datagrams-fragmented {
           type uint64;
           description "Ip6output datagrams fragmented";
         }
         leaf ip6-fragments-created {
           type uint64;
           description "Ip6 fragments created";
         }
         leaf ip6-datagrams-that-can-not-be-fragmented {
           type uint64;
           description "Ip6 datagrams that can not be fragmented";
         }
         leaf packets-that-violated-scope-rules {
           type uint64;
           description "Packets that violated scope rules";
         }
         leaf multicast-packets-which-we-do-not-join {
           type uint64;
           description "Multicast packets which we don't join";
         }
         leaf-list histogram {
           type string;
         }
         leaf ip6nh-hop-by-hop {
           type uint64;
           description "Hop by hop";
         }
         leaf ip6nh-icmp {
           type uint64;
           description "ICMP";
         }
         leaf ip6nh-igmp {
           type uint64;
           description "IGMP";
         }
         leaf ip6nh-ip {
           type uint64;
           description "IP";
         }
         leaf ip6nh-tcp {
           type uint64;
           description "TCP";
         }
         leaf ip6nh-udp {
           type uint64;
           description "UDP";
         }
         leaf ip6nh-idp {
           type uint64;
           description "IDP";
         }
         leaf ip6nh-tp {
           type uint64;
           description "TP";
         }
         leaf ip6nh-ip6 {
           type uint64;
           description "IP6";
         }
         leaf ip6nh-routing {
           type uint64;
           description "Routing";
         }
         leaf ip6nh-fragment {
           type uint64;
           description "Fragment";
         }
         leaf ip6nh-esp {
           type uint64;
           description "Esp";
         }
         leaf ip6nh-ah {
           type uint64;
           description "AH";
         }
         leaf ip6nh-icmp6 {
           type uint64;
           description "ICMP6";
         }
         leaf ip6nh-no-next-header {
           type uint64;
           description "No next header";
         }
         leaf ip6nh-destination-option {
           type uint64;
           description "Destination option";
         }
         leaf ip6nh-isoip {
           type uint64;
           description "ISOIP";
         }
         leaf ip6nh-ospf {
           type uint64;
           description "OSPF";
         }
         leaf ip6nh-ethernet {
           type uint64;
           description "Ethernet";
         }
         leaf ip6nh-pim {
           type uint64;
           description "PIM";
         }
         leaf mbuf-statistics {
           type string;
           description "Header";
         }
         leaf packets-whose-headers-are-not-continuous {
           type uint64;
           description "Packets whose headers are not continuous";
         }
         leaf tunneling-packets-that-can-not-find-gif {
           type uint64;
           description "Tunneling packets that can't find GIF";
         }
         leaf packets-discarded-due-to-too-may-headers {
           type uint64;
           description "Packets discarded due to too many headers";
         }
         leaf failures-of-source-address-selection {
           type uint64;
           description "Failures of source address selection";
         }
         leaf forward-cache-hit {
           type uint64;
           description "Forward cache hit";
         }
         leaf forward-cache-miss {
           type uint64;
           description "Forward cache miss";
         }
         leaf ip6-packets-destined-to-dead-next-hop {
           type uint64;
           description "Ip6 packets destined to dead next hop";
         }
         leaf ip6-option-packets-dropped-due-to-rate-limit {
           type uint64;
           description "Ip6 option packets dropped due to rate limit";
         }
         leaf ip6-packets-dropped {
           type uint64;
           description "Ip6 packets dropped";
         }
         leaf packets-dropped-due-to-bad-protocol {
           type uint64;
           description "Packets dropped due to bad protocol";
         }
         leaf transit-re-packet-dropped-on-mgmt-interface {
           type uint64;
           description "Transit re packet(null) dropped on mgmt interface";
         }
         leaf packet-used-first-nexthop-in-ecmp-unilist {
           type uint64;
           description "Packet(null) used first nexthop in ecmp unilist";
         }
         list header-type {
           leaf header-for-source-address-selection {
             type string;
             description "Header";
           }
           leaf node-locals {
             type uint64;
             description "Node locals as source address";
           }
           leaf link-locals {
             type uint64;
             description "Link locals as source address";
           }
           leaf site-locals {
             type uint64;
             description "Site locals as source address";
           }
           leaf globals {
             type uint64;
             description "Globals as source address";
           }
           leaf address-scope {
             type uint64;
             description "Address scope";
           }
           leaf hex-value {
             type uint64;
             description "Hexa decimal value";
           }
         }
       }
       container icmp6 {
         leaf protocol-name {
           type string;
         }
         leaf calls-to-icmp6-error {
           type uint64;
           description "Calls to icmp6 error";
         }
         leaf errors-not-generated-because-old-message-was-icmp-error {
           type uint64;
           description "Errors not generated because old message was icmp error";
         }
         leaf errors-not-generated-because-rate-limitation {
           type uint64;
           description "Errors not generated because rate limitation";
         }
         leaf icmp6-messages-with-bad-code-fields {
           type uint64;
           description "Icmp6 messages with bad code fields";
         }
         leaf messages-less-than-minimum-length {
           type uint64;
           description "Messages < minimum length";
         }
         leaf bad-checksums {
           type uint64;
           description "Bad checksums";
         }
         leaf icmp6-messages-with-bad-length {
           type uint64;
           description "Icmp6 messages with bad length";
         }
         leaf histogram-of-error-messages-to-be-generated {
           type string;
           description "Header";
         }
         leaf no-route {
           type uint64;
           description "No route";
         }
         leaf administratively-prohibited {
           type uint64;
           description "Administratively prohibited";
         }
         leaf beyond-scope {
           type uint64;
           description "Beyond scope";
         }
         leaf address-unreachable {
           type uint64;
           description "Address unreachable";
         }
         leaf port-unreachable {
           type uint64;
           description "Port unreachable";
         }
         leaf time-exceed-transit {
           type uint64;
           description "Time exceed transit";
         }
         leaf time-exceed-reassembly {
           type uint64;
           description "Time exceed reassembly";
         }
         leaf erroneous-header-field {
           type uint64;
           description "Erroneous header field";
         }
         leaf unrecognized-next-header {
           type uint64;
           description "Unrecognized next header";
         }
         leaf unrecognized-option {
           type uint64;
           description "Unrecognized option";
         }
         leaf unknown {
           type uint64;
           description "Unknown";
         }
         leaf icmp6-message-responses-generated {
           type uint64;
           description "Icmp6 message responses generated";
         }
         leaf messages-with-too-many-nd-options {
           type uint64;
           description "Messages with too many ND options";
         }
         leaf nd-system-max {
           type uint64;
           description "Max ND NH system cache";
         }
         leaf nd-public-max {
           type uint64;
           description "Max public ND NH cache";
         }
         leaf nd-iri-max {
           type uint64;
           description "Max iri ND NH cache";
         }
         leaf nd-mgt-max {
           type uint64;
           description "Max mgt intf ND NH cache";
         }
         leaf nd-public-cnt {
           type uint64;
           description "Current public ND NH count";
         }
         leaf nd-iri-cnt {
           type uint64;
           description "Current iri ND NH count";
         }
         leaf nd-mgt-cnt {
           type uint64;
           description "Current management ND NH count";
         }
         leaf nd-system-drop {
           type uint64;
           description "System ND NH drops";
         }
         leaf nd-public-drop {
           type uint64;
           description "Public ND NH drops";
         }
         leaf nd-iri-drop {
           type uint64;
           description "IRI ND NH drops";
         }
         leaf nd-mgt-drop {
           type uint64;
           description "Management intf ND NH drops";
         }
         leaf nd6-requests-dropped-on-entry {
           type uint64;
           description "ND nexthops dropped on entry by RED mark";
         }
         leaf nd6-requests-dropped-during-retry {
           type uint64;
           description "ND nexthop%s dropped on timer expire by RED mark";
         }
         leaf nd6-ndp-proxy-requests {
           type uint64;
           description "Interface-restricted ndp proxy requests";
         }
         leaf nd6-dad-proxy-requests {
           type uint64;
           description "Interface-restricted dad proxy requests";
         }
         leaf nd6-ndp-proxy-responses {
           type uint64;
           description "Interface-restricted ndp proxy responses";
         }
         leaf nd6-dad-proxy-conflicts {
           type uint64;
           description "Interface-restricted dad proxy conflicts";
         }
         leaf nd6-dup-proxy-responses {
           type uint64;
           description "Interface-restricted dad proxy duplicates";
         }
         leaf nd6-ndp-proxy-resolve-cnt {
           type uint64;
           description "Interface-restricted ndp proxy resolve requests";
         }
         leaf nd6-dad-proxy-resolve-cnt {
           type uint64;
           description "Interface-restricted dad proxy resolve requests";
         }
         leaf nd6-dad-proxy-eqmac-drop {
           type uint64;
           description "Interface-restricted dad packets from same node dropped";
         }
         leaf nd6-dad-proxy-nomac-drop {
           type uint64;
           description "Interface-restricted proxy packets dropped with nomac";
         }
         leaf nd6-ndp-proxy-unr-requests {
           type uint64;
           description "Interface-unrestricted ndp proxy requests";
         }
         leaf nd6-dad-proxy-unr-requests {
           type uint64;
           description "Interface-unrestricted dad proxy requests";
         }
         leaf nd6-ndp-proxy-unr-responses {
           type uint64;
           description "Interface-unrestricted ndp proxy responses";
         }
         leaf nd6-dad-proxy-unr-conflicts {
           type uint64;
           description "Interface-unrestricted dad proxy conflicts";
         }
         leaf nd6-dad-proxy-unr-responses {
           type uint64;
           description "Interface-unrestricted dad proxy duplicates";
         }
         leaf nd6-ndp-proxy-unr-resolve-cnt {
           type uint64;
           description "Interface-unrestricted ndp proxy resolve requests";
         }
         leaf nd6-dad-proxy-unr-resolve-cnt {
           type uint64;
           description "Interface-unrestricted dad proxy resolve requests";
         }
         leaf nd6-dad-proxy-unr-eqport-drop {
           type uint64;
           description "Interface-unrestricted dad packets from same port dropped";
         }
         leaf nd6-dad-proxy-unr-nomac-drop {
           type uint64;
           description "Interface-unrestricted proxy packets dropped with nomac";
         }
         leaf nd6-dad-ns-with-enhanced-dad {
           type uint64;
           description "NS DAD sent with nonce option";
         }
         leaf nd6-dad-ns-enhanced-dad-looped {
           type uint64;
           description "NS Enhanced DAD with same nonce looped";
         }
         leaf histogram-type {
           type string;
         }
         leaf unreachable-icmp6-packets {
           type uint64;
           description "Unreachable icmp6 packets";
         }
         leaf packet-too-big {
           type uint64;
           description "Packet too big";
         }
         leaf time-exceeded-icmp6-packets {
           type uint64;
           description "Time exceeded icmp6 packets";
         }
         leaf parameter-problem-icmp6-packets {
           type uint64;
           description "Parameter problem icmp6 packets";
         }
         leaf icmp6-echo {
           type uint64;
         }
         leaf icmp6-ext-echo {
           type uint64;
         }
         leaf icmp6-echo-reply {
           type uint64;
         }
         leaf icmp6-ext-echo-reply {
           type uint64;
         }
         leaf multicast-listener-query {
           type uint64;
           description "Multicast listener query";
         }
         leaf multicast-listener-report {
           type uint64;
           description "Multicast listener report";
         }
         leaf multicast-listener-done {
           type uint64;
           description "Multicast listener done";
         }
         leaf router-solicitation-icmp6-packets {
           type uint64;
           description "Router solicitation icmp6 packets";
         }
         leaf router-advertisement-icmp6-packets {
           type uint64;
           description "Router advertisement icmp6 packets";
         }
         leaf neighbor-solicitation {
           type uint64;
           description "Neighbor solicitation";
         }
         leaf neighbor-advertisement {
           type uint64;
           description "Neighbor advertisement";
         }
         leaf redirect {
           type uint64;
           description "Redirect";
         }
         leaf router-renumbering {
           type uint64;
           description "Router renumbering";
         }
         leaf node-information-request {
           type uint64;
           description "Node information request";
         }
         leaf node-information-reply {
           type uint64;
           description "Node information reply";
         }
         leaf version-2-multicast-listener-report {
           type uint64;
           description "Version 2 Multicast Listener Report";
         }
         container output-histogram {
         }
         container input-histogram {
         }
       }
       container esis {
         leaf total-esis-packets-received {
           type uint32;
           description "Total esis packets received";
         }
         leaf total-packets-consumed-by-protocol {
           type uint32;
           description "Total packets consumed by protocol";
         }
         leaf pdus-received-with-bad-checksum {
           type uint32;
           description "PDUs received with bad checksum";
         }
         leaf pdus-received-with-bad-version-number {
           type uint32;
           description "PDUs received with bad version number";
         }
         leaf pdus-received-with-bad-type-field {
           type uint32;
           description "PDUs received with bad type field";
         }
         leaf short-pdus-received {
           type uint32;
           description "Short pdus received";
         }
         leaf pdus-with-bogus-sdl-size {
           type uint32;
           description "Pdus with bogus sdl size";
         }
         leaf pdus-with-bad-header-length {
           type uint32;
           description "Pdus with bad header length";
         }
         leaf pdus-with-unknown-or-unsupport-protocol {
           type uint32;
           description "Pdus with unknown or unsupported protocol";
         }
         leaf no-free-memory-in-socket-buffer {
           type uint32;
           description "No free memory in socket buffer";
         }
         leaf send-packets-discarded {
           type uint32;
           description "Send packets discarded";
         }
         leaf sbappend-failure {
           type uint32;
           description "Sbappend failure";
         }
         leaf mcopy-failure {
           type uint32;
           description "Mcopy failure";
         }
         leaf iso-family-not-configured {
           type uint32;
           description "ISO family not configured";
         }
       }
       container tnp {
         leaf unicast-packets-received {
           type uint64;
           description "Unicast packets received";
         }
         leaf broadcast-packets-received {
           type uint64;
           description "Broadcast packets received";
         }
         leaf fragmented-packets-received {
           type uint64;
           description "Fragmented packets received";
         }
         leaf received-hello-packets-dropped {
           type uint64;
           description "Hello packets dropped";
         }
         leaf received-fragments-dropped {
           type uint64;
           description "Fragments dropped";
         }
         leaf fragment-reassembly-queue-flushes {
           type uint64;
           description "Fragment reassembly queue flushes";
         }
         leaf packets-with-tnp-src-address-collision-received {
           type uint64;
           description "Packets with tnp src address collision received";
         }
         leaf hello-packets-received {
           type uint64;
           description "Hello packets received";
         }
         leaf control-packets-received {
           type uint64;
           description "Control packets received";
         }
         leaf rdp-packets-received {
           type uint64;
           description "RDP packets received";
         }
         leaf udp-packets-received {
           type uint64;
           description "UDP packets received";
         }
         leaf tunnel-packets-received {
           type uint64;
           description "Tunnel packets received";
         }
         leaf input-packets-discarded-with-no-protocol {
           type uint64;
           description "Input packets discarded with no protocol";
         }
         leaf packets-of-version-unspecified-received {
           type uint64;
           description "Packets of version unspecified received";
         }
         leaf packets-of-version1-received {
           type uint64;
           description "Packets of version 1 received";
         }
         leaf packets-of-version2-received {
           type uint64;
           description "Packets of version 2 received";
         }
         leaf packets-of-version3-received {
           type uint64;
           description "Packets of version 3 received";
         }
         leaf unicast-packets-sent {
           type uint64;
           description "Unicast packets sent";
         }
         leaf broadcast-packets-sent {
           type uint64;
           description "Broadcast packets sent";
         }
         leaf fragmented-packets-sent {
           type uint64;
           description "Fragmented packets sent";
         }
         leaf sent-hello-packets-dropped {
           type uint64;
           description "Hello packets dropped";
         }
         leaf sent-fragments-dropped {
           type uint64;
           description "Fragments dropped";
         }
         leaf hello-packets-sent {
           type uint64;
           description "Hello packets sent";
         }
         leaf control-packets-sent {
           type uint64;
           description "Control packets sent";
         }
         leaf rdp-packets-sent {
           type uint64;
           description "Rdp packets sent";
         }
         leaf udp-packets-sent {
           type uint64;
           description "Udp packets sent";
         }
         leaf tunnel-packets-sent {
           type uint64;
           description "Tunnel packets sent";
         }
         leaf packets-sent-with-unknown-protocol {
           type uint64;
           description "Packets sent with unknown protocol";
         }
         leaf packets-of-version-unspecified-sent {
           type uint64;
           description "Packets of version unspecified sent";
         }
         leaf packets-of-version1-sent {
           type uint64;
           description "Packets of version 1 sent";
         }
         leaf packets-of-version2-sent {
           type uint64;
           description "Packets of version 2 sent";
         }
         leaf packets-of-version3-sent {
           type uint64;
           description "Packets of version 3 sent";
         }
       }
       container rdp {
         leaf input-packets {
           type uint64;
           description "Input packets";
         }
         leaf packets-discarded-for-bad-checksum {
           type uint64;
           description "Packets discarded for bad checksum";
         }
         leaf packets-discarded-due-to-bad-sequence-number {
           type uint64;
           description "Packets discarded due to bad sequence number";
         }
         leaf refused-connections {
           type uint64;
           description "Refused connections";
         }
         leaf acks-received {
           type uint64;
           description "Acks received";
         }
         leaf packets-dropped-due-to-full-socket-buffers {
           type uint64;
           description "Packets dropped due to full socket buffers";
         }
         leaf retransmits {
           type uint64;
           description "Retransmits";
         }
         leaf output-packets {
           type uint64;
           description "Output packets";
         }
         leaf acks-sent {
           type uint64;
           description "Acks sent";
         }
         leaf connects {
           type uint64;
           description "Connects";
         }
         leaf closes {
           type uint64;
           description "Closes";
         }
         leaf keepalives-received {
           type uint64;
           description "Keepalives received";
         }
         leaf keepalives-sent {
           type uint64;
           description "Keepalives sent";
         }
         leaf packets-dropped-full-repl-sock-buf {
           type uint64;
           description "Packets dropped due to full replicated socket buffer";
         }
       }
       container tudp {
         leaf datagrams-received {
           type uint32;
           description "Datagrams received";
         }
         leaf datagrams-with-incomplete-header {
           type uint32;
           description "Datagrams with incomplete header";
         }
         leaf datagrams-with-bad-data-length-field {
           type uint32;
           description "Datagrams with bad data length field";
         }
         leaf datagrams-with-bad-checksum {
           type uint32;
           description "Datagrams with bad checksum";
         }
         leaf datagrams-dropped-due-to-no-socket {
           type uint32;
           description "Datagrams dropped due to no socket";
         }
         leaf broadcast-or-multicast-datagrams-dropped-due-to-no-socket {
           type uint32;
           description "Broadcast/multicast datagrams dropped due to no socket";
         }
         leaf datagrams-dropped-due-to-full-socket-buffers {
           type uint32;
           description "Datagrams dropped due to full socket buffers";
         }
         leaf delivered {
           type uint32;
           description "Delivered";
         }
         leaf datagrams-output {
           type uint32;
           description "Datagrams output";
         }
       }
       container ttp {
         leaf ttp-packets-sent {
           type uint64;
           description "Ttp packets sent";
         }
         leaf packets-sent-while-unconnected {
           type uint64;
           description "Packets sent while unconnected";
         }
         leaf packets-sent-while-interface-down {
           type uint64;
           description "Packets sent while interface down";
         }
         leaf packets-sent-could-not-get-buffer {
           type uint64;
           description "Packets sent couldn't get buffer";
         }
         leaf packets-sent-could-not-find-neighbor {
           type uint64;
           description "Packets sent could't find neighbor";
         }
         leaf packets-sent-when-transmit-disabled {
           type uint64;
           description "Packets sent when transmit is disabled";
         }
         leaf packets-sent-when-host-unreachable {
           type uint64;
           description "Packets sent when host unreachable";
         }
         leaf l3-packets-sent-could-not-get-buffer {
           type uint64;
           description "L3 Packets sent couldn't get buffer";
         }
         leaf l3-packets-dropped {
           type uint64;
           description "L3 Packets dropped";
         }
         leaf packets-sent-with-bad-ifl {
           type uint64;
           description "Packets sent with bad logical interface";
         }
         leaf packets-sent-with-bad-af {
           type uint64;
           description "Packets sent with bad address family";
         }
         leaf l2-packets-received {
           type uint64;
           description "L2 packets received";
         }
         leaf unknown-l3-packets-received {
           type uint64;
           description "Unknown L3 packets received";
         }
         leaf ipv4-l3-packets-received {
           type uint64;
           description "IPv4 L3 packets received";
         }
         leaf mpls-l3-packets-received {
           type uint64;
           description "MPLS L3 packets received";
         }
         leaf mpls-to-ipv4-l3-packets-received {
           type uint64;
           description "MPLS->IPV4 L3 packets received";
         }
         leaf ipv4-to-mpls-l3-packets-received {
           type uint64;
           description "IPv4->MPLS L3 packets received";
         }
         leaf vpls-l3-packets-received {
           type uint64;
           description "VPLS L3 packets received";
         }
         leaf ipv6-l3-packets-received {
           type uint64;
           description "IPv6 L3 packets received";
         }
         leaf arp-l3-packets-received {
           type uint64;
           description "ARP L3 packets received";
         }
         leaf clnp-l3-packets-received {
           type uint64;
           description "CLNP L3 packets received";
         }
         leaf tnp-l3-packets-received {
           type uint64;
           description "TNP L3 packets received";
         }
         leaf null-l3-packets-received {
           type uint64;
           description "NULL L3 packets received";
         }
         leaf cyclotron-cycle-l3-packets-received {
           type uint64;
           description "Cyclotron cycle L3 packets received";
         }
         leaf cyclotron-send-l3-packets-received {
           type uint64;
           description "Cyclotron send L3 packets received";
         }
         leaf openflow-packets-received {
           type uint64;
           description "Openflow packets received";
         }
         leaf packets-received-while-unconnected {
           type uint64;
           description "Packets received while unconnected";
         }
         leaf packets-received-from-unknown-ifl {
           type uint64;
           description "Packets received from unknown ifl";
         }
         leaf input-packets-could-not-get-buffer {
           type uint64;
           description "Input packets couldn't get buffer";
         }
         leaf input-packets-with-bad-type {
           type uint64;
           description "Input packets with bad type";
         }
         leaf input-packets-with-discard-type {
           type uint64;
           description "Input packets with discard type";
         }
         leaf input-packets-with-too-many-tlvs {
           type uint64;
           description "Input packets with too many tlvs";
         }
         leaf input-packets-with-bad-tlv-header {
           type uint64;
           description "Input packets with tlv header error";
         }
         leaf input-packets-with-bad-tlv-type {
           type uint64;
           description "Input packets with bad tlv type";
         }
         leaf input-packets-tlv-dropped {
           type uint64;
           description "Input packets dropped based on tlv result";
         }
         leaf input-packets-with-bad-af {
           type uint64;
           description "Input packets with bad address family";
         }
         leaf input-packets-for-which-route-lookup-is-bypassed {
           type uint64;
           description "Input packets for which route lookup is bypassed";
         }
         leaf input-packets-with-ttp-tlv-p2mp-nbr-nhid-type {
           type uint64;
           description "Input packets with ttp tlv of type TTP_TLV_P2MP_NBR_NHID";
         }
         leaf input-packets-with-unknown-p2mp-nbr-nhid {
           type uint64;
           description "Input packets with unknown p2mp_nbr_nhid value";
         }
         leaf input-packets-with-vxlan-bfd-pkts {
           type uint64;
           description "Input packets of type vxlan bfd";
         }
       }
       container mpls {
         leaf total-mpls-packets-received {
           type uint32;
           description "Total MPLS packets received";
         }
         leaf packets-forwarded {
           type uint32;
           description "Packets forwarded";
         }
         leaf packets-dropped {
           type uint32;
           description "Packets dropped (src and int don't match)";
         }
         leaf packets-with-header-too-small {
           type uint32;
           description "Packets with header too small";
         }
         leaf after-tagging-packets-can-not-fit-link-mtu {
           type uint32;
           description "After tagging, packets can't fit link MTU";
         }
         leaf packets-with-ipv4-explicit-null-tag {
           type uint32;
           description "Packets with IPv4 explicit NULL tag";
         }
         leaf packets-with-ipv4-explicit-null-checksum-errors {
           type uint32;
           description "Packets with IPv4 explicit NULL cksum errors";
         }
         leaf packets-with-router-alert-tag {
           type uint32;
           description "Packets with router alert tag";
         }
         leaf lsp-ping-packets {
           type uint32;
           description "LSP ping packets (ttl-expired/router alert)";
         }
         leaf packets-with-ttl-expired {
           type uint32;
           description "Packets with ttl expired";
         }
         leaf packets-with-tag-encoding-error {
           type uint32;
           description "Packets with tag encoding error";
         }
         leaf packets-discarded-due-to-no-route {
           type uint32;
           description "Packets discarded due to no route";
         }
         leaf packets-used-first-nexthop-in-ecmp-unilist {
           type uint32;
           description "Packets used first nexthop in ecmp unilist";
         }
         leaf packets-dropped-due-to-ifl-down {
           type uint32;
           description "Packets dropped due to ifl down";
         }
         leaf packets-dropped-at-mpls-socket-send {
           type uint32;
           description "Packets dropped at mpls socket send op";
         }
         leaf packets-forwarded-at-mpls-socket-send {
           type uint32;
           description "Packets forwarded at mpls socket send op";
         }
         leaf mpls-bfd-packets-received {
           type uint32;
           description "Mpls bfd packets received";
         }
         leaf mpls-cfm-packets-received {
           type uint32;
           description "Mpls cfm packets received";
         }
         leaf packets-dropped-at-p2mp-cnh-output {
           type uint32;
           description "Packets dropped, over p2mp composite nexthop";
         }
       }
       container vpls {
         leaf total-packets-received {
           type uint64;
           description "Total packets received";
         }
         leaf vpls-packets-with-size-smaller-than-minimum {
           type uint64;
           description "Vpls packets with size smaller than minimum";
         }
         leaf vpls-packets-with-incorrect-version-number {
           type uint64;
           description "Vpls packets with incorrect version number";
         }
         leaf vpls-packets-for-this-host {
           type uint64;
           description "Vpls packets for this host";
         }
         leaf packets-with-no-logical-interface {
           type uint64;
           description "Packets with no logical interface";
         }
         leaf packets-with-no-family {
           type uint64;
           description "Packets with no family";
         }
         leaf packets-with-no-route-table {
           type uint64;
           description "Packets with no route table";
         }
         leaf packets-with-no-auxiliary-table {
           type uint64;
           description "Packets with no auxiliary table";
         }
         leaf packets-with-no-corefacing-entry {
           type uint64;
           description "Packets with no core-facing entry";
         }
         leaf packets-with-no-ce-facing-entry {
           type uint64;
           description "Packets with no CE-facing entry";
         }
         leaf mac-route-learning-requests {
           type uint64;
           description "MAC route learning requests";
         }
         leaf mac-routes-learned {
           type uint64;
           description "MAC routes learnt";
         }
         leaf requests-to-learn-an-existing-route {
           type uint64;
           description "Requests to learn an existing route";
         }
         leaf learning-requests-while-learning-disabled-on-interface {
           type uint64;
           description "Learning requests while learning disabled on interface";
         }
         leaf learning-requests-over-capacity {
           type uint64;
           description "Learning requests over capacity";
         }
         leaf mac-routes-moved {
           type uint64;
           description "MAC routes moved";
         }
         leaf requests-to-move-static-route {
           type uint64;
           description "Requests to move static route";
         }
         leaf mac-route-aging-requests {
           type uint64;
           description "MAC route aging requests";
         }
         leaf mac-routes-aged {
           type uint64;
           description "MAC routes aged";
         }
         leaf bogus-address-in-aging-requests {
           type uint64;
           description "Bogus address in aging requests";
         }
         leaf requests-to-age-static-route {
           type uint64;
           description "Requests to age static route";
         }
         leaf requests-to-re-ageout-aged-route {
           type uint64;
           description "Requests to re-ageout aged route";
         }
         leaf requests-involving-multiple-peer-fes {
           type uint64;
           description "Requests involving multiple peer FEs";
         }
         leaf aging-acks-from-pfe {
           type uint64;
           description "Aging acks from PFE";
         }
         leaf aging-non-acks-from-pfe {
           type uint64;
           description "Aging non-acks from PFE";
         }
         leaf aging-requests-timed-out-waiting-on-fes {
           type uint64;
           description "Aging requests timed out waiting on FEs";
         }
         leaf aging-requests-over-max-rate {
           type uint64;
           description "Aging requests over max-rate";
         }
         leaf errors-finding-peer-fes {
           type uint64;
           description "Errors finding peer FEs";
         }
         leaf unsupported-platform {
           type uint64;
           description "Unsupported platform";
         }
         leaf packets-dropped-due-to-no-l3-route-table {
           type uint64;
           description "Packets dropped due to no l3 route table";
         }
         leaf packets-dropped-due-to-no-local-ifl {
           type uint64;
           description "Packets dropped due to no local ifl";
         }
         leaf packets-punted {
           type uint64;
           description "Packets punted";
         }
         leaf packets-dropped-due-to-no-socket {
           type uint64;
           description "Packets dropped due to no socket";
         }
         leaf pim-packets-received {
           type uint64;
           description "PIM Packets received";
         }
         leaf igmp-packets-received {
           type uint64;
           description "IGMP Packets received";
         }
         leaf mld-packets-received {
           type uint64;
           description "MLD Packets received";
         }
       }
       container bridge {
         leaf heading {
           type string;
           description "Header";
         }
         leaf bridge-packets-received {
           type uint64;
           description "Bridge packets received";
         }
         leaf bridge-packets-forwarded {
           type uint64;
           description "Bridge packets forwarded";
         }
         leaf packets-failed-to-forward {
           type uint64;
           description "Packets failed to forward";
         }
         leaf bridge-packets-dropped {
           type uint64;
           description "Bridge packets dropped";
         }
         leaf packets-with-vmember-lookup-failures {
           type uint64;
           description "Packets with vmember lookup failures";
         }
         leaf packets-with-vlan-lookup-failures {
           type uint64;
           description "Packets with VLAN lookup failures";
         }
         leaf packets-with-stp-state-lookup-failures {
           type uint64;
           description "Packets with STP state lookup failures";
         }
         leaf packets-dropped-due-to-stp-blocked-or-listening {
           type uint64;
           description "Packets dropped due to STP blocked/listening";
         }
         leaf packets-dropped-due-to-stp-learning {
           type uint64;
           description "Packets dropped due to STP learning";
         }
         leaf packets-with-src-mac-learning-failures {
           type uint64;
           description "Packets with src MAC learning failures";
         }
         leaf packets-with-input-control-processing-failures {
           type uint64;
           description "Packets with input control processing failures";
         }
         leaf packets-sent-successfully {
           type uint64;
           description "Packets sent successfully";
         }
         leaf packets-with-send-failures {
           type uint64;
           description "Packets with send failures";
         }
         leaf packets-forwarded-to-l3-interface {
           type uint64;
           description "Packets forwarded to l3 interface";
         }
         leaf packets-with-l3-send-failures {
           type uint64;
           description "Packets with l3 send failures";
         }
         leaf packets-discarded {
           type uint64;
           description "Packets discarded";
         }
         leaf packets-with-l2-ifl-store-failures {
           type uint64;
           description "Packets with l2ifl store failures";
         }
         leaf packets-with-ifl-mismatch-failures {
           type uint64;
           description "Packets with ifl mismatch failures";
         }
         leaf packets-with-packet-duplication-failures {
           type uint64;
           description "Packets with packet duplication failures";
         }
         leaf packets-with-tag-lookup-failures {
           type uint64;
           description "Packets with tag lookup failures";
         }
         leaf packets-with-no-route-for-dmac {
           type uint64;
           description "Packets with no route for DMAC";
         }
         leaf packets-with-no-route-table {
           type uint64;
           description "Packets with no route table";
         }
         leaf packets-with-no-nexthop {
           type uint64;
           description "Packets with no nexthop";
         }
         leaf packets-with-dead-nexthop {
           type uint64;
           description "Packets with dead nexthop";
         }
         leaf packets-with-eof-reached-error {
           type uint64;
           description "Packets with eof reached error";
         }
         leaf macs-learned {
           type uint64;
           description "MACs learned";
         }
         leaf packets-sent-to-l3-interface {
           type uint64;
           description "Packets sent to l3 interface";
         }
         leaf packets-hit-hold-queue-while-learning {
           type uint64;
           description "Packets hit hold queue while learning";
         }
         leaf mac-moves {
           type uint64;
           description "MAC moves";
         }
         leaf packets-with-no-route-for-smac {
           type uint64;
           description "Packets with no route for SMAC";
         }
         leaf packets-dropped-due-to-no-resolve-route {
           type uint64;
           description "Packets dropped due to no resolve route";
         }
         leaf packets-with-l3-ifd-lookup-failures {
           type uint64;
           description "Packets with l3 ifd lookup failures";
         }
         leaf packets-with-l3-ifl-lookup-failures {
           type uint64;
           description "Packets with l3 ifl lookup failures";
         }
         leaf packets-with-l3-invalid-rnh {
           type uint64;
           description "Packets with l3 invalid RNH";
         }
         leaf packets-with-no-route-for-smac-in-clone-learning {
           type uint64;
           description "Packets with no route for SMAC in clone learning";
         }
         leaf packets-with-no-nexthop-in-clone-learning {
           type uint64;
           description "Packets with no nexhop in clone learning";
         }
         leaf packets-with-dead-nexthop-in-clone-learning {
           type uint64;
           description "Packets with dead nexthop in clone learning";
         }
         leaf packets-dropped-due-to-no-resolve-nh-in-clone-learning {
           type uint64;
           description "Packets dropped due to no resolve nh in clone learning";
         }
         leaf packets-dropped-due-to-interface-down {
           type uint64;
           description "Packets dropped due to interface down";
         }
         leaf packets-with-dev-output-failures {
           type uint64;
           description "Packets with dev output failures";
         }
         leaf blocked-ifl-discards {
           type uint64;
           description "Blocked ifl discards";
         }
         leaf packets-with-tag-insertion-failures {
           type uint64;
           description "Packets with tag insertion failures";
         }
         leaf packets-with-tag-removal-failures {
           type uint64;
           description "Packets with tag removal failures";
         }
         leaf packets-flooded {
           type uint64;
           description "Packets flooded";
         }
         leaf flood-failures {
           type uint64;
           description "Flood failures";
         }
         leaf packets-with-mpull-failures {
           type uint64;
           description "Packets with mpull failures";
         }
         leaf packets-with-ifl-lookup-failures {
           type uint64;
           description "Packets with ifl lookup failures";
         }
         leaf bridge-packets-with-size-smaller-than-minimum {
           type uint64;
           description "Bridge packets with size smaller than minimum";
         }
         leaf packets-with-double-tags {
           type uint64;
           description "Packets with double tags";
         }
         leaf packets-with-no-ifl {
           type uint64;
         }
         leaf packets-with-no-family {
           type uint64;
           description "Packets with no family";
         }
         leaf packets-with-receive-failures {
           type uint64;
           description "Packets with receive failures";
         }
       }
       container ethoamcfm {
         leaf total-packets-received {
           type uint64;
           description "Total packets received";
         }
         leaf input-packets-drop-bad-interface-state {
           type uint32;
           description "Input packets drop due to bad interface state";
         }
         leaf received-packets-forwarded {
           type uint32;
           description "Received packets forwarded";
         }
         leaf total-packets-transmitted {
           type uint32;
           description "Total transmitted packets";
         }
         leaf packets-sent {
           type uint32;
           description "Packets sent";
         }
         leaf output-packets-drop-bad-interface-state {
           type uint32;
           description "Output packets drop due to bad interface state";
         }
         leaf flood-requests-forwarded-to-pfe {
           type uint32;
           description "Flood requests forwarded to PFE";
         }
         leaf flood-requests-dropped {
           type uint32;
           description "Flood requests dropped";
         }
       }
       container ethoamlfm {
         leaf total-packets-received {
           type uint64;
           description "Total packets received";
         }
         leaf input-packets-drop-bad-interface-state {
           type uint32;
           description "Input packets drop due to bad interface state";
         }
         leaf received-packets-forwarded {
           type uint32;
           description "Received packets forwarded";
         }
         leaf total-packets-transmitted {
           type uint32;
           description "Total transmitted packets";
         }
         leaf packets-sent {
           type uint32;
           description "Packets sent";
         }
         leaf output-packets-drop-bad-interface-state {
           type uint32;
           description "Output packets drop due to bad interface state";
         }
       }
       container jsr {
         leaf handle-info {
           type string;
         }
         leaf handles-in-use {
           type uint32;
           description "Handles in use";
         }
         leaf handles-allocated-so-far {
           type uint32;
           description "Handles allocated so far";
         }
         leaf handles-freed-so-far {
           type uint32;
           description "Handles freed so far";
         }
         leaf handles-in-delayed-free-state {
           type uint32;
           description "Handles in delayed free state";
         }
         leaf iha {
           type string;
         }
         leaf iha-invalid-subtype-messages {
           type uint32;
           description "Invalid subtype messages";
         }
         leaf iha-invalid-length-messages {
           type uint32;
           description "Invalid length messages";
         }
         leaf iha-invalid-version-messages {
           type uint32;
           description "Invalid version messages";
         }
         leaf iha-too-short-messages {
           type uint32;
           description "IHA too short messages";
         }
         leaf iha-invalid-dst-handle-messages {
           type uint32;
           description "IHA invalid dst handle messages";
         }
         leaf iha-invalid-src-handle-messages {
           type uint32;
           description "IHA invalid src handle messages";
         }
         leaf iha-unmatched-src-handle-messages {
           type uint32;
           description "IHA unmatched src handle messages";
         }
         leaf iha-invalid-messages-for-primary {
           type uint32;
           description "IHA invalid messages for primary";
         }
         leaf iha-invalid-messages-for-secondary {
           type uint32;
           description "IHA invalid messages for secondary";
         }
         leaf iha-invalid-messages-for-current-state {
           type uint32;
           description "IHA invalid messages for current state";
         }
         leaf iha-messages-sent-for-subtype-init {
           type uint32;
           description "IHA messages sent for subtype init";
         }
         leaf iha-messages-rcvd-for-subtype-init {
           type uint32;
           description "IHA messages rcvd for subytpe init";
         }
         leaf iha-messages-sent-for-subtype-ack {
           type uint32;
           description "IHA messages sent for subtype ack";
         }
         leaf iha-messages-rcvd-for-subtype-ack {
           type uint32;
           description "IHA messages rcvd for subtype ack";
         }
         leaf iha-messages-sent-for-subtype-unrepl-sec {
           type uint32;
           description "IHA messages sent for subtype unrepl_sec";
         }
         leaf iha-messages-rcvd-for-subtype-unrepl-sec {
           type uint32;
           description "IHA messages rcvd for subtype unrepl_sec";
         }
         leaf iha-messages-sent-for-subtype-unrepl-pri {
           type uint32;
           description "IHA messages sent for subtype unrepl_pri";
         }
         leaf iha-messages-rcvd-for-subtype-unrepl-pri {
           type uint32;
           description "IHA messages rcvd for subtype unrepl_pri";
         }
         leaf iha-messages-sent-for-subtype-unrepl-am-sec {
           type uint32;
           description "IHA messages sent for subtype unrepl_am_sec";
         }
         leaf iha-messages-rcvd-for-subtype-unrepl-am-sec {
           type uint32;
           description "IHA messages rcvd for subtype unrepl_am_sec";
         }
         leaf iha-message-timeouts {
           type uint32;
           description "IHA message timeouts";
         }
         leaf iha-socket-unreplicate-messages {
           type uint32;
           description "IHA socket unreplicate messages";
         }
         leaf sdrl {
           type string;
         }
         leaf sdrl-socket-teardowns {
           type uint32;
           description "SDRL socket teardowns";
         }
         leaf sdrl-socket-teardown-failures {
           type uint32;
           description "SDRL socket teardown failures";
         }
         leaf sdrl-socket-unreplicates {
           type uint32;
           description "SDRL socket unreplicates";
         }
         leaf sdrl-socket-unreplicate-failures {
           type uint32;
           description "SDRL socket unreplicate failures";
         }
         leaf sdrl-external-timeouts {
           type uint32;
           description "SDRL external timeouts";
         }
         leaf sdrl-internal-timeouts {
           type uint32;
           description "SDRL internal timeouts";
         }
         leaf sdrl-ipc-messages-sent {
           type uint32;
           description "SDRL ipc messages sent";
         }
         leaf sdrl-ipc-send-failures {
           type uint32;
           description "SDRL ipc send failures";
         }
         leaf sdrl-ipc-messages-recvd {
           type uint32;
           description "SDRL ipc messages recvd";
         }
         leaf sdrl-ipc-recv-failures {
           type uint32;
           description "SDRL ipc recv failures";
         }
         leaf sdrl-primary-replication-messages-sent {
           type uint32;
           description "SDRL primary replication messages sent";
         }
         leaf sdrl-primary-replication-message-send-failures {
           type uint32;
           description "SDRL primary replication message send failures";
         }
         leaf sdrl-primary-ack-messages-received {
           type uint32;
           description "SDRL primary ack messages received";
         }
         leaf sdrl-primary-ack-message-receive-failures {
           type uint32;
           description "SDRL primary ack message receive failures";
         }
         leaf sdrl-primary-sock-replication-inits {
           type uint32;
           description "SDRL primary sock replication inits";
         }
         leaf sdrl-primary-sock-replication-init-failures {
           type uint32;
           description "SDRL primary sock message init failures";
         }
         leaf sdrl-primary-throttle-remove-messages {
           type uint32;
           description "SDRL primary throttle remove messages";
         }
         leaf sdrl-primary-throttle-remove-failures {
           type uint32;
           description "SDRL primary throtle remove failures";
         }
         leaf sdrl-primary-init-handshake-messages {
           type uint32;
           description "SDRL primary init handshake messages";
         }
         leaf sdrl-primary-init-handshake-failures {
           type uint32;
           description "SDRL primary init handshake failures";
         }
         leaf sdrl-secondary-replication-messages-received {
           type uint32;
           description "SDRL secondary replication messages received";
         }
         leaf sdrl-secondary-replication-message-receive-failures {
           type uint32;
           description "SDRL secondary replication message receive failures";
         }
         leaf sdrl-secondary-replication-acks-sent {
           type uint32;
           description "SDRL secondary replication acks sent";
         }
         leaf sdrl-secondary-replication-ack-send-failures {
           type uint32;
           description "SDRL secondary replication ack send failures";
         }
         leaf sdrl-secondary-sock-splits {
           type uint32;
           description "SDRL secondary sock splits";
         }
         leaf sdrl-secondary-sock-split-failures {
           type uint32;
           description "SDRL secondary sock split failures";
         }
         leaf sdrl-secondary-sock-merges {
           type uint32;
           description "SDRL secondary sock merges";
         }
         leaf sdrl-secondary-sock-merge-failures {
           type uint32;
           description "SDRL secondary sock merge failures";
         }
         leaf sdrl-secondary-sockets-closed {
           type uint32;
           description "SDRL secondary sockets closed";
         }
         leaf sdrl-secondary-rcv-snoop-fd-close-failures {
           type uint32;
           description "SDRL secondary rcv snoop fd close failures";
         }
         leaf sdrl-secondary-snd-snoop-fd-close-failures {
           type uint32;
           description "SDRL secondary snd snoop fd close failures";
         }
         leaf sdrl-secondary-init-handshake-messages {
           type uint32;
           description "SDRL secondary init handshake messages";
         }
         leaf sdrl-secondary-init-handshake-failures {
           type uint32;
           description "SDRL secondary init handshake failures";
         }
         leaf prl {
           type string;
         }
         leaf prl-packets-enqueued {
           type uint32;
           description "PRL packets enqueued";
         }
         leaf prl-packets-failed-to-enqueue {
           type uint32;
           description "PRL packets failed to enqueue";
         }
         leaf prl-packets-dequeued {
           type uint32;
           description "PRL packets dequeued";
         }
         leaf prl-packets-failed-to-dequeue {
           type uint32;
           description "PRL packets failed to dequeue";
         }
         leaf prl-queue-entry-allocations {
           type uint32;
           description "PRL queue entry allocations";
         }
         leaf prl-queue-entry-frees {
           type uint32;
           description "PRL queue entry frees";
         }
         leaf prl-calls-to-layer4-input-handlers {
           type uint32;
           description "Calls to layer 4 input handlers";
         }
         leaf prl-failed-calls-to-layer4-input-handlers {
           type uint32;
           description "Failed calls to layer 4 input handlers";
         }
         leaf prl-queue-drains {
           type uint32;
           description "PRL queue drains";
         }
         leaf prl-replication-timeouts {
           type uint32;
           description "PRL replication timeouts";
         }
         leaf prl-replication-messages-sent {
           type uint32;
           description "PRL replication messages sent";
         }
         leaf prl-replication-message-send-failures {
           type uint32;
           description "PRL replication message send failures";
         }
         leaf prl-acknowledgement-messages-sent {
           type uint32;
           description "PRL acknowledgment messages sent";
         }
         leaf prl-acknowledgement-message-send-failures {
           type uint32;
           description "PRL acknowledgement message send failures";
         }
         leaf prl-replication-message-received {
           type uint32;
           description "PRL replication message received";
         }
         leaf prl-replication-message-receive-failures {
           type uint32;
           description "PRL replication message receive failures";
         }
         leaf prl-acknowledgement-messages-received {
           type uint32;
           description "PRL acknowledgement message received";
         }
         leaf prl-acknowledgement-message-receive-failures {
           type uint32;
           description "PRL acknowledgment message receive failures";
         }
         leaf prl-messages-with-bad-ipc-type {
           type uint32;
           description "PRL messages with bad IPC type";
         }
         leaf prl-messages-with-no-handler {
           type uint32;
           description "PRL messages with no handler";
         }
         leaf prl-global-state-initializations {
           type uint32;
           description "PRL global state initializations";
         }
         leaf prl-global-state-cleanups {
           type uint32;
           description "PRL global state cleanups";
         }
         leaf prl-per-socket-state-creations {
           type uint32;
           description "PRL per-socket state creations";
         }
         leaf prl-per-socket-state-creation-failures {
           type uint32;
           description "PRL per-socket state creation failures";
         }
         leaf prl-per-socket-state-cleanups {
           type uint32;
           description "PRL per-socket state cleanups";
         }
         leaf prl-socket-closes {
           type uint32;
           description "PRL socket closes";
         }
         leaf prl-socket-merges {
           type uint32;
           description "PRL socket merges";
         }
         leaf prl-socket-unreplicates {
           type uint32;
           description "PRL socket unreplicates";
         }
         leaf prl-primary-socket-replication-initializations {
           type uint32;
           description "PRL primary socket replication initializations";
         }
         leaf prl-secondary-socket-replication-initializations {
           type uint32;
           description "PRL secondary socket replication initializations";
         }
         leaf prl-primary-socket-replication-activations {
           type int32;
           description "PRL primary socket replication activations";
         }
         leaf prl-secondary-socket-replication-activations {
           type uint32;
           description "PRL secondary socket replication activations";
         }
         leaf prl-packets-received-from-peers {
           type uint32;
           description "Packets received from peers";
         }
         leaf prl-packets-receive-operations-from-peer-failed {
           type uint32;
           description "PRL packets receive operations from peer failed";
         }
         leaf prl-buffer-pullup-failures {
           type uint32;
           description "PRL buffer pullup failures";
         }
         leaf prl-new-packets-dropped-on-security-socket {
           type uint32;
           description "New pkts dropped on secondary socket";
         }
         leaf psrm {
           type string;
         }
         leaf psrm-replication-timeouts {
           type uint32;
           description "PSRM replication timeouts";
         }
         leaf psrm-replication-messages-sent {
           type uint32;
           description "PSRM replication messages sent";
         }
         leaf psrm-replication-message-send-failures {
           type uint32;
           description "PSRM replication message send failures";
         }
         leaf psrm-acknowledgement-messages-sent {
           type uint32;
           description "PSRM acknowledgment messages sent";
         }
         leaf psrm-acknowledgement-message-send-failures {
           type uint32;
           description "PSRM acknowledgement message send failures";
         }
         leaf psrm-flow-control-messages-sent {
           type uint32;
           description "PSRM flow control messages sent";
         }
         leaf psrm-flow-control-message-send-failures {
           type uint32;
           description "PSRM flow control message send failures";
         }
         leaf psrm-replication-messages-received {
           type uint32;
           description "PSRM replication messages received";
         }
         leaf psrm-replication-message-receive-failures {
           type uint32;
           description "PSRM replication message receive failures";
         }
         leaf psrm-acknowledgement-messages-received {
           type uint32;
           description "PSRM acknowledgment messages received";
         }
         leaf psrm-acknowledgement-message-receive-failures {
           type uint32;
           description "PSRM acknowledgment message receive failures";
         }
         leaf psrm-flow-control-messages-received {
           type uint32;
           description "PSRM flow control messages received";
         }
         leaf psrm-flow-control-message-receive-failures {
           type uint32;
           description "PSRM flow control message receive failures";
         }
         leaf psrm-messages-with-bad-ipc-type {
           type uint32;
           description "PSRM messages with bad IPC type";
         }
         leaf psrm-messages-with-no-handler {
           type uint32;
           description "PSRM messages with no handler";
         }
         leaf psrm-global-state-initializations {
           type uint32;
           description "PSRM global state initializations";
         }
         leaf psrm-global-state-cleanups {
           type uint32;
           description "PSRM global state cleanups";
         }
         leaf psrm-per-socket-state-creations {
           type uint32;
           description "PSRM per-socket state creations";
         }
         leaf psrm-per-socket-state-creation-failures {
           type uint32;
           description "PSRM per-socket state creation failures";
         }
         leaf psrm-per-socket-state-cleanups {
           type uint32;
           description "PSRM per-socket state cleanups";
         }
         leaf psrm-socket-closes {
           type uint32;
           description "PSRM socket closes";
         }
         leaf psrm-socket-merges {
           type uint32;
           description "PSRM socket merges";
         }
         leaf psrm-socket-unreplicates {
           type uint32;
           description "PSRM socket unreplicates";
         }
         leaf psrm-primary-socket-replication-initializations {
           type uint32;
           description "PSRM primary socket replication initializations";
         }
         leaf psrm-secondary-socket-replication-initializations {
           type uint32;
           description "PSRM secondary socket replication initializations";
         }
         leaf psrm-primary-socket-replication-activations {
           type uint32;
           description "PSRM primary socket replication activations";
         }
         leaf psrm-secondary-socket-replication-activations {
           type uint32;
           description "PSRM secondary socket replication activations";
         }
         leaf psrm-tcpcb-updates {
           type uint32;
           description "PSRM tcpcb updates";
         }
         leaf psrm-buffer-pullup-failures {
           type uint32;
           description "PSRM buffer pullup failures";
         }
         leaf psrm-tcp-timestamp-msg-recv-counters {
           type uint32;
           description "PSRM tcp timestamp msg recv counters";
         }
         leaf psrm-tcp-timestamp-msg-recv-failures {
           type uint32;
           description "PSRM tcp timestamp msg recv failures";
         }
         leaf psrm-tcp-timestamp-msg-send-counters {
           type uint32;
           description "PSRM tcp timestamp msg send counters";
         }
         leaf psrm-tcp-timestamp-msg-send-failures {
           type uint32;
           description "PSRM tcp timestamp msg send failures";
         }
         leaf tcp-field {
           type string;
         }
         leaf tcp-out-of-order-packets-on-jsr-sockets {
           type uint32;
           description "TCP out-of-order packets on JSR sockets";
         }
       }
     }
   }
   augment "/jgs:genstate" {
     description "Adds statistics to top-level genstate";
     uses statistics-top;
   }
 }
