/*
 * Copyright (c) 2025 Juniper Networks, Inc.
 * All rights reserved.
 */
 module junos-rpc-request {
   namespace "http://yang.juniper.net/junos/rpc/request";

   prefix request;

   import junos-common-types {
     prefix jt;
     revision-date 2024-01-01;
   }

   organization "Juniper Networks, Inc.";

   contact "yang-support@juniper.net";

   description "Junos RPC YANG module for request command(s)";

   revision 2024-01-01 {
     description "Junos: 24.4R2.16-EVO";
   }

   rpc resize-configuraion-database {
     description "Resize the configuration database";
     input {
       uses command-forwarding;
       leaf force {
         description "Resize the configuration database even if modified";
         type empty;
       }
     }
     output {
       choice output_c {
         case output-tag {
           leaf output {
             type string;
           }
         }
         case multichassis-tag {
           anyxml multi-routing-engine-results;
         }
       }
     }
   }
   rpc request-save-rescue-configuration {
     description "Save committed configuration as rescue configuration";
     output {
       container rescue-management-results {
         uses rescue-management-results-block;
       }
     }
   }
   rpc request-delete-rescue-configuration {
     description "Delete the rescue configuration";
     output {
       container rescue-management-results {
         uses rescue-management-results-block;
       }
     }
   }
   rpc request-commit-server-cleanup {
     description "Commit queue clean up operations";
     input {
       choice queue-selector {
         case id {
           leaf id {
             description "Clean up queue id";
             type union {
               type uint32;
               type string {
                 pattern "<.*>|$.*";
               }
             }
           }
         }
         case job-status {
           leaf job-status {
             description "Clean up all entries with specified status";
             type enumeration {
               enum "error" {
                 description "Remove jobs that had errors";
               }
               enum "pending" {
                 description "Remove jobs that are pending";
               }
               enum "success" {
                 description "Remove jobs that succeeded";
               }
             }
           }
         }
       }
     }
     output {
       container commit-server-delete-results {
         uses commit-server-delete-results-block;
       }
     }
   }
   rpc request-commit-server-pause {
     description "Pause the commit server";
     output {
       container commit-server-operation {
         uses commit-server-operation-block;
       }
     }
   }
   rpc request-commit-server-start {
     description "Start the commit server";
     output {
       container commit-server-operation {
         uses commit-server-operation-block;
       }
     }
   }
   rpc request-delta-exporter-initialize {
     description "Initialize delta exporter database";
     output {
       choice output_c {
         case output-tag {
           leaf output {
             type string;
           }
         }
         case multichassis-tag {
           anyxml multi-routing-engine-results;
         }
       }
     }
   }
   rpc request-yang-add {
     description "Add YANG module(s) and action/translation script(s)";
     input {
       leaf package {
         description "Unique ID for future op - delete/update";
         type string;
         mandatory true;
       }
       leaf-list module {
         ordered-by user;
         description "YANG module(s) path";
         type jt:filename;
       }
       leaf-list action-script {
         ordered-by user;
         description "Action script path";
         type jt:filename;
       }
       leaf-list translation-script {
         ordered-by user;
         description "Translation script path";
         type jt:filename;
       }
       leaf-list deviation-module {
         ordered-by user;
         description "Deviation module path";
         type jt:filename;
       }
       leaf proxy-xml {
         description "XML proxy YANG module(s)";
         type empty;
       }
       leaf snmp {
         description "Add custom MIB in YANG format";
         type empty;
       }
       choice re-choice {
         case re0 {
           leaf re0 {
             description "Add/Delete YANG module(s) on RE0";
             type empty;
           }
         }
         case re1 {
           leaf re1 {
             description "Add/Delete YANG module(s) on RE1";
             type empty;
           }
         }
         case other-routing-engine {
           leaf other-routing-engine {
             description "Add/Delete YANG module(s) on other RE";
             type empty;
           }
         }
       }
     }
     output {
       choice output_c {
         case output-tag {
           leaf output {
             type string;
           }
         }
         case multichassis-tag {
           anyxml multi-routing-engine-results;
         }
       }
     }
   }
   rpc request-yang-delete {
     description "Remove YANG package";
     input {
       leaf package {
         description "ID to be removed";
         type string;
         mandatory true;
       }
       choice re-choice {
         case re0 {
           leaf re0 {
             description "Add/Delete YANG module(s) on RE0";
             type empty;
           }
         }
         case re1 {
           leaf re1 {
             description "Add/Delete YANG module(s) on RE1";
             type empty;
           }
         }
         case other-routing-engine {
           leaf other-routing-engine {
             description "Add/Delete YANG module(s) on other RE";
             type empty;
           }
         }
       }
     }
     output {
       choice output_c {
         case output-tag {
           leaf output {
             type string;
           }
         }
         case multichassis-tag {
           anyxml multi-routing-engine-results;
         }
       }
     }
   }
   rpc request-yang-enable {
     description "Enable YANG package to JUNOS translation";
     input {
       leaf package {
         description "ID";
         type string;
         mandatory true;
       }
     }
     output {
       choice output_c {
         case output-tag {
           leaf output {
             type string;
           }
         }
         case multichassis-tag {
           anyxml multi-routing-engine-results;
         }
       }
     }
   }
   rpc request-yang-disable {
     description "Disable YANG package to JUNOS translation";
     input {
       leaf package {
         description "ID";
         type string;
         mandatory true;
       }
     }
     output {
       choice output_c {
         case output-tag {
           leaf output {
             type string;
           }
         }
         case multichassis-tag {
           anyxml multi-routing-engine-results;
         }
       }
     }
   }
   rpc request-yang-validate {
     description "Validate YANG module(s) and action/translation script(s)";
     input {
       leaf-list module {
         ordered-by user;
         description "Name of the YANG module to be validated";
         type jt:filename;
       }
       leaf-list translation-script {
         ordered-by user;
         description "Name of the translation-script to be validated";
         type jt:filename;
       }
       leaf-list action-script {
         ordered-by user;
         description "Name of the action-script to be validated";
         type jt:filename;
       }
       leaf proxy-xml {
         description "XML proxy YANG module";
         type empty;
       }
       leaf snmp {
         description "Validate custom MIB in YANG format";
         type empty;
       }
     }
     output {
       choice output_c {
         case output-tag {
           leaf output {
             type string;
           }
         }
         case multichassis-tag {
           anyxml multi-routing-engine-results;
         }
       }
     }
   }
   rpc request-yang-update {
     description "Update YANG module(s) and action/translation script(s)";
     input {
       leaf package {
         description "ID";
         type string;
         mandatory true;
       }
       leaf-list module {
         ordered-by user;
         description "YANG module(s) path";
         type jt:filename;
       }
       leaf-list translation-script {
         ordered-by user;
         description "Translation script path";
         type jt:filename;
       }
       leaf-list deviation-module {
         ordered-by user;
         description "Deviation module path";
         type jt:filename;
       }
       leaf-list action-script {
         ordered-by user;
         description "Action script path";
         type jt:filename;
       }
       leaf proxy-xml {
         description "XML proxy YANG module(s)";
         type empty;
       }
       leaf snmp {
         description "Update custom MIBs in YANG format";
         type empty;
       }
     }
     output {
       choice output_c {
         case output-tag {
           leaf output {
             type string;
           }
         }
         case multichassis-tag {
           anyxml multi-routing-engine-results;
         }
       }
     }
   }
   rpc request-logout-user {
     description "Forcibly end user's CLI login session";
     input {
       uses command-forwarding;
       leaf pid {
         description "Management process ID for user";
         type union {
           type uint32;
           type string {
             pattern "<.*>|$.*";
           }
         }
       }
       leaf all {
         description "Logout all sessions owned by user";
         type empty;
       }
       leaf user {
         description "Name of user";
         type string {
         }
       }
       leaf terminal {
         description "Terminal user is logged in to";
         type string {
         }
       }
     }
     output {
       container logout-user {
         uses logout-user-block;
       }
     }
   }
   rpc request-json-configuration-conversion {
     description "Convert the given JSON configuration file as per Junos";
     input {
       leaf filename {
         description "Path to the input JSON configuration file";
         type jt:filename;
         mandatory true;
       }
       leaf output-filename {
         description "Path to the output file";
         type string {
         }
         mandatory true;
       }
       leaf origin-schema {
         description "Specify the Yang schema origin";
         default "juniper";
         type string;
       }
     }
     output {
       choice output_c {
         case output-tag {
           leaf output {
             type string;
           }
         }
         case multichassis-tag {
           anyxml multi-routing-engine-results;
         }
       }
     }
   }
   rpc reload-event-scripts {
     description "Reload all existing event-scripts";
   }
   rpc request-scripts-package-add {
     description "Add or upgrade jais package";
     input {
       leaf no-copy {
         description "Don't save copy of jais package file";
         type empty;
       }
       leaf unlink {
         description "Remove the package after successful installation";
         type empty;
       }
       leaf package-name {
         description "URL or pathname of package";
         type jt:filename;
         mandatory true;
       }
       choice chassis {
         case scc {
           leaf scc {
             description "Install package on SCC";
             type empty;
           }
         }
         case lcc {
           leaf lcc {
             description "Install package on an LCC";
             type union {
               type string {
                 pattern "<.*>|$.*";
               }
               type uint32;
             }
           }
         }
         case sfc {
           leaf sfc {
             description "Install package on SFC";
             type empty;
           }
         }
         case member {
           leaf member {
             description "Install package on member";
             type union {
               type string {
                 pattern "<.*>|$.*";
               }
               type uint32;
             }
           }
         }
         case dont-forward {
           leaf dont-forward {
             type empty;
           }
         }
         case master {
           leaf master {
             description "Run command on master";
             type empty;
           }
         }
         case backup {
           leaf backup {
             description "Run command on backup";
             type empty;
           }
         }
       }
     }
     output {
       choice output_c {
         case output-tag {
           leaf output {
             type string;
           }
         }
         case multichassis-tag {
           anyxml multi-routing-engine-results;
         }
       }
     }
   }
   rpc request-scripts-package-delete {
     description "Remove jais package";
     input {
       uses command-forwarding;
     }
     output {
       choice output_c {
         case output-tag {
           leaf output {
             type string;
           }
         }
         case multichassis-tag {
           anyxml multi-routing-engine-results;
         }
       }
     }
   }
   rpc request-scripts-package-rollback {
     description "Attempt to roll back to last jais package";
     input {
       uses command-forwarding;
     }
     output {
       choice output_c {
         case output-tag {
           leaf output {
             type string;
           }
         }
         case multichassis-tag {
           anyxml multi-routing-engine-results;
         }
       }
     }
   }
   rpc request-script-refresh-from {
     description "Refresh script from a given base URL";
     input {
       leaf type {
         type enumeration {
           enum "commit" {
             description "Refresh commit script from a given base URL";
           }
           enum "op" {
             description "Refresh op script from a given base URL";
           }
           enum "event" {
             description "Refresh event script from a given base URL";
           }
           enum "snmp" {
             description "Refresh snmp script from a given base URL";
           }
           enum "extension-service" {
             description "Refresh extension-services app from a given base URL";
           }
         }
         mandatory true;
       }
       leaf file {
         description "Local script file name";
         type string {
         }
         mandatory true;
       }
       leaf url {
         description "URL from where the content will be retrieved";
         type string;
         mandatory true;
       }
       leaf routing-instance {
         description "Specify the routing-instance name";
         type string;
       }
       leaf cert-file {
         description "Specify the ca certificate file name";
         type string;
       }
       leaf sync {
         description "Refresh script and synchronize with other RE";
         type empty;
       }
     }
     output {
       choice output_c {
         case output-tag {
           leaf output {
             type string;
           }
         }
         case multichassis-tag {
           anyxml multi-routing-engine-results;
         }
       }
     }
   }
   rpc request-scripts-synchronize {
     description "Push the scripts to other RE";
     input {
       leaf type {
         type enumeration {
           enum "commit" {
             description "Push commit script to other RE";
           }
           enum "op" {
             description "Push op script to other RE";
           }
           enum "event" {
             description "Push event script to other RE";
           }
           enum "snmp" {
             description "Push snmp script to other RE";
           }
           enum "jet" {
             description "Push jet app to other RE";
           }
           enum "lib" {
             description "Push lib script to other RE";
           }
           enum "all" {
             description "Push all the scripts to other RE";
           }
         }
         mandatory true;
       }
       leaf file {
         description "Local script file name";
         type string;
       }
       leaf newer-than {
         description "Push script to other RE if newer than this time (YYYY-MM-DD.HH:MM:SS)";
         type jt:time;
       }
     }
     output {
       choice output_c {
         case output-tag {
           leaf output {
             type string;
           }
         }
         case multichassis-tag {
           anyxml multi-routing-engine-results;
         }
       }
     }
   }
   rpc request-system-software-stage {
     description "Stage the specified version";
     input {
       leaf package-name {
         description "Pathname of package";
         type jt:filename;
       }
     }
     output {
       choice output_c {
         case output-tag {
           leaf output {
             type string;
           }
         }
         case multichassis-tag {
           anyxml multi-routing-engine-results;
         }
       }
     }
   }
   rpc request-system-software-activate {
     description "Activate the specified image";
     input {
       leaf with-old-snapshot-config {
         description "Set next boot pointer for the given image";
         type empty;
         mandatory true;
       }
       leaf reboot {
         description "Reboot the system after activation";
         type empty;
       }
       leaf package-name {
         description "Pathname of package";
         type jt:filename;
       }
     }
     output {
       choice output_c {
         case output-tag {
           leaf output {
             type string;
           }
         }
         case multichassis-tag {
           anyxml multi-routing-engine-results;
         }
       }
     }
   }
   rpc request-package-add {
     description "Add extension or upgrade package";
     input {
       leaf stage {
         description "Stage the specified version";
         type empty;
       }
       leaf force {
         description "Force addition of package (Ignore warnings and auto-delete older image(s) to make space)";
         type empty;
       }
       choice reset-options {
         case reboot {
           leaf reboot {
             description "Reboot system after adding package";
             type empty;
           }
         }
         case restart {
           leaf restart {
             description "Restart apps and nodes";
             type empty;
           }
         }
       }
       leaf ignore-third-party-packages {
         description "Skip install of existing third party packages for incoming JUNOS package";
         type empty;
       }
       leaf force-host {
         description "Force addition of host os package (ignore version check)";
         type empty;
       }
       leaf on-primary {
         description "Install image on primary partition while booted on secondary partition";
         type empty;
       }
       leaf no-auto-reboot {
         description "Do not reboot system automatically after adding package";
         type empty;
       }
       leaf delay-restart {
         description "Don't restart processes";
         type empty;
       }
       leaf no-copy {
         description "Don't save copies of package files";
         type empty;
       }
       leaf dualroot {
         description "Install Dual-Root image for Zeroization";
         type empty;
       }
       choice validate_choice {
         case no-validate {
           leaf no-validate {
             description "Don't check compatibility with current configuration";
             type empty;
           }
         }
         case validate {
           leaf validate {
             description "Check compatibility with current configuration";
             type empty;
           }
         }
         case validate-on-host {
           leaf validate-on-host {
             description "Remote host or user@host for configuration validation";
             type string;
           }
         }
         case validate-on-routing-engine {
           leaf validate-on-routing-engine {
             description "Routing engine for configuration validation";
             type string;
           }
         }
       }
       leaf best-effort-load {
         description "Load succeeds if at least one statement is valid";
         type empty;
       }
       leaf unlink {
         description "Remove the package after successful installation";
         type empty;
       }
       choice re-choice {
         case re0 {
           leaf re0 {
             description "Install package on RE0";
             type empty;
           }
         }
         case re1 {
           leaf re1 {
             description "Install package on RE1";
             type empty;
           }
         }
         case both-routing-engines {
           leaf both-routing-engines {
             description "Simultaneous upgrade on both the RE's";
             type empty;
           }
         }
       }
       choice chassis {
         case scc {
           leaf scc {
             description "Install package on SCC";
             type empty;
           }
         }
         case lcc {
           leaf lcc {
             description "Install package on an LCC";
             type union {
               type string {
                 pattern "<.*>|$.*";
               }
               type uint32;
             }
           }
         }
         case sfc {
           leaf sfc {
             description "Install package on SFC";
             type empty;
           }
         }
         case member {
           leaf member {
             description "Install package on member";
             type union {
               type string {
                 pattern "<.*>|$.*";
               }
               type uint32;
             }
           }
         }
         case dont-forward {
           leaf dont-forward {
             type empty;
           }
         }
         case service-node {
           leaf service-node {
             description "Install package on Service Node";
             type union {
               type string {
                 pattern "<.*>|$.*";
               }
               type uint32 {
                 range "0 .. 1";
               }
             }
           }
         }
         case upgrade-group {
           leaf upgrade-group {
             description "Satellite upgrade group name";
             type string;
           }
         }
         case satellite {
           leaf satellite {
             description "FPC slot of satellite system";
             type union {
               type int32;
               type string {
                 pattern "<.*>|$.*";
               }
             }
           }
         }
         case device-alias {
           leaf device-alias {
             description "Device alias of satellite system";
             type string;
           }
         }
       }
       leaf issu-internal {
         description "Internally executed by mgd, to allow software adds during issu";
         type empty;
       }
       leaf-list upgrade-with-config {
         ordered-by user;
         description "Additional configs ('text/xml' format) to be applied on upgrade";
         type jt:filename;
       }
       leaf package-name {
         description "Pathname of package";
         type jt:filename;
       }
       leaf virtual-machine-package {
         description "Add virtual-machine package";
         type empty;
       }
     }
     output {
       choice output_c {
         case output-tag {
           leaf output {
             type string;
           }
         }
         case multichassis-tag {
           anyxml multi-routing-engine-results;
         }
       }
     }
   }
   rpc request-package-latest-status {
     description "Status of package installation";
     output {
       container package-status {
         uses package-status-block;
       }
     }
   }
   rpc abort-in-service-upgrade {
     description "Abort in-service software upgrade";
     output {
       choice output_c {
         case output-tag {
           leaf output {
             type string;
           }
         }
         case multichassis-tag {
           anyxml multi-routing-engine-results;
         }
       }
     }
   }
   rpc request-package-in-service-upgrade {
     description "In-service software upgrade";
     input {
       leaf reboot {
         description "Reboot system after adding package";
         type empty;
       }
       leaf handle-incompatible-config {
         description "Automatically handle incompatible configurations";
         type empty;
       }
       choice package-options {
         case set {
           leaf-list set {
             ordered-by user;
             description "List of URLs or pathnames corresponding to packages for ISSU";
             type jt:filename;
           }
         }
         case package-name {
           leaf package-name {
             description "URL or pathname of package";
             type jt:filename;
           }
         }
       }
       leaf no-old-master-upgrade {
         description "Don't upgrade the old master after switchover";
         type empty;
       }
       leaf verbose {
         description "Enable detailed output";
         type empty;
       }
       leaf no-copy {
         description "Don't save copies of package files";
         type empty;
       }
       leaf unlink {
         description "Remove the package after successful installation";
         type empty;
       }
       leaf no-validate {
         description "Don't check compatibility with current configuration";
         type empty;
       }
       choice issu_internal {
       }
       leaf enhanced-mode {
         description "Try to upgrade without any traffic loss";
         type empty;
       }
     }
     output {
       choice output_c {
         case output-tag {
           leaf output {
             type string;
           }
         }
         case multichassis-tag {
           anyxml multi-routing-engine-results;
         }
       }
     }
   }
   rpc request-package-nonstop-upgrade {
     description "Nonstop software upgrade";
     input {
       leaf force-host {
         description "Force addition of host os package (ignore version check)";
         type empty;
       }
       leaf no-auto-recovery {
         description "Will not recover in case of NSSU failure";
         type empty;
       }
       choice package-options {
         case set {
           leaf-list set {
             ordered-by user;
             description "List of URLs or pathnames corresponding to packages";
             type jt:filename;
           }
         }
         case package-name {
           leaf package-name {
             description "URL or pathname of package";
             type jt:filename;
           }
         }
       }
       leaf no-copy {
         description "Don't save copies of package files";
         status deprecated;
         type empty;
       }
       leaf unlink {
         description "Remove the package after successful installation";
         status deprecated;
         type empty;
       }
       leaf no-validate {
         description "Don't check compatibility with current configuration";
         type empty;
       }
     }
     output {
       choice output_c {
         case output-tag {
           leaf output {
             type string;
           }
         }
         case multichassis-tag {
           anyxml multi-routing-engine-results;
         }
       }
     }
   }
   rpc request-package-delete {
     description "Remove extension or upgrade package";
     input {
       leaf archived {
         description "Removing of all archived software versions except current and rollback";
         type empty;
       }
       leaf force {
         description "Force removal of package (ignore warnings)";
         type empty;
       }
       leaf virtual-machine-package {
         description "Remove virtual-machine package";
         type empty;
       }
       leaf package-name {
         description "Name of package";
         type string;
       }
       leaf all-third-party-packages {
         description "Delete all third party packages";
         type empty;
       }
       leaf reboot {
         description "Reboot system after package delete";
         type empty;
       }
       choice re-choice {
         case re0 {
           leaf re0 {
             description "Delete package on RE0";
             type empty;
           }
         }
         case re1 {
           leaf re1 {
             description "Delete package on RE1";
             type empty;
           }
         }
       }
       choice chassis {
         case scc {
           leaf scc {
             description "Delete package on SCC";
             type empty;
           }
         }
         case lcc {
           leaf lcc {
             description "Delete package on an LCC";
             type union {
               type string {
                 pattern "<.*>|$.*";
               }
               type uint32 {
                 range "0 .. 3";
               }
             }
           }
         }
         case sfc {
           leaf sfc {
             description "Delete package on SFC";
             type empty;
           }
         }
         case member {
           leaf member {
             description "Delete package on VC Member";
             type union {
               type string {
                 pattern "<.*>|$.*";
               }
               type uint32;
             }
           }
         }
         case dont-forward {
           leaf dont-forward {
             type empty;
           }
         }
       }
     }
     output {
       choice output_c {
         case output-tag {
           leaf output {
             type string;
           }
         }
         case multichassis-tag {
           anyxml multi-routing-engine-results;
         }
       }
     }
   }
   rpc request-package-rollback {
     description "Attempt to roll back to previous set of packages";
     input {
       uses command-forwarding;
       leaf reboot {
         description "Reboot system after rollback";
         type empty;
       }
       choice satellite-arg {
         case upgrade-group {
           leaf upgrade-group {
             description "Satellite upgrade group name";
             type string;
           }
         }
         case satellite {
           leaf satellite {
             description "FPC slot of satellite system";
             type union {
               type int32;
               type string {
                 pattern "<.*>|$.*";
               }
             }
           }
         }
         case device-alias {
           leaf device-alias {
             description "Device alias of satellite system";
             type string;
           }
         }
       }
       leaf no-validate {
         description "Don't check compatibility with current configuration";
         type empty;
       }
       leaf package-name {
         description "Name of package version to rollback";
         type string;
       }
       leaf with-old-snapshot-config {
         description "Rollback to given version with old snapshot config";
         type empty;
       }
     }
     output {
       choice output_c {
         case output-tag {
           leaf output {
             type string;
           }
         }
         case multichassis-tag {
           anyxml multi-routing-engine-results;
         }
       }
     }
   }
   rpc request-package-validate {
     description "Verify package compatibility with current configuration";
     input {
       leaf-list upgrade-with-config {
         ordered-by user;
         description "Additional configs ('text/xml' format) to be validated";
         type jt:filename;
       }
       choice package-options {
         case set {
           leaf-list set {
             ordered-by user;
             description "List of URLs or pathnames corresponding to packages";
             type jt:filename;
           }
         }
         case package-name {
           leaf package-name {
             description "URL or pathname of package";
             type jt:filename;
           }
         }
       }
       choice chassis {
         case scc {
           leaf scc {
             description "Validate package on SCC";
             type empty;
           }
         }
         case lcc {
           leaf lcc {
             description "Validate package on an LCC";
             type union {
               type string {
                 pattern "<.*>|$.*";
               }
               type uint32;
             }
           }
         }
         case sfc {
           leaf sfc {
             description "Validate package on SFC";
             type empty;
           }
         }
         case member {
           leaf member {
             description "Validate package on member";
             type union {
               type string {
                 pattern "<.*>|$.*";
               }
               type uint32;
             }
           }
         }
         case dont-forward {
           leaf dont-forward {
             type empty;
           }
         }
       }
     }
     output {
       choice output_c {
         case output-tag {
           leaf output {
             type string;
           }
         }
         case multichassis-tag {
           anyxml multi-routing-engine-results;
         }
       }
     }
   }
   rpc check-in-service-upgrade {
     description "Check in-service software upgrade";
     input {
       choice package-options {
         case set {
           leaf-list set {
             ordered-by user;
             description "List of URLs or pathnames corresponding to packages for ISSU";
             type jt:filename;
           }
         }
         case package-name {
           leaf package-name {
             description "URL or pathname of package";
             type jt:filename;
           }
         }
       }
       leaf enhanced-mode {
         description "Try to upgrade without any traffic loss";
         type empty;
       }
     }
     output {
       choice output_c {
         case output-tag {
           leaf output {
             type string;
           }
         }
         case multichassis-tag {
           anyxml multi-routing-engine-results;
         }
       }
     }
   }
   rpc request-package-delete-backup {
     description "Delete old system software packages";
     status deprecated;
     output {
       choice output_c {
         case output-tag {
           leaf output {
             type string;
           }
         }
         case multichassis-tag {
           anyxml multi-routing-engine-results;
         }
       }
     }
   }
   rpc request-system-software-sync {
     description "Sync software from master RE node to other RE node";
     input {
       choice version_choice {
         case current {
           leaf current {
             description "Sync current sw version to other RE and reboot if current mismatch";
             type empty;
           }
         }
         case rollback {
           leaf rollback {
             description "Sync rollback sw version to other RE";
             type empty;
           }
         }
         case all-versions {
           leaf all-versions {
             description "Sync all sw versions to other RE and reboot if current mismatch";
             type empty;
           }
         }
       }
     }
     output {
       choice output_c {
         case output-tag {
           leaf output {
             type string;
           }
         }
         case multichassis-tag {
           anyxml multi-routing-engine-results;
         }
       }
     }
   }
   rpc request-system-software-validate-restart {
     description "Verify new package with current config and get ISSU impact";
     input {
       leaf package-name {
         description "URL or pathname of package";
         type jt:filename;
       }
     }
     output {
       choice output_c {
         case output-tag {
           leaf output {
             type string;
           }
         }
         case multichassis-tag {
           anyxml multi-routing-engine-results;
         }
       }
     }
   }
   rpc request-license-add {
     description "Add license keys from file, local or from server";
     input {
       leaf filename {
         description "Filename (URL, local, remote, or floppy)";
         type string;
       }
       leaf key-data {
         description "License key data";
         type string;
       }
     }
     output {
       container add-license-results {
         uses add-license-results-block;
       }
     }
   }
   rpc request-license-delete {
     description "Delete license keys";
     input {
       choice delete-choice {
         case all {
           leaf all {
             description "Delete all license keys";
             type empty;
           }
         }
         case license-identifier {
           leaf license-identifier {
             description "Identifier of installed license key";
             type string;
           }
         }
         case license-identifier-list {
           leaf-list license-identifier-list {
             ordered-by user;
             description "Identifier of installed license key";
             type string;
           }
         }
       }
     }
     output {
       choice output_c {
         case output-tag {
           leaf output {
             type string;
           }
         }
         case multichassis-tag {
           anyxml multi-routing-engine-results;
         }
       }
     }
   }
   rpc request-license-save {
     description "Save license keys to file, local or to server";
     input {
       leaf filename {
         description "Filename (URL, local, remote, or floppy)";
         type string;
         mandatory true;
       }
     }
     output {
       choice output_c {
         case output-tag {
           leaf output {
             type string;
           }
         }
         case multichassis-tag {
           anyxml multi-routing-engine-results;
         }
       }
     }
   }
   rpc request-license-update {
     description "Start autoupdate license keys from LMS servers";
     input {
       leaf trial {
         description "Start autoupdate trial license keys from LMS servers";
         type empty;
       }
     }
     output {
       container inform {
         uses inform-block;
       }
     }
   }
   rpc license-revoke-licenses {
     description "Revoke licenses in the Authorization key";
     status deprecated;
     input {
       leaf filename {
         description "Filename (URL, local, remote, or floppy)";
         type string;
         mandatory true;
       }
     }
     output {
       choice output_c {
         case output-tag {
           leaf output {
             type string;
           }
         }
         case multichassis-tag {
           anyxml multi-routing-engine-results;
         }
       }
     }
   }
   rpc enable-unified-services-chassis-mode {
     description "Enable unified services chassis mode";
     output {
       choice output_c {
         case output-tag {
           leaf output {
             type string;
           }
         }
         case multichassis-tag {
           anyxml multi-routing-engine-results;
         }
       }
     }
   }
   rpc disable-unified-services-chassis-mode {
     description "Disable unified services chassis mode";
     output {
       choice output_c {
         case output-tag {
           leaf output {
             type string;
           }
         }
         case multichassis-tag {
           anyxml multi-routing-engine-results;
         }
       }
     }
   }
   rpc fips-selftest {
     description "Execute FIPS known answer tests (KATs)";
     output {
       choice output_c {
         case output-tag {
           leaf output {
             type string;
           }
         }
         case multichassis-tag {
           anyxml multi-routing-engine-results;
         }
       }
     }
   }
   rpc request-system-erase {
     description "Secure erase SATA drives";
   }
   rpc request-personality-file-generate {
     description "Generate the personality-file tarball for the device";
     input {
       leaf personality-file-create {
         description "Url containing the remote server alongwith the name of the tarball";
         type string;
         mandatory true;
       }
     }
     output {
       choice output_c {
         case output-tag {
           leaf output {
             type string;
           }
         }
         case multichassis-tag {
           anyxml multi-routing-engine-results;
         }
       }
     }
   }
   rpc request-personality-file-retrieve {
     description "Retrieve the personality-file tarball of the device";
     input {
       leaf personality-file-retrieve {
         description "Url containing the remote server alongwith the name of the tarball";
         type string;
         mandatory true;
       }
       leaf retrieve-location {
         description "Path on the local device where the personality-file will be retrieved";
         type string;
         mandatory true;
       }
     }
     output {
       choice output_c {
         case output-tag {
           leaf output {
             type string;
           }
         }
         case multichassis-tag {
           anyxml multi-routing-engine-results;
         }
       }
     }
   }
   rpc transfer-control {
     description "Control transfers of core and log files";
     input {
       leaf operation {
         description "Transfer control operation";
         type enumeration {
           enum "abort" {
             description "Abort a transfer";
           }
           enum "pause" {
             description "Pause a transfer";
           }
           enum "restart" {
             description "Restart a transfer";
           }
         }
         mandatory true;
       }
       choice arg-type {
         case component {
         }
         case transfer-id {
           leaf transfer-id {
             description "Transfer identifier";
             type union {
               type int32;
               type string {
                 pattern "<.*>|$.*";
               }
             }
           }
         }
       }
     }
   }
   rpc request-log {
     description "Create an archive of all system logs";
   }
   rpc request-system-storage-cleanup {
     description "Clean up temporary files and rotate logs";
     input {
       leaf force-deep {
         description "Deep clean all temporary files and rotate logs";
         type empty;
       }
       leaf dry-run {
         description "Only list the cleanup candidates, do not remove them";
         type empty;
       }
       leaf no-confirm {
         description "Do not ask for confirmation";
         type empty;
       }
     }
     output {
       container system-storage-cleanup-information {
         uses system-storage-cleanup-information-block;
       }
     }
   }
   rpc request-system-storage-expand-user {
     description "Manage size of user disk";
     input {
       leaf operation {
         description "Expand user disk or revert to default";
         type enumeration {
           enum "expand" {
             description "Expand user disk to maximum available size";
           }
           enum "restore" {
             description "Restore user disk to default setting";
           }
         }
         mandatory true;
       }
     }
     output {
       choice output_c {
         case output-tag {
           leaf output {
             type string;
           }
         }
         case multichassis-tag {
           anyxml multi-routing-engine-results;
         }
       }
     }
   }
   rpc request-boot-media {
     description "Setup permanent boot media for subsequent reboots";
     input {
       leaf media {
         description "Media to be setup as boot device";
         type enumeration {
           enum "primary" {
             description "Boot from primary Junos partition";
           }
           enum "alternate" {
             description "Boot from alternate Junos partition";
           }
           enum "external" {
             description "Boot from external USB device";
           }
         }
         mandatory true;
       }
     }
   }
   rpc diag-mode {
     description "Switch to diag mode";
     output {
       choice output_c {
         case output-tag {
           leaf output {
             type string;
           }
         }
         case multichassis-tag {
           anyxml multi-routing-engine-results;
         }
       }
     }
   }
   rpc request-boot-console {
     description "Switch boot-console port";
     input {
       uses command-forwarding;
       leaf port {
         description "Choice of port";
         type enumeration {
           enum "console" {
             description "Set Console port as boot console";
           }
           enum "auxiliary" {
             description "Set Auxiliary port as boot console";
           }
         }
         mandatory true;
       }
     }
     output {
       choice output_c {
         case output-tag {
           leaf output {
             type string;
           }
         }
         case multichassis-tag {
           anyxml multi-routing-engine-results;
         }
       }
     }
   }
   rpc request-system-reboot {
     description "Reboot the system";
     input {
       uses command-forwarding;
       leaf hypervisor {
         description "Reboot both Junos and Hypervisor";
         type empty;
       }
       leaf fast-boot {
         description "Enable fast reboot";
         status deprecated;
         type empty;
       }
       choice time-arg-choice {
         case at {
           leaf at {
             description "Time at which to perform the operation in hh:mm 24 hrs format";
             default "now";
             type string;
           }
         }
         case in {
           leaf in {
             description "Number of minutes to delay before operation";
             default "now";
             type string;
           }
         }
       }
       leaf message {
         description "Message to display to all users";
         type string {
         }
       }
       leaf power-off {
         description "Power-off the software on RE";
         type enumeration {
           enum "fpc" {
             description "Power off FPCs";
           }
         }
       }
       leaf slice {
         description "Partition on boot media to boot from";
         type enumeration {
           enum "alternate" {
             description "Boot from alternate partition";
           }
           enum "1" {
             description "Boot from first partition";
           }
           enum "2" {
             description "Boot from second partition";
           }
         }
       }
     }
     output {
       choice output_c {
         case output-tag {
           leaf output {
             type string;
           }
         }
         case multichassis-tag {
           anyxml multi-routing-engine-results;
         }
       }
     }
   }
   rpc request-reboot-in-service {
     description "Reboot with minimal traffic disruption";
     output {
       choice output_c {
         case output-tag {
           leaf output {
             type string;
           }
         }
         case multichassis-tag {
           anyxml multi-routing-engine-results;
         }
       }
     }
   }
   rpc request-system-halt {
     description "Halt the system";
     input {
       uses command-forwarding;
       choice time-arg-choice {
         case at {
           leaf at {
             description "Time at which to perform the operation in hh:mm 24 hrs format";
             default "now";
             type string;
           }
         }
         case in {
           leaf in {
             description "Number of minutes to delay before operation";
             default "now";
             type string;
           }
         }
       }
       leaf message {
         description "Message to display to all users";
         type string {
         }
       }
       leaf power-off {
         description "Power-off the software on RE";
         type enumeration {
           enum "fpc" {
             description "Power off FPCs";
           }
         }
       }
       leaf slice {
         description "Partition on boot media to boot from";
         type enumeration {
           enum "alternate" {
             description "Boot from alternate partition";
           }
           enum "1" {
             description "Boot from first partition";
           }
           enum "2" {
             description "Boot from second partition";
           }
         }
       }
     }
     output {
       choice output_c {
         case output-tag {
           leaf output {
             type string;
           }
         }
         case multichassis-tag {
           anyxml multi-routing-engine-results;
         }
       }
     }
   }
   rpc request-system-power-off {
     description "Power off the system";
     input {
       uses command-forwarding;
       choice time-arg-choice {
         case at {
           leaf at {
             description "Time at which to perform the operation in hh:mm 24 hrs format";
             default "now";
             type string;
           }
         }
         case in {
           leaf in {
             description "Number of minutes to delay before operation";
             default "now";
             type string;
           }
         }
       }
       leaf message {
         description "Message to display to all users";
         type string {
         }
       }
       leaf power-off {
         description "Power-off the software on RE";
         type enumeration {
           enum "fpc" {
             description "Power off FPCs";
           }
         }
       }
       leaf slice {
         description "Partition on boot media to boot from";
         type enumeration {
           enum "alternate" {
             description "Boot from alternate partition";
           }
           enum "1" {
             description "Boot from first partition";
           }
           enum "2" {
             description "Boot from second partition";
           }
         }
       }
     }
     output {
       choice output_c {
         case output-tag {
           leaf output {
             type string;
           }
         }
         case multichassis-tag {
           anyxml multi-routing-engine-results;
         }
       }
     }
   }
   rpc request-process-terminate {
     description "Terminate the process";
     input {
       leaf process-id {
         description "Process ID";
         type union {
           type string {
             pattern "<.*>|$.*";
           }
           type uint32 {
             range "1 .. 99999";
           }
         }
         mandatory true;
       }
     }
     output {
       choice output_c {
         case output-tag {
           leaf output {
             type string;
           }
         }
         case multichassis-tag {
           anyxml multi-routing-engine-results;
         }
       }
     }
   }
   rpc request-system-zeroize {
     description "Erase all data, including configuration and log files";
     input {
       uses command-forwarding;
       leaf ztp-option {
         description "Zeroize with ztp-mode options";
         type enumeration {
           enum "secure-enable" {
             description "Secure Enable";
           }
           enum "secure-disable" {
             description "Secure Disable";
           }
         }
       }
       leaf retain-certificates {
         description "Keep certificates after zeroizing";
         type empty;
       }
       leaf media {
         type enumeration {
           enum "disk1" {
             description "Zeroize only disk1";
           }
           enum "disk2" {
             description "Zeroize only disk2";
           }
         }
       }
     }
     output {
       leaf system-zeroize-status {
         type string;
         description "Status of zeroize operation";
       }
     }
   }
   rpc request-snapshot {
     description "Create a normal Junos or a recovery snapshot";
     input {
       uses command-forwarding;
       leaf snapshot-name {
         description "Snapshot name";
         type string;
       }
       leaf configuration {
         default "configuration";
         type enumeration {
           enum "configuration" {
             description "Store device configuration in snapshot";
           }
           enum "no-configuration" {
             description "Do not store device configuration in snapshot";
           }
         }
       }
       leaf force {
         description "Force snapshot operation";
         type empty;
       }
       leaf recovery {
         description "Create a recovery snapshot";
         type empty;
       }
       leaf delete {
         description "Delete an existing snapshot";
         type string;
       }
       leaf load {
         description "Load a given snapshot and activate it upon reboot";
         type string;
       }
       leaf partition {
         description "Partition the media";
         type empty;
       }
       leaf as-primary {
         description "Setup snapshot to be used in the primary boot device";
         type empty;
       }
       leaf swap-size {
         description "Size of the swap partition";
         type string;
       }
       leaf config-size {
         description "Size of the config partition";
         type string;
       }
       leaf root-size {
         description "Size of the root partition";
         type string;
       }
       leaf data-size {
         description "Size of the data partition";
         type string;
       }
       leaf slice {
         description "Write snapshot to specified partition";
         status deprecated;
         type enumeration {
           enum "alternate" {
             description "Write snapshot to alternate partition";
             status deprecated;
           }
         }
       }
       leaf media {
         description "Media to snapshot to";
         default "compact-flash";
         type enumeration {
           enum "removable-compact-flash" {
             description "Write snapshot to removable compact flash";
           }
           enum "compact-flash" {
             description "Write snapshot to compact flash";
           }
           enum "usb" {
             description "Write snapshot to device connected to USB port";
           }
           enum "usb0" {
             description "Write snapshot to device connected to USB0 port";
           }
           enum "usb1" {
             description "Write snapshot to device connected to USB1 port";
           }
           enum "hard-disk" {
             description "Write snapshot to hard disk";
           }
           enum "internal" {
             description "Write snapshot to internal flash";
           }
           enum "external" {
             description "Write snapshot to external storage device";
           }
         }
       }
     }
     output {
       container snapshot-information {
         uses snapshot-information-block;
       }
     }
   }
   rpc request-system-firmware-reload-fpc {
     description "Reload FPC ROM monitor";
     input {
       leaf slot {
         description "FPC slot number";
         type union {
           type string {
             pattern "<.*>|$.*";
           }
           type uint32;
         }
         mandatory true;
       }
       choice which-arg {
         case wanio-fpga {
           leaf wanio-fpga {
             description "Reload wanio-fpga firmware";
             type empty;
           }
         }
         case i2cs-fpga {
           leaf i2cs-fpga {
             description "Reload i2cs-fpga firmware";
             type empty;
           }
         }
         case boot-cpld {
           leaf boot-cpld {
             description "Reload boot-cpld firmware";
             type empty;
           }
         }
       }
     }
     output {
       container system-firmware-information {
         uses system-firmware-information-block;
       }
     }
   }
   rpc request-system-firmware-reload-sib {
     description "Reload SIB firmware";
     input {
       leaf slot {
         description "SIB slot number";
         type union {
           type string {
             pattern "<.*>|$.*";
           }
           type uint32;
         }
         mandatory true;
       }
     }
     output {
       container system-firmware-information {
         uses system-firmware-information-block;
       }
     }
   }
   rpc request-jfw-cpld-upgrade {
     description "Upgrade CPLD firmware";
     input {
       leaf cpld-type {
         description "CPLD type: RE, MAIN, FAN";
         type string;
       }
     }
     output {
       choice output_c {
         case output-tag {
           leaf output {
             type string;
           }
         }
         case multichassis-tag {
           anyxml multi-routing-engine-results;
         }
       }
     }
   }
   rpc request-jfw-cpld-mainboard-upgrade {
     description "Upgrade mainboard CPLD firmware";
   }
   rpc request-jfw-main-board-upgrade-status {
     description "Show MAIN board upgrade status";
   }
   rpc request-jfw-cpld-fanboard-upgrade {
     description "Upgrade fanboard CPLD firmware";
   }
   rpc request-jfw-cpld-fanboard-upgrade-status {
     description "Show fanboard CPLD upgrade status";
   }
   rpc request-jfw-cpld-sys-upgrade {
     description "Upgrade Sys CPLD firmware";
   }
   rpc request-jfw-sys-cpld-upgrade-status {
     description "Show Sys cpld upgrade status";
   }
   rpc request-jfw-cpld-cpuboard-upgrade {
     description "Upgrade CPU board CPLD firmware";
   }
   rpc request-jfw-cpu-cpld-upgrade-status {
     description "Show CPU cpld upgrade status";
   }
   rpc request-jfw-eusb-upgrade {
     description "Upgrade eusb firmware";
   }
   rpc request-jfw-eusb-upgrade-status {
     description "Show eusb upgrade status";
   }
   rpc request-jfw-uboot-upgrade {
     description "Upgrade uboot binary";
   }
   rpc request-jfw-uboot-upgrade-status {
     description "Show uboot upgrade status";
   }
   rpc request-jfw-nic-i350-upgrade {
     description "Upgrade Builtin i350 NIC firmware";
     output {
       choice output_c {
         case output-tag {
           leaf output {
             type string;
           }
         }
         case multichassis-tag {
           anyxml multi-routing-engine-results;
         }
       }
     }
   }
   rpc request-jfirmware-nic-i210-upgrade {
     description "Upgrade Builtin i210 NIC firmware";
     output {
       choice output_c {
         case output-tag {
           leaf output {
             type string;
           }
         }
         case multichassis-tag {
           anyxml multi-routing-engine-results;
         }
       }
     }
   }
   rpc request-jfw-nic-x552-upgrade {
     description "Upgrade Builtin x552 NIC firmware";
   }
   rpc request-jfw-nic-x722-upgrade {
     description "Upgrade Builtin x722 NIC firmware";
   }
   rpc request-jfw-nic-x722-upgrade-status {
     description "Show NIC upgrade status";
   }
   rpc request-jfw-nic-x553-upgrade {
     description "Upgrade Builtin x553 NIC firmware";
   }
   rpc request-jfw-nic-i82599-1-upgrade {
     description "Upgrade Builtin i82599_1 NIC firmware";
   }
   rpc request-jfw-nic-i82599-2-upgrade {
     description "Upgrade Builtin i82599_2 NIC firmware";
   }
   rpc request-jfw-em-i350-copper-upgrade {
     description "Upgrade Expansion Module i350 NIC Copper firmware";
   }
   rpc request-jfw-em-i350-sfp-upgrade {
     description "Upgrade Expansion Module i350 NIC SFP firmware";
   }
   rpc request-jfw-bios-upgrade {
     description "Upgrade BIOS firmware";
     input {
       leaf disk {
         description "1, 2";
         type string;
       }
     }
     output {
       choice output_c {
         case output-tag {
           leaf output {
             type string;
           }
         }
         case multichassis-tag {
           anyxml multi-routing-engine-results;
         }
       }
     }
   }
   rpc request-jfw-bios-upgrade-status {
     description "Show BIOS upgrade status";
   }
   rpc request-jfw-psu-upgrade {
     description "Upgrade psu firmware";
     output {
       choice output_c {
         case output-tag {
           leaf output {
             type string;
           }
         }
         case multichassis-tag {
           anyxml multi-routing-engine-results;
         }
       }
     }
   }
   rpc request-jfw-psu-upgrade-status {
     description "Show PSU upgrade status";
   }
   rpc request-jfirmware-hv-psu-upgrade {
     description "Upgrade HV PSU firmware";
     output {
       choice output_c {
         case output-tag {
           leaf output {
             type string;
           }
         }
         case multichassis-tag {
           anyxml multi-routing-engine-results;
         }
       }
     }
   }
   rpc request-jfirmware-hv-psu-upgrade-status {
     description "Show HV PSU upgrade status";
     output {
       choice output_c {
         case output-tag {
           leaf output {
             type string;
           }
         }
         case multichassis-tag {
           anyxml multi-routing-engine-results;
         }
       }
     }
   }
   rpc request-jfw-ssd-upgrade {
     description "Upgrade SSD firmware";
     input {
       leaf disk {
         description "1, 2";
         type string;
       }
     }
     output {
       choice output_c {
         case output-tag {
           leaf output {
             type string;
           }
         }
         case multichassis-tag {
           anyxml multi-routing-engine-results;
         }
       }
     }
   }
   rpc get-jfw-tpm-upgrade {
     description "Upgrade TPM firmware";
     output {
       choice output_c {
         case output-tag {
           leaf output {
             type string;
           }
         }
         case multichassis-tag {
           anyxml multi-routing-engine-results;
         }
       }
     }
   }
   rpc request-jfw-poe-upgrade {
     description "Upgrade POE firmware";
     input {
       uses command-forwarding;
       leaf fpc-slot {
         description "FPC slot";
         type string;
         mandatory true;
       }
       leaf poe-firmware-type {
         description "POE_FIRMWARE_TYPE";
         type enumeration {
           enum "poe-at-firmware" {
             description "IEEE 802.3at PoE Firmware Support";
           }
           enum "poe-bt-firmware" {
             description "IEEE 802.3bt PoE Firmware Support";
           }
         }
       }
     }
     output {
       choice output_c {
         case output-tag {
           leaf output {
             type string;
           }
         }
         case multichassis-tag {
           anyxml multi-routing-engine-results;
         }
       }
     }
   }
   rpc request-jfw-bcm-pcie-upgrade {
     description "Upgrade BCM PCIe firmware";
     output {
       choice output_c {
         case output-tag {
           leaf output {
             type string;
           }
         }
         case multichassis-tag {
           anyxml multi-routing-engine-results;
         }
       }
     }
   }
   rpc request-jfirmware-pmic-upgrade {
     description "Upgrade PMIC firmware";
     output {
       choice output_c {
         case output-tag {
           leaf output {
             type string;
           }
         }
         case multichassis-tag {
           anyxml multi-routing-engine-results;
         }
       }
     }
   }
   rpc request-jfw-pmic-fpga-upgrade-status {
     description "Show PMIC Upgrade status";
     output {
       choice output_c {
         case output-tag {
           leaf output {
             type string;
           }
         }
         case multichassis-tag {
           anyxml multi-routing-engine-results;
         }
       }
     }
   }
   rpc request-jfw-re-fpga-upgrade {
     description "Upgrade RE FPGA";
     input {
       leaf file {
         description "Jfirmware package file";
         type string;
       }
     }
   }
   rpc request-jfw-re-fpga-upgrade-status {
     description "Show RE FPGA Upgrade status";
   }
   rpc request-jfw-tmc-fpga-upgrade {
     description "Upgrade Mainboard TMC FPGA";
   }
   rpc request-jfw-tmc-fpga-upgrade-status {
     description "Show TMC Upgrade status";
   }
   rpc request-jfw-power-cpld-upgrade {
     description "Upgrade Power CPLD";
   }
   rpc request-jfw-powercpld-upgrade-status {
     description "Show Powercpld Upgrade status";
   }
   rpc request-jfirmware-fanboard-fpga-upgrade {
     description "Upgrade Fanboard FPGA";
     output {
       choice output_c {
         case output-tag {
           leaf output {
             type string;
           }
         }
         case multichassis-tag {
           anyxml multi-routing-engine-results;
         }
       }
     }
   }
   rpc request-jfirmware-fanboard-fpga-upgrade-status {
     description "Show Fanboard FPGA Upgrade status";
     output {
       choice output_c {
         case output-tag {
           leaf output {
             type string;
           }
         }
         case multichassis-tag {
           anyxml multi-routing-engine-results;
         }
       }
     }
   }
   rpc request-jfw-optics-sfp-upgrade {
     description "Upgrade Optics FPGA/CPLD";
   }
   rpc request-jfw-optics-sfp-upgrade-status {
     description "Show SFP Upgrade status";
   }
   rpc request-jfw-optics-qsfp-upgrade {
     description "Upgrade Optics FPGA/CPLD";
   }
   rpc request-jfw-optics-qsfp-upgrade-status {
     description "Show QSFP Upgrade status";
   }
   rpc request-jfw-bmc-upgrade {
     description "Upgrade BMC firmware";
     input {
       leaf file {
         description "Jfirmware package file";
         type string;
       }
     }
     output {
       choice output_c {
         case output-tag {
           leaf output {
             type string;
           }
         }
         case multichassis-tag {
           anyxml multi-routing-engine-results;
         }
       }
     }
   }
   rpc request-jfw-bmc-upgrade-status {
     description "Show BMC Upgrade status";
     output {
       choice output_c {
         case output-tag {
           leaf output {
             type string;
           }
         }
         case multichassis-tag {
           anyxml multi-routing-engine-results;
         }
       }
     }
   }
   rpc request-jfw-allfw-upgrade {
     description "Upgrade all firmwares applicable in Jfirmware package";
     output {
       choice output_c {
         case output-tag {
           leaf output {
             type string;
           }
         }
         case multichassis-tag {
           anyxml multi-routing-engine-results;
         }
       }
     }
   }
   rpc request-jfw-allfw-upgrade-status {
     description "Show all firmware upgrade status";
   }
   rpc request-fpc-fpga-upgrade {
     description "Upgrade Line Card FPGAs";
     input {
       uses command-forwarding;
       leaf slot {
         description "FPC slot number";
         type union {
           type string {
             pattern "<.*>|$.*";
           }
           type uint32;
         }
       }
     }
   }
   rpc request-pem-firmware-upgrade {
     description "Upgrade CHASSIS PEM FW";
     input {
       leaf slot {
         description "PEM slot number";
         type union {
           type string {
             pattern "<.*>|$.*";
           }
           type uint32;
         }
       }
     }
     output {
       container system-firmware-information {
         uses system-firmware-information-block;
       }
     }
   }
   rpc request-fpc-eth-switch-upgrade {
     description "Upgrade Line Card ETH-SWITCH";
     input {
       leaf slot {
         description "FPC slot number";
         type union {
           type string {
             pattern "<.*>|$.*";
           }
           type uint32;
         }
         mandatory true;
       }
     }
   }
   rpc request-ftc-firmware-upgrade {
     description "Upgrade FTC firmware";
     input {
       leaf slot {
         description "FTC slot number";
         type union {
           type string {
             pattern "<.*>|$.*";
           }
           type uint32;
         }
         mandatory true;
       }
     }
     output {
       container system-firmware-information {
         uses system-firmware-information-block;
       }
     }
   }
   rpc request-ftc-fpga-firmware-upgrade {
     description "Upgrade FTC FPGA firmware";
     input {
       leaf slot {
         description "FAN slot number";
         type union {
           type string {
             pattern "<.*>|$.*";
           }
           type uint32;
         }
         mandatory true;
       }
     }
     output {
       container system-firmware-information {
         uses system-firmware-information-block;
       }
     }
   }
   rpc request-bitscpld-firmware-upgrade {
     description "Upgrade BITSCPLD programmable on SPMC Mezz board";
     output {
       container system-firmware-information {
         uses system-firmware-information-block;
       }
     }
   }
   rpc request-cb-fpga-upgrade {
     description "Upgrade baseboard FPGA";
     input {
       choice which-arg {
         case fpga {
           leaf fpga {
             description "Upgrade baseboard FPGA";
             type empty;
           }
         }
         case port-fpga {
           leaf port-fpga {
             description "Upgrade baseboard PORT FPGA";
             type empty;
           }
         }
         case port {
           leaf port {
             description "Upgrade baseboard port";
             type empty;
           }
         }
         case tic-fpga {
           leaf tic-fpga {
             description "Upgrade TIC FPGA";
             type empty;
           }
         }
         case optics {
           leaf optics {
             description "Upgrade Optics CPLD";
             type enumeration {
               enum "cpld0" {
                 description "Optics CPLD0";
               }
               enum "cpld1" {
                 description "Optics CPLD1";
               }
             }
           }
         }
         case fancpld {
           leaf fancpld {
             description "Upgrade fan board CPLD";
             type empty;
           }
         }
         case pciesw {
           leaf pciesw {
             description "Upgrade CB PCIe SW Firmware";
             type empty;
           }
         }
         case i2cs-fpga {
           leaf i2cs-fpga {
             description "Upgrade CB I2CS FPGA";
             type empty;
           }
         }
         case gnss {
           leaf gnss {
             description "Upgrade GNSS Firmware";
             type empty;
           }
         }
         case idtpll {
           leaf idtpll {
             description "Upgrade IDTPLL Firmware";
             type empty;
           }
         }
         case bits-fpga {
           leaf bits-fpga {
             description "Upgrade BITS FPGA Firmware";
             type empty;
           }
         }
         case cg0 {
           leaf cg0 {
             description "Upgrade Clock Gen Firmware";
             type empty;
           }
         }
       }
       leaf slot {
         description "CB slot number";
         type union {
           type string {
             pattern "<.*>|$.*";
           }
           type uint32;
         }
         mandatory true;
       }
       leaf tag {
         description "Firmware tag";
         type union {
           type string {
             pattern "<.*>|$.*";
           }
           type uint32 {
             range "0 .. 2";
           }
         }
         mandatory true;
       }
     }
     output {
       container system-firmware-information {
         uses system-firmware-information-block;
       }
     }
   }
   rpc request-i2c-fpga-upgrade {
     description "I2C FPGA Upgrade";
   }
   rpc request-system-firmware-upgrade-sfb {
     description "Upgrade SFB firmware";
     input {
       leaf slot {
         description "SFB slot number";
         type union {
           type string {
             pattern "<.*>|$.*";
           }
           type uint32;
         }
         mandatory true;
       }
       leaf tag {
         description "Firmware tag number";
         type union {
           type string {
             pattern "<.*>|$.*";
           }
           type uint32 {
             range "0 .. 1";
           }
         }
         mandatory true;
       }
     }
     output {
       container system-firmware-information {
         uses system-firmware-information-block;
       }
     }
   }
   rpc request-pem-firmware-downgrade {
     description "Upgrade CHASSIS PEM FW";
     input {
       leaf slot {
         description "PEM slot number";
         type union {
           type string {
             pattern "<.*>|$.*";
           }
           type uint32;
         }
       }
     }
     output {
       container system-firmware-information {
         uses system-firmware-information-block;
       }
     }
   }
   rpc request-bitscpld-firmware-downgrade {
     description "Upgrade BITSCPLD programmable on SPMC Mezz board";
     output {
       container system-firmware-information {
         uses system-firmware-information-block;
       }
     }
   }
   rpc request-cb-fpga-downgrade {
     description "Upgrade baseboard FPGA";
     input {
       choice which-arg {
         case fpga {
           leaf fpga {
             description "Upgrade baseboard FPGA";
             type empty;
           }
         }
         case port {
           leaf port {
             description "Upgrade baseboard port";
             type empty;
           }
         }
         case tic-fpga {
           leaf tic-fpga {
             description "Upgrade TIC FPGA";
             type empty;
           }
         }
       }
       leaf slot {
         description "CB slot number";
         type union {
           type string {
             pattern "<.*>|$.*";
           }
           type uint32;
         }
         mandatory true;
       }
       leaf tag {
         description "Firmware tag";
         type union {
           type string {
             pattern "<.*>|$.*";
           }
           type uint32 {
             range "0 .. 2";
           }
         }
         mandatory true;
       }
     }
     output {
       container system-firmware-information {
         uses system-firmware-information-block;
       }
     }
   }
   rpc request-i2c-fpga-downgrade {
     description "I2C FPGA Upgrade";
   }
   rpc request-system-firmware-downgrade-sfb {
     description "Downgrade SFB firmware";
     input {
       leaf slot {
         description "SFB slot number";
         type union {
           type string {
             pattern "<.*>|$.*";
           }
           type uint32;
         }
         mandatory true;
       }
       leaf tag {
         description "Firmware tag number";
         type union {
           type string {
             pattern "<.*>|$.*";
           }
           type uint32 {
             range "0 .. 1";
           }
         }
         mandatory true;
       }
     }
     output {
       container system-firmware-information {
         uses system-firmware-information-block;
       }
     }
   }
   rpc request-power-on-other-re {
     description "Power on the system";
     input {
       uses command-forwarding;
       leaf other-routing-engine {
         description "Power on other Routing Engine";
         type empty;
         mandatory true;
       }
     }
     output {
       choice output_c {
         case output-tag {
           leaf output {
             type string;
           }
         }
         case multichassis-tag {
           anyxml multi-routing-engine-results;
         }
       }
     }
   }
   rpc request-system-debug-info {
     description "Collect debug information of the system";
     input {
       leaf node {
         description "Node name";
         type string;
       }
       leaf mode {
         description "Debug Collector mode";
         type string;
       }
       leaf since {
         description "Log duration. Supported format: yyyy-mm-dd or #d (ex: 2d) or #h (ex: 5h)";
         type string;
       }
       leaf noninteractive {
         description "To skip any user interaction";
         type empty;
       }
       leaf outdir {
         description "Specify the output directory";
         type string;
       }
     }
     output {
       choice output_c {
         case output-tag {
           leaf output {
             type string;
           }
         }
         case multichassis-tag {
           anyxml multi-routing-engine-results;
         }
       }
     }
   }
   rpc set-system-memory-profiling {
     description "Memory profiling for applications";
     input {
       leaf node {
         description "Node name";
         type string;
       }
       leaf application {
         description "Application name";
         type string;
         mandatory true;
       }
       leaf status {
         description "Option enable, disable or dump";
         type enumeration {
           enum "enable" {
             description "Enable memory profiling.";
           }
           enum "disable" {
             description "Disable memory profiling.";
           }
           enum "dump" {
             description "Dump memory profile.";
           }
         }
         mandatory true;
       }
     }
     output {
       container memory-profiling-action {
         uses memory-profiling-action-block;
       }
     }
   }
   rpc request-system-malware-quick-scan {
     description "Scan process files";
     input {
       leaf-list pids {
         ordered-by user;
         description "Processes IDs to scan";
         type union {
           type uint32;
           type string {
             pattern "<.*>|$.*";
           }
         }
       }
       leaf clean-action {
         description "Action to handle suspected malware";
         type enumeration {
           enum "clean" {
             description "Kill processes and delete files";
           }
           enum "warn" {
             description "Do not kill process or delete file";
           }
         }
       }
       leaf test {
         description "Scan for example test malware";
         status deprecated;
         type empty;
       }
     }
     output {
       container jmrt-scan-result {
         uses jmrt-scan-result-block;
       }
     }
   }
   rpc request-system-malware-veriexec-check {
     description "Check whether Verified Exec is running";
     status deprecated;
     output {
       container jmrt-veriexec-check {
         uses jmrt-veriexec-check-block;
       }
     }
   }
   rpc request-system-malware-integrity-check {
     description "Check whether integrity mechanism is running";
     output {
       container jmrt-integrity-check {
         uses jmrt-integrity-check-block;
       }
     }
   }
   rpc request-system-malware-fake-malware {
     description "Run example malware";
     output {
       container jmrt-fake-malware {
         uses jmrt-fake-malware-block;
       }
     }
   }
   rpc request-system-malware-list-fake-malware {
     description "List running example malware processes";
     output {
       container jmrt-list-fake-malware {
         uses jmrt-list-fake-malware-block;
       }
     }
   }
   rpc get-ethernet-switching-status-evpn-vlan {
     description "Show vlans status";
     input {
       leaf no-confirm {
         description "Do not ask for confirmation";
         type empty;
       }
       leaf instance {
         description "Routing instance";
         type string;
       }
       leaf vlan {
         description "VLAN name";
         type string;
       }
       leaf verbosity {
         type enumeration {
           enum "detail" {
             description "Display detailed output";
           }
         }
       }
       leaf module {
         description "Module name";
         type enumeration {
           enum "mac-table" {
             description "MAC module";
           }
           enum "mac-ip-table" {
             description "MAC IP module";
           }
         }
       }
     }
     output {
       container system-evpn {
         uses system-evpn-block;
       }
     }
   }
   rpc get-ethernet-switching-status-hash-vlan {
     description "Show vlans status";
     input {
       leaf no-confirm {
         description "Do not ask for confirmation";
         type empty;
       }
       leaf instance {
         description "Routing instance";
         type string;
       }
       leaf vlan {
         description "VLAN name";
         type string;
       }
     }
     output {
       container system-evpn {
         uses system-evpn-block;
       }
     }
   }
   rpc request-system-power-cycle {
     description "Power cycle the system";
     input {
       choice which-arg {
         case at {
           leaf at {
             description "Time at which to perform the operation in hh:mm 24 hrs format";
             default "now";
             type string;
           }
         }
         case in {
           leaf in {
             description "Number of minutes to delay before operation";
             default "now";
             type string;
           }
         }
       }
       leaf message {
         description "Message to display to all users";
         type string {
         }
       }
     }
     output {
       choice output_c {
         case output-tag {
           leaf output {
             type string;
           }
         }
         case multichassis-tag {
           anyxml multi-routing-engine-results;
         }
       }
     }
   }
   rpc request-shutdown-reboot {
     description "Reboot the system";
     status deprecated;
     input {
       leaf at {
         description "Time at which to perform the operation in hh:mm 24 hrs format";
         default "now";
         type string;
       }
       leaf in {
         description "Number of minutes to delay before operation";
         default "now";
         type string;
       }
       leaf message {
         description "Message to display to all users";
         type string;
       }
       leaf media {
         type enumeration {
           enum "disk1" {
             description "Boot off disk1(primary) device";
           }
           enum "disk2" {
             description "Boot off disk2(backup) device";
           }
           enum "network1" {
             description "Network boot via PXE over port1";
           }
           enum "network2" {
             description "Network boot via PXE over port2";
           }
           enum "usb" {
             description "Boot off USB device";
           }
         }
       }
     }
     output {
       choice output_c {
         case output-tag {
           leaf output {
             type string;
           }
         }
         case multichassis-tag {
           anyxml multi-routing-engine-results;
         }
       }
     }
   }
   rpc request-shutdown-halt {
     description "Halt the system";
     status deprecated;
     input {
       leaf at {
         description "Time at which to perform the operation in hh:mm 24 hrs format";
         default "now";
         type string;
       }
       leaf in {
         description "Number of minutes to delay before operation";
         default "now";
         type string;
       }
       leaf message {
         description "Message to display to all users";
         type string;
       }
       leaf media {
         type enumeration {
           enum "disk1" {
             description "Boot off disk1(primary) device";
           }
           enum "disk2" {
             description "Boot off disk2(backup) device";
           }
           enum "network1" {
             description "Network boot via PXE over port1";
           }
           enum "network2" {
             description "Network boot via PXE over port2";
           }
           enum "usb" {
             description "Boot off USB device";
           }
         }
       }
     }
     output {
       choice output_c {
         case output-tag {
           leaf output {
             type string;
           }
         }
         case multichassis-tag {
           anyxml multi-routing-engine-results;
         }
       }
     }
   }
   rpc request-shutdown-power-off {
     description "Power off the system";
     status deprecated;
     input {
       leaf at {
         description "Time at which to perform the operation in hh:mm 24 hrs format";
         default "now";
         type string;
       }
       leaf in {
         description "Number of minutes to delay before operation";
         default "now";
         type string;
       }
       leaf message {
         description "Message to display to all users";
         type string;
       }
       leaf media {
         type enumeration {
           enum "disk1" {
             description "Boot off disk1(primary) device";
           }
           enum "disk2" {
             description "Boot off disk2(backup) device";
           }
           enum "network1" {
             description "Network boot via PXE over port1";
           }
           enum "network2" {
             description "Network boot via PXE over port2";
           }
           enum "usb" {
             description "Boot off USB device";
           }
         }
       }
     }
     output {
       choice output_c {
         case output-tag {
           leaf output {
             type string;
           }
         }
         case multichassis-tag {
           anyxml multi-routing-engine-results;
         }
       }
     }
   }
   rpc request-system-application {
     description "Admin start/stop application";
     input {
       leaf action-type {
         description "Admin start/stop/restart application";
         type enumeration {
           enum "restart" {
             description "Admin restart application";
           }
         }
         mandatory true;
       }
       leaf app {
         description "Application name";
         type string;
         mandatory true;
       }
       leaf node {
         description "Node name";
         type string;
         mandatory true;
       }
     }
     output {
       choice output_c {
         case output-tag {
           leaf output {
             type string;
           }
         }
         case multichassis-tag {
           anyxml multi-routing-engine-results;
         }
       }
     }
   }
   rpc request-security-uefi-revoke {
     description "Revoke platform UEFI keys";
     input {
       leaf cmd {
         type string;
         mandatory true;
       }
     }
     output {
       choice output_c {
         case output-tag {
           leaf output {
             type string;
           }
         }
         case multichassis-tag {
           anyxml multi-routing-engine-results;
         }
       }
     }
   }
   rpc request-security-bios-upgrade {
     description "Upgrade BIOS from the location";
     input {
       leaf package-name {
         description "URL or path name of package";
         type jt:filename;
       }
       leaf re-slot {
         description "RE slot number";
         type union {
           type string {
             pattern "<.*>|$.*";
           }
           type int32;
         }
         mandatory true;
       }
     }
     output {
       choice output_c {
         case output-tag {
           leaf output {
             type string;
           }
         }
         case multichassis-tag {
           anyxml multi-routing-engine-results;
         }
       }
     }
   }
   rpc generate-pki-key-pair {
     description "Generate RSA, DSA or ECDSA private and public key pair";
     input {
       uses command-forwarding;
       choice daemon-select {
         case logical-system {
         }
       }
       choice id-type {
         case certificate-id {
           leaf certificate-id {
             description "Certificate identifier";
             type string {
               length "1 .. 32";
             }
           }
         }
         case acme-key-id {
           leaf acme-key-id {
             description "Acme account key identifier";
             type string {
               length "1 .. 32";
             }
           }
         }
       }
       leaf size {
         description "Size of key";
         default "2048";
         units "bits";
         type enumeration {
           enum "256" {
             description "256 bits (ECDSA only)";
           }
           enum "384" {
             description "384 bits (ECDSA only)";
           }
           enum "521" {
             description "521 bits (ECDSA only)";
           }
           enum "512" {
             description "512 bits (RSA only)";
           }
           enum "1024" {
             description "1024 bits (RSA/DSA only)";
           }
           enum "2048" {
             description "2048 bits (RSA/DSA only)";
           }
           enum "4096" {
             description "4096 bits (RSA/DSA only)";
           }
         }
       }
       leaf type {
         description "Algorithm for encrypting public private keys";
         default "rsa";
         type enumeration {
           enum "rsa" {
             description "RSA encryption";
           }
           enum "dsa" {
             description "DSA encryption";
           }
           enum "ecdsa" {
             description "ECDSA encryption";
           }
         }
       }
     }
     output {
       container cert-key-pair {
         uses cert-key-pair-block;
       }
     }
   }
   rpc generate-pki-certificate-request {
     description "Generate the certificate request in PKCS-10 format";
     input {
       uses command-forwarding;
       leaf ip-address {
         description "Static IP address of the device";
         type jt:ipaddr;
       }
       leaf ipv6-address {
         description "Static IPv6 address of the device for subject-alt-name";
         type jt:ipv6addr;
       }
       choice daemon-select {
         case logical-system {
         }
       }
       leaf filename {
         description "Local location for copy of certificate request";
         type string;
       }
       leaf subject {
         description "DC=<Domain component>,CN=<Common-Name>,OU=<Organizational-Unit-name>,O=<Organization-name>,SN=<Serial-Number>,L=<Locality>,ST=<state>,C=<Country>";
         type string;
         mandatory true;
       }
       leaf digest {
         description "Hash algorithm for signing RSA certificates";
         type enumeration {
           enum "sha-1" {
             description "SHA-1 digests (RSA/DSA only, default value for RSA/DSA)";
           }
           enum "sha-256" {
             description "SHA-256 digests (RSA/ECDSA only, default value for ECDSA)";
           }
           enum "sha-384" {
             description "SHA-384 digests (ECDSA only)";
           }
         }
       }
       leaf validity-start-time {
         description "Certificate validity start time (YYYY-MM-DD.HH:MM:SS)";
         status deprecated;
         type jt:time;
       }
       leaf validity-end-time {
         description "Certificate validity end time (YYYY-MM-DD.HH:MM:SS)";
         status deprecated;
         type jt:time;
       }
       leaf certificate-id {
         description "Certificate identifier";
         type string {
           length "1 .. 32";
         }
         mandatory true;
       }
       leaf domain-name {
         description "Fully qualified domain name";
         type string;
       }
       leaf email {
         description "Email address";
         type string;
       }
     }
     output {
       choice output_c {
         case output-tag {
           leaf output {
             type string;
           }
         }
         case multichassis-tag {
           anyxml multi-routing-engine-results;
         }
       }
     }
   }
   rpc load-pki-ca-certificate {
     description "Load the certificate onto the routing platform";
     input {
       uses command-forwarding;
       leaf ca-profile {
         description "Certificate authority profile";
         type string {
           length "1 .. 32";
         }
         mandatory true;
       }
       choice daemon-select {
         case logical-system {
         }
       }
       leaf filename {
         description "File pathname containing certificate to load";
         type string;
         mandatory true;
       }
     }
     output {
       container cert-ca-load-status {
         uses cert-ca-load-status-block;
       }
     }
   }
   rpc request-security-pki-ca-profile-group {
     description "Perform operations on group of Certificate-authority(CA) certificates";
     input {
       choice daemon-select {
         case logical-system {
           leaf logical-system {
             description "Name of logical system, or 'all'";
             type string {
             }
           }
         }
       }
     }
   }
   rpc request-default-trusted-ca-certs {
     description "Perform actions on default trusted ca certificates";
     input {
       uses command-forwarding;
     }
     output {
       choice output_c {
         case output-tag {
           leaf output {
             type string;
           }
         }
         case multichassis-tag {
           anyxml multi-routing-engine-results;
         }
       }
     }
   }
   rpc request-default-trusted-ca-certs-download {
     description "Download default trusted CA certs from a CDN server";
     input {
       uses command-forwarding;
     }
     output {
       container default-trusted-ca-certs-download {
         uses default-trusted-ca-certs-download-block;
       }
     }
   }
   rpc request-default-trusted-ca-certs-download-cs {
     description "Check connectivity to CDN server to download default trusted CA certs";
     input {
       uses command-forwarding;
     }
     output {
       container default-trusted-ca-certs-download-cs {
         uses default-trusted-ca-certs-download-cs-block;
       }
     }
   }
   rpc request-default-trusted-ca-certs-download-status {
     description "Check current status of default trusted CA certs downloaded from CDN server";
     input {
       uses command-forwarding;
     }
     output {
       container default-trusted-ca-certs-download-status {
         uses default-trusted-ca-certs-download-status-block;
       }
     }
   }
   rpc request-security-pki-ca-profile-group-load {
     description "Load the certificate group onto the routing platform";
     input {
       uses command-forwarding;
       choice daemon-select {
         case logical-system {
         }
       }
       leaf ca-group-name {
         description "CA group identifier";
         type string {
           length "1 .. 24";
         }
         mandatory true;
       }
       leaf filename {
         description "File pathname containing certificate to load";
         type string;
         mandatory true;
       }
     }
   }
   rpc verify-pki-ca-certificate {
     description "Verify the certificate";
     input {
       uses command-forwarding;
       choice daemon-select {
         case logical-system {
         }
       }
       leaf ca-profile {
         description "Certificate authority profile";
         type string {
           length "1 .. 32";
         }
         mandatory true;
       }
     }
     output {
       choice output_c {
         case output-tag {
           leaf output {
             type string;
           }
         }
         case multichassis-tag {
           anyxml multi-routing-engine-results;
         }
       }
     }
   }
   rpc request-security-local-certificate-enroll {
     description "Enroll router certificate with CA online";
     input {
       uses command-forwarding;
       leaf certificate-id {
         description "Certificate identifier";
         status deprecated;
         type string {
           length "1 .. 32";
         }
         mandatory true;
       }
       leaf ca-profile {
         description "Certificate authority profile";
         status deprecated;
         type string {
           length "1 .. 32";
         }
         mandatory true;
       }
       leaf challenge-password {
         description "Password used by CA for enrollment and revocation";
         status deprecated;
         type string;
         mandatory true;
       }
       leaf scep-encryption-algorithm {
         description "Encrypion algorithm used for SCEP-PKCS7";
         status deprecated;
         type enumeration {
           enum "des" {
             description "DES Encryption";
             status deprecated;
           }
           enum "des3" {
             description "DES-3 Encryption (default)";
             status deprecated;
           }
         }
       }
       leaf scep-digest-algorithm {
         description "Hash algorithm used for SCEP-PKCS7";
         status deprecated;
         type enumeration {
           enum "md5" {
             description "MD-5 digest";
             status deprecated;
           }
           enum "sha1" {
             description "SHA-1 digest (default)";
             status deprecated;
           }
         }
       }
       leaf ip-address {
         description "Static IP address of the device";
         status deprecated;
         type jt:ipaddr;
       }
       leaf ipv6-address {
         description "Static IPv6 address of the device for subject-alt-name";
         status deprecated;
         type jt:ipv6addr;
       }
       leaf subject {
         description "DC=<Domain component>,CN=<Common-Name>,OU=<Organizational-Unit-name>,O=<Organization-name>,SN=<Serial-Number>,L=<Locality>,ST=<state>,C=<Country>";
         status deprecated;
         type string;
         mandatory true;
       }
       leaf validity-start-time {
         description "Certificate validity start time (YYYY-MM-DD.HH:MM:SS)";
         status deprecated;
         type jt:time;
       }
       leaf validity-end-time {
         description "Certificate validity end time (YYYY-MM-DD.HH:MM:SS)";
         status deprecated;
         type jt:time;
       }
       leaf digest {
         description "Hash algorithm for signing RSA certificates";
         status deprecated;
         type enumeration {
           enum "sha-1" {
             description "SHA-1 digests (default value)";
             status deprecated;
           }
           enum "sha-256" {
             description "SHA-256 digests";
             status deprecated;
           }
         }
       }
       choice daemon-select {
         case logical-system {
         }
       }
       leaf domain-name {
         description "Fully qualified domain name";
         status deprecated;
         type string;
       }
       leaf email {
         description "Email address";
         status deprecated;
         type string;
       }
     }
   }
   rpc request-security-local-certificate-enroll-cmpv2 {
     description "Enroll certificate using CMPv2 protocol";
     input {
       uses command-forwarding;
       choice daemon-select {
         case logical-system {
         }
       }
       leaf certificate-id {
         description "Certificate identifier";
         type string {
           length "1 .. 32";
         }
         mandatory true;
       }
       leaf ip-address {
         description "Static IP address of the device";
         type jt:ipaddr;
       }
       leaf ipv6-address {
         description "Static IPv6 address of the device for subject-alt-name";
         type jt:ipv6addr;
       }
       leaf domain-name {
         description "Fully qualified domain name for subject-alt-name";
         type string;
       }
       leaf email {
         description "Email address";
         type string;
       }
       leaf subject {
         description "DC=<Domain component>,CN=<Common-Name>,OU=<Organizational-Unit-name>,O=<Organization-name>,SN=<Serial-Number>,L=<Locality>,ST=<state>,C=<Country>";
         type string;
         mandatory true;
       }
       leaf ca-profile {
         description "Certificate authority profile";
         type string {
           length "1 .. 32";
         }
         mandatory true;
       }
       leaf ca-dn {
         description "Subject DN for CMPv2 server, if CA certificate is not enrolled";
         type string;
       }
       leaf ca-secret {
         description "Initial Authentication Key, received from CMPv2 server";
         type string;
         mandatory true;
       }
       leaf ca-reference {
         description "Reference value associated with secret, received from CMPv2 server";
         type string;
         mandatory true;
       }
     }
   }
   rpc request-security-local-certificate-enroll-acme {
     description "Enroll certificate using ACME protocol";
     input {
       uses command-forwarding;
       choice daemon-select {
         case logical-system {
         }
       }
       leaf acme-key-id {
         description "ACME account key identifier";
         type string {
           length "1 .. 32";
         }
         mandatory true;
       }
       leaf certificate-id {
         description "Certificate identifier";
         type string {
           length "1 .. 32";
         }
         mandatory true;
       }
       leaf letsencrypt-enrollment {
         description "Whether the enrollment server is Let's Encrypt or not";
         type enumeration {
           enum "yes" {
             description "Certificate enrollment using Let's Encrypt";
           }
           enum "no" {
             description "Certificate enrollment using other server";
           }
         }
         mandatory true;
       }
       leaf terms-of-service {
         description "Service agreement of Let's Encrypt (https://letsencrypt.org/repository)";
         type enumeration {
           enum "agree" {
             description "Agreed to terms of service";
           }
           enum "disagree" {
             description "Disagree to terms of service";
           }
         }
       }
       leaf domain-names {
         description "Fully qualified domain names for subject-alt-name separated by comma. Maximum limit is 5";
         type string {
         }
         mandatory true;
       }
       leaf email {
         description "Email address";
         type string;
         mandatory true;
       }
       leaf ca-profile {
         description "Certificate authority profile";
         type string {
           length "1 .. 32";
         }
         mandatory true;
       }
     }
   }
   rpc request-security-local-certificate-enroll-scep {
     description "Enroll end-entity certificate using SCEP protocol";
     input {
       uses command-forwarding;
       choice daemon-select {
         case logical-system {
         }
       }
       leaf certificate-id {
         description "Certificate identifier";
         type string {
           length "1 .. 32";
         }
         mandatory true;
       }
       leaf ca-profile {
         description "Certificate authority profile";
         type string {
           length "1 .. 32";
         }
         mandatory true;
       }
       leaf challenge-password {
         description "Password used by CA for enrollment and revocation";
         type string;
         mandatory true;
       }
       leaf scep-encryption-algorithm {
         description "Encrypion algorithm used for SCEP-PKCS7";
         type enumeration {
           enum "des" {
             description "DES Encryption";
           }
           enum "des3" {
             description "DES-3 Encryption (default)";
           }
         }
       }
       leaf scep-digest-algorithm {
         description "Hash algorithm used for SCEP-PKCS7";
         type enumeration {
           enum "md5" {
             description "MD-5 digest";
           }
           enum "sha1" {
             description "SHA-1 digest (default)";
           }
         }
       }
       leaf ip-address {
         description "Static IP address of the device";
         type jt:ipaddr;
       }
       leaf ipv6-address {
         description "Static IPv6 address of the device for subject-alt-name";
         type jt:ipv6addr;
       }
       leaf domain-name {
         description "Fully qualified domain name for subject-alt-name";
         type string;
       }
       leaf email {
         description "Email address";
         type string;
       }
       leaf subject {
         description "DC=<Domain component>,CN=<Common-Name>,OU=<Organizational-Unit-name>,O=<Organization-name>,SN=<Serial-Number>,L=<Locality>,ST=<state>,C=<Country>";
         type string;
         mandatory true;
       }
       leaf validity-start-time {
         description "Certificate validity start time (YYYY-MM-DD.HH:MM:SS)";
         status deprecated;
         type jt:time;
       }
       leaf validity-end-time {
         description "Certificate validity end time (YYYY-MM-DD.HH:MM:SS)";
         status deprecated;
         type jt:time;
       }
       leaf digest {
         description "Hash algorithm for signing RSA certificates";
         type enumeration {
           enum "sha-1" {
             description "SHA-1 digests (default value)";
           }
           enum "sha-256" {
             description "SHA-256 digests";
           }
         }
       }
     }
   }
   rpc request-security-local-certificate-re-enroll {
     description "Re-enroll router certificate with CA online";
     input {
       uses command-forwarding;
     }
   }
   rpc request-security-local-cert-re-enroll-acme {
     description "Enroll certificate using ACME protocol";
     input {
       uses command-forwarding;
       choice daemon-select {
         case logical-system {
         }
       }
       leaf acme-key-id {
         description "ACME account key identifier";
         type string {
           length "1 .. 32";
         }
         mandatory true;
       }
       leaf certificate-id {
         description "Certificate identifier";
         type string {
           length "1 .. 32";
         }
         mandatory true;
       }
       leaf ca-profile {
         description "Certificate authority profile";
         type string {
           length "1 .. 32";
         }
       }
       leaf re-generate-keypair {
         description "Generate new keypair for re-enrollment";
         type empty;
       }
     }
   }
   rpc request-security-local-cert-re-enroll-cmpv2 {
     description "Enroll certificate using CMPv2 protocol";
     input {
       uses command-forwarding;
       choice daemon-select {
         case logical-system {
         }
       }
       leaf certificate-id {
         description "Certificate identifier";
         type string {
           length "1 .. 32";
         }
         mandatory true;
       }
       leaf ca-profile {
         description "Certificate authority profile";
         type string {
           length "1 .. 32";
         }
       }
       leaf re-generate-keypair {
         description "Generate new keypair for re-enrollment";
         type empty;
       }
     }
   }
   rpc request-security-local-cert-re-enroll-scep {
     description "Enroll end-entity certificate using SCEP protocol";
     input {
       uses command-forwarding;
       choice daemon-select {
         case logical-system {
         }
       }
       leaf certificate-id {
         description "Certificate identifier";
         type string {
           length "1 .. 32";
         }
         mandatory true;
       }
       leaf ca-profile {
         description "Certificate authority profile";
         type string {
           length "1 .. 32";
         }
       }
       leaf challenge-password {
         description "Password used by CA for enrollment and revocation";
         type string;
         mandatory true;
       }
       leaf re-generate-keypair {
         description "Generate new keypair for re-enrollment";
         type empty;
       }
       leaf scep-encryption-algorithm {
         description "Encrypion algorithm used for SCEP-PKCS7";
         type enumeration {
           enum "des" {
             description "DES Encryption";
           }
           enum "des3" {
             description "DES-3 Encryption (default)";
           }
         }
       }
       leaf scep-digest-algorithm {
         description "Hash algorithm used for SCEP-PKCS7";
         type enumeration {
           enum "md5" {
             description "MD-5 digest";
           }
           enum "sha1" {
             description "SHA-1 digest (default)";
           }
         }
       }
     }
   }
   rpc request-security-local-certificate-export {
     description "Export Certificate";
     input {
       choice daemon-select {
         case logical-system {
           leaf logical-system {
             description "Name of logical system, or 'all'";
             type string {
             }
           }
         }
       }
       leaf certificate-id {
         description "Certificate identifier";
         type string {
           length "1 .. 32";
         }
         mandatory true;
       }
       leaf filename {
         description "Local location for copy of certificate.";
         type string;
         mandatory true;
       }
       leaf type {
         description "Type of certificate.";
         default "pem";
         type enumeration {
           enum "pem" {
             description "PEM format";
           }
           enum "der" {
             description "DER format";
           }
         }
       }
     }
   }
   rpc load-pki-local-certificate {
     description "Load the certificate onto the routing platform";
     input {
       uses command-forwarding;
       choice daemon-select {
         case logical-system {
         }
       }
       leaf certificate-id {
         description "Certificate identifier";
         type string {
           length "1 .. 32";
         }
         mandatory true;
       }
       leaf filename {
         description "File pathname containing certificate to load";
         type string;
         mandatory true;
       }
       leaf key {
         description "File pathname containing the private key/key-pair to load";
         type string;
       }
       leaf passphrase {
         description "Passphrase of the private key/key-pair (PEM) file";
         type string;
       }
     }
     output {
       container cert-load-status {
         uses cert-load-status-block;
       }
     }
   }
   rpc verify-pki-local-certificate {
     description "Verify the certificate";
     input {
       uses command-forwarding;
       choice daemon-select {
         case logical-system {
         }
       }
       leaf certificate-id {
         description "Certificate identifier";
         type string {
           length "1 .. 32";
         }
         mandatory true;
       }
     }
     output {
       choice output_c {
         case output-tag {
           leaf output {
             type string;
           }
         }
         case multichassis-tag {
           anyxml multi-routing-engine-results;
         }
       }
     }
   }
   rpc generate-pki-self-signed-local-certificate {
     description "Generate a self-signed certificate";
     input {
       uses command-forwarding;
       choice daemon-select {
         case logical-system {
         }
       }
       leaf certificate-id {
         description "Certificate identifier";
         type string {
           length "1 .. 32";
         }
         mandatory true;
       }
       leaf domain-name {
         description "Fully qualified domain name";
         type string;
         mandatory true;
       }
       leaf ip-address {
         description "Static IP address of the device";
         type jt:ipaddr;
       }
       leaf ipv6-address {
         description "Static IPV6 address of the device";
         type jt:ipaddr;
       }
       leaf email {
         description "Email address of the entity owning the certificate";
         type string;
       }
       leaf subject {
         description "DC=<Domain component>,CN=<Common-Name>,OU=<Organizational-Unit-name>,O=<Organization-name>,SN=<Serial-Number>,L=<Locality>,ST=<state>,C=<Country>";
         type string;
         mandatory true;
       }
       leaf add-ca-constraint {
         description "Certificate can be used for signing other certificates.";
         type empty;
       }
       leaf digest {
         description "Hash algorithm for signing RSA certificates";
         type enumeration {
           enum "sha-1" {
             description "SHA-1 digests";
           }
           enum "sha-256" {
             description "SHA-256 digests (default value)";
           }
         }
       }
     }
     output {
       choice output_c {
         case output-tag {
           leaf output {
             type string;
           }
         }
         case multichassis-tag {
           anyxml multi-routing-engine-results;
         }
       }
     }
   }
   rpc request-security-key-pair-export {
     description "Export Keypair in PEM format";
     input {
       choice daemon-select {
         case logical-system {
           leaf logical-system {
             description "Name of logical system, or 'all'";
             type string {
             }
           }
         }
       }
       leaf certificate-id {
         description "Certificate identifier for keypair";
         type string {
           length "1 .. 32";
         }
         mandatory true;
       }
       leaf filename {
         description "Local location for copy of keypair.";
         type string;
         mandatory true;
       }
       leaf type {
         description "Type of key-pair.";
         default "pem";
         type enumeration {
           enum "pem" {
             description "PEM format";
           }
           enum "der" {
             description "DER format";
           }
         }
       }
       leaf passphrase {
         description "Passphrase of the private key/key-pair (PEM) file";
         type string;
         mandatory true;
       }
     }
   }
   rpc load-pki-crl {
     description "Load the CRL onto the routing platform";
     input {
       uses command-forwarding;
       choice daemon-select {
         case logical-system {
         }
       }
       leaf ca-profile {
         description "Certificate authority profile";
         type string {
           length "1 .. 32";
         }
         mandatory true;
       }
       leaf filename {
         description "Pathname of file containing CRL to load";
         type string;
         mandatory true;
       }
     }
     output {
       choice output_c {
         case output-tag {
           leaf output {
             type string;
           }
         }
         case multichassis-tag {
           anyxml multi-routing-engine-results;
         }
       }
     }
   }
   rpc request-security-pki-file-sync {
     description "Perform PKI file-sync with MN-HA remote node";
     input {
       choice daemon-select {
         case logical-system {
           leaf logical-system {
             description "Name of logical system, or 'all'";
             type string {
             }
           }
         }
       }
     }
   }
   rpc node-local-generate-key-pair {
     description "Generate RSA, DSA or ECDSA private and public key pair";
     input {
       uses command-forwarding;
       choice daemon-select {
         case logical-system {
         }
       }
       leaf certificate-id {
         description "Certificate identifier";
         type string {
           length "1 .. 32";
         }
         mandatory true;
       }
       leaf size {
         description "Size of key";
         default "2048";
         units "bits";
         type enumeration {
           enum "256" {
             description "256 bits (ECDSA only)";
           }
           enum "384" {
             description "384 bits (ECDSA only)";
           }
           enum "521" {
             description "521 bits (ECDSA only)";
           }
           enum "512" {
             description "512 bits (RSA only)";
           }
           enum "1024" {
             description "1024 bits (RSA/DSA only)";
           }
           enum "2048" {
             description "2048 bits (RSA/DSA only)";
           }
           enum "4096" {
             description "4096 bits (RSA/DSA only)";
           }
         }
       }
       leaf type {
         description "Algorithm for encrypting public private keys";
         default "rsa";
         type enumeration {
           enum "rsa" {
             description "RSA encryption (Key-Size: 512/1024/2048/4096 bits";
           }
           enum "dsa" {
             description "DSA encryption (Key-Size: 1024/2048/4096 bits)";
           }
           enum "ecdsa" {
             description "ECDSA encryption (Key-Size: 256/384/521 bits)";
           }
         }
       }
     }
     output {
       container cert-key-pair {
         uses cert-key-pair-block;
       }
     }
   }
   rpc node-local-generate-csr {
     description "Generate the certificate request in PKCS-10 format";
     input {
       uses command-forwarding;
       leaf ip-address {
         description "Static IP address of the device";
         type jt:ipaddr;
       }
       leaf ipv6-address {
         description "Static IPv6 address of the device for subject-alt-name";
         type jt:ipv6addr;
       }
       choice daemon-select {
         case logical-system {
         }
       }
       leaf certificate-id {
         description "Certificate identifier";
         type string {
           length "1 .. 32";
         }
         mandatory true;
       }
       leaf domain-name {
         description "Fully qualified domain name for subject-alt-name";
         type string;
       }
       leaf email {
         description "Email address";
         type string;
       }
       leaf filename {
         description "Local location for copy of certificate request";
         type string;
       }
       leaf subject {
         description "DC=<Domain component>,CN=<Common-Name>,OU=<Organizational-Unit-name>,O=<Organization-name>,SN=<Serial-Number>,L=<Locality>,ST=<state>,C=<Country>";
         type string;
         mandatory true;
       }
       leaf digest {
         description "Hash algorithm for signing RSA certificates";
         type enumeration {
           enum "sha-1" {
             description "SHA-1 digests (RSA/DSA only, default value for RSA/DSA)";
           }
           enum "sha-256" {
             description "SHA-256 digests (RSA/ECDSA only, default value for ECDSA)";
           }
           enum "sha-384" {
             description "SHA-384 digests (ECDSA only)";
           }
         }
       }
       leaf validity-start-time {
         description "Certificate validity start time (YYYY-MM-DD.HH:MM:SS)";
         status deprecated;
         type jt:time;
       }
       leaf validity-end-time {
         description "Certificate validity end time (YYYY-MM-DD.HH:MM:SS)";
         status deprecated;
         type jt:time;
       }
     }
   }
   rpc node-local-local-certificate-enroll {
     description "Enroll router certificate with CA online";
     input {
       uses command-forwarding;
       leaf certificate-id {
         description "Certificate identifier";
         status deprecated;
         type string {
           length "1 .. 32";
         }
         mandatory true;
       }
       leaf domain-name {
         description "Fully qualified domain name for subject-alt-name";
         status deprecated;
         type string;
       }
       leaf email {
         description "Email address";
         status deprecated;
         type string;
       }
       leaf ca-profile {
         description "Certificate authority profile";
         status deprecated;
         type string {
           length "1 .. 32";
         }
         mandatory true;
       }
       leaf challenge-password {
         description "Password used by CA for enrollment and revocation";
         status deprecated;
         type string;
         mandatory true;
       }
       leaf scep-encryption-algorithm {
         description "Encrypion algorithm used for SCEP-PKCS7";
         status deprecated;
         type enumeration {
           enum "des" {
             description "DES Encryption";
             status deprecated;
           }
           enum "des3" {
             description "DES-3 Encryption (default)";
             status deprecated;
           }
         }
       }
       leaf scep-digest-algorithm {
         description "Hash algorithm used for SCEP-PKCS7";
         status deprecated;
         type enumeration {
           enum "md5" {
             description "MD-5 digest";
             status deprecated;
           }
           enum "sha1" {
             description "SHA-1 digest (default)";
             status deprecated;
           }
         }
       }
       leaf ip-address {
         description "Static IP address of the device";
         status deprecated;
         type jt:ipaddr;
       }
       leaf ipv6-address {
         description "Static IPv6 address of the device for subject-alt-name";
         status deprecated;
         type jt:ipv6addr;
       }
       leaf subject {
         description "DC=<Domain component>,CN=<Common-Name>,OU=<Organizational-Unit-name>,O=<Organization-name>,SN=<Serial-Number>,L=<Locality>,ST=<state>,C=<Country>";
         status deprecated;
         type string;
         mandatory true;
       }
       leaf validity-start-time {
         description "Certificate validity start time (YYYY-MM-DD.HH:MM:SS)";
         status deprecated;
         type jt:time;
       }
       leaf validity-end-time {
         description "Certificate validity end time (YYYY-MM-DD.HH:MM:SS)";
         status deprecated;
         type jt:time;
       }
       leaf digest {
         description "Hash algorithm for signing RSA certificates";
         status deprecated;
         type enumeration {
           enum "sha-1" {
             description "SHA-1 digests (default value)";
             status deprecated;
           }
           enum "sha-256" {
             description "SHA-256 digests";
             status deprecated;
           }
         }
       }
     }
   }
   rpc node-local-local-certificate-enroll-cmpv2 {
     description "Enroll certificate using CMPv2 protocol";
     input {
       choice daemon-select {
         case logical-system {
           leaf logical-system {
             description "Name of logical system, or 'all'";
             type string {
             }
           }
         }
       }
       leaf certificate-id {
         description "Certificate identifier";
         type string {
           length "1 .. 32";
         }
         mandatory true;
       }
       leaf ip-address {
         description "Static IP address of the device";
         type jt:ipaddr;
       }
       leaf ipv6-address {
         description "Static IPv6 address of the device for subject-alt-name";
         type jt:ipv6addr;
       }
       leaf domain-name {
         description "Fully qualified domain name for subject-alt-name";
         type string;
       }
       leaf email {
         description "Email address";
         type string;
       }
       leaf subject {
         description "DC=<Domain component>,CN=<Common-Name>,OU=<Organizational-Unit-name>,O=<Organization-name>,SN=<Serial-Number>,L=<Locality>,ST=<state>,C=<Country>";
         type string;
         mandatory true;
       }
       leaf ca-profile {
         description "Certificate authority profile";
         type string {
           length "1 .. 32";
         }
         mandatory true;
       }
       leaf ca-dn {
         description "Subject DN for CMPv2 server, if CA certificate is not enrolled";
         type string;
       }
       leaf ca-secret {
         description "Initial Authentication Key, received from CMPv2 server";
         type string;
         mandatory true;
       }
       leaf ca-reference {
         description "Reference value associated with secret, received from CMPv2 server";
         type string;
         mandatory true;
       }
     }
   }
   rpc node-local-local-certificate-enroll-scep {
     description "Enroll end-entity certificate using SCEP protocol";
     input {
       leaf certificate-id {
         description "Certificate identifier";
         type string {
           length "1 .. 32";
         }
         mandatory true;
       }
       leaf ca-profile {
         description "Certificate authority profile";
         type string {
           length "1 .. 32";
         }
         mandatory true;
       }
       leaf challenge-password {
         description "Password used by CA for enrollment and revocation";
         type string;
         mandatory true;
       }
       leaf scep-encryption-algorithm {
         description "Encrypion algorithm used for SCEP-PKCS7";
         type enumeration {
           enum "des" {
             description "DES Encryption";
           }
           enum "des3" {
             description "DES-3 Encryption (default)";
           }
         }
       }
       leaf scep-digest-algorithm {
         description "Hash algorithm used for SCEP-PKCS7";
         type enumeration {
           enum "md5" {
             description "MD-5 digest";
           }
           enum "sha1" {
             description "SHA-1 digest (default)";
           }
         }
       }
       leaf ip-address {
         description "Static IP address of the device";
         type jt:ipaddr;
       }
       leaf ipv6-address {
         description "Static IPv6 address of the device for subject-alt-name";
         type jt:ipv6addr;
       }
       leaf domain-name {
         description "Fully qualified domain name for subject-alt-name";
         type string;
       }
       leaf email {
         description "Email address";
         type string;
       }
       leaf subject {
         description "DC=<Domain component>,CN=<Common-Name>,OU=<Organizational-Unit-name>,O=<Organization-name>,SN=<Serial-Number>,L=<Locality>,ST=<state>,C=<Country>";
         type string;
         mandatory true;
       }
       leaf validity-start-time {
         description "Certificate validity start time (YYYY-MM-DD.HH:MM:SS)";
         status deprecated;
         type jt:time;
       }
       leaf validity-end-time {
         description "Certificate validity end time (YYYY-MM-DD.HH:MM:SS)";
         status deprecated;
         type jt:time;
       }
       leaf digest {
         description "Hash algorithm for signing RSA certificates";
         type enumeration {
           enum "sha-1" {
             description "SHA-1 digests (default value)";
           }
           enum "sha-256" {
             description "SHA-256 digests";
           }
         }
       }
     }
   }
   rpc load-node-local-local-certificate {
     description "Load the certificate onto the routing platform";
     input {
       uses command-forwarding;
       choice daemon-select {
         case logical-system {
         }
       }
       leaf certificate-id {
         description "Certificate identifier";
         type string {
           length "1 .. 32";
         }
         mandatory true;
       }
       leaf filename {
         description "File pathname containing certificate to load";
         type string;
         mandatory true;
       }
       leaf key {
         description "File pathname containing the private key/key-pair to load";
         type string;
       }
       leaf passphrase {
         description "Passphrase of the private key/key-pair (PEM) file";
         type string;
       }
     }
     output {
       container cert-load-status {
         uses cert-load-status-block;
       }
     }
   }
   rpc verify-pki-node-local-local-certificate {
     description "Verify the certificate";
     input {
       uses command-forwarding;
       choice daemon-select {
         case logical-system {
         }
       }
       leaf certificate-id {
         description "Certificate identifier";
         type string {
           length "1 .. 32";
         }
         mandatory true;
       }
     }
   }
   rpc generate-node-local-self-signed-certificate {
     description "Generate a self-signed certificate";
     input {
       uses command-forwarding;
       choice daemon-select {
         case logical-system {
         }
       }
       leaf certificate-id {
         description "Certificate identifier";
         type string {
           length "1 .. 32";
         }
         mandatory true;
       }
       leaf domain-name {
         description "Fully qualified domain name";
         type string;
         mandatory true;
       }
       leaf ip-address {
         description "Static IP address of the device";
         type jt:ipaddr;
       }
       leaf email {
         description "Email address of the entity owning the certificate";
         type string;
       }
       leaf subject {
         description "DC=<Domain component>,CN=<Common-Name>,OU=<Organizational-Unit-name>,O=<Organization-name>,SN=<Serial-Number>,L=<Locality>,ST=<state>,C=<Country>";
         type string;
         mandatory true;
       }
       leaf add-ca-constraint {
         description "Certificate can be used for signing other certificates.";
         type empty;
       }
       leaf digest {
         description "Hash algorithm for signing RSA certificates";
         type enumeration {
           enum "sha-1" {
             description "SHA-1 digests";
           }
           enum "sha-256" {
             description "SHA-256 digests (default value)";
           }
         }
       }
     }
   }
   rpc node-local-local-certificate-re-enroll {
     description "Re-enroll router certificate with CA online";
     input {
       uses command-forwarding;
     }
   }
   rpc node-local-local-cert-re-enroll-cmpv2 {
     description "Enroll certificate using CMPv2 protocol";
     input {
       choice daemon-select {
         case logical-system {
           leaf logical-system {
             description "Name of logical system, or 'all'";
             type string {
             }
           }
         }
       }
       leaf certificate-id {
         description "Certificate identifier";
         type string {
           length "1 .. 32";
         }
         mandatory true;
       }
       leaf ca-profile {
         description "Certificate authority profile";
         type string {
           length "1 .. 32";
         }
       }
       leaf re-generate-keypair {
         description "Generate new keypair for re-enrollment";
         type empty;
       }
     }
   }
   rpc node-local-local-cert-re-enroll-scep {
     description "Enroll end-entity certificate using SCEP protocol";
     input {
       choice daemon-select {
         case logical-system {
           leaf logical-system {
             description "Name of logical system, or 'all'";
             type string {
             }
           }
         }
       }
       leaf certificate-id {
         description "Certificate identifier";
         type string {
           length "1 .. 32";
         }
         mandatory true;
       }
       leaf ca-profile {
         description "Certificate authority profile";
         type string {
           length "1 .. 32";
         }
       }
       leaf challenge-password {
         description "Password used by CA for enrollment and revocation";
         type string;
         mandatory true;
       }
       leaf re-generate-keypair {
         description "Generate new keypair for re-enrollment";
         type empty;
       }
       leaf scep-encryption-algorithm {
         description "Encrypion algorithm used for SCEP-PKCS7";
         type enumeration {
           enum "des" {
             description "DES Encryption";
           }
           enum "des3" {
             description "DES-3 Encryption (default)";
           }
         }
       }
       leaf scep-digest-algorithm {
         description "Hash algorithm used for SCEP-PKCS7";
         type enumeration {
           enum "md5" {
             description "MD-5 digest";
           }
           enum "sha1" {
             description "SHA-1 digest (default)";
           }
         }
       }
     }
   }
   rpc node-local-local-certificate-export {
     description "Export Certificate";
     input {
       uses command-forwarding;
       choice daemon-select {
         case logical-system {
         }
       }
       leaf certificate-id {
         description "Certificate identifier";
         type string {
           length "1 .. 32";
         }
         mandatory true;
       }
       leaf filename {
         description "Local location for copy of certificate.";
         type string;
         mandatory true;
       }
       leaf type {
         description "Type of certificate.";
         default "pem";
         type enumeration {
           enum "pem" {
             description "PEM format";
           }
           enum "der" {
             description "DER format";
           }
         }
       }
     }
   }
   rpc node-local-key-pair-export {
     description "Export Keypair in PEM format";
     input {
       uses command-forwarding;
       choice daemon-select {
         case logical-system {
         }
       }
       leaf certificate-id {
         description "Certificate identifier for keypair";
         type string {
           length "1 .. 32";
         }
         mandatory true;
       }
       leaf filename {
         description "Local location for copy of keypair.";
         type string;
         mandatory true;
       }
       leaf type {
         description "Type of key-pair.";
         default "pem";
         type enumeration {
           enum "pem" {
             description "PEM format";
           }
           enum "der" {
             description "DER format";
           }
         }
       }
       leaf passphrase {
         description "Passphrase of the private key/key-pair (PEM) file";
         type string;
         mandatory true;
       }
     }
   }
   rpc request-security-pki-ca-profile-group-status {
     description "Status of CA certs in default CA profile group";
     input {
       uses command-forwarding;
       choice daemon-select {
         case logical-system {
         }
       }
       leaf ca-group-name {
         description "CA group identifier";
         type string {
           length "1 .. 24";
         }
         mandatory true;
       }
     }
     output {
       container ca-profile-group-cert-status {
         uses ca-profile-group-cert-status-block;
       }
     }
   }
   rpc verify-integrity-status {
     description "Check the integrity of PKI files (in CC mode)";
     input {
       uses command-forwarding;
       choice daemon-select {
         case logical-system {
         }
       }
     }
     output {
       container verify-integrity-status {
         uses verify-integrity-status-block;
       }
     }
   }
   rpc request-pki-debug-memory-profile {
     description "Enable or disable memory profile";
     input {
       leaf profile-state {
         type enumeration {
           enum "enable" {
             description "Enable PKI memory profiling";
           }
           enum "disable" {
             description "Disable PKI memory profiling";
           }
           enum "dump" {
             description "Dump PKI memory profile debug info";
           }
         }
         mandatory true;
       }
     }
     output {
       choice output_c {
         case output-tag {
           leaf output {
             type string;
           }
         }
         case multichassis-tag {
           anyxml multi-routing-engine-results;
         }
       }
     }
   }
   rpc get-enable-ike-debug {
     description "Enable ike debug";
     input {
       uses command-forwarding;
       leaf remote {
         description "Remote ip address";
         type jt:ipaddr;
         mandatory true;
       }
     }
     output {
       choice output_c {
         case output-tag {
           leaf output {
             type string;
           }
         }
         case multichassis-tag {
           anyxml multi-routing-engine-results;
         }
       }
     }
   }
   rpc get-disable-ike-debug {
     description "Disable ike debug";
     input {
       uses command-forwarding;
     }
     output {
       choice output_c {
         case output-tag {
           leaf output {
             type string;
           }
         }
         case multichassis-tag {
           anyxml multi-routing-engine-results;
         }
       }
     }
   }
   rpc request-key-manager-profile-config {
     description "Get the config for configured key profile";
     input {
       leaf profile-name {
         description "Name of the configured key profile";
         type string {
           length "1 .. 32";
         }
         mandatory true;
       }
     }
   }
   rpc request-key-manager-profile-status {
     description "Get the status for configured key profile";
     input {
       leaf profile-name {
         description "Name of the configured key profile";
         type string {
           length "1 .. 32";
         }
         mandatory true;
       }
       leaf peer-sae-id {
         description "Specify peer sae id";
         type string {
           length "1 .. 250";
         }
       }
     }
   }
   rpc request-key-manager-profile-keys {
     description "Get the key(s) for configured key profile";
     input {
       leaf profile-name {
         description "Name of the configured key profile";
         type string {
           length "1 .. 32";
         }
         mandatory true;
       }
       leaf-list peer-sae-id {
         ordered-by user;
         description "Specify peer sae id";
         type string {
           length "1 .. 250";
         }
         max-elements 20;
       }
       leaf key-count {
         description "Specify the number of keys";
         type union {
           type string {
             pattern "<.*>|$.*";
           }
           type uint32 {
             range "1 .. 20";
           }
         }
       }
       leaf key-size {
         description "Specify the size of key(s) in bits";
         type union {
           type string {
             pattern "<.*>|$.*";
           }
           type uint32 {
             range "256 .. 4096";
           }
         }
       }
     }
   }
   rpc request-key-manager-profile-keys-with-id {
     description "Get the key(s) for given key-id(s) for configured key profile";
     input {
       leaf profile-name {
         description "Name of the configured key profile";
         type string {
           length "1 .. 32";
         }
         mandatory true;
       }
       leaf peer-sae-id {
         description "Specify peer sae id";
         type string {
           length "1 .. 250";
         }
       }
       leaf-list key-id {
         ordered-by user;
         description "Specify key id";
         type string {
           length "1 .. 512";
         }
         max-elements 20;
       }
     }
   }
   rpc revert-redundancy-interface-to-primary {
     description "Revert redundancy interface to its primary";
     input {
       leaf interface-name {
         description "Name of interface";
         type union {
           type jt:interface-wildcard;
           type string {
             pattern "<.*>|$.*";
           }
         }
         mandatory true;
       }
     }
     output {
       choice output_c {
         case output-tag {
           leaf output {
             type string;
           }
         }
         case multichassis-tag {
           anyxml multi-routing-engine-results;
         }
       }
     }
   }
   rpc switch-redundancy-interface-to-secondary {
     description "Switch redundancy interface over to its secondary";
     input {
       leaf interface-name {
         description "Name of interface";
         type union {
           type jt:interface-wildcard;
           type string {
             pattern "<.*>|$.*";
           }
         }
         mandatory true;
       }
     }
     output {
       choice output_c {
         case output-tag {
           leaf output {
             type string;
           }
         }
         case multichassis-tag {
           anyxml multi-routing-engine-results;
         }
       }
     }
   }
   rpc request-intf-modem-reset {
     description "Reset the modem device";
     input {
       leaf interface-name {
         description "Name of physical interface";
         type string;
         mandatory true;
       }
     }
     output {
       choice output_c {
         case output-tag {
           leaf output {
             type string;
           }
         }
         case multichassis-tag {
           anyxml multi-routing-engine-results;
         }
       }
     }
   }
   rpc request-load-balancing-revert {
     description "Revert load-balancing member interface";
     input {
       leaf interface-name {
         description "Name of member-interface";
         type union {
           type jt:interface-wildcard;
           type string {
             pattern "<.*>|$.*";
           }
         }
         mandatory true;
       }
     }
   }
   rpc request-load-balancing-switchover {
     description "Switch load-balancing member interface to backup";
     input {
       leaf interface-name {
         description "Name of member interface";
         type union {
           type jt:interface-wildcard;
           type string {
             pattern "<.*>|$.*";
           }
         }
         mandatory true;
       }
       leaf force {
         description "Force a active member switchover";
         type empty;
       }
     }
     output {
       leaf rdd-action-result {
         type string;
       }
     }
   }
   rpc request-interface-mcae-switchover {
     description "Request MC-AE mastership switchover";
     input {
       leaf mcae-id {
         description "MC-AE id";
         type union {
           type uint16;
           type string {
             pattern "<.*>|$.*";
           }
         }
         mandatory true;
       }
     }
   }
   rpc request-interface-mcae-switchover-immediate {
     description "Request MC-AE mastership switchover immediate";
     input {
       leaf mcae-id {
         description "MC-AE id";
         type union {
           type uint16;
           type string {
             pattern "<.*>|$.*";
           }
         }
         mandatory true;
       }
     }
   }
   rpc request-interface-link-degade-recover {
     description "Perform manual link recovery";
     input {
       leaf interface-name {
         description "Name of interface";
         type union {
           type jt:interface-device;
           type string {
             pattern "<.*>|$.*";
           }
         }
         mandatory true;
       }
     }
     output {
       choice output_c {
         case output-tag {
           leaf output {
             type string;
           }
         }
         case multichassis-tag {
           anyxml multi-routing-engine-results;
         }
       }
     }
   }
   rpc request-interface-optics-reset {
     description "Perform manual optics-reset";
     input {
       leaf transceiver-name {
         description "Transceiver name";
         type string {
         }
         mandatory true;
       }
     }
     output {
       choice output_c {
         case output-tag {
           leaf output {
             type string;
           }
         }
         case multichassis-tag {
           anyxml multi-routing-engine-results;
         }
       }
     }
   }
   rpc request-rebalance-interface {
     description "Request rebalance of interfaces on the interface";
     input {
       leaf interface-name {
         description "Name of the interface";
         type string;
         mandatory true;
       }
     }
     output {
       container rebalance-interface {
         uses rebalance-interface-block;
       }
     }
   }
   rpc request-bounce-interface {
     description "Bounce the port";
     input {
       leaf interface-name {
         description "Name of the interface";
         type string;
         mandatory true;
       }
       leaf interval {
         description "Interval (in secs) between DOWN and UP";
         type union {
           type string {
             pattern "<.*>|$.*";
           }
           type uint32 {
             range "1 .. 30";
           }
         }
       }
     }
     output {
       container bounce-interface {
         uses bounce-interface-block;
       }
     }
   }
   rpc extension-service-start {
     description "Start JET application";
     input {
       leaf invoke-debugger {
         description "Invoke extension-service in debugger mode";
         type enumeration {
           enum "cli" {
             description "Invoke debugger in cli";
           }
         }
       }
       leaf application-name {
         description "Application name";
         type jt:filename;
         mandatory true;
       }
     }
     output {
       choice output_c {
         case output-tag {
           leaf output {
             type string;
           }
         }
         case multichassis-tag {
           anyxml multi-routing-engine-results;
         }
       }
     }
   }
   rpc extension-service-stop {
     description "Stop JET application";
     input {
       leaf application-name {
         description "Application name";
         type jt:filename;
         mandatory true;
       }
     }
     output {
       choice output_c {
         case output-tag {
           leaf output {
             type string;
           }
         }
         case multichassis-tag {
           anyxml multi-routing-engine-results;
         }
       }
     }
   }
   rpc extension-service-restart {
     description "Restart JET application";
     input {
       leaf application-name {
         description "Application name";
         type jt:filename;
         mandatory true;
       }
     }
     output {
       choice output_c {
         case output-tag {
           leaf output {
             type string;
           }
         }
         case multichassis-tag {
           anyxml multi-routing-engine-results;
         }
       }
     }
   }
   rpc extension-service-daemonize-restart {
     description "Restart daemonize JET application";
     input {
       leaf application-name {
         description "Application name";
         type jt:filename;
         mandatory true;
       }
     }
     output {
       container extension-service-daemonize-restart-status {
         uses extension-service-daemonize-restart-status-block;
       }
     }
   }
   rpc get-csds-information {
     description "Perform one-way key exchange to host";
     input {
       leaf csds-instance-id {
         description "CSDS Instance ID";
         type union {
           type int32;
           type string {
             pattern "<.*>|$.*";
           }
         }
       }
     }
     output {
       choice output_c {
         case output-tag {
           leaf output {
             type string;
           }
         }
         case multichassis-tag {
           anyxml multi-routing-engine-results;
         }
       }
     }
   }
   rpc request-csds-jdm-package-add {
     description "Install fresh JDM package or upgrade package";
     input {
       leaf csds-instance-id {
         description "CSDS host Instance ID";
         type union {
           type int32;
           type string {
             pattern "<.*>|$.*";
           }
         }
         mandatory true;
       }
       leaf image {
         description "JDM package name";
         type jt:filename;
         mandatory true;
       }
       leaf force {
         description "Perform operation by discarding any uncommitted changes";
         type empty;
       }
     }
     output {
       choice output_c {
         case output-tag {
           leaf output {
             type string;
           }
         }
         case multichassis-tag {
           anyxml multi-routing-engine-results;
         }
       }
     }
   }
   rpc request-csds-jdm-package-delete {
     description "Remove currently installed JDM package";
     input {
       leaf csds-instance-id {
         description "CSDS Instance ID";
         type union {
           type int32;
           type string {
             pattern "<.*>|$.*";
           }
         }
         mandatory true;
       }
       leaf force {
         description "Perform operation by discarding any uncommitted changes";
         type empty;
       }
     }
     output {
       choice output_c {
         case output-tag {
           leaf output {
             type string;
           }
         }
         case multichassis-tag {
           anyxml multi-routing-engine-results;
         }
       }
     }
   }
   rpc request-csds-vsrx-package-add {
     description "Add VSRX package to JDM";
     input {
       leaf csds-instance-id {
         description "CSDS Instance ID";
         type union {
           type int32;
           type string {
             pattern "<.*>|$.*";
           }
         }
         mandatory true;
       }
       leaf image {
         description "VSRX package name";
         type jt:filename;
         mandatory true;
       }
     }
     output {
       choice output_c {
         case output-tag {
           leaf output {
             type string;
           }
         }
         case multichassis-tag {
           anyxml multi-routing-engine-results;
         }
       }
     }
   }
   rpc request-csds-vsrx-package-delete {
     description "Remove currently running VNFs";
     input {
       leaf csds-instance-id {
         description "CSDS Instance ID";
         type union {
           type int32;
           type string {
             pattern "<.*>|$.*";
           }
         }
         mandatory true;
       }
       leaf force {
         description "Perform operation by discarding any uncommitted changes";
         type empty;
       }
     }
     output {
       choice output_c {
         case output-tag {
           leaf output {
             type string;
           }
         }
         case multichassis-tag {
           anyxml multi-routing-engine-results;
         }
       }
     }
   }
   rpc request-csds-extract-vsrx-keys {
     description "Extract keys from VSRX's devices";
     input {
       leaf csds-instance-id {
         description "CSDS Instance ID";
         type union {
           type int32;
           type string {
             pattern "<.*>|$.*";
           }
         }
         mandatory true;
       }
       leaf force {
         description "Perform operation by discarding any uncommitted changes";
         type empty;
       }
     }
     output {
       choice output_c {
         case output-tag {
           leaf output {
             type string;
           }
         }
         case multichassis-tag {
           anyxml multi-routing-engine-results;
         }
       }
     }
   }
   rpc request-csds-sync-controller-keys {
     description "Sync other controller";
     input {
       leaf other-controller-ip {
         description "Primary controller IP";
         type jt:ipaddr;
         mandatory true;
       }
       leaf force {
         description "Perform operation by discarding any uncommitted changes";
         type empty;
       }
     }
     output {
       choice output_c {
         case output-tag {
           leaf output {
             type string;
           }
         }
         case multichassis-tag {
           anyxml multi-routing-engine-results;
         }
       }
     }
   }
   rpc mgd-jnu-role {
     description "JNU Role";
     input {
       uses command-forwarding;
       leaf jnu-role {
         type enumeration {
           enum "controller" {
             description "Controller";
           }
           enum "satellite" {
             description "Satellite";
           }
         }
         mandatory true;
       }
     }
     output {
       choice output_c {
         case output-tag {
           leaf output {
             type string;
           }
         }
         case multichassis-tag {
           anyxml multi-routing-engine-results;
         }
       }
     }
   }
   rpc mgd-jnu-schema-delete {
     description "Delete a JNU satellite schema";
     input {
       leaf model {
         description "Satellite model";
         type string;
         mandatory true;
       }
       leaf version {
         description "Satellite version";
         type string {
         }
         mandatory true;
       }
     }
     output {
       choice output_c {
         case output-tag {
           leaf output {
             type string;
           }
         }
         case multichassis-tag {
           anyxml multi-routing-engine-results;
         }
       }
     }
   }
   rpc mgd-jnu-schema-merge {
     description "Merge JNU schema to this controller";
     input {
       leaf satschema {
         description "Satellite Schema Path";
         type jt:filename;
         mandatory true;
       }
       leaf conschema {
         description "Controller Schema Path";
         type jt:filename;
         mandatory true;
       }
     }
     output {
       choice output_c {
         case output-tag {
           leaf output {
             type string;
           }
         }
         case multichassis-tag {
           anyxml multi-routing-engine-results;
         }
       }
     }
   }
   rpc mgd-jnu-schema-add {
     description "Add JNU schema to this controller";
     input {
       leaf model {
         description "Satellite model";
         type string;
         mandatory true;
       }
       leaf version {
         description "Satellite version";
         type string {
         }
         mandatory true;
       }
       leaf filename {
         description "Satellite schema TLV package filename";
         type jt:filename;
         mandatory true;
       }
     }
     output {
       choice output_c {
         case output-tag {
           leaf output {
             type string;
           }
         }
         case multichassis-tag {
           anyxml multi-routing-engine-results;
         }
       }
     }
   }
   rpc request-jnu-satellite-sync {
     description "Sync satellite with controller";
     output {
       choice output_c {
         case output-tag {
           leaf output {
             type string;
           }
         }
         case multichassis-tag {
           anyxml multi-routing-engine-results;
         }
       }
     }
   }
   rpc clear-jdaf-command-client-stats {
     description "Clear JDAF client side statistics";
   }
   rpc clear-jdaf-command-server-stats {
     description "Clear JDAF server statistics";
     output {
       choice output_c {
         case output-tag {
           leaf output {
             type string;
           }
         }
         case multichassis-tag {
           anyxml multi-routing-engine-results;
         }
       }
     }
   }
   rpc clear-jdaf-config-client-stats {
     description "Clear JDAF client side statistics";
   }
   rpc clear-jdaf-config-server-stats {
     description "Clear JDAF server statistics";
     output {
       choice output_c {
         case output-tag {
           leaf output {
             type string;
           }
         }
         case multichassis-tag {
           anyxml multi-routing-engine-results;
         }
       }
     }
   }
   rpc clear-jdaf-firewall-client-stats {
     description "Clear JDAF client side statistics";
     input {
       leaf client-id {
         description "Client id";
         default "0";
         type union {
           type uint32;
           type string {
             pattern "<.*>|$.*";
           }
         }
       }
     }
   }
   rpc clear-jdaf-firewall-server-stats {
     description "Clear JDAF server statistics";
     output {
       choice output_c {
         case output-tag {
           leaf output {
             type string;
           }
         }
         case multichassis-tag {
           anyxml multi-routing-engine-results;
         }
       }
     }
   }
   rpc clear-jdaf-interface-client-stats {
     description "Clear JDAF client side statistics";
     input {
       leaf client-id {
         description "Client id";
         default "0";
         type union {
           type uint32;
           type string {
             pattern "<.*>|$.*";
           }
         }
       }
     }
   }
   rpc clear-jdaf-interface-server-stats {
     description "Clear JDAF server statistics";
     output {
       choice output_c {
         case output-tag {
           leaf output {
             type string;
           }
         }
         case multichassis-tag {
           anyxml multi-routing-engine-results;
         }
       }
     }
   }
   rpc clear-jdaf-route-client-stats {
     description "Clear JDAF client side statistics";
     input {
       leaf client-id {
         description "Client id";
         default "0";
         type union {
           type uint32;
           type string {
             pattern "<.*>|$.*";
           }
         }
       }
     }
   }
   rpc clear-jdaf-route-server-stats {
     description "Clear JDAF server statistics";
     output {
       choice output_c {
         case output-tag {
           leaf output {
             type string;
           }
         }
         case multichassis-tag {
           anyxml multi-routing-engine-results;
         }
       }
     }
   }
   rpc request-dhcp-server-reconfigure-information {
     description "Perform DHCP server reconfigure operation";
     input {
       choice reconfigure-choice {
         case address {
           leaf address {
             description "IP address or MAC address or Session Id of DHCP client binding";
             type string;
           }
         }
         case all {
           leaf all {
             description "Reconfigure all clients";
             type empty;
           }
         }
       }
       leaf routing-instance {
         description "Name of routing instance";
         type string;
       }
       choice daemon-select {
         case logical-system {
           leaf logical-system {
             description "Name of logical system";
             type string {
             }
           }
         }
       }
     }
     output {
       choice output_c {
         case output-tag {
           leaf output {
             type string;
           }
         }
         case multichassis-tag {
           anyxml multi-routing-engine-results;
         }
       }
     }
   }
   rpc request-dhcp-server-reconfigure-interface {
     description "Name of interface";
     input {
       leaf interface-name {
         description "Name of interface";
         type string;
         mandatory true;
       }
     }
     output {
       choice output_c {
         case output-tag {
           leaf output {
             type string;
           }
         }
         case multichassis-tag {
           anyxml multi-routing-engine-results;
         }
       }
     }
   }
   rpc request-dhcp-server-regenerate-persistent-file {
     description "Triggers the flat file backup operation";
     output {
       choice output_c {
         case output-tag {
           leaf output {
             type string;
           }
         }
         case multichassis-tag {
           anyxml multi-routing-engine-results;
         }
       }
     }
   }
   rpc request-dhcp-server-restore-client-from-file {
     description "Triggers the flat file restore operation";
     input {
       leaf from-file {
         description "Restore subscribers from file";
         type empty;
         mandatory true;
       }
       choice daemon-select {
         case logical-system {
           leaf logical-system {
             description "Name of logical system";
             type string {
             }
           }
         }
       }
     }
     output {
       choice output_c {
         case output-tag {
           leaf output {
             type string;
           }
         }
         case multichassis-tag {
           anyxml multi-routing-engine-results;
         }
       }
     }
   }
   rpc request-dhcp-client-renew-information {
     description "Request DHCP client renew";
     input {
       choice renew-choice {
         case interface {
           leaf interface {
             description "Interface name of DHCP client";
             type string;
           }
         }
         case all {
           leaf all {
             description "Renew all clients";
             type empty;
           }
         }
       }
       leaf routing-instance {
         description "Name of routing instance";
         type string;
       }
       choice lsys-tenant {
       }
       choice daemon-select {
         case logical-system {
           leaf logical-system {
             description "Name of logical system";
             type string {
             }
           }
         }
       }
     }
     output {
       choice output_c {
         case output-tag {
           leaf output {
             type string;
           }
         }
         case multichassis-tag {
           anyxml multi-routing-engine-results;
         }
       }
     }
   }
   rpc request-dhcp-relay-leasequery {
     description "Perform DHCP relay leasequery operation";
     input {
       leaf address {
         description "Query by IPv4 address or mac-address or Client-ID";
         type string;
         mandatory true;
       }
       leaf gateway-address {
         description "Giaddr of leasequery packet";
         type string;
         mandatory true;
       }
       choice query-server {
         case server-address {
           leaf server-address {
             description "Send leasequery to server address";
             type string;
           }
         }
         case server-group {
           leaf server-group {
             description "Send leasequery to servers in server-group";
             type string;
           }
         }
       }
       leaf routing-instance {
         description "Name of routing instance";
         type string;
       }
       choice daemon-select {
         case logical-system {
           leaf logical-system {
             description "Name of logical system";
             type string {
             }
           }
         }
       }
     }
     output {
       choice output_c {
         case output-tag {
           leaf output {
             type string;
           }
         }
         case multichassis-tag {
           anyxml multi-routing-engine-results;
         }
       }
     }
   }
   rpc request-dhcp-relay-bulk-leasequery {
     description "Perform DHCP relay bulk leasequery operation";
     input {
       leaf address {
         description "Query by IPv4 address or mac-address or Client-ID";
         type string;
       }
       choice query-server {
         case server-address {
           leaf server-address {
             description "Send leasequery to server address";
             type string;
           }
         }
         case server-group {
           leaf server-group {
             description "Send leasequery to servers in server-group";
             type string;
           }
         }
       }
       leaf all-configured-ip {
         description "Query by all-configure-ip-addresss";
         type empty;
       }
       leaf routing-instance {
         description "Name of routing instance";
         type string;
       }
       choice daemon-select {
         case logical-system {
           leaf logical-system {
             description "Name of logical system";
             type string {
             }
           }
         }
       }
     }
     output {
       choice output_c {
         case output-tag {
           leaf output {
             type string;
           }
         }
         case multichassis-tag {
           anyxml multi-routing-engine-results;
         }
       }
     }
   }
   rpc request-dhcp-relay-bulk-leasequery-relay-id {
     description "Query by relay-id";
     input {
       leaf relay-id {
         description "Query by relay-id";
         type string;
         mandatory true;
       }
       choice query-server {
         case server-address {
           leaf server-address {
             description "Send leasequery to server address";
             type string;
           }
         }
         case server-group {
           leaf server-group {
             description "Send leasequery to servers in server-group";
             type string;
           }
         }
       }
       leaf routing-instance {
         description "Name of routing instance";
         type string;
       }
       choice daemon-select {
         case logical-system {
           leaf logical-system {
             description "Name of logical system";
             type string {
             }
           }
         }
       }
     }
     output {
       choice output_c {
         case output-tag {
           leaf output {
             type string;
           }
         }
         case multichassis-tag {
           anyxml multi-routing-engine-results;
         }
       }
     }
   }
   rpc request-dhcp-relay-bulk-leasequery-remote-id {
     description "Query by remote-id";
     input {
       leaf remote-id {
         description "Query by remote-id";
         type string;
         mandatory true;
       }
       choice query-server {
         case server-address {
           leaf server-address {
             description "Send leasequery to server address";
             type string;
           }
         }
         case server-group {
           leaf server-group {
             description "Send leasequery to servers in server-group";
             type string;
           }
         }
       }
       leaf routing-instance {
         description "Name of routing instance";
         type string;
       }
       choice daemon-select {
         case logical-system {
           leaf logical-system {
             description "Name of logical system";
             type string {
             }
           }
         }
       }
     }
     output {
       choice output_c {
         case output-tag {
           leaf output {
             type string;
           }
         }
         case multichassis-tag {
           anyxml multi-routing-engine-results;
         }
       }
     }
   }
   rpc request-dhcp-relay-active-leasequery {
     description "Request DHCP active-leasequery operations";
     input {
       leaf discover-neighbor {
         description "Discover neighbors capable of hosting subscribers";
         type empty;
         mandatory true;
       }
       leaf routing-instance {
         description "Name of routing instance";
         type string;
       }
       choice daemon-select {
         case logical-system {
           leaf logical-system {
             description "Name of logical system";
             type string {
             }
           }
         }
       }
     }
     output {
       choice output_c {
         case output-tag {
           leaf output {
             type string;
           }
         }
         case multichassis-tag {
           anyxml multi-routing-engine-results;
         }
       }
     }
   }
   rpc request-dhcp-relay-alq-peer {
     description "Active-leasequery peer";
     input {
       leaf peer-address {
         description "Active-leasequery peer address";
         type jt:ipaddr;
         mandatory true;
       }
       leaf routing-instance {
         description "Name of routing instance";
         type string;
       }
       choice daemon-select {
         case logical-system {
           leaf logical-system {
             description "Name of logical system";
             type string {
             }
           }
         }
       }
     }
     output {
       choice output_c {
         case output-tag {
           leaf output {
             type string;
           }
         }
         case multichassis-tag {
           anyxml multi-routing-engine-results;
         }
       }
     }
   }
   rpc request-dhcp-relay-alq-interface {
     description "Active-leasequery interface";
     input {
       leaf interface-name {
         description "Active-leasequery interface name";
         type string;
         mandatory true;
       }
     }
     output {
       choice output_c {
         case output-tag {
           leaf output {
             type string;
           }
         }
         case multichassis-tag {
           anyxml multi-routing-engine-results;
         }
       }
     }
   }
   rpc request-dhcp-relay-regenerate-persistent-file {
     description "Triggers the flat file backup operation";
     output {
       choice output_c {
         case output-tag {
           leaf output {
             type string;
           }
         }
         case multichassis-tag {
           anyxml multi-routing-engine-results;
         }
       }
     }
   }
   rpc request-dhcp-relay-restore-client-from-file {
     description "Triggers the flat file restore operation";
     input {
       leaf from-file {
         description "Restore subscribers from file";
         type empty;
         mandatory true;
       }
       choice daemon-select {
         case logical-system {
           leaf logical-system {
             description "Name of logical system";
             type string {
             }
           }
         }
       }
     }
     output {
       choice output_c {
         case output-tag {
           leaf output {
             type string;
           }
         }
         case multichassis-tag {
           anyxml multi-routing-engine-results;
         }
       }
     }
   }
   rpc request-dhcp-regenerate-persistent-file {
     description "Triggers the flat file backup operation";
     output {
       choice output_c {
         case output-tag {
           leaf output {
             type string;
           }
         }
         case multichassis-tag {
           anyxml multi-routing-engine-results;
         }
       }
     }
   }
   rpc request-dhcp-restore-client-from-file {
     description "Triggers the flat file restore operation";
     input {
       leaf from-file {
         description "Restore subscribers from file";
         type empty;
         mandatory true;
       }
       choice daemon-select {
         case logical-system {
           leaf logical-system {
             description "Name of logical system";
             type string {
             }
           }
         }
       }
     }
     output {
       choice output_c {
         case output-tag {
           leaf output {
             type string;
           }
         }
         case multichassis-tag {
           anyxml multi-routing-engine-results;
         }
       }
     }
   }
   rpc request-dhcpv6-client-renew-information {
     description "Request DHCP client renew";
     input {
       choice renew-choice {
         case interface {
           leaf interface {
             description "Interface name of DHCP client";
             type string;
           }
         }
         case all {
           leaf all {
             description "Renew all clients";
             type empty;
           }
         }
       }
       leaf routing-instance {
         description "Name of routing instance";
         type string;
       }
       choice lsys-tenant {
       }
       choice daemon-select {
         case logical-system {
           leaf logical-system {
             description "Name of logical system";
             type string {
             }
           }
         }
       }
     }
     output {
       choice output_c {
         case output-tag {
           leaf output {
             type string;
           }
         }
         case multichassis-tag {
           anyxml multi-routing-engine-results;
         }
       }
     }
   }
   rpc request-dhcpv6-server-reconfigure-information {
     description "Perform DHCPv6 server reconfigure operation";
     input {
       choice reconfigure-choice {
         case address {
           leaf address {
             description "IPv6 Prefix, session-id or CID of DHCPv6 client binding";
             type string;
           }
         }
         case all {
           leaf all {
             description "Reconfigure all clients";
             type empty;
           }
         }
       }
       leaf routing-instance {
         description "Name of routing instance";
         type string;
       }
       choice daemon-select {
         case logical-system {
           leaf logical-system {
             description "Name of logical system";
             type string {
             }
           }
         }
       }
     }
     output {
       choice output_c {
         case output-tag {
           leaf output {
             type string;
           }
         }
         case multichassis-tag {
           anyxml multi-routing-engine-results;
         }
       }
     }
   }
   rpc request-dhcpv6-server-reconfigure-interface {
     description "Name of interface";
     input {
       leaf interface-name {
         description "Name of interface";
         type string;
         mandatory true;
       }
     }
     output {
       choice output_c {
         case output-tag {
           leaf output {
             type string;
           }
         }
         case multichassis-tag {
           anyxml multi-routing-engine-results;
         }
       }
     }
   }
   rpc request-dhcpv6-server-regenerate-persistent-file {
     description "Triggers the flat file backup operation";
     output {
       choice output_c {
         case output-tag {
           leaf output {
             type string;
           }
         }
         case multichassis-tag {
           anyxml multi-routing-engine-results;
         }
       }
     }
   }
   rpc request-dhcpv6-server-restore-client-from-file {
     description "Triggers the flat file restore operation";
     input {
       leaf from-file {
         description "Restore subscribers from file";
         type empty;
         mandatory true;
       }
       choice daemon-select {
         case logical-system {
           leaf logical-system {
             description "Name of logical system";
             type string {
             }
           }
         }
       }
     }
     output {
       choice output_c {
         case output-tag {
           leaf output {
             type string;
           }
         }
         case multichassis-tag {
           anyxml multi-routing-engine-results;
         }
       }
     }
   }
   rpc request-dhcpv6-relay-leasequery {
     description "Perform DHCPv6 relay leasequery operation";
     input {
       leaf address {
         description "Query by IPv6 Prefix or CID of DHCPv6 client binding";
         type string;
         mandatory true;
       }
       choice query-server {
         case server-address {
           leaf server-address {
             description "Send leasequery to server address";
             type string;
           }
         }
         case server-group {
           leaf server-group {
             description "Send leasequery to servers in server-group";
             type string;
           }
         }
       }
       leaf routing-instance {
         description "Name of routing instance";
         type string;
       }
       choice daemon-select {
         case logical-system {
           leaf logical-system {
             description "Name of logical system";
             type string {
             }
           }
         }
       }
     }
     output {
       choice output_c {
         case output-tag {
           leaf output {
             type string;
           }
         }
         case multichassis-tag {
           anyxml multi-routing-engine-results;
         }
       }
     }
   }
   rpc request-dhcpv6-relay-bulk-leasequery {
     description "Perform DHCPv6 relay bulk leasequery operation";
     input {
       leaf address {
         description "Query by IPv6 Prefix or CID of DHCPv6 client binding";
         type string;
       }
       choice query-server {
         case server-address {
           leaf server-address {
             description "Send leasequery to server address";
             type string;
           }
         }
         case server-group {
           leaf server-group {
             description "Send leasequery to servers in server-group";
             type string;
           }
         }
       }
       leaf routing-instance {
         description "Name of routing instance";
         type string;
       }
       choice daemon-select {
         case logical-system {
           leaf logical-system {
             description "Name of logical system";
             type string {
             }
           }
         }
       }
     }
     output {
       choice output_c {
         case output-tag {
           leaf output {
             type string;
           }
         }
         case multichassis-tag {
           anyxml multi-routing-engine-results;
         }
       }
     }
   }
   rpc request-dhcpv6-relay-bulk-leasequery-relay-id {
     description "Query by relay-id";
     input {
       leaf relay-id {
         description "Query by relay-id";
         type string;
         mandatory true;
       }
       choice query-server {
         case server-address {
           leaf server-address {
             description "Send leasequery to server address";
             type string;
           }
         }
         case server-group {
           leaf server-group {
             description "Send leasequery to servers in server-group";
             type string;
           }
         }
       }
       leaf routing-instance {
         description "Name of routing instance";
         type string;
       }
       choice daemon-select {
         case logical-system {
           leaf logical-system {
             description "Name of logical system";
             type string {
             }
           }
         }
       }
     }
     output {
       choice output_c {
         case output-tag {
           leaf output {
             type string;
           }
         }
         case multichassis-tag {
           anyxml multi-routing-engine-results;
         }
       }
     }
   }
   rpc request-dhcpv6-relay-bulk-leasequery-link-addr {
     description "Query by link-address";
     input {
       leaf link-addr {
         description "Query by link-address";
         type string;
         mandatory true;
       }
       choice query-server {
         case server-address {
           leaf server-address {
             description "Send leasequery to server address";
             type string;
           }
         }
         case server-group {
           leaf server-group {
             description "Send leasequery to servers in server-group";
             type string;
           }
         }
       }
       leaf routing-instance {
         description "Name of routing instance";
         type string;
       }
       choice daemon-select {
         case logical-system {
           leaf logical-system {
             description "Name of logical system";
             type string {
             }
           }
         }
       }
     }
     output {
       choice output_c {
         case output-tag {
           leaf output {
             type string;
           }
         }
         case multichassis-tag {
           anyxml multi-routing-engine-results;
         }
       }
     }
   }
   rpc request-dhcpv6-relay-bulk-leasequery-remote-id {
     description "Query by remote-id";
     input {
       leaf remote-id {
         description "Query by remote-id";
         type string;
         mandatory true;
       }
       choice query-server {
         case server-address {
           leaf server-address {
             description "Send leasequery to server address";
             type string;
           }
         }
         case server-group {
           leaf server-group {
             description "Send leasequery to servers in server-group";
             type string;
           }
         }
       }
       leaf routing-instance {
         description "Name of routing instance";
         type string;
       }
       choice daemon-select {
         case logical-system {
           leaf logical-system {
             description "Name of logical system";
             type string {
             }
           }
         }
       }
     }
     output {
       choice output_c {
         case output-tag {
           leaf output {
             type string;
           }
         }
         case multichassis-tag {
           anyxml multi-routing-engine-results;
         }
       }
     }
   }
   rpc request-dhcpv6-relay-regenerate-persistent-file {
     description "Triggers the flat file backup operation";
     output {
       choice output_c {
         case output-tag {
           leaf output {
             type string;
           }
         }
         case multichassis-tag {
           anyxml multi-routing-engine-results;
         }
       }
     }
   }
   rpc request-dhcpv6-relay-restore-client-from-file {
     description "Triggers the flat file restore operation";
     input {
       leaf from-file {
         description "Restore subscribers from file";
         type empty;
         mandatory true;
       }
       choice daemon-select {
         case logical-system {
           leaf logical-system {
             description "Name of logical system";
             type string {
             }
           }
         }
       }
     }
     output {
       choice output_c {
         case output-tag {
           leaf output {
             type string;
           }
         }
         case multichassis-tag {
           anyxml multi-routing-engine-results;
         }
       }
     }
   }
   rpc request-dhcpv6-relay-active-leasequery {
     description "Request DHCP active-leasequery operations";
     input {
       leaf discover-neighbor {
         description "Discover neighbors capable of hosting subscribers";
         type empty;
         mandatory true;
       }
       leaf routing-instance {
         description "Name of routing instance";
         type string;
       }
       choice daemon-select {
         case logical-system {
           leaf logical-system {
             description "Name of logical system";
             type string {
             }
           }
         }
       }
     }
     output {
       choice output_c {
         case output-tag {
           leaf output {
             type string;
           }
         }
         case multichassis-tag {
           anyxml multi-routing-engine-results;
         }
       }
     }
   }
   rpc request-dhcpv6-relay-alq-peer {
     description "Active-leasequery peer";
     input {
       leaf peer-address {
         description "Active-leasequery peer address";
         type jt:ipaddr;
         mandatory true;
       }
       leaf routing-instance {
         description "Name of routing instance";
         type string;
       }
       choice daemon-select {
         case logical-system {
           leaf logical-system {
             description "Name of logical system";
             type string {
             }
           }
         }
       }
     }
     output {
       choice output_c {
         case output-tag {
           leaf output {
             type string;
           }
         }
         case multichassis-tag {
           anyxml multi-routing-engine-results;
         }
       }
     }
   }
   rpc request-dhcpv6-relay-alq-interface {
     description "Active-leasequery interface";
     input {
       leaf interface-name {
         description "Active-leasequery interface name";
         type string;
         mandatory true;
       }
     }
     output {
       choice output_c {
         case output-tag {
           leaf output {
             type string;
           }
         }
         case multichassis-tag {
           anyxml multi-routing-engine-results;
         }
       }
     }
   }
   rpc request-as-ra-guard-forward-interface {
     description "Name of interface";
     input {
       leaf interface-name {
         description "Name of interface";
         type union {
           type jt:interface-name;
           type string {
             pattern "<.*>|$.*";
           }
         }
         mandatory true;
       }
     }
     output {
       choice output_c {
         case output-tag {
           leaf output {
             type string;
           }
         }
         case multichassis-tag {
           anyxml multi-routing-engine-results;
         }
       }
     }
   }
   rpc request-as-ra-guard-block-interface {
     description "Name of interface";
     input {
       leaf interface-name {
         description "Name of interface";
         type union {
           type jt:interface-name;
           type string {
             pattern "<.*>|$.*";
           }
         }
         mandatory true;
       }
     }
     output {
       choice output_c {
         case output-tag {
           leaf output {
             type string;
           }
         }
         case multichassis-tag {
           anyxml multi-routing-engine-results;
         }
       }
     }
   }
   rpc request-as-ra-guard-learn-interface {
     description "RA Guard Learn on an Interface";
     input {
       leaf interface {
         description "RA Guard Learn on an interface";
         type union {
           type jt:interface-name;
           type string {
             pattern "<.*>|$.*";
           }
         }
         mandatory true;
       }
       leaf duration {
         description "Time window for RA Guard learn";
         units "seconds";
         type union {
           type string {
             pattern "<.*>|$.*";
           }
           type uint32 {
             range "1 .. 3600";
           }
         }
         mandatory true;
       }
     }
     output {
       choice output_c {
         case output-tag {
           leaf output {
             type string;
           }
         }
         case multichassis-tag {
           anyxml multi-routing-engine-results;
         }
       }
     }
   }
   rpc request-slaac-unblock-all {
     description "Unblock all interfaces";
     output {
       choice output_c {
         case output-tag {
           leaf output {
             type string;
           }
         }
         case multichassis-tag {
           anyxml multi-routing-engine-results;
         }
       }
     }
   }
   rpc request-slaac-unblock-interface {
     description "Name of interface to unblock";
     input {
       leaf interface-name {
         description "Interface-name";
         type union {
           type jt:interface-name;
           type string {
             pattern "<.*>|$.*";
           }
         }
         mandatory true;
       }
     }
     output {
       choice output_c {
         case output-tag {
           leaf output {
             type string;
           }
         }
         case multichassis-tag {
           anyxml multi-routing-engine-results;
         }
       }
     }
   }
   rpc request-static-subscribers-login {
     description "Login static subscribers";
     input {
       choice filter {
         case interface {
           leaf interface {
             description "Interface name";
             type union {
               type jt:interface-name;
               type string {
                 pattern "<.*>|$.*";
               }
             }
           }
         }
         case group {
           leaf group {
             description "Group name";
             type string {
               length "1 .. 64";
             }
           }
         }
       }
     }
   }
   rpc request-static-subscribers-logout {
     description "Logout static subscribers";
     input {
       choice filter {
         case interface {
           leaf interface {
             description "Interface name";
             type union {
               type jt:interface-name;
               type string {
                 pattern "<.*>|$.*";
               }
             }
           }
         }
         case group {
           leaf group {
             description "Group name";
             type string {
               length "1 .. 64";
             }
           }
         }
       }
     }
   }
   rpc request-services-flow-collector-test-file-transfer {
     description "Transfer a test file to the current primary server";
     input {
       leaf filename {
         description "Specify the filename to use";
         type string;
         mandatory true;
       }
       leaf channel {
         description "File transfer channel to use";
         type enumeration {
           enum "channel-zero" {
             description "Channel 0";
           }
           enum "channel-one" {
             description "Channel 1";
           }
         }
       }
       leaf destination-type {
         type enumeration {
           enum "primary" {
             description "Primary server";
           }
           enum "secondary" {
             description "Secondary server";
           }
         }
       }
       leaf interface {
         description "Interface name";
         type string;
         mandatory true;
       }
     }
   }
   rpc request-services-flow-collector-destination {
     description "Change to Destination server";
     input {
       leaf destination-type {
         description "Destination server";
         type enumeration {
           enum "primary" {
             description "Primary server";
           }
           enum "secondary" {
             description "Secondary server";
           }
         }
         mandatory true;
       }
       leaf interface {
         description "Physical interface";
         type union {
           type jt:interface-device;
           type string {
             pattern "<.*>|$.*";
           }
         }
         mandatory true;
       }
       leaf clear-files {
         description "Remove existing files";
         type empty;
       }
       leaf clear-logs {
         description "Remove existing logs";
         type empty;
       }
       leaf how-to-switch {
         description "Options when switching destination";
         default "gracefully";
         type enumeration {
           enum "gracefully" {
             description "Retain existing FTP connections";
           }
           enum "immediately" {
             description "Terminate existing FTP connections";
           }
         }
       }
     }
   }
   rpc request-extensible-subscriber-services-reload-dictionary {
     description "Reload dictionary";
   }
   rpc request-ggsn-restart-node {
     description "Restart GGSN node activity";
   }
   rpc request-ggsn-restart-interface {
     description "Restart GGSN service interface";
     input {
       leaf interface-name {
         description "Name of GGSN service interface";
         type union {
           type jt:interface-device;
           type string {
             pattern "<.*>|$.*";
           }
         }
         mandatory true;
       }
     }
   }
   rpc request-ggsn-stop-node {
     description "Stop GGSN node activity";
     output {
       choice output_c {
         case output-tag {
           leaf output {
             type string;
           }
         }
         case multichassis-tag {
           anyxml multi-routing-engine-results;
         }
       }
     }
   }
   rpc request-ggsn-stop-interface {
     description "Stop GGSN service interface";
     input {
       leaf interface-name {
         description "Name of GGSN service interface";
         type union {
           type jt:interface-device;
           type string {
             pattern "<.*>|$.*";
           }
         }
         mandatory true;
       }
     }
   }
   rpc request-ggsn-terminate-context {
     description "Terminate specified kind of PDP context";
     input {
       leaf imsi {
         description "Identifier for International Mobile Subscriber Identity";
         type string {
         }
         mandatory true;
       }
       leaf nsapi {
         description "Network layer service access point identifier";
         type union {
           type string {
             pattern "<.*>|$.*";
           }
           type uint32 {
             range "0 .. 15";
           }
         }
       }
     }
   }
   rpc request-ggsn-terminate-msisdn-context {
     description "Terminate context for Mobile Station Integrated Services Digital Network";
     input {
       leaf msisdn {
         description "Identifier for MSISDN";
         type string {
         }
         mandatory true;
       }
     }
     output {
       choice output_c {
         case output-tag {
           leaf output {
             type string;
           }
         }
         case multichassis-tag {
           anyxml multi-routing-engine-results;
         }
       }
     }
   }
   rpc request-ggsn-terminate-contexts-apn {
     description "Terminate all PDP contexts in access point name";
     input {
       leaf apn-name {
         description "Name of access point name";
         type string;
         mandatory true;
       }
       leaf user-category {
         description "Name of user category ('default' or 1..63)";
         type string;
       }
     }
   }
   rpc request-ggsn-start-imsi-trace {
     description "Start tracing International Mobile Subscriber Identity";
     input {
       leaf imsi-identifier {
         description "Identifier for IMSI";
         type string {
         }
         mandatory true;
       }
     }
     output {
       choice output_c {
         case output-tag {
           leaf output {
             type string;
           }
         }
         case multichassis-tag {
           anyxml multi-routing-engine-results;
         }
       }
     }
   }
   rpc request-ggsn-start-msisdn-trace {
     description "Start tracing Mobile Station Integrated Services Digital Network";
     input {
       leaf msisdn-identifier {
         description "Identifier for MSISDN";
         type string {
         }
         mandatory true;
       }
     }
     output {
       choice output_c {
         case output-tag {
           leaf output {
             type string;
           }
         }
         case multichassis-tag {
           anyxml multi-routing-engine-results;
         }
       }
     }
   }
   rpc request-ggsn-software-update {
     description "Start GGSN in service update";
   }
   rpc request-ggsn-stop-imsi-trace {
     description "Stop tracing International Mobile Subscriber Identity";
     input {
       leaf imsi-identifier {
         description "Identifier for IMSI";
         type string {
         }
         mandatory true;
       }
     }
     output {
       choice output_c {
         case output-tag {
           leaf output {
             type string;
           }
         }
         case multichassis-tag {
           anyxml multi-routing-engine-results;
         }
       }
     }
   }
   rpc request-ggsn-stop-msisdn-trace {
     description "Stop tracing Mobile Station Integrated Services Digital Network";
     input {
       leaf msisdn-identifier {
         description "Identifier for MSISDN";
         type string {
         }
         mandatory true;
       }
     }
     output {
       choice output_c {
         case output-tag {
           leaf output {
             type string;
           }
         }
         case multichassis-tag {
           anyxml multi-routing-engine-results;
         }
       }
     }
   }
   rpc request-ggsn-stop-trace-activity {
     description "Stop all tracing";
     output {
       choice output_c {
         case output-tag {
           leaf output {
             type string;
           }
         }
         case multichassis-tag {
           anyxml multi-routing-engine-results;
         }
       }
     }
   }
   rpc rdm-reload-dictionary {
     description "Reload dictionary";
     input {
       leaf dictionary-path {
         description "Complete path with dictionary name";
         type jt:filename;
         mandatory true;
       }
     }
   }
   rpc rdm-sd-reconfigure {
     description "Reconfigure service device";
     input {
       leaf service-device-name {
         description "Service device name";
         type string;
         mandatory true;
       }
     }
   }
   rpc start-twamp-client {
     description "Start clients configured with test-start manual";
     input {
       leaf control-connection {
         description "Name of control connection";
         type string {
           length "1 .. 32";
         }
       }
       leaf repeat {
         description "Number of test iterations to be performed";
         type union {
           type string {
             pattern "<.*>|$.*";
           }
           type uint32 {
             range "1 .. 65535";
           }
         }
       }
     }
     output {
       choice output_c {
         case output-tag {
           leaf output {
             type string;
           }
         }
         case multichassis-tag {
           anyxml multi-routing-engine-results;
         }
       }
     }
   }
   rpc stop-twamp-client {
     description "Stops clients configured with test-start manual";
     input {
       leaf control-connection {
         description "Name of control connection";
         type string {
           length "1 .. 32";
         }
       }
     }
     output {
       choice output_c {
         case output-tag {
           leaf output {
             type string;
           }
         }
         case multichassis-tag {
           anyxml multi-routing-engine-results;
         }
       }
     }
   }
   rpc request-secintel-download {
     description "Download security intelligence feed";
     input {
       uses command-forwarding;
     }
   }
   rpc request-secintel-download-status {
     description "Show feed download status";
     input {
       uses command-forwarding;
     }
   }
   rpc request-secintel-uninstall {
     description "Uninstall feed data";
     input {
       uses command-forwarding;
     }
   }
   rpc request-secintel-uninstall-status {
     description "Show uninstall status";
     input {
       uses command-forwarding;
     }
   }
   rpc request-netconf-trace {
     description "NETCONF tracing";
     input {
       leaf on-demand {
         description "Control on-demand tracing";
         type enumeration {
           enum "start" {
             description "Start NETCONF tracing";
           }
           enum "stop" {
             description "Stop NETCONF tracing";
           }
         }
         mandatory true;
       }
     }
     output {
       choice output_c {
         case output-tag {
           leaf output {
             type string;
           }
         }
         case multichassis-tag {
           anyxml multi-routing-engine-results;
         }
       }
     }
   }
   rpc request-service-capture-snapshot {
     description "Request a snapshot of the current packet capture";
     input {
       leaf interface {
         description "Name of adaptive services interface";
         type string;
         mandatory true;
       }
       leaf file {
         type string;
         mandatory true;
       }
     }
   }
   rpc request-service-capture-clear {
     description "Clear the current packet capture";
     input {
       leaf interface {
         description "Name of adaptive services interface";
         type string;
         mandatory true;
       }
     }
   }
   rpc request-services-redundancy-set {
     description "Request services redundancy-set";
     input {
       leaf id {
         description "Set id";
         type union {
           type uint32;
           type string {
             pattern "<.*>|$.*";
           }
         }
         mandatory true;
       }
       leaf trigger {
         description "Trigger a redundancy-event";
         type empty;
         mandatory true;
       }
       leaf redundancy-event {
         description "Redundancy event which needs to be triggered";
         type string;
         mandatory true;
       }
       leaf force {
         description "Trigger event forcefully overriding warnings";
         type empty;
       }
     }
   }
   rpc request-flb-maintenance-down {
     description "Request for destination to go in maintenance-down mode";
     input {
       leaf destination {
         description "Destination VSRX";
         type string;
       }
     }
   }
   rpc request-traffic-loadbalance-real-service-rejoin {
     description "Rejoin for load-balance request";
     input {
       leaf group {
         description "Group name";
         default "all";
         type string;
       }
       leaf instance {
         description "Instance name";
         default "all";
         type string;
       }
       leaf real-service {
         description "Real service name";
         default "all";
         type string;
       }
       leaf virtual-service {
         description "Virtual service name";
         default "all";
         type string;
       }
     }
     output {
       choice output_c {
         case output-tag {
           leaf output {
             type string;
           }
         }
         case multichassis-tag {
           anyxml multi-routing-engine-results;
         }
       }
     }
   }
   rpc request-url-filter-force-dns-resolution-all {
     description "All profiles";
   }
   rpc request-url-filter-force-dns-resolution-profile {
     description "Profile name";
     input {
       leaf profile-name {
         description "Profile name";
         type string;
         mandatory true;
       }
       leaf url-filter-template {
         description "Template name";
         type string;
       }
     }
   }
   rpc request-url-filter-database-update {
     description "Update the specific url-filter-database";
     input {
       leaf file {
         description "URL filter database file";
         type string;
         mandatory true;
       }
     }
   }
   rpc request-dns-filter-database-update {
     description "Update the specific dns-filter-database";
     input {
       choice file_type {
         case file {
           leaf file {
             description "DNS filter database file";
             type string;
           }
         }
         case multi-tenant-file {
           leaf multi-tenant-file {
             description "Multi-tenant-file";
             type enumeration {
               enum "plain-text" {
                 description "DNS filter plain-text database file ";
               }
               enum "hashed" {
                 description "DNS filter encrypted database file ";
               }
             }
           }
         }
       }
     }
   }
   rpc request-url-filter-validate {
     description "Validate the web-filter database";
     input {
       choice file {
         case all {
           leaf all {
             description "Validate the url-filter database for all profiles";
             type empty;
           }
         }
         case url-filter-file-name {
           leaf url-filter-file-name {
             description "URL filter database file";
             type string;
           }
         }
         case dns-filter-file-name {
           leaf dns-filter-file-name {
             description "DNS filter database file";
             type string;
           }
         }
       }
       leaf hash-method {
         description "Hash method";
         type enumeration {
           enum "hmac-md5-96" {
             description "HMAC-MD5-96 algorithm";
           }
           enum "hmac-sha1-96" {
             description "HMAC-SHA1-96 algorithm";
           }
           enum "hmac-sha2-256" {
             description "HMAC-SHA2-256 algorithm";
           }
           enum "hmac-sha-256-128" {
             description "HMAC-SHA-256-128 algorithm";
           }
         }
       }
       leaf hash-key {
         description "Hash key";
         type string;
       }
     }
   }
   rpc request-services-url-filter-delete-gencfg-data {
     description "Gencfg data";
   }
   rpc request-lacp-link-protection-switchover {
     description "Request LACP link protection switchover";
     input {
       leaf interface-name {
         description "Name of AE interface";
         type union {
           type jt:interface-wildcard;
           type string {
             pattern "<.*>|$.*";
           }
         }
         mandatory true;
       }
     }
     output {
       container lacp-link-switchover {
         uses lacp-link-switchover-block;
       }
     }
   }
   rpc request-message {
     description "Send text message to other users";
     input {
       leaf user {
         description "Name of user (account@terminal) to receive message";
         type string;
         mandatory true;
       }
       leaf terminal {
         description "Device name of target terminal (/dev/ttyXX)";
         type string;
       }
       leaf message {
         description "Text of message";
         type string;
       }
     }
     output {
       choice output_c {
         case output-tag {
           leaf output {
             type string;
           }
         }
         case multichassis-tag {
           anyxml multi-routing-engine-results;
         }
       }
     }
   }
   rpc request-message-all {
     description "Send message to all logged-in users";
     input {
       leaf message {
         description "Text of message";
         type string;
       }
     }
     output {
       choice output_c {
         case output-tag {
           leaf output {
             type string;
           }
         }
         case multichassis-tag {
           anyxml multi-routing-engine-results;
         }
       }
     }
   }
   rpc request-compute-node-cleanup-log {
     description "Compute node cleanup /var/tmp and /var/log";
     input {
       uses command-forwarding;
       leaf compute-cluster {
         description "Compute cluster name";
         type string {
           length "1 .. 15";
         }
       }
       leaf compute-node {
         description "Compute node name";
         type string {
           length "1 .. 15";
         }
       }
     }
     output {
       choice output_c {
         case output-tag {
           leaf output {
             type string;
           }
         }
         case multichassis-tag {
           anyxml multi-routing-engine-results;
         }
       }
     }
   }
   rpc request-compute-node-file-copy {
     description "Copy file from host to vjunos";
     input {
       leaf host-path {
         description "Copy files related to";
         type enumeration {
           enum "crash" {
             description "Files in /var/crash";
           }
           enum "log" {
             description "Files in /var/log";
           }
         }
         mandatory true;
       }
       leaf from-jhost {
         description "Host file name";
         type string {
         }
         mandatory true;
       }
       leaf to-vjunos {
         description "Junos file name";
         type string;
         mandatory true;
       }
     }
     output {
       choice output_c {
         case output-tag {
           leaf output {
             type string;
           }
         }
         case multichassis-tag {
           anyxml multi-routing-engine-results;
         }
       }
     }
   }
   rpc request-guest-virtual-machine-package-copy {
     description "Copy guest virtual-machine package to Junos";
     input {
       leaf package-name {
         description "Name of the virtual-machine package";
         type string;
         mandatory true;
       }
       leaf destination-path {
         description "Path to the destination directory in Junos";
         type string;
         mandatory true;
       }
     }
     output {
       choice output_c {
         case output-tag {
           leaf output {
             type string;
           }
         }
         case multichassis-tag {
           anyxml multi-routing-engine-results;
         }
       }
     }
   }
   rpc request-vmhost-poweroff {
     description "Power off the software on RE";
     input {
       leaf other-routing-engine {
         description "Power off other Routing Engine";
         type empty;
       }
     }
     output {
       choice output_c {
         case output-tag {
           leaf output {
             type string;
           }
         }
         case multichassis-tag {
           anyxml multi-routing-engine-results;
         }
       }
     }
   }
   rpc request-vmhost-halt {
     description "Halt the software on RE";
     input {
       uses command-forwarding;
     }
     output {
       choice output_c {
         case output-tag {
           leaf output {
             type string;
           }
         }
         case multichassis-tag {
           anyxml multi-routing-engine-results;
         }
       }
     }
   }
   rpc request-vmhost-power-on-other-re {
     description "Power on the system";
     input {
       leaf other-routing-engine {
         description "Power on other Routing Engine";
         type empty;
         mandatory true;
       }
     }
     output {
       choice output_c {
         case output-tag {
           leaf output {
             type string;
           }
         }
         case multichassis-tag {
           anyxml multi-routing-engine-results;
         }
       }
     }
   }
   rpc request-vmhost-power-cycle {
     description "Power cycle the vmhost";
     input {
       uses command-forwarding;
     }
     output {
       choice output_c {
         case output-tag {
           leaf output {
             type string;
           }
         }
         case multichassis-tag {
           anyxml multi-routing-engine-results;
         }
       }
     }
   }
   rpc request-vmhost-power-cycle-cb {
     description "Power Cycle Chassis";
     output {
       choice output_c {
         case output-tag {
           leaf output {
             type string;
           }
         }
         case multichassis-tag {
           anyxml multi-routing-engine-results;
         }
       }
     }
   }
   rpc request-vmhost-power-cycle-re {
     description "Power Cycle Chassis";
     output {
       choice output_c {
         case output-tag {
           leaf output {
             type string;
           }
         }
         case multichassis-tag {
           anyxml multi-routing-engine-results;
         }
       }
     }
   }
   rpc request-vmhost-reboot {
     description "Reboot RE vmhost";
     input {
       uses command-forwarding;
       leaf media {
         type enumeration {
           enum "disk1" {
             description "Boot off disk1(primary) device";
           }
           enum "disk2" {
             description "Boot off disk2(backup) device";
           }
           enum "network" {
             description "Network boot via PXE";
           }
           enum "usb" {
             description "Boot off USB device";
           }
         }
       }
       leaf partition {
         type enumeration {
           enum "primary" {
             description "Boot from primary partition";
           }
           enum "alternate" {
             description "Boot from alternate partition";
           }
         }
       }
       leaf in {
         description "Number of minutes to delay before reboot operation";
         type union {
           type string {
             pattern "<.*>|$.*";
           }
           type uint32 {
             range "0 .. 100";
           }
         }
       }
     }
     output {
       choice output_c {
         case output-tag {
           leaf output {
             type string;
           }
         }
         case multichassis-tag {
           anyxml multi-routing-engine-results;
         }
       }
     }
   }
   rpc request-vmhost-file-cleanup {
     description "RE vmhost cleanup /var/tmp, /var/crash and /var/log";
     input {
       uses command-forwarding;
     }
     output {
       choice output_c {
         case output-tag {
           leaf output {
             type string;
           }
         }
         case multichassis-tag {
           anyxml multi-routing-engine-results;
         }
       }
     }
   }
   rpc request-vmhost-file-cleanup-dry-run {
     description "Only list the cleanup candidates, do not remove them";
     output {
       choice output_c {
         case output-tag {
           leaf output {
             type string;
           }
         }
         case multichassis-tag {
           anyxml multi-routing-engine-results;
         }
       }
     }
   }
   rpc request-vmhost-file-copy {
     description "Copy file from vmhost to vjunos";
     input {
       leaf node-path {
         description "Copy files related to";
         type enumeration {
           enum "crash" {
             description "Files in /var/crash";
           }
           enum "log" {
             description "Files in /var/log";
           }
         }
         mandatory true;
       }
       leaf from-jnode {
         description "Host file name";
         type string;
         mandatory true;
       }
       leaf to-vjunos {
         description "Junos file name";
         type string;
         mandatory true;
       }
     }
     output {
       choice output_c {
         case output-tag {
           leaf output {
             type string;
           }
         }
         case multichassis-tag {
           anyxml multi-routing-engine-results;
         }
       }
     }
   }
   rpc request-copy-vjunos-to-jnode {
     description "Copy file from vjunos to vmhost";
     input {
       leaf from-vjunos {
         description "Junos file name";
         type string;
         mandatory true;
       }
       leaf to-jnode {
         description "Host file name";
         type string;
         mandatory true;
       }
     }
     output {
       choice output_c {
         case output-tag {
           leaf output {
             type string;
           }
         }
         case multichassis-tag {
           anyxml multi-routing-engine-results;
         }
       }
     }
   }
   rpc request-copy-jnode-to-vjunos {
     description "Copy file from vmhost to vjunos";
     input {
       leaf from-jnode {
         description "Host file name";
         type string;
         mandatory true;
       }
       leaf to-vjunos {
         description "Junos file name";
         type string;
         mandatory true;
       }
     }
     output {
       choice output_c {
         case output-tag {
           leaf output {
             type string;
           }
         }
         case multichassis-tag {
           anyxml multi-routing-engine-results;
         }
       }
     }
   }
   rpc request-vmhost-package-add {
     description "Add extension or upgrade package";
     input {
       leaf i40-driver {
         description "Upgrade only the i40 driver";
         type empty;
       }
       choice package-options {
         case set {
           leaf-list set {
             ordered-by user;
             description "List of URLs or pathnames corresponding to packages";
             type jt:filename;
           }
         }
         case package-name {
           leaf package-name {
             description "URL or pathname of package";
             type jt:filename;
           }
         }
       }
       leaf reboot {
         description "Reboot RE vmhost after adding package";
         type empty;
       }
       leaf in {
         description "Number of minutes to delay before reboot operation";
         type union {
           type string {
             pattern "<.*>|$.*";
           }
           type uint32 {
             range "0 .. 100";
           }
         }
       }
       choice re-choice {
         case re0 {
           leaf re0 {
             description "Install package on RE0";
             type empty;
           }
         }
         case re1 {
           leaf re1 {
             description "Install package on RE1";
             type empty;
           }
         }
       }
       choice validate_choice {
         case no-validate {
           leaf no-validate {
             description "Don't check compatibility with current configuration";
             type empty;
           }
         }
       }
       choice chassis {
         case dont-forward {
           leaf dont-forward {
             type empty;
           }
         }
       }
       leaf issu-internal {
         description "Internally executed by mgd, to allow software adds during issu";
         type empty;
       }
       leaf upgrade-to-model {
         description "Name of the model to upgrade to";
         type string;
       }
       leaf unlink {
         description "Remove the package after successful installation";
         type empty;
       }
     }
     output {
       choice output_c {
         case output-tag {
           leaf output {
             type string;
           }
         }
         case multichassis-tag {
           anyxml multi-routing-engine-results;
         }
       }
     }
   }
   rpc request-vmhost-package-delete {
     description "Remove extension or upgrade package";
     input {
       leaf force {
         description "Force removal of package (ignore warnings)";
         type empty;
       }
       choice package-options {
         case set {
           leaf-list set {
             ordered-by user;
             description "List of package name";
             type string;
           }
         }
         case package-name {
           leaf package-name {
             description "Name of package";
             type string;
           }
         }
         case upgrade-group {
           leaf upgrade-group {
             description "Satellite upgrade group name";
             type string;
           }
         }
         case version {
           leaf version {
             description "Version of satellite package";
             type string;
           }
         }
       }
       leaf reboot {
         description "Reboot system after package delete";
         type empty;
       }
     }
     output {
       choice output_c {
         case output-tag {
           leaf output {
             type string;
           }
         }
         case multichassis-tag {
           anyxml multi-routing-engine-results;
         }
       }
     }
   }
   rpc abort-vmhost-in-service-upgrade {
     description "Abort in-service software upgrade";
     output {
       choice output_c {
         case output-tag {
           leaf output {
             type string;
           }
         }
         case multichassis-tag {
           anyxml multi-routing-engine-results;
         }
       }
     }
   }
   rpc request-vmhost-package-in-service-upgrade {
     description "In-service software upgrade";
     input {
       leaf package-name {
         description "URL or pathname of package";
         type jt:filename;
         mandatory true;
       }
       leaf no-old-master-upgrade {
         description "Don't upgrade the old master after switchover";
         type empty;
       }
       leaf verbose {
         description "Enable detailed output";
         type empty;
       }
       leaf reboot {
         description "Reboot RE vmhost after adding package";
         type empty;
       }
       leaf enhanced-mode {
         description "Try to upgrade without any traffic loss";
         type empty;
       }
     }
     output {
       choice output_c {
         case output-tag {
           leaf output {
             type string;
           }
         }
         case multichassis-tag {
           anyxml multi-routing-engine-results;
         }
       }
     }
   }
   rpc request-vmhost-nonstop-upgrade {
     description "Nonstop software upgrade";
     input {
       leaf force-host {
         description "Force addition of host os package (ignore version check)";
         type empty;
       }
       leaf no-auto-recovery {
         description "Will not recover in case of NSSU failure";
         type empty;
       }
       choice package-options {
         case set {
           leaf-list set {
             ordered-by user;
             description "List of URLs or pathnames corresponding to packages";
             type jt:filename;
           }
         }
         case package-name {
           leaf package-name {
             description "URL or pathname of package";
             type jt:filename;
           }
         }
       }
       leaf no-copy {
         description "Don't save copies of package files";
         status deprecated;
         type empty;
       }
       leaf unlink {
         description "Remove the package after successful installation";
         status deprecated;
         type empty;
       }
       leaf no-validate {
         description "Don't check compatibility with current configuration";
         type empty;
       }
     }
     output {
       choice output_c {
         case output-tag {
           leaf output {
             type string;
           }
         }
         case multichassis-tag {
           anyxml multi-routing-engine-results;
         }
       }
     }
   }
   rpc request-vmhost-package-validate {
     description "Verify package compatibility with current configuration";
     input {
       choice package-options {
         case package-name {
           leaf package-name {
             description "URL or pathname of package";
             type jt:filename;
           }
         }
       }
       choice chassis {
         case member {
           leaf member {
             description "Validate package on member";
             type union {
               type string {
                 pattern "<.*>|$.*";
               }
               type uint32;
             }
           }
         }
         case dont-forward {
           leaf dont-forward {
             type empty;
           }
         }
       }
     }
     output {
       choice output_c {
         case output-tag {
           leaf output {
             type string;
           }
         }
         case multichassis-tag {
           anyxml multi-routing-engine-results;
         }
       }
     }
   }
   rpc request-vmhost-package-rollback {
     description "Attempt to roll back to previous set of packages";
     input {
       uses command-forwarding;
       leaf reboot {
         description "Reboot system after rollback";
         type empty;
       }
     }
     output {
       choice output_c {
         case output-tag {
           leaf output {
             type string;
           }
         }
         case actual-tag-1 {
           anyxml rollback-information;
         }
         case multichassis-tag {
           anyxml multi-routing-engine-results;
         }
       }
     }
   }
   rpc request-vmhost-jdm-package-add {
     description "Install fresh JDM package or upgrade package";
     input {
       leaf package-name {
         description "JDM package name";
         type jt:filename;
         mandatory true;
       }
       leaf force {
         description "Force package add";
         type empty;
       }
     }
     output {
       choice output_c {
         case output-tag {
           leaf output {
             type string;
           }
         }
         case multichassis-tag {
           anyxml multi-routing-engine-results;
         }
       }
     }
   }
   rpc request-vmhost-jdm-package-delete {
     description "Remove currently installed JDM package";
     output {
       choice output_c {
         case output-tag {
           leaf output {
             type string;
           }
         }
         case multichassis-tag {
           anyxml multi-routing-engine-results;
         }
       }
     }
   }
   rpc request-package-vmhost-jdm-start {
     description "Start the JDM";
     output {
       choice output_c {
         case output-tag {
           leaf output {
             type string;
           }
         }
         case multichassis-tag {
           anyxml multi-routing-engine-results;
         }
       }
     }
   }
   rpc request-package-vmhost-jdm-stop {
     description "Stop the JDM";
     output {
       choice output_c {
         case output-tag {
           leaf output {
             type string;
           }
         }
         case multichassis-tag {
           anyxml multi-routing-engine-results;
         }
       }
     }
   }
   rpc request-vmhost-jdm-login {
     description "Login to JDM";
     output {
       choice output_c {
         case output-tag {
           leaf output {
             type string;
           }
         }
         case multichassis-tag {
           anyxml multi-routing-engine-results;
         }
       }
     }
   }
   rpc request-vmhost-snapshot {
     description "Create a vmhost recovery snapshot";
     input {
       uses command-forwarding;
       leaf no-confirm {
         description "Do not ask for confirmation";
         type empty;
       }
     }
   }
   rpc request-vmhost-snapshot-config {
     description "Sychronise Configuration between the disks";
     input {
       uses command-forwarding;
     }
   }
   rpc request-vmhost-snapshot-partition {
     description "Partition the target media";
     input {
       uses command-forwarding;
     }
   }
   rpc request-vmhost-snapshot-recovery {
     description "Recover the primary media from snapshot";
     input {
       uses command-forwarding;
     }
   }
   rpc request-vmhost-snapshot-recovery-partition {
     description "Partition the media before snapshot";
     input {
       uses command-forwarding;
     }
   }
   rpc request-vmhost-zeroize {
     description "Erase all data, including configuration and log files";
     input {
       uses command-forwarding;
     }
   }
   rpc request-vmhost-hard-disk-test {
     description "Run smartd self tests on hard disks";
     input {
       choice test-type {
         case short {
           leaf short {
             description "Run short test";
             type empty;
           }
         }
         case long {
           leaf long {
             description "Run SMART extended self test";
             type empty;
           }
         }
         case show-status {
           leaf show-status {
             description "Display status of test";
             type empty;
           }
         }
       }
       leaf disk {
         description "Name of hard disk";
         type string;
       }
     }
     output {
       container raid-information {
         uses raid-information-block;
       }
     }
   }
   rpc request-vmhost-last-known-good-bios {
     description "Backup/Restore last known good bios image";
   }
   rpc request-vmhost-last-known-good-bios-backup {
     description "Backup last known good bios";
     input {
       leaf path {
         description "Path to take backup";
         type string;
       }
     }
     output {
       choice output_c {
         case output-tag {
           leaf output {
             type string;
           }
         }
         case multichassis-tag {
           anyxml multi-routing-engine-results;
         }
       }
     }
   }
   rpc request-vmhost-last-known-good-bios-restore {
     description "Restore last known good bios";
     input {
       leaf path {
         description "Path which contains last known bios";
         type string;
       }
     }
     output {
       choice output_c {
         case output-tag {
           leaf output {
             type string;
           }
         }
         case multichassis-tag {
           anyxml multi-routing-engine-results;
         }
       }
     }
   }
   rpc request-snmp-spoof-trap {
     description "Generate artificial SNMP notification";
     input {
       leaf trap {
         description "The name of the trap to spoof";
         type string;
         mandatory true;
       }
       leaf variable-bindings {
         description "The list of variables & values to include in the trap";
         type string;
       }
     }
     output {
       container snmp-spoof-trap-results {
         uses snmp-spoof-trap-results-block;
       }
     }
   }
   rpc request-snmp-utility-mib-set {
     description "Set values in utility mib objects";
     input {
       leaf object-type {
         type enumeration {
           enum "counter" {
             description "Set counter value";
           }
           enum "counter64" {
             description "Set 64 bit counter value";
           }
           enum "integer" {
             description "Set signed integer value";
           }
           enum "unsigned-integer" {
             description "Set unsigned integer value";
           }
           enum "string" {
             description "Set string value";
           }
         }
         mandatory true;
       }
       leaf instance {
         type string {
           length "1 .. 80";
         }
         mandatory true;
       }
       leaf object-value {
         type string;
         mandatory true;
       }
     }
     output {
       container snmp-utility-mib-results {
         uses snmp-utility-mib-results-block;
       }
     }
   }
   rpc request-snmp-utility-mib-clear {
     description "Clear values in utility mib objects";
     input {
       leaf object-type {
         type enumeration {
           enum "counter" {
             description "Set counter value";
           }
           enum "counter64" {
             description "Set 64 bit counter value";
           }
           enum "integer" {
             description "Set signed integer value";
           }
           enum "unsigned-integer" {
             description "Set unsigned integer value";
           }
           enum "string" {
             description "Set string value";
           }
         }
         mandatory true;
       }
       leaf instance {
         type string {
           length "1 .. 80";
         }
         mandatory true;
       }
     }
     output {
       container snmp-utility-mib-results {
         uses snmp-utility-mib-results-block;
       }
     }
   }
   rpc request-ancp-oam-information {
     description "Request ANCP operation, administration, and management";
   }
   rpc request-ancp-oam-neighbor-information {
     description "Neighbor identifier";
     input {
       choice neighbor-opts {
         case system-name {
           leaf system-name {
             description "MAC address of the neighbor";
             type string;
           }
         }
         case ip-address {
           leaf ip-address {
             description "IP address of the neighbor";
             type jt:ipaddr;
           }
         }
       }
       leaf subscriber {
         description "Subscriber identifier";
         type string;
         mandatory true;
       }
       leaf count {
         description "Number of local loopback messages";
         default "1";
         type union {
           type string {
             pattern "<.*>|$.*";
           }
           type uint16 {
             range "1 .. 32";
           }
         }
       }
       leaf timeout {
         description "Timeout for loopback response from the neighbor";
         default "30";
         units "seconds";
         type union {
           type string {
             pattern "<.*>|$.*";
           }
           type uint32 {
             range "1 .. 255";
           }
         }
       }
     }
   }
   rpc request-ancp-oam-interface-information {
     description "ANCP interface specific options";
     input {
       choice interface-opts {
         case interface-name {
           leaf interface-name {
             description "Name of ANCP interface";
             type string;
           }
         }
         case interface-set {
           leaf interface-set {
             description "Name of ANCP interface set";
             type string {
             }
           }
         }
       }
       leaf count {
         description "Number of local loopback messages";
         default "1";
         type union {
           type string {
             pattern "<.*>|$.*";
           }
           type uint16 {
             range "1 .. 32";
           }
         }
       }
       leaf timeout {
         description "Timeout for loopback response from the neighbor";
         default "30";
         units "seconds";
         type union {
           type string {
             pattern "<.*>|$.*";
           }
           type uint32 {
             range "1 .. 255";
           }
         }
       }
     }
   }
   rpc request-ancp-oam-port-up {
     description "ANCP port-up processing";
     input {
       choice interface-opts {
         case neighbor {
           leaf neighbor {
             description "IP address of the neighbor";
             type jt:ipaddr;
           }
         }
         case subscriber-interface {
           leaf subscriber-interface {
             description "Subscriber-facing interface";
             type string;
           }
         }
       }
       leaf circuit-id {
         description "Access loop circuit id";
         type string {
         }
         mandatory true;
       }
       leaf remote-id {
         description "Access loop remote id";
         type string {
         }
         mandatory true;
       }
       leaf outer-vlan-id {
         description "Access aggregation circuit id binary";
         type union {
           type string {
             pattern "<.*>|$.*";
           }
           type uint16 {
             range "1 .. 4094";
           }
         }
         mandatory true;
       }
     }
   }
   rpc request-ancp-oam-port-down {
     description "ANCP port-down processing";
     input {
       choice interface-opts {
         case neighbor {
           leaf neighbor {
             description "IP address of the neighbor";
             type jt:ipaddr;
           }
         }
         case subscriber-interface {
           leaf subscriber-interface {
             description "Subscriber-facing interface";
             type string;
           }
         }
       }
       leaf circuit-id {
         description "Access loop circuit id";
         type string {
         }
       }
       leaf remote-id {
         description "Access loop remote id";
         type string {
         }
       }
       leaf outer-vlan-id {
         description "Access aggregation circuit id binary";
         type union {
           type string {
             pattern "<.*>|$.*";
           }
           type uint16 {
             range "1 .. 4094";
           }
         }
       }
     }
   }
   rpc request-auto-configuration-reconnect-pending {
     description "Request reconnect of pending out-of-band sessions";
     output {
       choice output_c {
         case output-tag {
           leaf output {
             type string;
           }
         }
         case multichassis-tag {
           anyxml multi-routing-engine-results;
         }
       }
     }
   }
   rpc request-system-mode-change {
     description "Change member's current system-mode configuration";
     input {
       uses command-forwarding;
       leaf mode {
         type enumeration {
           enum "mode-104port" {
             description "104port-mode. This will restart PFE";
           }
           enum "non-oversubscribed-mode" {
             description "Non-oversubscribed-mode. This will restart PFE";
           }
           enum "flexi-pic-mode" {
             description "Flexi-pic-mode. This will restart PFE";
           }
           enum "mode-2x100G" {
             description "PIC mode configuration 2x100G. This will restart PFE and disable VCP ports";
           }
           enum "default-mode" {
             description "Default-mode is oversubscribed mode. This will restart PFE";
           }
         }
         mandatory true;
       }
     }
     output {
       choice output_c {
         case output-tag {
           leaf output {
             type string;
           }
         }
         case multichassis-tag {
           anyxml multi-routing-engine-results;
         }
       }
     }
   }
   rpc request-chassis-device-recorder {
     description "Device recorder configuration";
     input {
       uses command-forwarding;
       leaf cmd {
         type enumeration {
           enum "enable" {
             description "Enable device recorder";
           }
           enum "disable" {
             description "Disable device recorder";
           }
         }
         mandatory true;
       }
     }
     output {
       choice output_c {
         case output-tag {
           leaf output {
             type string;
           }
         }
         case multichassis-tag {
           anyxml multi-routing-engine-results;
         }
       }
     }
   }
   rpc request-chassis-mic {
     description "Change Media Interface Card status";
     input {
       uses command-forwarding;
       leaf fpc-slot {
         description "Slot number of FPC that houses MIC";
         type union {
           type string {
             pattern "<.*>|$.*";
           }
           type uint32;
         }
         mandatory true;
       }
       leaf mic-slot {
         description "MIC slot number";
         type union {
           type string {
             pattern "<.*>|$.*";
           }
           type uint32;
         }
         mandatory true;
       }
       leaf cmd {
         type enumeration {
           enum "offline" {
             description "Take MIC offline";
           }
           enum "online" {
             description "Bring MIC online";
           }
         }
         mandatory true;
       }
     }
     output {
       container chassis-mic-state {
         uses chassis-mic-state-block;
       }
     }
   }
   rpc request-chassis-optics {
     description "Change linecard optics status";
     input {
       uses command-forwarding;
       leaf fpc-slot {
         description "Slot number of FPC that houses optics";
         type union {
           type string {
             pattern "<.*>|$.*";
           }
           type uint32;
         }
         mandatory true;
       }
       leaf reactivate {
         description "Reactivate linecard optics";
         type empty;
         mandatory true;
       }
     }
     output {
       container chassis-optics-state {
         uses chassis-optics-state-block;
       }
     }
   }
   rpc request-chassis-pic {
     description "Change Physical Interface Card status";
     input {
       uses command-forwarding;
       leaf fpc-slot {
         description "Slot number of FPC that houses PIC";
         type union {
           type string {
             pattern "<.*>|$.*";
           }
           type uint32;
         }
         mandatory true;
       }
       leaf pic-slot {
         description "PIC slot number";
         type union {
           type string {
             pattern "<.*>|$.*";
           }
           type uint32;
         }
         mandatory true;
       }
       leaf cmd {
         type enumeration {
           enum "offline" {
             description "Take PIC offline";
           }
           enum "online" {
             description "Bring PIC online";
           }
         }
         mandatory true;
       }
     }
     output {
       choice output_c {
         case output-tag {
           leaf output {
             type string;
           }
         }
         case multichassis-tag {
           anyxml multi-routing-engine-results;
         }
       }
     }
   }
   rpc request-chassis-port-led-switch-on {
     description "Switch on LED";
     input {
       uses command-forwarding;
       leaf fpc-slot {
         description "Slot number of FPC that houses PIC";
         type union {
           type string {
             pattern "<.*>|$.*";
           }
           type uint32;
         }
         mandatory true;
       }
       leaf pic-slot {
         description "PIC slot number";
         type union {
           type string {
             pattern "<.*>|$.*";
           }
           type uint32;
         }
         mandatory true;
       }
       container port {
         leaf all-10g {
           description "All 10Gig ports";
           type empty;
         }
         leaf all-25g {
           description "All 25Gig ports";
           type empty;
         }
         leaf all-50g {
           description "All 50Gig ports";
           type empty;
         }
         leaf all-40g {
           description "All 40Gig ports";
           type empty;
         }
         leaf all-100g {
           description "All 100Gig ports";
           type empty;
         }
         leaf all-400g {
           description "All 400Gig ports";
           type empty;
         }
         leaf all-200g {
           description "All 200Gig ports";
           type empty;
         }
         leaf all-800g {
           description "All 800Gig ports";
           type empty;
         }
         leaf all-ports {
           description "All PIC ports";
           type empty;
         }
         leaf pic-port {
           description "PIC port number";
           type union {
             type string {
               pattern "<.*>|$.*";
             }
             type uint32;
           }
         }
       }
       leaf duration {
         description "Duration (in seconds) to perform LED blinking";
         type union {
           type string {
             pattern "<.*>|$.*";
           }
           type uint32 {
             range "1 .. 65535";
           }
         }
       }
     }
     output {
       choice output_c {
         case output-tag {
           leaf output {
             type string;
           }
         }
         case multichassis-tag {
           anyxml multi-routing-engine-results;
         }
       }
     }
   }
   rpc request-chassis-port-led-switch-off {
     description "Switch off LED";
     input {
       uses command-forwarding;
       leaf fpc-slot {
         description "Slot number of FPC that houses PIC";
         type union {
           type string {
             pattern "<.*>|$.*";
           }
           type uint32;
         }
         mandatory true;
       }
       leaf pic-slot {
         description "PIC slot number";
         type union {
           type string {
             pattern "<.*>|$.*";
           }
           type uint32;
         }
         mandatory true;
       }
       container port {
         leaf all-10g {
           description "All 10Gig ports";
           type empty;
         }
         leaf all-25g {
           description "All 25Gig ports";
           type empty;
         }
         leaf all-50g {
           description "All 50Gig ports";
           type empty;
         }
         leaf all-40g {
           description "All 40Gig ports";
           type empty;
         }
         leaf all-100g {
           description "All 100Gig ports";
           type empty;
         }
         leaf all-400g {
           description "All 400Gig ports";
           type empty;
         }
         leaf all-200g {
           description "All 200Gig ports";
           type empty;
         }
         leaf all-800g {
           description "All 800Gig ports";
           type empty;
         }
         leaf all-ports {
           description "All PIC ports";
           type empty;
         }
         leaf pic-port {
           description "PIC port number";
           type union {
             type string {
               pattern "<.*>|$.*";
             }
             type uint32;
           }
         }
       }
     }
     output {
       choice output_c {
         case output-tag {
           leaf output {
             type string;
           }
         }
         case multichassis-tag {
           anyxml multi-routing-engine-results;
         }
       }
     }
   }
   rpc request-redundancy-feb {
     description "Change Forwarding Engine Board redundancy status";
     input {
       leaf slot {
         description "FEB slot number";
         type union {
           type string {
             pattern "<.*>|$.*";
           }
           type uint32;
         }
         mandatory true;
       }
       leaf cmd {
         type enumeration {
           enum "switch-to-backup" {
             description "Switch mastership to other FEB";
           }
           enum "revert-from-backup" {
             description "Revert mastership back to configured default";
           }
         }
         mandatory true;
       }
     }
     output {
       choice output_c {
         case output-tag {
           leaf output {
             type string;
           }
         }
         case multichassis-tag {
           anyxml multi-routing-engine-results;
         }
       }
     }
   }
   rpc request-chassis-fpc {
     description "Change Flexible PIC Concentrator status";
     input {
       uses command-forwarding;
       leaf slot {
         description "FPC slot number";
         type union {
           type string {
             pattern "<.*>|$.*";
           }
           type uint32;
         }
         mandatory true;
       }
       leaf pfe-instance {
         description "PFE-instance number";
         type union {
           type string {
             pattern "<.*>|$.*";
           }
           type uint32;
         }
       }
       leaf pfe {
         description "Pfe id number";
         type union {
           type string {
             pattern "<.*>|$.*";
           }
           type uint32;
         }
       }
       leaf slc {
         description "SLC ID";
         type union {
           type string {
             pattern "<.*>|$.*";
           }
           type uint32 {
             range "1 .. 2";
           }
         }
       }
       leaf force {
         description "Forcefully restart the FPC";
         type empty;
       }
       leaf cmd {
         type enumeration {
           enum "offline" {
             description "Take FPC or PFE-instance offline";
           }
           enum "online" {
             description "Bring FPC or PFE-instance online";
           }
           enum "restart" {
             description "Restart FPC or PFE-instance";
           }
         }
         mandatory true;
       }
       leaf tag {
         description "Firmware tag for online-reload";
         type union {
           type int32;
           type string {
             pattern "<.*>|$.*";
           }
         }
       }
       leaf no-confirm {
         description "Do not ask for confirmation";
         type empty;
       }
     }
     output {
       container chassis-fpc-state {
         uses chassis-fpc-state-block;
       }
     }
   }
   rpc request-fpc-optical-module {
     description "Change optical module status";
     output {
       choice output_c {
         case output-tag {
           leaf output {
             type string;
           }
         }
         case multichassis-tag {
           anyxml multi-routing-engine-results;
         }
       }
     }
   }
   rpc request-fpc-optical-module-amplifier-chain {
     description "Change amplifier-chain status";
     output {
       choice output_c {
         case output-tag {
           leaf output {
             type string;
           }
         }
         case multichassis-tag {
           anyxml multi-routing-engine-results;
         }
       }
     }
   }
   rpc request-fpc-optical-module-ila {
     description "Change inline-amplifier status";
     output {
       choice output_c {
         case output-tag {
           leaf output {
             type string;
           }
         }
         case multichassis-tag {
           anyxml multi-routing-engine-results;
         }
       }
     }
   }
   rpc request-fpc-optical-module-ila-firmware-upgrade {
     description "Change firmware bundle of inline-amplifier";
     input {
       leaf fpc-slot {
         description "FPC slot number";
         type union {
           type string {
             pattern "<.*>|$.*";
           }
           type uint32;
         }
         mandatory true;
       }
       leaf ila-number {
         description "In-line amplifier number";
         type union {
           type uint32;
           type string {
             pattern "<.*>|$.*";
           }
         }
         mandatory true;
       }
     }
     output {
       choice output_c {
         case output-tag {
           leaf output {
             type string;
           }
         }
         case multichassis-tag {
           anyxml multi-routing-engine-results;
         }
       }
     }
   }
   rpc request-fpc-optical-module-ila-soft-reset {
     description "Perform soft-reset on inline-amplifier";
     input {
       leaf fpc-slot {
         description "FPC slot number";
         type union {
           type string {
             pattern "<.*>|$.*";
           }
           type uint32;
         }
         mandatory true;
       }
       leaf ila-number {
         description "In-line amplifier number";
         type union {
           type uint32;
           type string {
             pattern "<.*>|$.*";
           }
         }
         mandatory true;
       }
     }
     output {
       choice output_c {
         case output-tag {
           leaf output {
             type string;
           }
         }
         case multichassis-tag {
           anyxml multi-routing-engine-results;
         }
       }
     }
   }
   rpc request-fpc-optical-module-ila-hard-reset {
     description "Perform hard-reset on inline-amplifier";
     input {
       leaf fpc-slot {
         description "FPC slot number";
         type union {
           type string {
             pattern "<.*>|$.*";
           }
           type uint32;
         }
         mandatory true;
       }
       leaf ila-number {
         description "In-line amplifier number";
         type union {
           type uint32;
           type string {
             pattern "<.*>|$.*";
           }
         }
         mandatory true;
       }
     }
     output {
       choice output_c {
         case output-tag {
           leaf output {
             type string;
           }
         }
         case multichassis-tag {
           anyxml multi-routing-engine-results;
         }
       }
     }
   }
   rpc request-fpc-optical-module-firmware-upgrade {
     description "Change firmware bundle of optical module";
     input {
       leaf fpc-slot {
         description "FPC slot number";
         type union {
           type string {
             pattern "<.*>|$.*";
           }
           type uint32;
         }
         mandatory true;
       }
     }
     output {
       choice output_c {
         case output-tag {
           leaf output {
             type string;
           }
         }
         case multichassis-tag {
           anyxml multi-routing-engine-results;
         }
       }
     }
   }
   rpc request-chassis-fabric-plane-sfb {
     description "Change Switch Fabric Card status";
     input {
       uses command-forwarding;
       leaf slot {
         description "SFB slot number";
         type union {
           type string {
             pattern "<.*>|$.*";
           }
           type uint32 {
             range "0 .. 7";
           }
         }
         mandatory true;
       }
       leaf cmd {
         type enumeration {
           enum "offline" {
             description "Take SFB offline";
           }
           enum "online" {
             description "Bring SFB online";
           }
         }
         mandatory true;
       }
     }
     output {
       container chassis-fabric-plane-state {
         uses chassis-fabric-plane-state-block;
       }
     }
   }
   rpc request-chassis-afeb {
     description "Change Forwarding Engine Board status";
     input {
       leaf cmd {
         type enumeration {
           enum "offline" {
             description "Take AFEB offline";
           }
           enum "online" {
             description "Bring AFEB online";
           }
           enum "restart" {
             description "Restart AFEB";
           }
         }
         mandatory true;
       }
     }
     output {
       container chassis-afeb-state {
         uses chassis-afeb-state-block;
       }
     }
   }
   rpc request-chassis-tfeb {
     description "Change Taz Forwarding Engine Board status";
     input {
       leaf cmd {
         type enumeration {
           enum "offline" {
             description "Take TFEB offline";
           }
           enum "online" {
             description "Bring TFEB online";
           }
           enum "restart" {
             description "Restart TFEB";
           }
         }
         mandatory true;
       }
     }
     output {
       container chassis-tfeb-state {
         uses chassis-tfeb-state-block;
       }
     }
   }
   rpc request-chassis-spmb {
     description "Change Switch Processor Mezzanine Board status";
     input {
       uses command-forwarding;
       leaf slot {
         description "SPMB slot number";
         type union {
           type string {
             pattern "<.*>|$.*";
           }
           type uint32;
         }
         mandatory true;
       }
       leaf cmd {
         type enumeration {
           enum "restart" {
             description "Restart SPMB";
           }
         }
         mandatory true;
       }
     }
     output {
       choice output_c {
         case output-tag {
           leaf output {
             type string;
           }
         }
         case multichassis-tag {
           anyxml multi-routing-engine-results;
         }
       }
     }
   }
   rpc request-chassis-sib {
     description "Change Switch Interface Board status";
     input {
       uses command-forwarding;
       leaf slot {
         description "SIB slot number";
         type union {
           type string {
             pattern "<.*>|$.*";
           }
           type uint32;
         }
         mandatory true;
       }
       choice cmd {
         case online-offline {
           leaf online-offline {
             type enumeration {
               enum "offline" {
                 description "Take SIB offline";
               }
               enum "online" {
                 description "Bring SIB online";
               }
               enum "restart" {
                 description "Perform Sib restart";
               }
             }
           }
         }
         case start-receiver {
           leaf start-receiver {
             description "Start SIB optical receiver";
             type union {
               type string {
                 pattern "<.*>|$.*";
               }
               type uint32;
             }
           }
         }
         case stop-receiver {
           leaf stop-receiver {
             description "Stop SIB optical receiver";
             type union {
               type string {
                 pattern "<.*>|$.*";
               }
               type uint32;
             }
           }
         }
         case train-rx-tx {
           leaf train-rx-tx {
             type enumeration {
               enum "train-link-receive" {
                 description "Train link receiver";
               }
               enum "train-link-transmit" {
                 description "Train link transmitter";
               }
             }
           }
         }
       }
     }
     output {
       choice output_c {
         case output-tag {
           leaf output {
             type string;
           }
         }
         case multichassis-tag {
           anyxml multi-routing-engine-results;
         }
       }
     }
   }
   rpc request-chassis-frutype-replacement {
     description "Perform fru replacement start or stop";
     input {
       leaf frutype {
         description "Select frutype";
         type enumeration {
           enum "sfb" {
             description "Replace SFB";
           }
         }
         mandatory true;
       }
       leaf replacement {
         description "Starts or stops the fru replacement";
         type enumeration {
           enum "start" {
             description "Start the fru replacement";
           }
           enum "stop" {
             description "Stop the fru replacement";
           }
         }
         mandatory true;
       }
     }
     output {
       choice output_c {
         case output-tag {
           leaf output {
             type string;
           }
         }
         case multichassis-tag {
           anyxml multi-routing-engine-results;
         }
       }
     }
   }
   rpc request-chassis-ccg {
     description "Change clock generator status";
     input {
       leaf slot {
         description "CCG slot number";
         type union {
           type string {
             pattern "<.*>|$.*";
           }
           type uint32 {
             range "0 .. 1";
           }
         }
         mandatory true;
       }
       leaf cmd {
         type enumeration {
           enum "offline" {
             description "Take CCG offline";
           }
           enum "online" {
             description "Bring CCG online";
           }
         }
         mandatory true;
       }
     }
     output {
       choice output_c {
         case output-tag {
           leaf output {
             type string;
           }
         }
         case multichassis-tag {
           anyxml multi-routing-engine-results;
         }
       }
     }
   }
   rpc request-chassis-routing-engine {
     description "Change Routing Engine status";
     output {
       container chassis-routing-engine-state {
         uses chassis-routing-engine-state-block;
       }
     }
   }
   rpc request-chassis-routing-engine-hard-disk-test {
     description "Run smartd self tests on hard disks";
     input {
       choice test-type {
         case short {
           leaf short {
             description "Run short test";
             type empty;
           }
         }
         case long {
           leaf long {
             description "Run SMART extended self test";
             type empty;
           }
         }
         case show-status {
           leaf show-status {
             description "Display status of test";
             type empty;
           }
         }
       }
       leaf disk {
         description "Name of hard disk";
         type string;
         mandatory true;
       }
     }
     output {
       container raid-information {
         uses raid-information-block;
       }
     }
   }
   rpc request-chassis-routing-engine-acquire {
     description "Attempt to become master Routing Engine";
     input {
       leaf no-confirm {
         description "Do not ask for confirmation";
         type empty;
       }
       leaf check {
         description "Check status of graceful switchover";
         type empty;
       }
     }
     output {
       container chassis-routing-engine-state {
         uses chassis-routing-engine-state-block;
       }
     }
   }
   rpc request-chassis-routing-engine-release {
     description "Request that other Routing Engine become master";
     input {
       leaf no-confirm {
         description "Do not ask for confirmation";
         type empty;
       }
       leaf check {
         description "Check status of graceful switchover";
         type empty;
       }
     }
     output {
       container chassis-routing-engine-state {
         uses chassis-routing-engine-state-block;
       }
     }
   }
   rpc request-chassis-routing-engine-switch {
     description "Toggle mastership between Routing Engines";
     input {
       leaf no-confirm {
         description "Do not ask for confirmation";
         type empty;
       }
       leaf check {
         description "Check status of graceful switchover";
         type empty;
       }
     }
     output {
       container chassis-routing-engine-state {
         uses chassis-routing-engine-state-block;
       }
     }
   }
   rpc request-feb {
     description "Change Forwarding Engine Board status";
     input {
       leaf slot {
         description "FEB slot number";
         type union {
           type string {
             pattern "<.*>|$.*";
           }
           type uint32;
         }
         mandatory true;
       }
       leaf cmd {
         type enumeration {
           enum "offline" {
             description "Take FEB offline";
           }
           enum "online" {
             description "Bring FEB online";
           }
           enum "restart" {
             description "Restart FEB";
           }
         }
         mandatory true;
       }
       leaf force {
         description "Force execute the offline/restart command";
         type empty;
       }
     }
     output {
       choice output_c {
         case output-tag {
           leaf output {
             type string;
           }
         }
         case multichassis-tag {
           anyxml multi-routing-engine-results;
         }
       }
     }
   }
   rpc request-chassis-cb {
     description "Change Control Board status";
     input {
       uses command-forwarding;
       leaf slot {
         description "CB slot number";
         type union {
           type string {
             pattern "<.*>|$.*";
           }
           type uint32;
         }
         mandatory true;
       }
       leaf cmd {
         type enumeration {
           enum "offline" {
             description "Take CB offline";
           }
           enum "online" {
             description "Bring CB online";
           }
         }
         mandatory true;
       }
     }
     output {
       choice output_c {
         case output-tag {
           leaf output {
             type string;
           }
         }
         case multichassis-tag {
           anyxml multi-routing-engine-results;
         }
       }
     }
   }
   rpc request-chassis-fpm {
     description "Change craft interface status";
     input {
       uses command-forwarding;
       leaf cmd {
         type enumeration {
           enum "resync" {
             description "Resynchronize craft interface";
           }
         }
         mandatory true;
       }
     }
     output {
       container chassis-fpm {
         uses chassis-fpm-block;
       }
     }
   }
   rpc request-chassis-beacon {
     description "Change beacon status";
     input {
       leaf cmd {
         type enumeration {
           enum "off" {
             description "Turn beacon off";
           }
           enum "on" {
             description "Turn beacon on";
           }
         }
         mandatory true;
       }
       leaf timer {
         description "Set timer for beacon LED";
         type union {
           type string {
             pattern "<.*>|$.*";
           }
           type uint32 {
             range "1 .. 120";
           }
         }
       }
       choice which-arg {
         case all {
           leaf all {
             description "All beacons";
             type empty;
           }
         }
         case fpc {
           leaf fpc {
             description "Flexible PIC Controller slot number";
             type union {
               type string {
                 pattern "<.*>|$.*";
               }
               type uint32;
             }
           }
         }
         case cb {
           leaf cb {
             description "Control Board slot number";
             type union {
               type string {
                 pattern "<.*>|$.*";
               }
               type uint32;
             }
           }
         }
         case service-node {
           leaf service-node {
             description "Service node slot number";
             type union {
               type string {
                 pattern "<.*>|$.*";
               }
               type uint32 {
                 range "0 .. 1";
               }
             }
           }
         }
       }
       leaf pic-slot {
         description "PIC slot number";
         type union {
           type string {
             pattern "<.*>|$.*";
           }
           type uint32;
         }
       }
       choice port-num {
         case port {
           leaf port {
             description "Port number";
             type union {
               type string {
                 pattern "<.*>|$.*";
               }
               type uint32;
             }
           }
         }
         case port-range {
           leaf port-range {
             description "Port range";
             type empty;
           }
         }
       }
       leaf lower-limit {
         description "Port range lower limit";
         type union {
           type string {
             pattern "<.*>|$.*";
           }
           type uint32;
         }
       }
       leaf upper-limit {
         description "Port range upper limit";
         type union {
           type string {
             pattern "<.*>|$.*";
           }
           type uint32;
         }
       }
     }
     output {
       container chassis-beacon-information {
         uses chassis-beacon-information-block;
       }
     }
   }
   rpc request-chassis-satellite-device-mode {
     description "Satellite device specific commands";
     input {
       leaf interface {
         description "Interface name";
         type string;
         mandatory true;
       }
       leaf device-mode {
         description "Device Mode";
         type enumeration {
           enum "satellite" {
             description "Satellite Mode";
           }
         }
         mandatory true;
       }
     }
     output {
       choice output_c {
         case output-tag {
           leaf output {
             type string;
           }
         }
         case multichassis-tag {
           anyxml multi-routing-engine-results;
         }
       }
     }
   }
   rpc request-chassis-satellite-reboot {
     description "Reboot one or more satellite";
     input {
       choice arg {
         case fpc-slot {
           leaf fpc-slot {
             description "Satellite slot number";
             type union {
               type string {
                 pattern "<.*>|$.*";
               }
               type uint32 {
                 range "65 .. 254";
               }
             }
           }
         }
         case range {
           leaf range {
             description "Slot range as <start-end> slot number (e.g. 100-110)";
             type string;
           }
         }
       }
     }
     output {
       choice output_c {
         case output-tag {
           leaf output {
             type string;
           }
         }
         case multichassis-tag {
           anyxml multi-routing-engine-results;
         }
       }
     }
   }
   rpc request-chassis-satellite-restart {
     description "Restart a process on one or more satellite";
     input {
       choice arg {
         case fpc-slot {
           leaf fpc-slot {
             description "Satellite slot number";
             type union {
               type string {
                 pattern "<.*>|$.*";
               }
               type uint32 {
                 range "65 .. 254";
               }
             }
           }
         }
         case range {
           leaf range {
             description "Slot range as <start-end> slot number (e.g. 100-110)";
             type string;
           }
         }
       }
       leaf process {
         description "Remote fpc shell command";
         type enumeration {
           enum "packet-forwarding-engine" {
             description "SPFE process";
           }
           enum "discovery-and-provisioning-daemon" {
             description "DPD process";
           }
           enum "chassis-management-daemon" {
             description "LCMD process";
           }
           enum "api-management-daemon" {
             description "AMD process";
           }
           enum "ppman" {
             description "PPMAN process";
           }
           enum "ppman-lite" {
             description "PPMAN-lite process";
           }
         }
         mandatory true;
       }
     }
     output {
       choice output_c {
         case output-tag {
           leaf output {
             type string;
           }
         }
         case multichassis-tag {
           anyxml multi-routing-engine-results;
         }
       }
     }
   }
   rpc request-chassis-satellite-shell-command {
     description "Execute shell command on one or more satellite";
     input {
       choice arg {
         case fpc-slot {
           leaf fpc-slot {
             description "Satellite slot number";
             type union {
               type string {
                 pattern "<.*>|$.*";
               }
               type uint32 {
                 range "65 .. 254";
               }
             }
           }
         }
         case range {
           leaf range {
             description "Slot range as <start-end> slot number (e.g. 100-110)";
             type string;
           }
         }
       }
       leaf remote-command {
         description "Remote fpc shell command";
         type string;
         mandatory true;
       }
     }
     output {
       choice output_c {
         case output-tag {
           leaf output {
             type string;
           }
         }
         case multichassis-tag {
           anyxml multi-routing-engine-results;
         }
       }
     }
   }
   rpc request-chassis-satellite-file-copy {
     description "File copy";
     input {
       leaf cmd {
         type enumeration {
           enum "local" {
             description "Local user";
           }
           enum "remote" {
             description "Remote user";
           }
         }
       }
       leaf source {
         description "URL of source file e.g. For SD, use sd100:/..";
         type string;
       }
       leaf destination {
         description "URL of destination file e.g. For SD, use sd100:/..";
         type string;
       }
     }
     output {
       choice output_c {
         case output-tag {
           leaf output {
             type string;
           }
         }
         case multichassis-tag {
           anyxml multi-routing-engine-results;
         }
       }
     }
   }
   rpc request-chassis-satellite-login {
     description "Connect to satellite device";
     input {
       leaf fpc-slot {
         description "Satellite slot number";
         type union {
           type string {
             pattern "<.*>|$.*";
           }
           type uint32 {
             range "65 .. 254";
           }
         }
       }
       leaf interface-name {
         description "Name of the interface";
         type string;
       }
     }
     output {
       choice output_c {
         case output-tag {
           leaf output {
             type string;
           }
         }
         case multichassis-tag {
           anyxml multi-routing-engine-results;
         }
       }
     }
   }
   rpc request-chassis-satellite-beacon {
     description "Change beacon status";
     input {
       choice arg {
         case fpc-slot {
           leaf fpc-slot {
             description "Satellite slot number";
             type union {
               type string {
                 pattern "<.*>|$.*";
               }
               type uint32 {
                 range "65 .. 254";
               }
             }
           }
         }
         case range {
           leaf range {
             description "Slot range as <start-end> slot number (e.g. 100-110)";
             type string;
           }
         }
       }
       leaf cmd {
         type enumeration {
           enum "off" {
             description "Beacon(s) in OFF state";
           }
           enum "on" {
             description "Beacon(s) in ON state";
           }
         }
         mandatory true;
       }
     }
     output {
       choice output_c {
         case output-tag {
           leaf output {
             type string;
           }
         }
         case multichassis-tag {
           anyxml multi-routing-engine-results;
         }
       }
     }
   }
   rpc request-chassis-satellite-disable {
     description "Disable satellite";
     input {
       choice arg {
         case fpc-slot {
           leaf fpc-slot {
             description "Satellite slot number";
             type union {
               type string {
                 pattern "<.*>|$.*";
               }
               type uint32 {
                 range "65 .. 254";
               }
             }
           }
         }
         case device-alias {
           leaf device-alias {
             description "Device alias";
             type string;
           }
         }
       }
     }
     output {
       choice output_c {
         case output-tag {
           leaf output {
             type string;
           }
         }
         case multichassis-tag {
           anyxml multi-routing-engine-results;
         }
       }
     }
   }
   rpc request-chassis-satellite-enable {
     description "Enable satellite";
     input {
       choice arg {
         case fpc-slot {
           leaf fpc-slot {
             description "Satellite slot number";
             type union {
               type string {
                 pattern "<.*>|$.*";
               }
               type uint32 {
                 range "65 .. 254";
               }
             }
           }
         }
         case device-alias {
           leaf device-alias {
             description "Device alias";
             type string;
           }
         }
       }
     }
     output {
       choice output_c {
         case output-tag {
           leaf output {
             type string;
           }
         }
         case multichassis-tag {
           anyxml multi-routing-engine-results;
         }
       }
     }
   }
   rpc request-chassis-satellite-install {
     description "Convert satellite device to standalone Junos device";
     input {
       choice arg {
         case fpc-slot {
           leaf fpc-slot {
             description "Satellite slot number";
             type union {
               type string {
                 pattern "<.*>|$.*";
               }
               type uint32 {
                 range "65 .. 254";
               }
             }
           }
         }
         case device-alias {
           leaf device-alias {
             description "Device alias";
             type string;
           }
         }
       }
       leaf package-name {
         description "URL or pathname of package";
         type jt:filename;
       }
       leaf no-confirm {
         description "Do not ask for confirmation";
         type empty;
       }
     }
     output {
       choice output_c {
         case output-tag {
           leaf output {
             type string;
           }
         }
         case multichassis-tag {
           anyxml multi-routing-engine-results;
         }
       }
     }
   }
   rpc request-ofp-configuration-reload {
     description "Reload OFP configuration file";
   }
   rpc request-ofp-sync-database-dump {
     description " Dump sync database to disk";
     input {
       leaf node {
         description "OFP node name or ID";
         type string;
       }
       leaf domain {
         description "OFP domain ID";
         type union {
           type uint64;
           type string {
             pattern "<.*>|$.*";
           }
         }
       }
       leaf topology {
         description "OFP topology ID";
         type union {
           type uint32;
           type string {
             pattern "<.*>|$.*";
           }
         }
       }
     }
   }
   rpc request-ofp-fragment-database-dump {
     description "Dump fragment database to disk";
     input {
       leaf node {
         description "OFP node name or ID";
         type string;
       }
       leaf domain {
         description "OFP domain ID";
         type union {
           type uint64;
           type string {
             pattern "<.*>|$.*";
           }
         }
       }
     }
   }
   rpc request-node-reboot {
     description "Reboot the node";
     input {
       choice time-arg-choice {
         case at {
           leaf at {
             description "Time at which to perform the operation in hh:mm 24 hrs format";
             default "now";
             type string;
           }
         }
         case in {
           leaf in {
             description "Number of minutes to delay before operation";
             default "now";
             type string;
           }
         }
       }
       leaf message {
         description "Message to display to all users";
         type string;
       }
       leaf media {
         type enumeration {
           enum "disk1" {
             description "Boot off disk1(primary) device";
           }
           enum "disk2" {
             description "Boot off disk2(backup) device";
           }
           enum "network1" {
             description "Network boot via PXE over port1";
           }
           enum "network2" {
             description "Network boot via PXE over port2";
           }
           enum "usb" {
             description "Boot off USB device";
           }
         }
       }
       leaf node {
         description "Node name";
         type string;
         mandatory true;
       }
     }
     output {
       choice output_c {
         case output-tag {
           leaf output {
             type string;
           }
         }
         case multichassis-tag {
           anyxml multi-routing-engine-results;
         }
       }
     }
   }
   rpc request-node-power-off {
     description "Power-off the node";
     input {
       choice time-arg-choice {
         case at {
           leaf at {
             description "Time at which to perform the operation in hh:mm 24 hrs format";
             default "now";
             type string;
           }
         }
         case in {
           leaf in {
             description "Number of minutes to delay before operation";
             default "now";
             type string;
           }
         }
       }
       leaf message {
         description "Message to display to all users";
         type string;
       }
       leaf node {
         description "Node name";
         type string;
         mandatory true;
       }
     }
     output {
       choice output_c {
         case output-tag {
           leaf output {
             type string;
           }
         }
         case multichassis-tag {
           anyxml multi-routing-engine-results;
         }
       }
     }
   }
   rpc request-node-power-cycle {
     description "Power-cycle the node";
     input {
       choice time-arg-choice {
         case at {
           leaf at {
             description "Time at which to perform the operation in hh:mm 24 hrs format";
             default "now";
             type string;
           }
         }
         case in {
           leaf in {
             description "Number of minutes to delay before operation";
             default "now";
             type string;
           }
         }
       }
       leaf message {
         description "Message to display to all users";
         type string;
       }
       leaf node {
         description "Node name";
         type string;
         mandatory true;
       }
     }
     output {
       choice output_c {
         case output-tag {
           leaf output {
             type string;
           }
         }
         case multichassis-tag {
           anyxml multi-routing-engine-results;
         }
       }
     }
   }
   rpc request-node-halt {
     description "Halt the node";
     input {
       choice time-arg-choice {
         case at {
           leaf at {
             description "Time at which to perform the operation in hh:mm 24 hrs format";
             default "now";
             type string;
           }
         }
         case in {
           leaf in {
             description "Number of minutes to delay before operation";
             default "now";
             type string;
           }
         }
       }
       leaf message {
         description "Message to display to all users";
         type string;
       }
       leaf node {
         description "Node name";
         type string;
         mandatory true;
       }
     }
     output {
       choice output_c {
         case output-tag {
           leaf output {
             type string;
           }
         }
         case multichassis-tag {
           anyxml multi-routing-engine-results;
         }
       }
     }
   }
   rpc request-node-power-on {
     description "Power-on the node";
     input {
       leaf node {
         description "Node name";
         type string;
         mandatory true;
       }
     }
     output {
       choice output_c {
         case output-tag {
           leaf output {
             type string;
           }
         }
         case multichassis-tag {
           anyxml multi-routing-engine-results;
         }
       }
     }
   }
   rpc request-node-offline {
     description "Offline the node";
     input {
       leaf node {
         description "Node name";
         type string;
         mandatory true;
       }
     }
     output {
       choice output_c {
         case output-tag {
           leaf output {
             type string;
           }
         }
         case multichassis-tag {
           anyxml multi-routing-engine-results;
         }
       }
     }
   }
   rpc request-node-online {
     description "Online the node";
     input {
       leaf node {
         description "Node name";
         type string;
         mandatory true;
       }
     }
     output {
       choice output_c {
         case output-tag {
           leaf output {
             type string;
           }
         }
         case multichassis-tag {
           anyxml multi-routing-engine-results;
         }
       }
     }
   }
   rpc request-fibd-statistics-clear {
     description "Clear fibd statistics information";
   }
   rpc request-fibd-statistics-filtered-clear {
     description "Clear fibd filtered statistics information";
   }
   rpc request-fibd-statistics-set-filter {
     description "Define filter for fibd statistics";
     input {
       leaf process-name {
         description "Process name";
         type string;
       }
       leaf pid {
         description "Process ID";
         type union {
           type uint32;
           type string {
             pattern "<.*>|$.*";
           }
         }
       }
       leaf protocol {
         description "IP Protocol number";
         type union {
           type uint16;
           type string {
             pattern "<.*>|$.*";
           }
         }
       }
       leaf vrf {
         description "VRF";
         type union {
           type uint16;
           type string {
             pattern "<.*>|$.*";
           }
         }
       }
       leaf local-address {
         description "Local address";
         type jt:ipaddr;
       }
       leaf remote-address {
         description "Remote address";
         type jt:ipaddr;
       }
       leaf local-port {
         description "Local port";
         type union {
           type uint16;
           type string {
             pattern "<.*>|$.*";
           }
         }
       }
       leaf remote-port {
         description "Remote port";
         type union {
           type uint16;
           type string {
             pattern "<.*>|$.*";
           }
         }
       }
       leaf address-family {
         description "Address family";
         type enumeration {
           enum "inet" {
             description "Protocol AF_INET (i.e. IPv4 TCP/UDP/RAW)";
           }
           enum "inet6" {
             description "Protocol AF_INET6 (i.e. IPv6 TCP/UDP/RAW)";
           }
           enum "packet" {
             description "Protocol AF_PACKET (i.e. RAW and DATAGRAM)";
           }
         }
       }
     }
     output {
       container fibd-statistics-filter {
         uses fibd-statistics-filter-block;
       }
     }
   }
   rpc request-fibd-statistics-clear-filter {
     description "Clear user supplied filter";
   }
   rpc fibd-smo-log-enable {
     description "Enable libsmo logs in fibd";
     output {
       container multi-routing-engine-results-smo-log {
         uses multi-routing-engine-results-smo-log-block;
       }
     }
   }
   rpc fibd-smo-log-disable {
     description "Disable libsmo logs in fibd";
     output {
       container multi-routing-engine-results-smo-log {
         uses multi-routing-engine-results-smo-log-block;
       }
     }
   }
   rpc flowdebug-start {
     description "Start flow-based debugging";
     output {
       container flowdebug-start {
         uses flowdebug-start-block;
       }
     }
   }
   rpc flowdebug-stop {
     description "Stop flow-based debugging";
     output {
       container flowdebug-stop {
         uses flowdebug-stop-block;
       }
     }
   }
   rpc flowdebug-showfilter {
     description "Show the filter that specifies the flow to debug";
     output {
       container flowdebug-showfilter {
         uses flowdebug-showfilter-block;
       }
     }
   }
   rpc flowdebug-setfilter {
     description "Set the filter that specifies the flow to debug";
     input {
       leaf flow-name {
         description "A flow name to be included in log messages";
         type string;
       }
       leaf pid {
         description "The target flow's process ID";
         type union {
           type string {
             pattern "<.*>|$.*";
           }
           type uint32 {
             range "0 .. 4294967295";
           }
         }
       }
       leaf process-name {
         description "The target flow's process name";
         type string;
       }
       leaf vrf {
         description "The target flow's VRF number";
         type union {
           type string {
             pattern "<.*>|$.*";
           }
           type uint32 {
             range "0 .. 4294967295";
           }
         }
       }
       leaf protocol {
         description "The target flow's protocol";
         type enumeration {
           enum "inet-tcp" {
             description "IPv4 TCP (i.e. socket domain=AF_INET and type=SOCK_STREAM)";
           }
           enum "inet-udp" {
             description "IPv4 UDP (i.e. socket domain=AF_INET and type=SOCK_DGRAM)";
           }
           enum "inet-raw" {
             description "IPv4 RAW (i.e. socket domain=AF_INET and type=SOCK_RAW)";
           }
           enum "inet6-tcp" {
             description "IPv6 TCP (i.e. socket domain=AF_INET6 and type=SOCK_STREAM)";
           }
           enum "inet6-udp" {
             description "IPv6 UDP (i.e. socket domain=AF_INET6 and type=SOCK_DGRAM)";
           }
           enum "inet6-raw" {
             description "IPv6 RAW (i.e. socket domain=AF_INET6 and type=SOCK_RAW)";
           }
           enum "packet-dgram" {
             description "Packet datagram (i.e. socket domain=AF_PACKET and type=SOCK_DGRAM)";
           }
           enum "packet-raw" {
             description "Packet raw (i.e. socket domain=AF_PACKET and type=SOCK_RAW)";
           }
         }
       }
       leaf local-address {
         description "The target flow's local IPv4 or IPv6 or MAC address";
         type string;
       }
       leaf remote-address {
         description "The target flow's remote IPv4 or IPv6 or MAC address";
         type string;
       }
       leaf port {
         description "The target flow's local or remote port";
         type union {
           type string {
             pattern "<.*>|$.*";
           }
           type uint32 {
             range "0 .. 65535";
           }
         }
       }
       leaf local-port {
         description "The target flow's local port";
         type union {
           type string {
             pattern "<.*>|$.*";
           }
           type uint32 {
             range "0 .. 65535";
           }
         }
       }
       leaf remote-port {
         description "The target flow's remote port";
         type union {
           type string {
             pattern "<.*>|$.*";
           }
           type uint32 {
             range "0 .. 65535";
           }
         }
       }
       leaf ifd {
         description "The target flow's interface device (IFD) index";
         type union {
           type string {
             pattern "<.*>|$.*";
           }
           type uint32 {
             range "0 .. 4294967295";
           }
         }
       }
       leaf ifl {
         description "The target flow's logical interface (IFL) index";
         type union {
           type string {
             pattern "<.*>|$.*";
           }
           type uint32 {
             range "0 .. 4294967295";
           }
         }
       }
       leaf mpls-tag {
         description "The target flow's MPLS tag";
         type union {
           type string {
             pattern "<.*>|$.*";
           }
           type uint32 {
             range "0 .. 4294967295";
           }
         }
       }
       leaf vlan {
         description "The target flow's VLAN ID";
         type union {
           type string {
             pattern "<.*>|$.*";
           }
           type uint32 {
             range "0 .. 4294967295";
           }
         }
       }
       leaf l2-type {
         description "The target flow's layer 2 type";
         type union {
           type string {
             pattern "<.*>|$.*";
           }
           type uint32 {
             range "0 .. 65535";
           }
         }
       }
     }
     output {
       container flowdebug-setfilter {
         uses flowdebug-setfilter-block;
       }
     }
   }
   rpc self-mirror-enable-disable {
     description "Enable or disable port-mirroring";
     input {
       leaf instance {
         description "Name of port-mirroring instance";
         type string;
         mandatory true;
       }
       leaf family {
         description "Family of port-mirroring instance";
         type enumeration {
           enum "inet" {
             description "IPv4 instance";
           }
           enum "inet6" {
             description "IPv6 instance";
           }
           enum "any" {
             description "Any instance";
           }
         }
       }
       choice which-cmd {
         case self-mirror-stop {
           leaf self-mirror-stop {
             description "Stop the capture";
             type empty;
           }
         }
         case self-mirror-start {
           leaf self-mirror-start {
             description "Duration in seconds";
             default "300";
             units "seconds";
             type union {
               type string {
                 pattern "<.*>|$.*";
               }
               type int32 {
                 range "1 .. 1800";
               }
             }
           }
         }
       }
     }
   }
   rpc request-protection-group-ethernet-aps {
     description "Ethernet APS related operations";
     input {
       leaf maintenance-domain {
         description "Name of maintenance domain";
         type string {
           length "1 .. 45";
         }
         mandatory true;
       }
       leaf maintenance-association {
         description "Name of maintenance association";
         type string {
           length "1 .. 45";
         }
         mandatory true;
       }
       leaf eaps-action {
         type enumeration {
           enum "switch-to-working" {
             description "Switch data path to use working path";
           }
           enum "switch-to-protect" {
             description "Switch data path to use protection path";
           }
           enum "lockout" {
             description "Lockout protection";
           }
           enum "force-switch" {
             description "Force switch data path to use protection path";
           }
           enum "manual-switch" {
             description "Manual switch data path to use protection path";
           }
           enum "exercise" {
             description "Excercise APS protocol";
           }
           enum "clear" {
             description "Clears active local command";
           }
         }
         mandatory true;
       }
       choice daemon-select {
         case logical-system {
           leaf logical-system {
             description "Name of logical system, or 'all'";
             type string {
             }
           }
         }
       }
     }
     output {
       choice output_c {
         case output-tag {
           leaf output {
             type string;
           }
         }
         case multichassis-tag {
           anyxml multi-routing-engine-results;
         }
       }
     }
   }
   rpc request-protection-group-erps-clear {
     description "Clears active local commands";
     input {
       leaf group-name {
         description "Name of protection group";
         type string {
           length "1 .. 32";
         }
       }
     }
     output {
       choice output_c {
         case output-tag {
           leaf output {
             type string;
           }
         }
         case multichassis-tag {
           anyxml multi-routing-engine-results;
         }
       }
     }
   }
   rpc request-protection-group-erps-manual-switch {
     description "Manual switch data path to use protection path";
     input {
       leaf interface-name {
         description "Name of interface";
         type union {
           type jt:interface-wildcard;
           type string {
             pattern "<.*>|$.*";
           }
         }
         mandatory true;
       }
       leaf group-name {
         description "Name of protection group";
         type string {
           length "1 .. 32";
         }
       }
     }
     output {
       choice output_c {
         case output-tag {
           leaf output {
             type string;
           }
         }
         case multichassis-tag {
           anyxml multi-routing-engine-results;
         }
       }
     }
   }
   rpc request-protection-group-erps-force-switch {
     description "Force switch data path to use protection path";
     input {
       leaf interface-name {
         description "Name of interface";
         type union {
           type jt:interface-wildcard;
           type string {
             pattern "<.*>|$.*";
           }
         }
         mandatory true;
       }
       leaf group-name {
         description "Name of protection group";
         type string {
           length "1 .. 32";
         }
       }
     }
     output {
       choice output_c {
         case output-tag {
           leaf output {
             type string;
           }
         }
         case multichassis-tag {
           anyxml multi-routing-engine-results;
         }
       }
     }
   }
   rpc get-flight-recorder-information {
     description "Debug high cpu issues and scheduler slips";
     input {
       leaf disable {
         description "Disable the flight recorder";
         type empty;
       }
       leaf logical-system {
         description "Enable logical systems";
         type empty;
       }
       leaf cpu-threshold {
         description "Threshold over which the collection is triggered";
         type union {
           type string {
             pattern "<.*>|$.*";
           }
           type uint32 {
             range "1 .. 400";
           }
         }
       }
       leaf polling-frequency {
         description "Frequency of polling for high cpu";
         type union {
           type string {
             pattern "<.*>|$.*";
           }
           type uint32 {
             range "5 .. 100";
           }
         }
       }
       leaf backoff-duration {
         description "Time to wait between two snapshots";
         type union {
           type string {
             pattern "<.*>|$.*";
           }
           type uint32 {
             range "10 .. 1000";
           }
         }
       }
       leaf collect-core {
         description "Whether to take a running core with every snapshot";
         type empty;
       }
       leaf num-snapshots {
         description "How many snapshots to collect before quitting";
         type union {
           type string {
             pattern "<.*>|$.*";
           }
           type uint32 {
             range "1 .. 20";
           }
         }
       }
     }
     output {
       container flight-recorder-information {
         uses flight-recorder-information-block;
       }
     }
   }
   rpc request-l2ckt-switchover {
     description "Perform l2circuit switchover";
     input {
       choice daemon-select {
         case logical-system {
           leaf logical-system {
             description "Name of logical system, or 'all'";
             type string {
             }
           }
         }
       }
       leaf neighbor {
         description "IP address of neighbor";
         type jt:ipv4addr;
         mandatory true;
       }
       leaf virtual-circuit-id {
         description "Layer 2 circuit ID";
         default "all";
         type string;
       }
     }
     output {
       choice output_c {
         case output-tag {
           leaf output {
             type string;
           }
         }
         case multichassis-tag {
           anyxml multi-routing-engine-results;
         }
       }
     }
   }
   rpc request-vpls-switchover {
     description "Perform LDP VPLS pseudowire switchover";
     input {
       choice daemon-select {
         case logical-system {
           leaf logical-system {
             description "Name of logical system, or 'all'";
             type string {
             }
           }
         }
       }
       leaf instance {
         description "Name of VPLS instance";
         type string;
         mandatory true;
       }
       leaf neighbor {
         description "IP address of neighbor";
         type jt:ipv4addr;
         mandatory true;
       }
       leaf vpls-id {
         description "Layer 2 circuit ID";
         default "all";
         type string;
       }
     }
     output {
       choice output_c {
         case output-tag {
           leaf output {
             type string;
           }
         }
         case multichassis-tag {
           anyxml multi-routing-engine-results;
         }
       }
     }
   }
   rpc request-mpls-lsp-autobandwidth-adjust {
     description "Request LSP autobandwidth adjustment now";
     input {
       choice daemon-select {
         case logical-system {
           leaf logical-system {
             description "Name of logical system, or 'all'";
             type string {
             }
           }
         }
       }
       leaf regex {
         description "Regular expression for LSP names to match";
         type string;
       }
       leaf instance {
         description "Name of routing instance";
         type string;
       }
     }
     output {
       choice output_c {
         case output-tag {
           leaf output {
             type string;
           }
         }
         case multichassis-tag {
           anyxml multi-routing-engine-results;
         }
       }
     }
   }
   rpc request-mpls-container-lsp-autobandwidth-adjust {
     description "Request LSP autobandwidth adjustment now";
     input {
       choice daemon-select {
         case logical-system {
           leaf logical-system {
             description "Name of logical system, or 'all'";
             type string {
             }
           }
         }
       }
       leaf regex {
         description "Regular expression for LSP names to match";
         type string;
       }
       leaf instance {
         description "Name of routing instance";
         type string;
       }
     }
     output {
       choice output_c {
         case output-tag {
           leaf output {
             type string;
           }
         }
         case multichassis-tag {
           anyxml multi-routing-engine-results;
         }
       }
     }
   }
   rpc request-mpls-container-lsp-normalization {
     description "Request container LSP normalization now";
     input {
       choice daemon-select {
         case logical-system {
           leaf logical-system {
             description "Name of logical system, or 'all'";
             type string {
             }
           }
         }
       }
       leaf regex {
         description "Regular expression for LSP names to match";
         type string;
       }
       leaf instance {
         description "Name of routing instance";
         type string;
       }
       leaf bandwidth {
         description "Use the bandwidth for manual normalization";
         type union {
           type uint64;
           type string {
             pattern "<.*>|$.*";
           }
         }
       }
     }
     output {
       choice output_c {
         case output-tag {
           leaf output {
             type string;
           }
         }
         case multichassis-tag {
           anyxml multi-routing-engine-results;
         }
       }
     }
   }
   rpc request-mpls-lable-range-reserve {
     description "Request label space repartition now";
     output {
       choice output_c {
         case output-tag {
           leaf output {
             type string;
           }
         }
         case multichassis-tag {
           anyxml multi-routing-engine-results;
         }
       }
     }
   }
   rpc pim-multicast-tunnel {
     description "Request PIM MT rebalance";
     input {
       choice daemon-select {
         case logical-system {
           leaf logical-system {
             description "Name of logical system, or 'all'";
             type string {
             }
           }
         }
       }
       leaf instance {
         description "Name of instance";
         type string;
       }
     }
     output {
       choice output_c {
         case output-tag {
           leaf output {
             type string;
           }
         }
         case multichassis-tag {
           anyxml multi-routing-engine-results;
         }
       }
     }
   }
   rpc request-validation-policy {
     description "Request policy reevaluation";
     input {
       choice daemon-select {
         case logical-system {
           leaf logical-system {
             description "Name of logical system";
             type string {
             }
           }
         }
       }
       leaf record {
         description "Filter by record";
         type jt:ipprefix;
       }
       leaf instance {
         description "Name of route validation instance";
         type string;
       }
     }
     output {
       container rv-request-policy-information {
         uses rv-request-policy-information-block;
       }
     }
   }
   rpc request-validation-reload-source-file {
     description "Request reload source file";
   }
   rpc monitor-mobile-gateways-call-trace-start {
     description "Trace subscriber events";
   }
   rpc get-mobile-gateways-call-trace-start-information {
     description "Start subscriber events trace";
     input {
       leaf msisdn {
         description "Trace events for a specific msisdn";
         type string {
           length "3 .. 15";
         }
       }
       leaf imsi {
         description "Trace events for a specific imsi";
         type string {
           length "5 .. 15";
         }
       }
       leaf next-call {
         description "Trace the next call events";
         default "1";
         type union {
           type string {
             pattern "<.*>|$.*";
           }
           type uint32 {
             range "1 .. 50";
           }
         }
       }
       leaf fpc-slot {
         description "FPC slot number";
         type union {
           type uint32;
           type string {
             pattern "<.*>|$.*";
           }
         }
       }
       leaf pic-slot {
         description "PIC slot number";
         type union {
           type uint32;
           type string {
             pattern "<.*>|$.*";
           }
         }
       }
       leaf apn-name {
         description "Name of APN";
         type string {
           length "1 .. 100";
         }
       }
       leaf file-name-prefix {
         description "Name of file prefix";
         type string {
           length "4 .. 24";
         }
       }
       leaf comment {
         description "Comment to be added in the file";
         type string {
           length "4 .. 100";
         }
       }
     }
   }
   rpc get-mobile-gateways-call-trace-stop-information {
     description "Stop subscriber events trace";
     input {
       leaf identifier {
         description "Name of identifier";
         type string {
           length "1 .. 100";
         }
       }
       leaf all {
         description "All call traces";
         type empty;
       }
     }
   }
   rpc get-mobile-gateways-call-trace-clear {
     description "Clear subscriber events trace";
     output {
       choice output_c {
         case output-tag {
           leaf output {
             type string;
           }
         }
         case multichassis-tag {
           anyxml multi-routing-engine-results;
         }
       }
     }
   }
   rpc get-mobile-gateways-call-trace-information {
     description "Show subscriber events trace";
     input {
       leaf selector {
         default "all";
         type enumeration {
           enum "current" {
             description "Display information about current traces";
           }
           enum "completed" {
             description "Display information about completed traces";
           }
           enum "all" {
             description "Display information about all trace";
           }
         }
       }
       leaf verbosity-level {
         description "Select the verbosity level";
         default "brief";
         type enumeration {
           enum "brief" {
             description "Display brief output (default)";
           }
           enum "detail" {
             description "Display detailed output";
           }
         }
       }
     }
   }
   rpc get-mobile-gateways-sgw-call-trace-start-information {
     description "Start subscriber events trace";
     input {
       leaf msisdn {
         description "Trace events for a specific msisdn";
         type string {
           length "3 .. 15";
         }
       }
       leaf imsi {
         description "Trace events for a specific imsi";
         type string {
           length "5 .. 15";
         }
       }
       leaf next-call {
         description "Trace the next call events";
         default "1";
         type union {
           type string {
             pattern "<.*>|$.*";
           }
           type uint32 {
             range "1 .. 50";
           }
         }
       }
       leaf fpc-slot {
         description "FPC slot number";
         type union {
           type uint32;
           type string {
             pattern "<.*>|$.*";
           }
         }
       }
       leaf pic-slot {
         description "PIC slot number";
         type union {
           type uint32;
           type string {
             pattern "<.*>|$.*";
           }
         }
       }
     }
   }
   rpc get-mobile-gateways-sgw-call-trace-stop-information {
     description "Stop subscriber events trace";
     input {
       leaf identifier {
         description "Name of identifier";
         type string {
           length "1 .. 100";
         }
       }
       leaf all {
         description "All call traces";
         type empty;
       }
     }
   }
   rpc get-mobile-gateways-sgw-call-trace-clear {
     description "Clear subscriber events trace";
     output {
       choice output_c {
         case output-tag {
           leaf output {
             type string;
           }
         }
         case multichassis-tag {
           anyxml multi-routing-engine-results;
         }
       }
     }
   }
   rpc get-mobile-gateways-sgw-call-trace-information {
     description "Show subscriber events trace";
     input {
       leaf selector {
         default "all";
         type enumeration {
           enum "current" {
             description "Display information about current traces";
           }
           enum "completed" {
             description "Display information about completed traces";
           }
           enum "all" {
             description "Display information about all trace";
           }
         }
       }
       leaf verbosity-level {
         description "Select the verbosity level";
         default "brief";
         type enumeration {
           enum "brief" {
             description "Display brief output (default)";
           }
           enum "detail" {
             description "Display detailed output";
           }
         }
       }
     }
   }
   rpc get-mobile-gateways-tdf-call-trace-start-information {
     description "Start subscriber events trace";
     input {
       leaf msisdn {
         description "Trace events for a specific msisdn";
         type string {
           length "3 .. 15";
         }
       }
       leaf imsi {
         description "Trace events for a specific imsi";
         type string {
           length "5 .. 15";
         }
       }
       leaf next-call {
         description "Trace the next call events on each session PIC";
         type empty;
       }
       leaf v4-addr {
         description "Trace events for a specific IPV4 subscriber";
         type jt:ipaddr;
       }
       leaf v6-addr {
         description "Trace events for a specific IPV6 subscriber";
         type jt:ipv6addr;
       }
       leaf routing-instance {
         description "Routing Instance which the subscriber belong to";
         type string;
       }
       leaf user-name {
         description "Subscriber User Name";
         type string;
       }
       leaf subscriber-name {
         description "Non-IP Subscriber Name";
         type string;
       }
     }
   }
   rpc get-mobile-gateways-tdf-call-trace-stop-information {
     description "Stop subscriber events trace";
     input {
       leaf identifier {
         description "Name of identifier";
         type string {
           length "1 .. 100";
         }
       }
       leaf all {
         description "All call traces";
         type empty;
       }
     }
   }
   rpc get-mobile-gateways-tdf-call-trace-clear {
     description "Clear subscriber events trace";
     output {
       choice output_c {
         case output-tag {
           leaf output {
             type string;
           }
         }
         case multichassis-tag {
           anyxml multi-routing-engine-results;
         }
       }
     }
   }
   rpc get-mobile-gateways-tdf-call-trace-information {
     description "Show subscriber events trace";
     input {
       leaf selector {
         default "all";
         type enumeration {
           enum "current" {
             description "Display information about current traces";
           }
           enum "completed" {
             description "Display information about completed traces";
           }
           enum "all" {
             description "Display information about all traces";
           }
         }
       }
       leaf verbosity-level {
         description "Select the verbosity level";
         default "brief";
         type enumeration {
           enum "brief" {
             description "Display brief output (default)";
           }
           enum "detail" {
             description "Display detailed output";
           }
         }
       }
     }
   }
   rpc nsagentd-smo-log-enable {
     description "Enable libsmo logs in nsagentd";
     output {
       container multi-routing-engine-results-smo-log {
         uses multi-routing-engine-results-smo-log-block;
       }
     }
   }
   rpc nsagentd-smo-log-disable {
     description "Disable libsmo logs in nsagentd";
     output {
       container multi-routing-engine-results-smo-log {
         uses multi-routing-engine-results-smo-log-block;
       }
     }
   }
   rpc request-path-computation-client-main-pce {
     description "Request new active PCE";
     input {
       leaf pce-id {
         description "PCE ID from configuration";
         type string;
         mandatory true;
       }
     }
     output {
       choice output_c {
         case output-tag {
           leaf output {
             type string;
           }
         }
         case multichassis-tag {
           anyxml multi-routing-engine-results;
         }
       }
     }
   }
   rpc request-path-computation-retry-delegation {
     description "Request retry delegation";
     input {
       leaf lsp-name {
         description "Name of static label-switched-path";
         type string;
         mandatory true;
       }
     }
     output {
       choice output_c {
         case output-tag {
           leaf output {
             type string;
           }
         }
         case multichassis-tag {
           anyxml multi-routing-engine-results;
         }
       }
     }
   }
   rpc request-component-login {
     description "Login to remote node in the fabric";
     input {
       leaf node-name {
         description "Inventory name for the remote node";
         type string;
         mandatory true;
       }
     }
     output {
       choice output_c {
         case output-tag {
           leaf output {
             type string;
           }
         }
         case multichassis-tag {
           anyxml multi-routing-engine-results;
         }
       }
     }
   }
   rpc request-mac-pool-add {
     description "Add a new MAC block to the system";
     input {
       leaf mac-base {
         description "MAC base of the mac block";
         type jt:mac-addr;
         mandatory true;
       }
       leaf count {
         description "Number of addresses in the mac block";
         type string;
         mandatory true;
       }
     }
     output {
       choice output_c {
         case output-tag {
           leaf output {
             type string;
           }
         }
         case multichassis-tag {
           anyxml multi-routing-engine-results;
         }
       }
     }
   }
   rpc request-mac-pool-delete {
     description "Delete a MAC block from the system";
     input {
       leaf mac-base {
         description "MAC base of the mac block";
         type jt:mac-addr;
         mandatory true;
       }
     }
     output {
       choice output_c {
         case output-tag {
           leaf output {
             type string;
           }
         }
         case multichassis-tag {
           anyxml multi-routing-engine-results;
         }
       }
     }
   }
   rpc fabric-administration-clear-node-device {
     description "Remove a Node device from the inventory";
     input {
       leaf node-device {
         description "The Node device to remove";
         type string;
         mandatory true;
       }
     }
   }
   rpc fabric-administration-clear-interconnect-device {
     description "Remove a Interconnect device from the inventory";
     input {
       leaf interconnect-device {
         description "The Interconnect device to remove";
         type string;
         mandatory true;
       }
     }
   }
   rpc request-tdr-interface-diagnostics {
     description "Enter TDR interface name";
     input {
       leaf interface-name {
         description "Interface name";
         type string;
       }
     }
   }
   rpc abort-tdr-interface-diagnostics {
     description "Enter TDR interface name";
     input {
       leaf interface-name {
         description "Interface name";
         type string;
       }
     }
   }
   grouping command-forwarding {
     leaf no-forwarding {
       description "No forwarding";
       type empty;
     }
     choice chassis-selector {
       case case_1 {
         leaf all-chassis {
           description "All chassis";
           type empty;
         }
       }
       case case_2 {
         leaf all-lcc {
           description "All LCC chassis";
           type empty;
         }
       }
       case case_3 {
         leaf scc {
           description "SCC";
           type empty;
         }
       }
       case case_4 {
         leaf sfc {
           description "SFC";
           type union {
             type string {
               pattern "<.*>|$.*";
             }
             type uint32;
           }
         }
       }
       case case_5 {
         leaf lcc {
           description "Specific LCC";
           type union {
             type string {
               pattern "<.*>|$.*";
             }
             type uint32;
           }
         }
       }
       case case_6 {
         leaf node {
           description "Specific node";
           type string;
         }
       }
       case case_7 {
         leaf bsys {
           description "Base system";
           type empty;
         }
       }
       case case_8 {
         leaf gnf {
           description "Specific guest network function";
           type union {
             type string {
               pattern "<.*>|$.*";
             }
             type uint32 {
               range "1 .. 10";
             }
           }
         }
       }
       case case_9 {
         leaf all-gnfs {
           description "All guest network functions";
           type empty;
         }
       }
       case case_10 {
         leaf all-system {
           description "All system (BSYS and GNFs)";
           type empty;
         }
       }
       case case_11 {
         leaf server {
           description "Specific server slot";
           type union {
             type string {
               pattern "<.*>|$.*";
             }
             type uint32 {
               range "0 .. 1";
             }
           }
         }
       }
       case case_12 {
         leaf all-servers {
           description "All servers";
           type empty;
         }
       }
       case case_13 {
         leaf vnf {
           description "Specific virtual-network-function";
           type string;
         }
       }
       case case_14 {
         leaf all-vnfs {
           description "All virtual-network-functions";
           type empty;
         }
       }
     }
     choice re-selector {
       case case_1 {
         leaf re0 {
           description "RE0";
           type empty;
         }
       }
       case case_2 {
         leaf re1 {
           description "RE1";
           type empty;
         }
       }
       case case_3 {
         leaf routing-engine {
           description "Specific routing engine";
           type enumeration {
             enum "local" {
               description "Local routing engine";
             }
             enum "other" {
               description "Other routing engine";
             }
             enum "master" {
               description "Master routing engine";
             }
             enum "backup" {
               description "Backup routing engine";
             }
             enum "both" {
               description "Both routing engines";
             }
           }
         }
       }
     }
     choice lr-selector {
       case case_1 {
         leaf logical-system {
           description "Name of logical system, or 'all'";
           type string;
         }
       }
     }
     choice tenant-selector {
       case case_1 {
         leaf tenant {
           description "Name of tenant, or 'all'";
           type string;
         }
       }
     }
     choice vc-selector {
       case case_1 {
         leaf local {
           description "Local virtual chassis member";
           type empty;
         }
       }
       case case_2 {
         leaf all-members {
           description "All virtual chassis members";
           type empty;
         }
       }
       case case_3 {
         leaf member {
           description "Specific virtual chassis member which is master";
           type union {
             type string {
               pattern "<.*>|$.*";
             }
             type uint32;
           }
         }
       }
     }
   }
   grouping rescue-management-results-block {
     list routing-engine {
       leaf commit-check-success {
         type empty;
         description "Configuration check succeeds";
       }
       leaf commit-success {
         type empty;
         description "Configuration commit is complete";
       }
       leaf commit-queued {
         type empty;
         description "Configuration commit is queued";
       }
       leaf commit-prepare-success {
         type empty;
         description "Commit cache is successfully prepared";
       }
       leaf success {
         type empty;
         description "Rescue configuration operation succeeded";
       }
       container satellite-commit-check-results {
         list satellite {
           leaf name {
             type string;
             description "Syslog message tag name";
           }
           leaf satellite-commit-check-success {
             type empty;
             description "Configuration check succeeds";
           }
         }
       }
       leaf name {
         type string;
         description "Syslog message tag name";
       }
     }
   }
   grouping commit-server-delete-results-block {
     leaf commit-server-delete-success {
       type empty;
     }
     leaf commit-server-delete-failed-match {
       type empty;
     }
   }
   grouping commit-server-operation-block {
     leaf-list message {
       type string;
       description "Pause message";
     }
     container pause-status {
       description "Commit server pause status";
       leaf pause-success {
         type empty;
         description "Pause success";
       }
       leaf pause-error {
         type empty;
         description "Pause error";
       }
       leaf pause-already {
         type empty;
         description "Commit server is already paused";
       }
     }
     container start-status {
       description "Commit server start status";
       leaf start-success {
         type empty;
         description "Start success";
       }
       leaf start-error {
         type empty;
         description "Start error";
       }
       leaf start-already {
         type empty;
         description "Commit server is already running";
       }
     }
   }
   grouping logout-user-block {
     leaf logout-user-message {
       type string;
     }
   }
   grouping package-status-block {
     leaf package-status-message {
       type string;
       description "Show software installation status";
     }
   }
   grouping add-license-results-block {
     leaf add-success {
       type empty;
       description "Add completed with no errors";
     }
     leaf add-error-count {
       type int32;
       description "Number of errors during add license operation";
     }
     list add-individual-result {
       description "Report status of individual license add operation";
       leaf filename {
         type string;
         description "File name in which error exist";
       }
       leaf line-number {
         type int32;
         description "Line number where error exist";
       }
       leaf operation-status {
         type string;
         description "Defines that status of a license operation";
       }
       leaf name {
         type string;
         description "Identifier for this object";
       }
       leaf message {
         type string;
         description "Text to explain the status of an operation";
       }
     }
   }
   grouping inform-block {
     leaf source-daemon {
       type string;
     }
     leaf message {
       type string;
       description "Syslog message text";
     }
   }
   grouping system-storage-cleanup-information-block {
     leaf dre-repository-status {
       type string;
       description "DRE repository status";
     }
     container file-list {
       container file {
         leaf size {
           type int32;
           description "File size in bytes";
         }
         leaf date {
           type string;
           description "Modification time";
         }
         leaf file-name {
           type string;
           description "File name";
         }
         container file-fetch {
           leaf source-filename {
             type string;
           }
           leaf source-address {
             type string;
           }
           leaf staging-directory {
             type string;
           }
           leaf routing-instance {
             type string;
           }
           leaf cert-file {
             type string;
           }
           leaf no-check-certificate {
             type string;
           }
           leaf no-stage {
             type string;
           }
           leaf destination-filename {
             type string;
           }
         }
         container file-put {
           leaf source-filename {
             type string;
           }
           leaf destination-filename {
             type string;
           }
           leaf source-address {
             type string;
           }
           leaf routing-instance {
             type string;
           }
           leaf cleanup-source {
             type empty;
           }
           leaf filename {
             type string;
           }
           leaf encoding {
             type string;
             description "Encoding type: ascii or base64";
           }
           leaf permission {
             type string;
             description "Permission of destination file";
           }
           leaf delete-if-exist {
             type empty;
             description "Delete destination file if it exists";
           }
           leaf file-contents {
             type string;
             description "Base64 encoded contents of file";
           }
         }
         container send-file {
           leaf source-filename {
             type string;
           }
           leaf alias-filename {
             type string;
           }
           leaf display-spinner {
             type empty;
           }
           leaf source-address {
             type string;
           }
           leaf routing-instance {
             type string;
           }
         }
       }
     }
     container dre-repository-content {
       leaf dre-repository-content-header {
         type string;
         description "DRE repository content header";
       }
       leaf dre-repository-content-entry {
         type string;
         description "DRE repository content entry";
       }
       leaf dre-repository-content-footer {
         type string;
         description "DRE repository content footer";
       }
     }
     leaf node-name {
       type string;
     }
     container core-file-list {
       leaf description {
         type string;
       }
       container file {
         description "Information about a cleanup candidate";
         leaf size {
           type string;
         }
         leaf date {
           type string;
           description "Modification time";
         }
         leaf file-name {
           type string;
         }
       }
     }
     container core-local-host-file-list {
       leaf description {
         type string;
       }
       container file {
         description "Information about a cleanup candidate";
         leaf size {
           type string;
         }
         leaf date {
           type string;
           description "Modification time";
         }
         leaf file-name {
           type string;
         }
       }
     }
     container core-subdir-file-list {
       leaf description {
         type string;
       }
       container file {
         description "Information about a cleanup candidate";
         leaf size {
           type string;
         }
         leaf date {
           type string;
           description "Modification time";
         }
         leaf file-name {
           type string;
         }
       }
     }
     container fpc-file-list {
       leaf description {
         type string;
       }
       container file {
         description "Information about a cleanup candidate";
         leaf size {
           type string;
         }
         leaf date {
           type string;
           description "Modification time";
         }
         leaf file-name {
           type string;
         }
       }
     }
     container logical-systems-file-list {
       leaf description {
         type string;
       }
       container file {
         description "Information about a cleanup candidate";
         leaf size {
           type string;
         }
         leaf date {
           type string;
           description "Modification time";
         }
         leaf file-name {
           type string;
         }
       }
     }
     container journal-log-file-list {
       leaf description {
         type string;
       }
     }
     container log-file-list {
       leaf description {
         type string;
       }
       container file {
         description "Information about a cleanup candidate";
         leaf size {
           type string;
         }
         leaf date {
           type string;
           description "Modification time";
         }
         leaf file-name {
           type string;
         }
       }
     }
     container objmon-file-list {
       leaf description {
         type string;
       }
       container file {
         description "Information about a cleanup candidate";
         leaf size {
           type string;
         }
         leaf date {
           type string;
           description "Modification time";
         }
         leaf file-name {
           type string;
         }
       }
     }
     container trace-file-list {
       leaf description {
         type string;
       }
     }
     container si-trace-file-list {
       leaf description {
         type string;
       }
     }
     container ehmd-file-list {
       leaf description {
         type string;
       }
     }
     container iso-file-list {
       leaf description {
         type string;
       }
       container file {
         description "Information about a cleanup candidate";
         leaf size {
           type string;
         }
         leaf date {
           type string;
           description "Modification time";
         }
         leaf file-name {
           type string;
         }
       }
     }
     container system-software-versions-list {
       leaf description {
         type string;
       }
       leaf boot-device-type {
         type string;
       }
       leaf boot-device {
         type string;
       }
       container version-list {
         leaf current-version {
           type string;
         }
         leaf current-version-timestamp {
           type string;
         }
         leaf current-version-type {
           type string;
         }
         leaf nextboot-version {
           type string;
         }
         leaf nextboot-version-timestamp {
           type string;
         }
         leaf nextboot-version-type {
           type string;
         }
         leaf rollback-version {
           type string;
         }
         leaf rollback-version-timestamp {
           type string;
         }
         leaf rollback-version-type {
           type string;
         }
         container current-version-external-package-information {
           container package-information {
             list package-item {
               leaf package-name {
                 type string;
               }
               leaf package-version {
                 type string;
               }
             }
           }
           container external-package-information {
             list external-package-item {
               leaf external-package-name {
                 type string;
               }
               leaf external-package-version {
                 type string;
               }
               list content {
                 leaf content-name {
                   type string;
                 }
                 leaf content-type {
                   type string;
                 }
               }
             }
           }
         }
         container nextboot-version-external-package-information {
           container package-information {
             list package-item {
               leaf package-name {
                 type string;
               }
               leaf package-version {
                 type string;
               }
             }
           }
           container external-package-information {
             list external-package-item {
               leaf external-package-name {
                 type string;
               }
               leaf external-package-version {
                 type string;
               }
               list content {
                 leaf content-name {
                   type string;
                 }
                 leaf content-type {
                   type string;
                 }
               }
             }
           }
         }
         container rollback-version-external-package-information {
           container package-information {
             list package-item {
               leaf package-name {
                 type string;
               }
               leaf package-version {
                 type string;
               }
             }
           }
           container external-package-information {
             list external-package-item {
               leaf external-package-name {
                 type string;
               }
               leaf external-package-version {
                 type string;
               }
               list content {
                 leaf content-name {
                   type string;
                 }
                 leaf content-type {
                   type string;
                 }
               }
             }
           }
         }
       }
       container other-versions-list {
         list version-information {
           leaf other-versions {
             type string;
           }
           leaf other-versions-timestamp {
             type string;
           }
           leaf other-versions-type {
             type string;
           }
           container package-information {
             list package-item {
               leaf package-name {
                 type string;
               }
               leaf package-version {
                 type string;
               }
             }
           }
           container external-package-information {
             list external-package-item {
               leaf external-package-name {
                 type string;
               }
               leaf external-package-version {
                 type string;
               }
               list content {
                 leaf content-name {
                   type string;
                 }
                 leaf content-type {
                   type string;
                 }
               }
             }
           }
         }
       }
     }
     container tmp-file-list {
       leaf description {
         type string;
       }
     }
     container disc-size {
       leaf description {
         type string;
       }
     }
   }
   grouping snapshot-information-block {
     leaf snapshot-medium {
       type string;
       description "Media type of the snapshot";
     }
     leaf creation-date {
       type string;
       description "Snapshot creation date";
     }
     container inform {
       leaf source-daemon {
         type string;
       }
       leaf message {
         type string;
         description "Syslog message text";
       }
     }
     container snapshot-copy {
       leaf source-directory {
         type string;
         description "Directory to backup";
       }
       leaf destination-directory {
         type string;
         description "Backup directory";
       }
     }
     container archived-directory-list {
       leaf directory-name {
         type string;
         description "Directory name";
       }
     }
     container snapshot-partitions {
       description "Partitions on snapshot medium";
       list partition-information {
         description "Partition information";
         leaf partition {
           type string;
           description "Partition letter";
         }
         leaf mount-point {
           type string;
           description "Mount point";
         }
         leaf partition-size {
           type string;
           description "Size of partition";
         }
         leaf snapshot-argument {
           type string;
           description "Argument to snapshot used to configure size";
         }
       }
     }
     container software-version {
       description "Version of software snapshot";
       list package {
         description "Package in software snapshot";
         leaf package-name {
           type string;
           description "Name of software package";
         }
         leaf package-version {
           type string;
           description "Version of software package";
         }
       }
     }
   }
   grouping system-firmware-information-block {
     list system-firmware {
       container system-module {
         leaf firmware-name {
           type string;
           description "Name of this component";
         }
         container firmware-state {
           leaf firmware-type {
             type string;
             description "Type of this component";
           }
           leaf firmware-status {
             type string;
             description "Firmware status for this component";
           }
         }
       }
       container system-sub-module-firmware-list {
         list system-sub-module-firmware {
           leaf firmware-name {
             type string;
             description "Name of this component";
           }
           leaf firmware-type {
             type string;
             description "Type of this component";
           }
           leaf firmware-tag {
             type int32;
             description "Multiple firmware per FRU delimiter";
           }
           leaf firmware-revision {
             type string;
             description "Firmware version for this component";
           }
           leaf firmware-revision-available {
             type string;
             description "Firmware version available on disk for this component";
           }
           leaf firmware-status {
             type string;
             description "Firmware status for this component";
           }
         }
       }
       leaf firmware-name {
         type string;
         description "Name of this component";
       }
       leaf firmware-type {
         type string;
         description "Type of this component";
       }
       leaf firmware-tag {
         type int32;
         description "Multiple firmware per FRU delimiter";
       }
       leaf firmware-revision {
         type string;
         description "Firmware version for this component";
       }
       leaf firmware-revision-available {
         type string;
         description "Firmware version available on disk for this component";
       }
       leaf firmware-status {
         type string;
         description "Firmware status for this component";
       }
     }
   }
   grouping memory-profiling-action-block {
     leaf memory-profiling-action-results {
       type string;
       description "Memory profiling action";
     }
   }
   grouping jmrt-scan-result-block {
     leaf found-malware {
       type string;
       description "Found malware?";
     }
     container scan-results {
       description "Scan results";
       list result {
         description "Single scan result";
         leaf rule {
           type string;
           description "Scan rule";
         }
         leaf-list pid {
           type uint32;
           description "Process ID of matched process";
         }
         leaf-list file {
           type string;
           description "File that matched the rule";
         }
       }
     }
   }
   grouping jmrt-veriexec-check-block {
     leaf veriexec-running {
       type string;
       description "Veriexec is running?";
     }
   }
   grouping jmrt-integrity-check-block {
     leaf integrity-enforced {
       type string;
       description "Integrity is enforced?";
     }
   }
   grouping jmrt-fake-malware-block {
     leaf-list pid {
       type int32;
       description "PID of spawned example malware process";
     }
   }
   grouping jmrt-list-fake-malware-block {
     leaf-list pid {
       type int32;
       description "PID of spawned example malware process";
     }
   }
   grouping system-evpn-block {
     leaf evpn-host {
       type string;
       description "Evpn host";
     }
     container vlans {
       leaf summary {
         type string;
         description "Summary";
       }
       leaf vlans-in-sync {
         type string;
         description "Vlans in sync";
       }
       leaf vlans-out-of-sync {
         type string;
         description "Vlans out of sync";
       }
       list mac-table {
         leaf instance {
           type string;
           description "Routing instance name";
         }
         leaf vlan {
           type string;
           description "Vlan name";
         }
         leaf entry {
           type string;
           description "Entry";
         }
         leaf error {
           type string;
           description "Error";
         }
       }
       list mac-ip-table {
         leaf instance {
           type string;
           description "Routing instance name";
         }
         leaf vlan {
           type string;
           description "Vlan name";
         }
         leaf entry {
           type string;
           description "Entry";
         }
         leaf error {
           type string;
           description "Error";
         }
       }
       list mac-table-hash {
         leaf instance {
           type string;
           description "Routing instance name";
         }
         leaf vlan {
           type string;
           description "Vlan name";
         }
         leaf l2-hash {
           type string;
           description "L2 hash";
         }
       }
       list mac-ip-table-hash {
         leaf instance {
           type string;
           description "Routing instance name";
         }
         leaf vlan {
           type string;
           description "Vlan name";
         }
         leaf l2-hash {
           type string;
           description "L2 hash";
         }
       }
     }
   }
   grouping cert-key-pair-block {
     leaf cert-key-pair-name {
       type string;
       description "Key pair name";
     }
     leaf cert-key-pair-size {
       type string;
       description "Key pair size";
     }
   }
   grouping cert-ca-load-status-block {
     leaf cert-ca-profile {
       type string;
       description "Certificate Authority profile";
     }
   }
   grouping default-trusted-ca-certs-download-block {
     leaf trusted-ca-certs-download-status {
       type string;
       description "Download default trusted CA cert status";
     }
   }
   grouping default-trusted-ca-certs-download-cs-block {
     leaf default-trusted-ca-certs-download-check-server-status {
       type string;
       description "Default trusted CA certs check CDN server status";
     }
   }
   grouping default-trusted-ca-certs-download-status-block {
     leaf default-trusted-ca-certs-version-on-system {
       type string;
       description "Existing default trusted CA certs on system status";
     }
   }
   grouping cert-load-status-block {
     leaf cert-certificate-id {
       type string;
       description "Certificate identifier";
     }
   }
   grouping ca-profile-group-cert-status-block {
     leaf ca-group-cert-status {
       type string;
       description "CA Profile Group CA Cert Status";
     }
     leaf ca-group-missing-certs {
       type string;
       description "CA Profile Group CA Cert Status";
     }
   }
   grouping verify-integrity-status-block {
     leaf int-check-verification-status {
       type string;
       description "Integrity check verification status";
     }
   }
   grouping rebalance-interface-block {
     container rebalance-operation-status {
       leaf interface-name {
         type string;
         description "Interface name";
       }
     }
   }
   grouping bounce-interface-block {
     container bounce-operation-status {
       leaf interface-name {
         type string;
         description "Interface name";
       }
       leaf interval {
         type uint32;
       }
     }
   }
   grouping extension-service-daemonize-restart-status-block {
     leaf extension-service-stop-status {
       type string;
     }
     leaf extension-service-start-status {
       type string;
     }
   }
   grouping lacp-link-switchover-block {
     leaf aggregate-name {
       type string;
       description "Aggregated Interface name";
     }
     leaf lacp-status {
       type string;
       description "Lacp return status";
     }
   }
   grouping raid-information-block {
     leaf raid-status {
       type string;
     }
     list raid-members {
       leaf raid-member-device {
         type string;
       }
       leaf raid-member-format {
         type string;
       }
       leaf raid-member-name {
         type string;
       }
       leaf raid-member-type {
         type string;
       }
       leaf raid-member-status {
         type string;
       }
       leaf raid-member-size {
         type string;
       }
       leaf raid-member-offset {
         type string;
       }
     }
   }
   grouping snmp-spoof-trap-results-block {
     leaf snmp-spoofable-traps {
       type string;
       description "SNMP traps supported for spoofing";
     }
     leaf snmp-spoof-trap-result {
       type string;
       description "Result of SNMP 'spoof-trap' request";
     }
   }
   grouping snmp-utility-mib-results-block {
     leaf snmp-utility-mib-result {
       type string;
       description "Result of SNMP 'utility-mib' request";
     }
   }
   grouping chassis-mic-state-block {
     leaf summary {
       type string;
     }
     leaf-list error-info {
       type string;
     }
   }
   grouping chassis-optics-state-block {
     leaf summary {
       type string;
     }
     leaf-list error-info {
       type string;
     }
   }
   grouping chassis-fpc-state-block {
     leaf summary {
       type string;
     }
     leaf-list error-info {
       type string;
     }
   }
   grouping chassis-fabric-plane-state-block {
     leaf summary {
       type string;
     }
     leaf-list error-info {
       type string;
     }
   }
   grouping chassis-afeb-state-block {
     leaf summary {
       type string;
     }
     leaf-list error-info {
       type string;
     }
   }
   grouping chassis-tfeb-state-block {
     leaf summary {
       type string;
     }
     leaf-list error-info {
       type string;
     }
   }
   grouping chassis-routing-engine-state-block {
     leaf summary {
       type string;
     }
     leaf message {
       type string;
     }
     leaf error {
       type string;
     }
   }
   grouping chassis-fpm-block {
     leaf summary {
       type string;
     }
     leaf-list error-info {
       type string;
     }
   }
   grouping chassis-beacon-information-block {
     container chassis-beacon-item {
       leaf beacon-name {
         type string;
       }
       leaf beacon-state {
         type string;
       }
     }
   }
   grouping fibd-statistics-filter-block {
     leaf fibd-filter-request {
       type string;
       description "Set fibd filter request";
     }
   }
   grouping multi-routing-engine-results-smo-log-block {
     list multi-routing-engine-item-smo-log {
       leaf re-name {
         type string;
         description "Hostname of the Routing Engine";
       }
       leaf smo-resp {
         type string;
       }
     }
   }
   grouping flowdebug-start-block {
     leaf resp {
       type string;
     }
   }
   grouping flowdebug-stop-block {
     leaf resp {
       type string;
     }
   }
   grouping flowdebug-showfilter-block {
     leaf resp {
       type string;
     }
   }
   grouping flowdebug-setfilter-block {
     leaf resp {
       type string;
     }
   }
   grouping flight-recorder-information-block {
     container summary {
       leaf output {
         type string;
       }
     }
   }
   grouping rv-request-policy-information-block {
     leaf ip-prefix-count {
       type uint32;
     }
     leaf ip6-prefix-count {
       type uint32;
     }
   }
 }
