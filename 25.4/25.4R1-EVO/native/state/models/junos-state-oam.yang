module junos-state-oam {
  yang-version 1.1;
  namespace "http://yang.juniper.net/junos/state/oam";
  prefix js-oam;

  import junos-extensions {
    prefix jx;
  }

  import junos-state {
    prefix js;
  }

  import junos-state-protocols {
    prefix js-pro;
  }

  organization
    "Juniper Networks, Inc.";

  contact
    "Juniper Networks, Inc.

     1133 Innovation Way
     Sunnyvale, CA 94089

     +1 888 314-5822

     E-mail: yang-support@juniper.net";

  description
    "This module contains a collection of top level nodes for JUNOS
     OAM state data.

     Copyright (c) 2025 Juniper Networks, Inc.
     All rights reserved.";

  revision 2025-04-25 {
    description
     "Addition of jx:origin annotation";
    reference "0.1.1";
  }

  revision 2023-03-27 {
    description
      "Initial revision";
    reference "0.1.0";
  }

  jx:version "0.1.1";
  jx:origin "juniper";

  grouping oam-ethernet-top {
    description
      "Top-level grouping for OAM Ethernet state data";

    container ethernet {
      description
        "Encapsulating container for OAM Ethernet state";
    }
  }

  grouping oam-top {
    description
      "Top-level grouping for OAM state data";

    container oam {
      description
        "Top-level protocol container for OAM state";

      uses oam-ethernet-top;
    }
  }

  augment "/js:state/js-pro:protocols" {
    description
      "Adds OAM domain to protocol state";

    uses oam-top;
  }
}
