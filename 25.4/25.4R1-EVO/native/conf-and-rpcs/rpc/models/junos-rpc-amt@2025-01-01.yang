/*
 * Copyright (c) 2025 Juniper Networks, Inc.
 * All rights reserved.
 */
 module junos-rpc-amt {
   namespace "http://yang.juniper.net/junos/rpc/amt";

   prefix amt;

   import junos-common-types {
     prefix jt;
     revision-date 2025-01-01;
   }

   organization "Juniper Networks, Inc.";

   contact "yang-support@juniper.net";

   description "Junos RPC YANG module for amt command(s)";

   revision 2025-01-01 {
     description "Junos: 25.4R1.13-EVO";
   }

   rpc get-amt-tunnel-information {
     description "Show AMT tunnel parameters";
     input {
       choice daemon-select {
         case logical-system {
           leaf logical-system {
             description "Name of logical system, or 'all'";
             type string {
             }
           }
         }
       }
       leaf instance {
         description "Name of instance";
         type string;
       }
       leaf verbosity_level {
         default "brief";
         type enumeration {
           enum "brief" {
             description "Display brief output (default)";
           }
           enum "detail" {
             description "Display detailed output";
           }
         }
       }
     }
     output {
       container amt-tunnel-information {
         uses amt-tunnel-information-block;
       }
     }
   }
   rpc get-amt-tunnel-interface {
     description "AMT tunnel interface";
     input {
       choice daemon-select {
         case logical-system {
           leaf logical-system {
             description "Name of logical system, or 'all'";
             type string {
             }
           }
         }
       }
       leaf instance {
         description "Name of instance";
         type string;
       }
       leaf verbosity_level {
         default "brief";
         type enumeration {
           enum "brief" {
             description "Display brief output (default)";
           }
           enum "detail" {
             description "Display detailed output";
           }
         }
       }
       leaf interface {
         description "Name of the interface";
         type string;
         mandatory true;
       }
     }
     output {
       container amt-tunnel-information {
         uses amt-tunnel-information-block;
       }
     }
   }
   rpc get-amt-tunnel-gateway-address {
     description "AMT tunnel gateway address";
     input {
       choice daemon-select {
         case logical-system {
           leaf logical-system {
             description "Name of logical system, or 'all'";
             type string {
             }
           }
         }
       }
       leaf instance {
         description "Name of instance";
         type string;
       }
       leaf verbosity_level {
         default "brief";
         type enumeration {
           enum "brief" {
             description "Display brief output (default)";
           }
           enum "detail" {
             description "Display detailed output";
           }
         }
       }
       leaf address {
         description "IP address of the gateway";
         type string;
         mandatory true;
       }
       leaf port {
         description "UDP port of the gateway";
         type union {
           type string {
             pattern "<.*>|$.*";
           }
           type uint16 {
             range "1 .. 65535";
           }
         }
       }
     }
     output {
       container amt-tunnel-information {
         uses amt-tunnel-information-block;
       }
     }
   }
   rpc get-amt-summary {
     description "Show AMT configuration summary";
     input {
       choice daemon-select {
         case logical-system {
           leaf logical-system {
             description "Name of logical system, or 'all'";
             type string {
             }
           }
         }
       }
       leaf instance {
         description "Name of instance";
         type string;
       }
     }
     output {
       container amt-summary {
         uses amt-summary-block;
       }
     }
   }
   rpc get-amt-statistics {
     description "Show AMT statistics summary";
     input {
       choice daemon-select {
         case logical-system {
           leaf logical-system {
             description "Name of logical system, or 'all'";
             type string {
             }
           }
         }
       }
       leaf instance {
         description "Name of instance";
         type string;
       }
     }
     output {
       container amt-instance-statistics {
         uses amt-instance-statistics-block;
       }
     }
   }
   grouping command-forwarding {
     leaf no-forwarding {
       description "No forwarding";
       type empty;
     }
     choice chassis-selector {
       case case_1 {
         leaf all-chassis {
           description "All chassis";
           type empty;
         }
       }
       case case_2 {
         leaf all-lcc {
           description "All LCC chassis";
           type empty;
         }
       }
       case case_3 {
         leaf scc {
           description "SCC";
           type empty;
         }
       }
       case case_4 {
         leaf sfc {
           description "SFC";
           type union {
             type string {
               pattern "<.*>|$.*";
             }
             type uint32;
           }
         }
       }
       case case_5 {
         leaf lcc {
           description "Specific LCC";
           type union {
             type string {
               pattern "<.*>|$.*";
             }
             type uint32;
           }
         }
       }
       case case_6 {
         leaf node {
           description "Specific node";
           type string;
         }
       }
       case case_7 {
         leaf bsys {
           description "Base system";
           type empty;
         }
       }
       case case_8 {
         leaf gnf {
           description "Specific guest network function";
           type union {
             type string {
               pattern "<.*>|$.*";
             }
             type uint32 {
               range "1 .. 10";
             }
           }
         }
       }
       case case_9 {
         leaf all-gnfs {
           description "All guest network functions";
           type empty;
         }
       }
       case case_10 {
         leaf all-system {
           description "All system (BSYS and GNFs)";
           type empty;
         }
       }
       case case_11 {
         leaf server {
           description "Specific server slot";
           type union {
             type string {
               pattern "<.*>|$.*";
             }
             type uint32 {
               range "0 .. 1";
             }
           }
         }
       }
       case case_12 {
         leaf all-servers {
           description "All servers";
           type empty;
         }
       }
       case case_13 {
         leaf vnf {
           description "Specific virtual-network-function";
           type string;
         }
       }
       case case_14 {
         leaf all-vnfs {
           description "All virtual-network-functions";
           type empty;
         }
       }
     }
     choice re-selector {
       case case_1 {
         leaf re0 {
           description "RE0";
           type empty;
         }
       }
       case case_2 {
         leaf re1 {
           description "RE1";
           type empty;
         }
       }
       case case_3 {
         leaf routing-engine {
           description "Specific routing engine";
           type enumeration {
             enum "local" {
               description "Local routing engine";
             }
             enum "other" {
               description "Other routing engine";
             }
             enum "master" {
               description "Master routing engine";
             }
             enum "backup" {
               description "Backup routing engine";
             }
             enum "both" {
               description "Both routing engines";
             }
           }
         }
       }
     }
     choice lr-selector {
       case case_1 {
         leaf logical-system {
           description "Name of logical system, or 'all'";
           type string;
         }
       }
     }
     choice tenant-selector {
       case case_1 {
         leaf tenant {
           description "Name of tenant, or 'all'";
           type string;
         }
       }
     }
     choice vc-selector {
       case case_1 {
         leaf local {
           description "Local virtual chassis member";
           type empty;
         }
       }
       case case_2 {
         leaf all-members {
           description "All virtual chassis members";
           type empty;
         }
       }
       case case_3 {
         leaf member {
           description "Specific virtual chassis member which is master";
           type union {
             type string {
               pattern "<.*>|$.*";
             }
             type uint32;
           }
         }
       }
     }
   }
   grouping amt-tunnel-information-block {
     list amt-tunnel {
       description "Display AMT tunnel information";
       leaf amt-tunnel-gateway-address {
         type string;
         description "AMT gateway address for the tunnel";
       }
       leaf amt-tunnel-gateway-port {
         type int32;
         description "AMT gateway UDP port for the tunnel";
       }
       leaf amt-tunnel-interface {
         type string;
         description "AMT tunnel logical interface";
       }
       leaf amt-tunnel-state {
         type string;
         description "AMT tunnel logical interface";
       }
       leaf amt-inactivity-timeout {
         type int32;
         description "AMT tunnel inactivity timeout";
       }
       leaf amt-tunnel-gateway-nonce {
         type int32;
         description "AMT membership request nonce";
       }
       leaf amt-tunnel-gateway-mac {
         type string;
         description "AMT membership request mac";
       }
       leaf amt-tunnel-multicast-groups {
         type int32;
         description "Number of active multicast groups on this AMT tunnel";
       }
       list mgm-group {
         leaf multicast-group-address {
           type jt:ipaddr;
           description "Group address";
         }
         leaf mgm-group-mode-type {
           type string;
           description "Group operational mode (Include/Exclude).";
         }
         leaf multicast-source-address {
           type jt:ipaddr;
           description "Source address";
         }
         list host-record {
           leaf record-type {
             type string;
           }
           leaf receiver {
             type jt:ipaddr;
           }
           leaf record-timeout {
             type int32;
           }
         }
         list reverse-oif {
           leaf oif-name {
             type string;
             description "Reverse OIF name";
           }
           leaf host-count {
             type int32;
             description "Host reference count";
           }
         }
         leaf last-address {
           type jt:ipaddr;
         }
         leaf mgm-timeout {
           type int32;
         }
         leaf mgm-type {
           type string;
         }
         leaf mgm-source-timeout {
           type int32;
           description "Amount of time for which the traffic from source is forwarded.";
         }
         leaf mgm-type-instance {
           type string;
         }
         leaf mgm-group-output-interface {
           type string;
           description "Group output interface";
         }
         leaf mgm-output-interface-status {
           type string;
           description "Group output interface status";
         }
       }
       container amt-tunnel-message-count {
         leaf amt-request-message {
           type int32;
           description "Number of AMT membership request messages received";
         }
         leaf amt-membership-update-message {
           type int32;
           description "Number of AMT membership updates received";
         }
       }
     }
   }
   grouping amt-summary-block {
     leaf amt-anycast-prefix {
       type string;
       description "AMT anycast prefix";
     }
     leaf amt-anycast-address {
       type string;
       description "AMT anycast address";
     }
     leaf amt-local-address {
       type string;
       description "AMT local address";
     }
     leaf amt-tunnel-limit {
       type int32;
       description "Maximum number of AMT tunnels";
     }
     leaf amt-active-tunnels {
       type int32;
       description "Number of currently active AMT tunnels";
     }
     leaf amt-unicast-stream-limit {
       type int32;
       description "Maximum number of unicast streams";
     }
     leaf amt-active-unicast-streams {
       type int32;
       description "Number of currently active AMT unicast streams";
     }
   }
   grouping amt-instance-statistics-block {
     leaf amt-relay-discovery-messages {
       type int32;
       description "Number of AMT relay discovery messages received";
     }
     leaf amt-membership-request-messages {
       type int32;
       description "Number of AMT membership request messages received";
     }
     leaf amt-membership-update-messages {
       type int32;
       description "Number of AMT membership update messages received";
     }
     leaf amt-relay-advertisement-messages {
       type int32;
       description "Number of AMT relay advertisement messages sent";
     }
     leaf amt-membership-query-messages {
       type int32;
       description "Number of AMT membership query messages sent";
     }
     leaf amt-incomplete-packet {
       type int32;
       description "Number of incomplete AMT messages received";
     }
     leaf amt-invalid-mac {
       type int32;
       description "Number of AMT membership update messages received with invalid MAC";
     }
     leaf amt-unexpected-type {
       type int32;
       description "Number of AMT messages received with unexpected messages type";
     }
     leaf amt-relay-discovery-invalid-address {
       type int32;
       description "Number of AMT relay discovery messages received with invalid address";
     }
     leaf amt-membership-request-invalid-address {
       type int32;
       description "Number of AMT membership request messages received with invalid address";
     }
     leaf amt-membership-update-invalid-address {
       type int32;
       description "Number of AMT membership update messages received with invalid address";
     }
     leaf amt-incomplete-relay-discovery {
       type int32;
       description "Number of incomplete AMT relay discovery messages";
     }
     leaf amt-incomplete-membership-request {
       type int32;
       description "Number of incomplete AMT membership request messages";
     }
     leaf amt-incomplete-membership-update {
       type int32;
       description "Number of incomplete AMT membership update messages";
     }
     leaf amt-no-active-gateway {
       type int32;
       description "Number AMT membership update messages received with no active gateway";
     }
     leaf amt-invalid-inner-packet-checksum {
       type int32;
       description "Number of AMT packets with invalid inner packet checksum";
     }
     leaf amt-gateways-timed-out {
       type int32;
       description "Number of AMT gateways that have timed out due to inactivity";
     }
   }
 }
