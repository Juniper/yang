/*
 * Copyright (c) 2025 Juniper Networks, Inc.
 * All rights reserved.
 */
 module junos-rpc-dvmrp {
   namespace "http://yang.juniper.net/junos/rpc/dvmrp";

   prefix dvmrp;

   import junos-common-types {
     prefix jt;
     revision-date 2025-01-01;
   }

   organization "Juniper Networks, Inc.";

   contact "yang-support@juniper.net";

   description "Junos RPC YANG module for dvmrp command(s)";

   revision 2025-01-01 {
     description "Junos: 25.4R1.13-EVO";
   }

   rpc get-dvmrp-neighbors-information {
     description "Show DVMRP neighbors";
     input {
       choice daemon-select {
         case logical-system {
           leaf logical-system {
             description "Name of logical system, or 'all'";
             type string {
             }
           }
         }
       }
     }
     output {
       container dvmrp-neighbors-information {
         uses dvmrp-neighbors-information-block;
       }
     }
   }
   rpc get-dvmrp-interfaces-information {
     description "Show DVMRP interfaces";
     input {
       choice daemon-select {
         case logical-system {
           leaf logical-system {
             description "Name of logical system, or 'all'";
             type string {
             }
           }
         }
       }
     }
     output {
       container dvmrp-interfaces-information {
         uses dvmrp-interfaces-information-block;
       }
     }
   }
   rpc get-dvmrp-prunes-information {
     description "Show DVMRP prunes";
     input {
       choice daemon-select {
         case logical-system {
           leaf logical-system {
             description "Name of logical system, or 'all'";
             type string {
             }
           }
         }
       }
       leaf type {
         default "all";
         type enumeration {
           enum "all" {
             description "Display both received and transmitted prunes";
           }
           enum "rx" {
             description "Display received prunes";
           }
           enum "tx" {
             description "Display transmitted prunes";
           }
         }
       }
     }
     output {
       container dvmrp-prunes-information {
         uses dvmrp-prunes-information-block;
       }
     }
   }
   rpc get-dvmrp-prefix-information {
     description "Show DVMRP prefixes";
     input {
       choice daemon-select {
         case logical-system {
           leaf logical-system {
             description "Name of logical system, or 'all'";
             type string {
             }
           }
         }
       }
       leaf verbosity_level {
         default "brief";
         type enumeration {
           enum "brief" {
             description "Display brief output (default)";
           }
           enum "detail" {
             description "Display detailed output";
           }
         }
       }
       leaf prefix {
         description "DVMRP prefix";
         type string;
       }
     }
     output {
       container dvmrp-prefix-information {
         uses dvmrp-prefix-information-block;
       }
     }
   }
   grouping command-forwarding {
     leaf no-forwarding {
       description "No forwarding";
       type empty;
     }
     choice chassis-selector {
       case case_1 {
         leaf all-chassis {
           description "All chassis";
           type empty;
         }
       }
       case case_2 {
         leaf all-lcc {
           description "All LCC chassis";
           type empty;
         }
       }
       case case_3 {
         leaf scc {
           description "SCC";
           type empty;
         }
       }
       case case_4 {
         leaf sfc {
           description "SFC";
           type union {
             type string {
               pattern "<.*>|$.*";
             }
             type uint32;
           }
         }
       }
       case case_5 {
         leaf lcc {
           description "Specific LCC";
           type union {
             type string {
               pattern "<.*>|$.*";
             }
             type uint32;
           }
         }
       }
       case case_6 {
         leaf node {
           description "Specific node";
           type string;
         }
       }
       case case_7 {
         leaf bsys {
           description "Base system";
           type empty;
         }
       }
       case case_8 {
         leaf gnf {
           description "Specific guest network function";
           type union {
             type string {
               pattern "<.*>|$.*";
             }
             type uint32 {
               range "1 .. 10";
             }
           }
         }
       }
       case case_9 {
         leaf all-gnfs {
           description "All guest network functions";
           type empty;
         }
       }
       case case_10 {
         leaf all-system {
           description "All system (BSYS and GNFs)";
           type empty;
         }
       }
       case case_11 {
         leaf server {
           description "Specific server slot";
           type union {
             type string {
               pattern "<.*>|$.*";
             }
             type uint32 {
               range "0 .. 1";
             }
           }
         }
       }
       case case_12 {
         leaf all-servers {
           description "All servers";
           type empty;
         }
       }
       case case_13 {
         leaf vnf {
           description "Specific virtual-network-function";
           type string;
         }
       }
       case case_14 {
         leaf all-vnfs {
           description "All virtual-network-functions";
           type empty;
         }
       }
     }
     choice re-selector {
       case case_1 {
         leaf re0 {
           description "RE0";
           type empty;
         }
       }
       case case_2 {
         leaf re1 {
           description "RE1";
           type empty;
         }
       }
       case case_3 {
         leaf routing-engine {
           description "Specific routing engine";
           type enumeration {
             enum "local" {
               description "Local routing engine";
             }
             enum "other" {
               description "Other routing engine";
             }
             enum "master" {
               description "Master routing engine";
             }
             enum "backup" {
               description "Backup routing engine";
             }
             enum "both" {
               description "Both routing engines";
             }
           }
         }
       }
     }
     choice lr-selector {
       case case_1 {
         leaf logical-system {
           description "Name of logical system, or 'all'";
           type string;
         }
       }
     }
     choice tenant-selector {
       case case_1 {
         leaf tenant {
           description "Name of tenant, or 'all'";
           type string;
         }
       }
     }
     choice vc-selector {
       case case_1 {
         leaf local {
           description "Local virtual chassis member";
           type empty;
         }
       }
       case case_2 {
         leaf all-members {
           description "All virtual chassis members";
           type empty;
         }
       }
       case case_3 {
         leaf member {
           description "Specific virtual chassis member which is master";
           type union {
             type string {
               pattern "<.*>|$.*";
             }
             type uint32;
           }
         }
       }
     }
   }
   grouping dvmrp-neighbors-information-block {
     list dvmrp-instance {
       leaf instance-name {
         type string;
       }
       list dvmrp-interface {
         leaf interface-name {
           type string;
           description "Name of interface";
         }
         leaf dvmrp-interface-state {
           type string;
         }
         leaf dvmrp-interface-leaf {
           type string;
         }
         leaf dvmrp-interface-metric {
           type int32;
         }
         leaf dvmrp-interface-announcements {
           type int32;
         }
         leaf dvmrp-interface-mode {
           type string;
         }
         leaf dvmrp-interface-holdtime {
           type int32;
         }
       }
       list dvmrp-graft {
         leaf multicast-group-address {
           type jt:ipaddr;
           description "Group address";
         }
         leaf multicast-source-address {
           type jt:ipaddr;
           description "Source address";
         }
         leaf dvmrp-graft-expire-time {
           type int32;
         }
         leaf dvmrp-neighbor-address {
           type jt:ipaddr;
         }
       }
       list dvmrp-neighbor {
         leaf dvmrp-neighbor-address {
           type jt:ipaddr;
         }
         leaf interface-name {
           type string;
           description "Name of interface";
         }
         leaf dvmrp-major-version {
           type int32;
         }
         leaf dvmrp-minor-version {
           type int32;
         }
         leaf dvmrp-neighbor-routes {
           type int32;
         }
         leaf dvmrp-neighbor-timeout {
           type int32;
         }
         leaf dvmrp-neighbor-transitions {
           type int32;
         }
         container dvmrp-capability-flags {
           leaf dvmrp-neighbor-one-way {
             type empty;
           }
           leaf dvmrp-neighbor-prune {
             type empty;
           }
           leaf dvmrp-neighbor-generation-id {
             type empty;
           }
           leaf dvmrp-neighbor-mtrace {
             type empty;
           }
           leaf dvmrp-neighbor-leave {
             type empty;
           }
           leaf dvmrp-neighbor-snmp {
             type empty;
           }
           leaf dvmrp-neighbor-netmask {
             type empty;
           }
         }
       }
       list dvmrp-prefix-entry {
         leaf dvmrp-prefix {
           type jt:ipaddr;
         }
         leaf dvmrp-prefix-length {
           type int32;
         }
         leaf dvmrp-next-hop {
           type jt:ipaddr;
         }
         leaf dvmrp-prefix-age {
           type string;
         }
         list dvmrp-group {
           leaf multicast-group-address {
             type jt:ipaddr;
             description "Group address";
           }
           leaf dvmrp-prunes-sent {
             type int32;
           }
           leaf dvmrp-grafts-sent {
             type int32;
           }
           leaf dvmrp-cache-lifetime {
             type int32;
           }
           leaf dvmrp-prune-time {
             type int32;
           }
           leaf dvmrp-prune-lifetime {
             type int32;
           }
           list dvmrp-prune {
             leaf dvmrp-neighbor-address {
               type jt:ipaddr;
             }
           }
         }
       }
       list dvmrp-prune {
         leaf multicast-group-address {
           type jt:ipaddr;
           description "Group address";
         }
         leaf multicast-source-address {
           type jt:ipaddr;
           description "Source address";
         }
         leaf multicast-source-prefix-length {
           type uint32;
           description "Source prefix length";
         }
         leaf dvmrp-prune-timeout {
           type int32;
         }
         leaf dvmrp-neighbor-address {
           type jt:ipaddr;
         }
       }
     }
   }
   grouping dvmrp-interfaces-information-block {
     list dvmrp-instance {
       leaf instance-name {
         type string;
       }
       list dvmrp-interface {
         leaf interface-name {
           type string;
           description "Name of interface";
         }
         leaf dvmrp-interface-state {
           type string;
         }
         leaf dvmrp-interface-leaf {
           type string;
         }
         leaf dvmrp-interface-metric {
           type int32;
         }
         leaf dvmrp-interface-announcements {
           type int32;
         }
         leaf dvmrp-interface-mode {
           type string;
         }
         leaf dvmrp-interface-holdtime {
           type int32;
         }
       }
       list dvmrp-graft {
         leaf multicast-group-address {
           type jt:ipaddr;
           description "Group address";
         }
         leaf multicast-source-address {
           type jt:ipaddr;
           description "Source address";
         }
         leaf dvmrp-graft-expire-time {
           type int32;
         }
         leaf dvmrp-neighbor-address {
           type jt:ipaddr;
         }
       }
       list dvmrp-neighbor {
         leaf dvmrp-neighbor-address {
           type jt:ipaddr;
         }
         leaf interface-name {
           type string;
           description "Name of interface";
         }
         leaf dvmrp-major-version {
           type int32;
         }
         leaf dvmrp-minor-version {
           type int32;
         }
         leaf dvmrp-neighbor-routes {
           type int32;
         }
         leaf dvmrp-neighbor-timeout {
           type int32;
         }
         leaf dvmrp-neighbor-transitions {
           type int32;
         }
         container dvmrp-capability-flags {
           leaf dvmrp-neighbor-one-way {
             type empty;
           }
           leaf dvmrp-neighbor-prune {
             type empty;
           }
           leaf dvmrp-neighbor-generation-id {
             type empty;
           }
           leaf dvmrp-neighbor-mtrace {
             type empty;
           }
           leaf dvmrp-neighbor-leave {
             type empty;
           }
           leaf dvmrp-neighbor-snmp {
             type empty;
           }
           leaf dvmrp-neighbor-netmask {
             type empty;
           }
         }
       }
       list dvmrp-prefix-entry {
         leaf dvmrp-prefix {
           type jt:ipaddr;
         }
         leaf dvmrp-prefix-length {
           type int32;
         }
         leaf dvmrp-next-hop {
           type jt:ipaddr;
         }
         leaf dvmrp-prefix-age {
           type string;
         }
         list dvmrp-group {
           leaf multicast-group-address {
             type jt:ipaddr;
             description "Group address";
           }
           leaf dvmrp-prunes-sent {
             type int32;
           }
           leaf dvmrp-grafts-sent {
             type int32;
           }
           leaf dvmrp-cache-lifetime {
             type int32;
           }
           leaf dvmrp-prune-time {
             type int32;
           }
           leaf dvmrp-prune-lifetime {
             type int32;
           }
           list dvmrp-prune {
             leaf dvmrp-neighbor-address {
               type jt:ipaddr;
             }
           }
         }
       }
       list dvmrp-prune {
         leaf multicast-group-address {
           type jt:ipaddr;
           description "Group address";
         }
         leaf multicast-source-address {
           type jt:ipaddr;
           description "Source address";
         }
         leaf multicast-source-prefix-length {
           type uint32;
           description "Source prefix length";
         }
         leaf dvmrp-prune-timeout {
           type int32;
         }
         leaf dvmrp-neighbor-address {
           type jt:ipaddr;
         }
       }
     }
   }
   grouping dvmrp-prunes-information-block {
     list dvmrp-instance {
       leaf instance-name {
         type string;
       }
       list dvmrp-interface {
         leaf interface-name {
           type string;
           description "Name of interface";
         }
         leaf dvmrp-interface-state {
           type string;
         }
         leaf dvmrp-interface-leaf {
           type string;
         }
         leaf dvmrp-interface-metric {
           type int32;
         }
         leaf dvmrp-interface-announcements {
           type int32;
         }
         leaf dvmrp-interface-mode {
           type string;
         }
         leaf dvmrp-interface-holdtime {
           type int32;
         }
       }
       list dvmrp-graft {
         leaf multicast-group-address {
           type jt:ipaddr;
           description "Group address";
         }
         leaf multicast-source-address {
           type jt:ipaddr;
           description "Source address";
         }
         leaf dvmrp-graft-expire-time {
           type int32;
         }
         leaf dvmrp-neighbor-address {
           type jt:ipaddr;
         }
       }
       list dvmrp-neighbor {
         leaf dvmrp-neighbor-address {
           type jt:ipaddr;
         }
         leaf interface-name {
           type string;
           description "Name of interface";
         }
         leaf dvmrp-major-version {
           type int32;
         }
         leaf dvmrp-minor-version {
           type int32;
         }
         leaf dvmrp-neighbor-routes {
           type int32;
         }
         leaf dvmrp-neighbor-timeout {
           type int32;
         }
         leaf dvmrp-neighbor-transitions {
           type int32;
         }
         container dvmrp-capability-flags {
           leaf dvmrp-neighbor-one-way {
             type empty;
           }
           leaf dvmrp-neighbor-prune {
             type empty;
           }
           leaf dvmrp-neighbor-generation-id {
             type empty;
           }
           leaf dvmrp-neighbor-mtrace {
             type empty;
           }
           leaf dvmrp-neighbor-leave {
             type empty;
           }
           leaf dvmrp-neighbor-snmp {
             type empty;
           }
           leaf dvmrp-neighbor-netmask {
             type empty;
           }
         }
       }
       list dvmrp-prefix-entry {
         leaf dvmrp-prefix {
           type jt:ipaddr;
         }
         leaf dvmrp-prefix-length {
           type int32;
         }
         leaf dvmrp-next-hop {
           type jt:ipaddr;
         }
         leaf dvmrp-prefix-age {
           type string;
         }
         list dvmrp-group {
           leaf multicast-group-address {
             type jt:ipaddr;
             description "Group address";
           }
           leaf dvmrp-prunes-sent {
             type int32;
           }
           leaf dvmrp-grafts-sent {
             type int32;
           }
           leaf dvmrp-cache-lifetime {
             type int32;
           }
           leaf dvmrp-prune-time {
             type int32;
           }
           leaf dvmrp-prune-lifetime {
             type int32;
           }
           list dvmrp-prune {
             leaf dvmrp-neighbor-address {
               type jt:ipaddr;
             }
           }
         }
       }
       list dvmrp-prune {
         leaf multicast-group-address {
           type jt:ipaddr;
           description "Group address";
         }
         leaf multicast-source-address {
           type jt:ipaddr;
           description "Source address";
         }
         leaf multicast-source-prefix-length {
           type uint32;
           description "Source prefix length";
         }
         leaf dvmrp-prune-timeout {
           type int32;
         }
         leaf dvmrp-neighbor-address {
           type jt:ipaddr;
         }
       }
     }
   }
   grouping dvmrp-prefix-information-block {
     list dvmrp-instance {
       leaf instance-name {
         type string;
       }
       list dvmrp-interface {
         leaf interface-name {
           type string;
           description "Name of interface";
         }
         leaf dvmrp-interface-state {
           type string;
         }
         leaf dvmrp-interface-leaf {
           type string;
         }
         leaf dvmrp-interface-metric {
           type int32;
         }
         leaf dvmrp-interface-announcements {
           type int32;
         }
         leaf dvmrp-interface-mode {
           type string;
         }
         leaf dvmrp-interface-holdtime {
           type int32;
         }
       }
       list dvmrp-graft {
         leaf multicast-group-address {
           type jt:ipaddr;
           description "Group address";
         }
         leaf multicast-source-address {
           type jt:ipaddr;
           description "Source address";
         }
         leaf dvmrp-graft-expire-time {
           type int32;
         }
         leaf dvmrp-neighbor-address {
           type jt:ipaddr;
         }
       }
       list dvmrp-neighbor {
         leaf dvmrp-neighbor-address {
           type jt:ipaddr;
         }
         leaf interface-name {
           type string;
           description "Name of interface";
         }
         leaf dvmrp-major-version {
           type int32;
         }
         leaf dvmrp-minor-version {
           type int32;
         }
         leaf dvmrp-neighbor-routes {
           type int32;
         }
         leaf dvmrp-neighbor-timeout {
           type int32;
         }
         leaf dvmrp-neighbor-transitions {
           type int32;
         }
         container dvmrp-capability-flags {
           leaf dvmrp-neighbor-one-way {
             type empty;
           }
           leaf dvmrp-neighbor-prune {
             type empty;
           }
           leaf dvmrp-neighbor-generation-id {
             type empty;
           }
           leaf dvmrp-neighbor-mtrace {
             type empty;
           }
           leaf dvmrp-neighbor-leave {
             type empty;
           }
           leaf dvmrp-neighbor-snmp {
             type empty;
           }
           leaf dvmrp-neighbor-netmask {
             type empty;
           }
         }
       }
       list dvmrp-prefix-entry {
         leaf dvmrp-prefix {
           type jt:ipaddr;
         }
         leaf dvmrp-prefix-length {
           type int32;
         }
         leaf dvmrp-next-hop {
           type jt:ipaddr;
         }
         leaf dvmrp-prefix-age {
           type string;
         }
         list dvmrp-group {
           leaf multicast-group-address {
             type jt:ipaddr;
             description "Group address";
           }
           leaf dvmrp-prunes-sent {
             type int32;
           }
           leaf dvmrp-grafts-sent {
             type int32;
           }
           leaf dvmrp-cache-lifetime {
             type int32;
           }
           leaf dvmrp-prune-time {
             type int32;
           }
           leaf dvmrp-prune-lifetime {
             type int32;
           }
           list dvmrp-prune {
             leaf dvmrp-neighbor-address {
               type jt:ipaddr;
             }
           }
         }
       }
       list dvmrp-prune {
         leaf multicast-group-address {
           type jt:ipaddr;
           description "Group address";
         }
         leaf multicast-source-address {
           type jt:ipaddr;
           description "Source address";
         }
         leaf multicast-source-prefix-length {
           type uint32;
           description "Source prefix length";
         }
         leaf dvmrp-prune-timeout {
           type int32;
         }
         leaf dvmrp-neighbor-address {
           type jt:ipaddr;
         }
       }
     }
   }
 }
