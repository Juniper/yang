module junos-genstate-lacp-interface-information-list {
   yang-version 1;
   namespace "http://yang.juniper.net/junos/genstate/lacp-interface-information-list";
   prefix jgliil;

   import junos-genstate {
     prefix jgs;
     revision-date 2025-01-01;
   }

   import junos-common-types {
     prefix jt;
     revision-date 2025-01-01;
   }

   organization
     "Juniper Networks, Inc.";

   contact
     "Juniper Networks, Inc.

      1133 Innovation Way
      Sunnyvale, CA 94089

      +1 888 314-5822

      E-mail: yang-support@juniper.net";

   description "Junos genstate data model for lacp-interface-information-list";

   revision 2025-01-01 {
     description "Junos: 25.4R1.13-EVO";
   }

   grouping lacp-interface-information-list-top {
     description "Top-level grouping";
     container lacp-interface-information-list {
       description "Information about one or more aggregated interfaces";
       list lacp-interface-information {
         description "Information about an aggregated interface";
         list lag-lacp-header {
           key "aggregate-name";
           description "LACP header";
           leaf aggregate-name {
             type string;
             description "Aggregated Interface name";
           }
         }
         list lag-lacp-info {
           key "name";
           description "LACP information";
           leaf name {
             type string;
             description "Interface name";
           }
           leaf lacp-role {
             type string;
             description "Whether it is an actor or partner";
           }
           leaf lacp-sys-priority {
             type string;
             description "System priority";
           }
           leaf lacp-system-id {
             type string;
             description "LACP system identifier";
           }
           leaf lacp-port-priority {
             type string;
             description "Priority of the port";
           }
           leaf lacp-port-number {
             type string;
             description "Port number";
           }
           leaf lacp-port-key {
             type string;
             description "Operational key of the port";
           }
         }
         list lag-lacp-state {
           key "name";
           description "LACP protocol state information";
           leaf name {
             type string;
             description "Interface name";
           }
           leaf lacp-role {
             type string;
             description "Whether it is an actor or partner";
           }
           leaf lacp-expired {
             type string;
             description "State of the receive lacp machine is EXPIRED?";
           }
           leaf lacp-defaulted {
             type string;
             description "State of the receive lacp machine is DEFAULTED?";
           }
           leaf lacp-distributing {
             type string;
             description "State of the mux lacp machine is DISTRIBUTING?";
           }
           leaf lacp-collecting {
             type string;
             description "State of the mux lacp machine is COLLECTING?";
           }
           leaf lacp-synchronization {
             type string;
             description "Actor view of partner information is in sync";
           }
           leaf lacp-aggregation {
             type string;
             description "Actor view of partner information is in sync";
           }
           leaf lacp-timeout {
             type string;
             description "Configured as either fast or slow periodic";
           }
           leaf lacp-activity {
             type string;
             description "Configured as either active or passive";
           }
         }
         list lag-lacp-protocol {
           key "name";
           description "LACP protocol information";
           leaf name {
             type string;
             description "Interface name";
           }
           leaf lacp-receive-state {
             type string;
             description "State of the receive lacp machine";
           }
           leaf lacp-transmit-state {
             type string;
             description "State of the transmit lacp machine";
           }
           leaf lacp-mux-state {
             type string;
             description "State of the mux lacp machine";
           }
         }
         container lacp-hold-up-state {
           description "Hold-up timer state";
           leaf lacp-hold-up-time {
             type int32;
             description "LACP hold time up";
           }
         }
         list lacp-hold-up-information {
           key "name";
           description "LACP hold-up information";
           leaf name {
             type string;
             description "Interface name";
           }
           leaf status {
             type string;
           }
           leaf restart-count {
             type int32;
           }
           leaf time-to-expire {
             type int32;
           }
           leaf start-time {
             type string;
           }
         }
       }
     }
   }
   augment "/jgs:genstate" {
     description "Adds lacp-interface-information-list to top-level genstate";
     uses lacp-interface-information-list-top;
   }
 }
