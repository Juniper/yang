module junos-genstate-l2ng-l2ald-global-configuration {
   yang-version 1;
   namespace "http://yang.juniper.net/junos/genstate/l2ng-l2ald-global-configuration";
   prefix jgllgc;

   import junos-genstate {
     prefix jgs;
     revision-date 2025-01-01;
   }

   import junos-common-types {
     prefix jt;
     revision-date 2025-01-01;
   }

   organization
     "Juniper Networks, Inc.";

   contact
     "Juniper Networks, Inc.

      1133 Innovation Way
      Sunnyvale, CA 94089

      +1 888 314-5822

      E-mail: yang-support@juniper.net";

   description "Junos genstate data model for l2ng-l2ald-global-configuration";

   revision 2025-01-01 {
     description "Junos: 25.4R1.13-EVO";
   }

   grouping l2ng-l2ald-global-configuration-top {
     description "Top-level grouping";
     container l2ng-l2ald-global-configuration {
       description "Global configuration values for the the media access control address learning process";
       leaf l2ng-l2ald-mac-aging-time {
         type uint32;
         description "Configured aging interval for media access control entries";
       }
       leaf l2ng-l2ald-mac-learning-status {
         type string;
         description "Status of media access control address learning (enabled or disabled)";
       }
       leaf l2ng-l2ald-statistics-status {
         type string;
         description "Status of statistics collection for media access control entries (enabled or disabled)";
       }
       leaf l2ng-l2ald-global-mac-limit-count {
         type string;
         description "Count of number of MACs allowed globally in the system";
       }
       leaf l2ng-l2ald-global-mac-limit {
         type string;
         description "Status of global mac limit (whether reached or not)";
       }
       leaf l2ng-l2ald-global-packet-action-drop {
         type string;
         description "Status of packet action drop (enabled or disabled)";
       }
       leaf l2ng-l2ald-mac-ip-aging-time-ipv4 {
         type uint32;
         description "Configured aging interval for MAC+IPv4 bindings";
       }
       leaf l2ng-l2ald-mac-ip-aging-time-ipv6 {
         type uint32;
         description "Configured aging interval for MAC+IPv6 bindings";
       }
       leaf l2ng-l2ald-global-mac-ip-limit-count {
         type string;
         description "Count of number of MAC+IPs allowed globally in the system";
       }
       leaf l2ng-l2ald-global-mac-ip-limit-reached {
         type string;
         description "Status of global mac+ip limit (whether reached or not)";
       }
       leaf l2ng-l2ald-gc-global-mode {
         type string;
         description "Global Mode";
       }
       leaf l2ng-l2ald-re-state {
         type string;
         description "RE State";
       }
       leaf l2ng-l2ald-global-evpn-bum-blocking-hold-timer {
         type string;
         description "Timer value for evpn bum blocking hold timer";
       }
       leaf l2ng-l2ald-fast-update-enable {
         type string;
         description "Fast update feature state";
       }
       leaf l2ng-l2ald-crb-proxy-mac-inet4 {
         type string;
         description "CRB PROXY MAC for IPv4";
       }
       leaf l2ng-l2ald-crb-proxy-mac-inet6 {
         type string;
         description "CRB PROXY MAC for IPv6";
       }
       leaf l2ng-l2ald-evpn-vxlan-host-gbp-src-tag {
         type uint32;
         description "Configured GBP src tag value for host originated vxlan packets";
       }
       leaf l2ng-l2ald-event-retry-time {
         type string;
         description "Event retry time";
       }
       leaf l2ald-global-mp-discard-notification-interval {
         type uint32;
         description "Timer value for Mac Pinning discard notification interval";
       }
     }
   }
   augment "/jgs:genstate" {
     description "Adds l2ng-l2ald-global-configuration to top-level genstate";
     uses l2ng-l2ald-global-configuration-top;
   }
 }
