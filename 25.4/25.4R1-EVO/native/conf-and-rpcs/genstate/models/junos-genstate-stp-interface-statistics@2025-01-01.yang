module junos-genstate-stp-interface-statistics {
   yang-version 1;
   namespace "http://yang.juniper.net/junos/genstate/stp-interface-statistics";
   prefix jgsis;

   import junos-genstate {
     prefix jgs;
     revision-date 2025-01-01;
   }

   import junos-common-types {
     prefix jt;
     revision-date 2025-01-01;
   }

   organization
     "Juniper Networks, Inc.";

   contact
     "Juniper Networks, Inc.

      1133 Innovation Way
      Sunnyvale, CA 94089

      +1 888 314-5822

      E-mail: yang-support@juniper.net";

   description "Junos genstate data model for stp-interface-statistics";

   revision 2025-01-01 {
     description "Junos: 25.4R1.13-EVO";
   }

   grouping stp-interface-statistics-top {
     description "Top-level grouping";
     container stp-interface-statistics {
       description "Statistics information about one or more STP interfaces";
       list statistics-routing-instance-info {
         key "routing-instance-name";
         leaf routing-instance-name {
           type string;
           description "Routing instance name";
         }
         list stp-interface-statistics-entry {
           key "interface-name";
           description "Spanning Tree Protocol interface statistics";
           leaf interface-name {
             type string;
             description "Name of interface";
           }
           leaf total-bpdus-sent {
             type int32;
             description "Total number of BPDUs sent out";
           }
           leaf total-bpdus-received {
             type int32;
             description "Total number of BPDUs received";
           }
           leaf next-bpdu-time {
             type int32;
             description "Next bpdu send time in the steady state in seconds";
           }
           leaf total-tcn-bpdus-sent-received {
             type string;
             description "Total number of TCN BPDUs sent/received";
           }
           leaf total-proposal-bpdus-sent-received {
             type string;
             description "Total number of Proposal BPDUs sent/received";
           }
           leaf total-agreement-bpdus-sent-received {
             type string;
             description "Total number of Agreement BPDUs sent/received";
           }
         }
         list vstp-interface-statistics {
           key "vlan-id";
           description "Statistics information about one or more VLAN STP interfaces";
           leaf vlan-id {
             type int32;
             description "VLAN identifier";
           }
           list stp-interface-statistics-entry {
             key "interface-name";
             description "Spanning Tree Protocol interface statistics";
             leaf interface-name {
               type string;
               description "Name of interface";
             }
             leaf total-bpdus-sent {
               type int32;
               description "Total number of BPDUs sent out";
             }
             leaf total-bpdus-received {
               type int32;
               description "Total number of BPDUs received";
             }
             leaf next-bpdu-time {
               type int32;
               description "Next bpdu send time in the steady state in seconds";
             }
             leaf total-tcn-bpdus-sent-received {
               type string;
               description "Total number of TCN BPDUs sent/received";
             }
             leaf total-proposal-bpdus-sent-received {
               type string;
               description "Total number of Proposal BPDUs sent/received";
             }
             leaf total-agreement-bpdus-sent-received {
               type string;
               description "Total number of Agreement BPDUs sent/received";
             }
           }
         }
       }
     }
   }
   augment "/jgs:genstate" {
     description "Adds stp-interface-statistics to top-level genstate";
     uses stp-interface-statistics-top;
   }
 }
