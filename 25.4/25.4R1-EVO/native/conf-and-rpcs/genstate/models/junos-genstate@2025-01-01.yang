module junos-genstate {
   yang-version 1;
   namespace "http://yang.juniper.net/junos/genstate";
   prefix jgs;

   organization
     "Juniper Networks, Inc.";

   contact
     "Juniper Networks, Inc.

      1133 Innovation Way
      Sunnyvale, CA 94089

      +1 888 314-5822

      E-mail: yang-support@juniper.net";

   description
     "This module contains a collection of top level nodes for JUNOS genstate data.

      Copyright (c) 2024 Juniper Networks, Inc.
      All rights reserved.";

   revision 2025-01-01 {
     description "Junos: 25.4R1.13-EVO";
   }

   grouping genstate-top {
     description "Top-level grouping for JUNOS genstate data";
     container genstate {
       description "Encapsulating top-level state container for all JUNOS genstate data";
       config false;
     }
   }
   uses genstate-top;
 }
