module junos-genstate-l2ng-l2ald-routing-table-information {
   yang-version 1;
   namespace "http://yang.juniper.net/junos/genstate/l2ng-l2ald-routing-table-information";
   prefix jgllrti;

   import junos-genstate {
     prefix jgs;
     revision-date 2025-01-01;
   }

   import junos-common-types {
     prefix jt;
     revision-date 2025-01-01;
   }

   organization
     "Juniper Networks, Inc.";

   contact
     "Juniper Networks, Inc.

      1133 Innovation Way
      Sunnyvale, CA 94089

      +1 888 314-5822

      E-mail: yang-support@juniper.net";

   description "Junos genstate data model for l2ng-l2ald-routing-table-information";

   revision 2025-01-01 {
     description "Junos: 25.4R1.13-EVO";
   }

   grouping l2ng-l2ald-routing-table-information-top {
     description "Top-level grouping";
     container l2ng-l2ald-routing-table-information {
       description "Top-level container";
       list l2ng-l2ald-rtb-entry {
         key "l2ng-l2rtb-name l2ng-l2rtb-id";
         leaf l2ng-l2rtb-instance-type {
           type string;
           description "Type of instance (routing instance/bridge domain)";
         }
         leaf l2ng-l2rtb-logical-system {
           type string;
           description "Logical system name";
         }
         leaf l2ng-l2rtb-name {
           type string;
           description "Name of the routing instance";
         }
         leaf l2ng-l2rtb-vlan-name {
           type string;
           description "Name of the bridging domain";
         }
         leaf l2ng-l2rtb-id {
           type uint32;
           description "Routing instance identifier";
         }
         leaf l2ng-l2rtb-l2irb-ifl-index {
           type uint32;
         }
         leaf l2ng-l2rtb-flags {
           type string;
           description "Attributes associated with this routing instance";
         }
         leaf l2ng-l2bd-vlan-id {
           type string;
           description "Bridge domain VLAN";
         }
       }
     }
   }
   augment "/jgs:genstate" {
     description "Adds l2ng-l2ald-routing-table-information to top-level genstate";
     uses l2ng-l2ald-routing-table-information-top;
   }
 }
