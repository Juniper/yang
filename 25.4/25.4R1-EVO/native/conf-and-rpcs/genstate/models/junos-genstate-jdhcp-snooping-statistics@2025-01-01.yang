module junos-genstate-jdhcp-snooping-statistics {
   yang-version 1;
   namespace "http://yang.juniper.net/junos/genstate/jdhcp-snooping-statistics";
   prefix jgjss;

   import junos-genstate {
     prefix jgs;
     revision-date 2025-01-01;
   }

   import junos-common-types {
     prefix jt;
     revision-date 2025-01-01;
   }

   organization
     "Juniper Networks, Inc.";

   contact
     "Juniper Networks, Inc.

      1133 Innovation Way
      Sunnyvale, CA 94089

      +1 888 314-5822

      E-mail: yang-support@juniper.net";

   description "Junos genstate data model for jdhcp-snooping-statistics";

   revision 2025-01-01 {
     description "Junos: 25.4R1.13-EVO";
   }

   grouping jdhcp-snooping-statistics-top {
     description "Top-level grouping";
     container jdhcp-snooping-statistics {
       description "Top-level container";
       leaf successful-transfers {
         type int32;
         description "Successful transfers";
       }
       leaf failed-transfers {
         type int32;
         description "Failed transfers";
       }
       leaf successful-reads {
         type int32;
         description "Successful reads";
       }
       leaf failed-reads {
         type int32;
         description "Failed reads";
       }
       leaf successful-writes {
         type int32;
         description "Successful writes";
       }
       leaf failed-writes {
         type int32;
         description "Failed writes";
       }
     }
   }
   augment "/jgs:genstate" {
     description "Adds jdhcp-snooping-statistics to top-level genstate";
     uses jdhcp-snooping-statistics-top;
   }
 }
