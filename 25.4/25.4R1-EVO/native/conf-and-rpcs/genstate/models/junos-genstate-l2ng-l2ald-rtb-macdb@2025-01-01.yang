module junos-genstate-l2ng-l2ald-rtb-macdb {
   yang-version 1;
   namespace "http://yang.juniper.net/junos/genstate/l2ng-l2ald-rtb-macdb";
   prefix jgllrm;

   import junos-genstate {
     prefix jgs;
     revision-date 2025-01-01;
   }

   import junos-common-types {
     prefix jt;
     revision-date 2025-01-01;
   }

   organization
     "Juniper Networks, Inc.";

   contact
     "Juniper Networks, Inc.

      1133 Innovation Way
      Sunnyvale, CA 94089

      +1 888 314-5822

      E-mail: yang-support@juniper.net";

   description "Junos genstate data model for l2ng-l2ald-rtb-macdb";

   revision 2025-01-01 {
     description "Junos: 25.4R1.13-EVO";
   }

   grouping l2ng-l2ald-rtb-macdb-top {
     description "Top-level grouping";
     container l2ng-l2ald-rtb-macdb {
       description "Top-level container";
       list l2ng-l2ald-rtb-mac-count-entry {
         key "rtb-name vlan-name";
         leaf rtb-mac-count {
           type int32;
           description "Media access control addresses count";
         }
         leaf rtb-name {
           type string;
           description "Bridging media access control address count for routing-instance";
         }
         leaf vlan-name {
           type string;
           description "Name of the VLAN";
         }
         container l2ald-rtb-if-mac-count {
           description "MAC address count for all the interfaces in the routing instance";
           list l2ng-l2ald-rtb-if-mac-count-entry {
             key "interface-name";
             leaf interface-name {
               type string;
               description "Bridging media access control address interface";
             }
             leaf mac-count {
               type uint32;
               description "Number of media access control addresses";
             }
             leaf l2ng-l2-active-source {
               type string;
               description "Remote VXLAN tunnel endpoint ip address or ESI value";
             }
           }
         }
         container l2ng-l2ald-rtb-learn-vlan-mac-count {
           description "MAC address count for all the learn vlans within the routing instance";
           list l2ng-l2ald-rtb-learn-vlan-mac-count-entry {
             key "learn-vlan";
             leaf learn-vlan {
               type uint32;
               description "VLAN ID of the routing instance in which the MAC address was learned";
             }
             leaf mac-count {
               type uint32;
               description "Number of media access control addresses";
             }
             leaf static-mac-count {
               type uint32;
             }
           }
         }
       }
       list l2ng-l2ald-mac-entry-vlan {
         key "l2ng-l2-mac-address l2ng-l2-mac-logical-interface l2ng-l2-mac-routing-instance l2ng-l2-mac-vlan-name";
         leaf l2ng-l2-mac-address {
           type jt:mac-addr;
         }
         leaf l2ng-l2-mac-logical-interface {
           type string;
         }
         leaf l2ng-l2-mac-logical-system {
           type string;
         }
         leaf l2ng-l2-mac-routing-instance {
           type string;
         }
         leaf l2ng-l2-mac-vlan-name {
           type string;
         }
         leaf l2ng-l2-remote-beb-mac-address {
           type jt:mac-addr;
         }
         leaf l2ng-l2-mac-elp-nh {
           type uint32;
         }
         leaf l2ng-l2-mac-fwd-next-hop {
           type uint32;
         }
         leaf l2ng-l2-mac-rtr-id {
           type uint32;
         }
         leaf l2ng-l2-mac-epoch {
           type uint32;
         }
         leaf l2ng-l2-mac-ifl-generation {
           type uint32;
         }
         leaf l2ng-l2-mac-sequence-number {
           type uint32;
         }
         leaf l2ng-l2-mac-bgp-sequence-number {
           type uint32;
         }
         leaf l2ng-l2-mac-learn-mask {
           type string;
         }
         leaf l2ng-l2-mac-entry-flags {
           type string;
         }
         leaf l2ng-l2-mac-property {
           type string;
         }
         leaf l2ng-l2-mac-flags {
           type string;
         }
         leaf l2ng-l2-vlan-id {
           type string;
         }
         leaf l2ng-l2-mac-move-limit-reached-time {
           type string;
         }
         leaf l2ng-l2-mac-move-limit-action-applied {
           type string;
         }
         leaf l2ng-l2-bridge-isid {
           type uint32;
         }
         leaf mac-count-global {
           type uint32;
         }
         leaf learnt-mac-count {
           type int32;
         }
         leaf l2ng-l2-active-source {
           type string;
           description "Remote VXLAN tunnel endpoint ip address or ESI value";
         }
         leaf l2ng-l2-mac-svlbnh-venh {
           type uint32;
         }
         leaf l2ng-l2-mac-mcae-id {
           type uint32;
           description "MCAE ID of the mac entry";
         }
         leaf l2ng-l2-mac-mcae-ifl-unit {
           type uint32;
           description "MCAE IFL unit of the mac entry";
         }
         leaf l2ng-l2-mac-svc-id {
           type uint32;
           description "MCAE SVC ID of the mac entry";
         }
         leaf l2ng-l2-mac-rg-id {
           type uint32;
           description "RG ID of the mac entry";
         }
         leaf l2ng-l2-mac-rtm-op {
           type uint32;
           description "MCAE mac operation of the mac entry";
         }
         leaf l2ng-l2-mac-gbptag {
           type int32;
           description "L2 MAC gbp tag value";
         }
         leaf l2ng-l2-mac-time-info {
           type string;
           description "Mac learning time";
         }
         list l2ng-l2ald-mac-source-address-statistics {
           leaf packet-count {
             type uint64;
             description "Packet count";
           }
           leaf byte-count {
             type uint64;
             description "Byte count";
           }
         }
         list l2ng-l2ald-mac-destination-address-statistics {
           leaf packet-count {
             type uint64;
             description "Packet count";
           }
           leaf byte-count {
             type uint64;
             description "Byte count";
           }
         }
       }
     }
   }
   augment "/jgs:genstate" {
     description "Adds l2ng-l2ald-rtb-macdb to top-level genstate";
     uses l2ng-l2ald-rtb-macdb-top;
   }
 }
