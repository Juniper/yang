module junos-genstate-l2cpd-bpdu-block-information {
   yang-version 1;
   namespace "http://yang.juniper.net/junos/genstate/l2cpd-bpdu-block-information";
   prefix jglbbi;

   import junos-genstate {
     prefix jgs;
     revision-date 2025-01-01;
   }

   import junos-common-types {
     prefix jt;
     revision-date 2025-01-01;
   }

   organization
     "Juniper Networks, Inc.";

   contact
     "Juniper Networks, Inc.

      1133 Innovation Way
      Sunnyvale, CA 94089

      +1 888 314-5822

      E-mail: yang-support@juniper.net";

   description "Junos genstate data model for l2cpd-bpdu-block-information";

   revision 2025-01-01 {
     description "Junos: 25.4R1.13-EVO";
   }

   grouping l2cpd-bpdu-block-information-top {
     description "Top-level grouping";
     container l2cpd-bpdu-block-information {
       description "Information about the bpdu-block configured on the interface for stp";
       leaf recovery-timeout {
         type string;
         description "Recovery timeout value";
       }
       list l2cpd-bpdu-block-interface-information-entry {
         key "interface-name";
         description "L2 control information on bpdu-block";
         leaf interface-name {
           type string;
           description "Name of interface";
         }
         leaf action-configured {
           type string;
         }
         leaf drop-count {
           type int32;
         }
       }
     }
   }
   augment "/jgs:genstate" {
     description "Adds l2cpd-bpdu-block-information to top-level genstate";
     uses l2cpd-bpdu-block-information-top;
   }
 }
