module junos-genstate-system-applications-info {
   yang-version 1;
   namespace "http://yang.juniper.net/junos/genstate/system-applications-info";
   prefix jgsai;

   import junos-genstate {
     prefix jgs;
     revision-date 2025-01-01;
   }

   import junos-common-types {
     prefix jt;
     revision-date 2025-01-01;
   }

   organization
     "Juniper Networks, Inc.";

   contact
     "Juniper Networks, Inc.

      1133 Innovation Way
      Sunnyvale, CA 94089

      +1 888 314-5822

      E-mail: yang-support@juniper.net";

   description "Junos genstate data model for system-applications-info";

   revision 2025-01-01 {
     description "Junos: 25.4R1.13-EVO";
   }

   grouping system-applications-info-top {
     description "Top-level grouping";
     container system-applications-info {
       description "Top-level container";
       list system-applications-info-entry {
         key "system-application-name";
         leaf system-application-name {
           type string;
         }
         container system-application-memory {
           leaf system-application-vmsize-kb {
             type uint64;
           }
           leaf system-application-vmrss-kb {
             type uint64;
           }
           leaf system-application-vmswap-kb {
             type uint64;
           }
         }
         container system-application-processor {
           leaf system-application-cpu-time {
             type decimal64 {
               fraction-digits 9;
             }
           }
           leaf system-application-cpu-utilization {
             type decimal64 {
               fraction-digits 9;
             }
           }
         }
       }
     }
   }
   augment "/jgs:genstate" {
     description "Adds system-applications-info to top-level genstate";
     uses system-applications-info-top;
   }
 }
