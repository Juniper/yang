module junos-genstate-lacp-interface-statistics-list {
   yang-version 1;
   namespace "http://yang.juniper.net/junos/genstate/lacp-interface-statistics-list";
   prefix jglisl;

   import junos-genstate {
     prefix jgs;
     revision-date 2025-01-01;
   }

   import junos-common-types {
     prefix jt;
     revision-date 2025-01-01;
   }

   organization
     "Juniper Networks, Inc.";

   contact
     "Juniper Networks, Inc.

      1133 Innovation Way
      Sunnyvale, CA 94089

      +1 888 314-5822

      E-mail: yang-support@juniper.net";

   description "Junos genstate data model for lacp-interface-statistics-list";

   revision 2025-01-01 {
     description "Junos: 25.4R1.13-EVO";
   }

   grouping lacp-interface-statistics-list-top {
     description "Top-level grouping";
     container lacp-interface-statistics-list {
       description "Information about one or more aggregated interfaces";
       list lacp-interface-statistics {
         description "Statistics for an aggregated interface";
         list lag-lacp-header {
           key "aggregate-name";
           description "LACP header";
           leaf aggregate-name {
             type string;
             description "Aggregated Interface name";
           }
         }
         list lag-lacp-statistics {
           key "name";
           leaf name {
             type string;
             description "Interface name";
           }
           leaf lacp-rx-packets {
             type string;
             description "Number of LACP packets received";
           }
           leaf lacp-tx-packets {
             type string;
             description "Number of LACP packets transmitted";
           }
           leaf unknown-rx-packets {
             type string;
             description "Number of unknown type packets received";
           }
           leaf illegal-rx-packets {
             type string;
             description "Number of ill formed packets received";
           }
         }
       }
     }
   }
   augment "/jgs:genstate" {
     description "Adds lacp-interface-statistics-list to top-level genstate";
     uses lacp-interface-statistics-list-top;
   }
 }
