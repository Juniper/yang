module junos-ietf-interfaces-deviations {
  yang-version 1.1;
  namespace "http://yang.juniper.net/ietf/ietf-interfaces/deviations";
  prefix jnx-if-dev;

  import junos-base-extensions {
    prefix junos-base;
  }

  import ietf-interfaces {
    prefix if;
  }

  organization
    "Juniper Networks, Inc.";

  contact
    "Juniper Networks, Inc.

    1133 Innovation Way
    Sunnyvale, CA 94089

    +1 888 314-5822

    E-mail: yang-support@juniper.net";

  description
    "This module contains deviations for ietf-interfaces module.

    Copyright (c) 2023 Juniper Networks, Inc.
    All rights reserved.";

  revision 2023-07-09 {
    description
      "Initial revision";
    reference "0.1.0";
  }

  junos-base:version "0.1.0";

  deviation "/if:interfaces" {
    deviate not-supported;
    description
      "Subtree not-supported, import-only module";
  }

  deviation "/if:interfaces-state" {
    deviate not-supported;
    description
      "Subtree not-supported, import-only module";
  }
}
