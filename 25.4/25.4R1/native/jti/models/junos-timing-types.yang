module junos-timing-types {
  yang-version 1.1;
  namespace "http://yang.juniper.net/junos/timing/types";
  prefix "jtt";

  import junos-extensions {
    prefix jx;
  }

  organization
    "Juniper Networks, Inc.";

  contact
    "Juniper Networks, Inc.

     1133 Innovation Way
     Sunnyvale, CA 94089

     +1 888 314-5822

     E-mail: yang-support@juniper.net";

  description
    "This module contains the definitions for types
     related to timing(e.g. PTP,SyncE)..

     Copyright (c) 2025 Juniper Networks, Inc.
     All rights reserved.";

  revision 2025-04-25 {
    description
     "Addition of jx:origin annotation";
    reference "0.1.1";
  }

  revision 2024-09-06 {
    description
      "Initial revision.";
    reference "0.1.0";
  }

  jx:version "0.1.1";
  jx:origin "juniper";

  typedef clock-mode-status {
    type enumeration {
      enum free-run {
        description
          "Using the free-running local oscillator.";
      }
      enum locked {
        description
          "System clock is in locked state with clock source.";
      }
      enum locked-holdover-acq {
        description
          "System clock is in locked state and has acquired holdover memory.";
      }
      enum holdover {
        description
          "System clock is in holdover state.";
      }
      enum acquiring {
        description
          "System clock is in acquiring state.";
      }
    }
    description
      "SyncE clock mode status.";
  }

}
