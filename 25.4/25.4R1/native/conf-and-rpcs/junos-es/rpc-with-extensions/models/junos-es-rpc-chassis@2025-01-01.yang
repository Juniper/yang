/*
 * Copyright (c) 2025 Juniper Networks, Inc.
 * All rights reserved.
 */
 module junos-es-rpc-chassis {
   namespace "http://yang.juniper.net/junos-es/rpc/chassis";

   prefix chassis;

   import junos-common-ddl-extensions {
     prefix junos;
     revision-date 2025-01-01;
   }

   import junos-common-types {
     prefix jt;
     revision-date 2025-01-01;
   }

   organization "Juniper Networks, Inc.";

   contact "yang-support@juniper.net";

   description "Junos RPC YANG module for chassis command(s)";

   revision 2025-01-01 {
     description "Junos: 25.4R1.12";
   }

   rpc get-scb-ha-port-statistics-information {
     description "Show Switch Control Board HA port statistics";
     junos:command "show chassis scb-ha-port statistics";
     output {
       container chassis-scb-ha-port {
         uses chassis-scb-ha-port-block;
       }
     }
   }
   rpc get-power-usage-information {
     description "Show Chassis Power Usages";
     junos:command "show chassis power";
     input {
       uses command-forwarding;
     }
     output {
       container power-usage-information {
         uses power-usage-information-block;
       }
     }
   }
   rpc get-power-usage-information-detail {
     description "Show chassis power usage detail";
     junos:command "show chassis power detail";
     input {
       uses command-forwarding;
     }
     output {
       container power-usage-information {
         uses power-usage-information-block;
       }
     }
   }
   rpc get-fru-power-on-sequence {
     description "Show chassis fru power on sequence";
     junos:command "show chassis power sequence";
     input {
       uses command-forwarding;
     }
     output {
       container fru-power-on-sequence {
         uses fru-power-on-sequence-block;
       }
     }
   }
   rpc get-alarm-information {
     description "Show alarm status";
     junos:command "show chassis alarms";
     input {
       uses command-forwarding;
     }
     output {
       container alarm-information {
         uses alarm-information-block;
       }
     }
   }
   rpc get-chassis-errors {
     description "Show chassis errors";
     junos:command "show chassis errors";
     input {
       leaf error-id {
         description "Error identifier for the error to be cleared";
         type string {
           length "1 .. 255";
           junos:posix-pattern "^(/[^/ ]+/[0-9:]+){4}/[^/ ]+$";
           junos:pattern-message "Invalid error identifier format";
         }
         mandatory true;
       }
       leaf fpc-slot {
         description "Slot number of FPC";
         type union {
           type string {
             pattern "<.*>|$.*";
           }
           type uint32;
         }
         mandatory true;
       }
     }
   }
   rpc get-chassis-active-errors {
     description "Show active errors";
     junos:command "show chassis errors active";
     input {
       leaf fpc-slot {
         description "Slot number of FPC";
         type union {
           type string {
             pattern "<.*>|$.*";
           }
           type uint32;
         }
       }
     }
   }
   rpc get-active-error-information-detail {
     description "Show detailed output";
     junos:command "show chassis errors active detail";
     input {
       leaf fpc-slot {
         description "Slot number of FPC";
         type union {
           type string {
             pattern "<.*>|$.*";
           }
           type uint32;
         }
       }
     }
   }
   rpc ambient-temperature {
     description "Show chassis ambient temperature";
     junos:command "show chassis ambient-temperature";
     output {
       container ambient-temperature {
         uses ambient-temperature-block;
       }
     }
   }
   rpc get-satellite-device-list {
     description "Displays active satellite devices";
     junos:command "show chassis port-extender";
     output {
       container satellite-device-list {
         uses satellite-device-list-block;
       }
     }
   }
   rpc get-craft-information {
     description "Show craft interface status";
     junos:command "show chassis craft-interface";
     input {
       uses command-forwarding;
     }
     output {
       container craft-information {
         uses craft-information-block;
       }
     }
   }
   rpc get-ethernet-switch-information {
     description "Show Ethernet switch information";
     junos:command "show chassis ethernet-switch";
     input {
       uses command-forwarding;
     }
     output {
       container ethernet-switch-information {
         uses ethernet-switch-information-block;
       }
     }
   }
   rpc get-ethernet-switch-statistics-information {
     description "Show Ethernet switch traffic statistics";
     junos:command "show chassis ethernet-switch statistics";
     input {
       uses command-forwarding;
       leaf port {
         description "Port number";
         junos:cli-feature "nokeyword";
         type union {
           type string {
             pattern "<.*>|$.*";
           }
           type uint32;
         }
       }
     }
     output {
       container ethernet-switch-statistics-information {
         uses ethernet-switch-statistics-information-block;
       }
     }
   }
   rpc get-ethernet-switch-error-information {
     description "Show accumulated Ethernet switch errors";
     junos:command "show chassis ethernet-switch errors";
     input {
       uses command-forwarding;
       leaf port {
         description "Port number";
         junos:cli-feature "nokeyword";
         type union {
           type string {
             pattern "<.*>|$.*";
           }
           type uint32;
         }
       }
     }
     output {
       container ethernet-switch-error-information {
         uses ethernet-switch-error-information-block;
       }
     }
   }
   rpc get-ioc-npc-connectivity-information {
     description "Show connectivity between IOC and NPC";
     junos:command "show chassis ioc-npc-connectivity";
     output {
       container ioc-npc-connectivity {
         uses ioc-npc-connectivity-block;
       }
     }
   }
   rpc get-environment-information {
     description "Show component status and temperature, cooling system speeds";
     junos:command "show chassis environment";
     input {
       uses command-forwarding;
     }
     output {
       container environment-information {
         uses environment-information-block;
       }
     }
   }
   rpc get-environment-fpc-information {
     description "Show Flexible PIC Concentrator information";
     junos:command "show chassis environment fpc";
     input {
       uses command-forwarding;
       leaf fpc-slot {
         description "FPC slot number";
         junos:cli-feature "nokeyword";
         type union {
           type string {
             pattern "<.*>|$.*";
           }
           type uint32;
         }
       }
     }
     output {
       container environment-component-information {
         uses environment-component-information-block;
       }
     }
   }
   rpc get-environment-fpm-information {
     description "Show craft interface information";
     junos:command "show chassis environment fpm";
     input {
       uses command-forwarding;
     }
     output {
       container environment-component-information {
         uses environment-component-information-block;
       }
     }
   }
   rpc get-environment-cb-information {
     description "Show Control Board information";
     junos:command "show chassis environment cb";
     input {
       uses command-forwarding;
       leaf slot {
         description "CB slot number";
         junos:cli-feature "nokeyword";
         type union {
           type string {
             pattern "<.*>|$.*";
           }
           type uint32;
         }
       }
     }
     output {
       container environment-component-information {
         uses environment-component-information-block;
       }
     }
   }
   rpc get-environment-power-supply-unit-information {
     description "Show power supply unit information";
     junos:command "show chassis environment power-supply-unit";
     input {
       uses command-forwarding;
       leaf slot {
         description "FPC slot number";
         type union {
           type string {
             pattern "<.*>|$.*";
           }
           type uint32;
         }
       }
     }
     output {
       container environment-component-information {
         uses environment-component-information-block;
       }
     }
   }
   rpc get-environment-pem-information {
     description "Show Power Entry Module information";
     junos:command "show chassis environment pem";
     input {
       uses command-forwarding;
       leaf slot {
         description "PEM slot number";
         junos:cli-feature "nokeyword";
         type union {
           type string {
             pattern "<.*>|$.*";
           }
           type uint32;
         }
       }
     }
     output {
       container environment-component-information {
         uses environment-component-information-block;
       }
     }
   }
   rpc get-environment-re-information {
     description "Show Routing Engine information";
     junos:command "show chassis environment routing-engine";
     input {
       uses command-forwarding;
       leaf slot {
         description "Routing Engine slot number";
         junos:cli-feature "nokeyword";
         type union {
           type string {
             pattern "<.*>|$.*";
           }
           type uint32;
         }
       }
     }
     output {
       container environment-component-information {
         uses environment-component-information-block;
       }
     }
   }
   rpc get-firmware-information {
     description "Show firmware and operating system version for components";
     junos:command "show chassis firmware";
     input {
       uses command-forwarding;
     }
     output {
       container firmware-information {
         uses firmware-information-block;
       }
     }
   }
   rpc get-usb-storage-status {
     description "Show USB storage status";
     junos:command "show chassis usb storage";
   }
   rpc get-fpc-information {
     description "Show Flexible PIC Concentrator status";
     junos:command "show chassis fpc";
     input {
       uses command-forwarding;
       leaf detail {
         description "Display detailed output";
         type empty;
       }
       leaf fpc-slot {
         description "FPC slot number";
         junos:cli-feature "nokeyword";
         type union {
           type string {
             pattern "<.*>|$.*";
           }
           type uint32;
         }
       }
     }
     output {
       container fpc-information {
         uses fpc-information-block;
       }
     }
   }
   rpc get-pic-information {
     description "Show Physical Interface Cards installed in FPC";
     junos:command "show chassis fpc pic-status";
     input {
       uses command-forwarding;
       leaf slot {
         description "FPC slot number";
         junos:cli-feature "nokeyword";
         type union {
           type string {
             pattern "<.*>|$.*";
           }
           type uint32;
         }
       }
     }
     output {
       container fpc-information {
         uses fpc-information-block;
       }
     }
   }
   rpc get-mic-information {
     description "Show Modular Interface Cards installed in FPC";
     junos:command "show chassis fpc mic-status";
     input {
       leaf slot {
         description "FPC slot number";
         junos:cli-feature "nokeyword";
         type union {
           type string {
             pattern "<.*>|$.*";
           }
           type uint32;
         }
       }
     }
     output {
       container fpc-information {
         uses fpc-information-block;
       }
     }
   }
   rpc get-fpc-ether-types-information {
     description "Show Ether Types";
     junos:command "show chassis fpc ether-types";
     input {
       leaf slot {
         description "FPC slot number";
         junos:cli-feature "nokeyword";
         type union {
           type string {
             pattern "<.*>|$.*";
           }
           type uint32;
         }
       }
     }
     output {
       container fpc-ether-types-information {
         uses fpc-ether-types-information-block;
       }
     }
   }
   rpc get-fpc-port-information {
     description "Show Port status installed in FPC";
     junos:command "show chassis fpc port-status";
     input {
       leaf slot {
         description "FPC slot number";
         junos:cli-feature "nokeyword";
         type union {
           type string {
             pattern "<.*>|$.*";
           }
           type uint32;
         }
       }
     }
     output {
       container fpc-port-information {
         uses fpc-port-information-block;
       }
     }
   }
   rpc get-fpc-error-information {
     description "Show ASIC errors on all the FPC's";
     junos:command "show chassis fpc errors";
     input {
       uses command-forwarding;
       leaf fpc-slot {
         description "FPC slot number";
         junos:cli-feature "nokeyword";
         type union {
           type string {
             pattern "<.*>|$.*";
           }
           type uint32;
         }
       }
       leaf detail {
         description "Display detailed output";
         type empty;
       }
       leaf scope {
         description "Error scope";
         type enumeration {
           enum "board" {
             description "Show board errors";
           }
           enum "pfe" {
             description "Show pfe errors";
           }
         }
       }
       leaf category {
         description "Error category";
         type enumeration {
           enum "functional" {
             description "Functional category errors";
           }
           enum "memory" {
             description "Memory category errors";
           }
           enum "io" {
             description "Io category errors";
           }
           enum "storage" {
             description "Storage category errors";
           }
           enum "switch" {
             description "Switch category errors";
           }
           enum "processing" {
             description "Processing category errors";
           }
         }
       }
     }
     output {
       container fpc-error-information {
         uses fpc-error-information-block;
       }
     }
   }
   rpc get-fpc-error-i2c {
     description "Display I2C error statistics";
     junos:command "show chassis fpc errors i2c";
     input {
       uses command-forwarding;
       leaf fpc-slot {
         description "FPC slot number";
         type union {
           type string {
             pattern "<.*>|$.*";
           }
           type uint32;
         }
       }
     }
   }
   rpc get-pic-detail {
     description "Show Physical Interface Card state, type, and uptime";
     junos:command "show chassis pic";
     input {
       uses command-forwarding;
       leaf fpc-slot {
         description "Slot number of FPC that houses PIC";
         type union {
           type string {
             pattern "<.*>|$.*";
           }
           type uint32;
         }
       }
       leaf pic-slot {
         description "PIC slot number";
         type union {
           type string {
             pattern "<.*>|$.*";
           }
           type int32;
         }
         mandatory true;
       }
     }
     output {
       container fpc-information {
         uses fpc-information-block;
       }
     }
   }
   rpc get-port-profile-speed-information {
     description "Show Physical Interface Card Port Profile information";
     junos:command "show chassis pic port-profile";
     input {
       leaf fpc-slot {
         description "Slot number of FPC that houses PIC";
         type union {
           type string {
             pattern "<.*>|$.*";
           }
           type uint32;
         }
         mandatory true;
       }
       leaf pic-slot {
         description "PIC slot number";
         type union {
           type string {
             pattern "<.*>|$.*";
           }
           type int32;
         }
         mandatory true;
       }
     }
   }
   rpc get-replacement-status {
     description "Show fru replacement status";
     junos:command "show chassis fru";
     input {
       leaf replacement {
         description "Shows the replacemeent status";
         type enumeration {
           enum "status" {
             description "Shows the fru replacement status";
           }
         }
         mandatory true;
       }
     }
     output {
       choice output_c {
         case output-tag {
           leaf output {
             type string;
           }
         }
         case multichassis-tag {
           anyxml multi-routing-engine-results;
         }
       }
     }
   }
   rpc get-jnu-satellites-information {
     description "Show jnu satellites information";
     junos:command "show chassis jnu satellites";
     output {
       container jnu-satellites-information {
         uses jnu-satellites-information-block;
       }
     }
   }
   rpc get-jnu-role-information {
     description "Show jnu role";
     junos:command "show chassis jnu role";
     output {
       container jnu-role-information {
         uses jnu-role-information-block;
       }
     }
   }
   rpc get-fm-fpc-state-information {
     description "Show summary fabric management FPC state from Routing Engine";
     junos:command "show chassis fabric fpcs";
     input {
       uses command-forwarding;
     }
     output {
       container fm-fpc-state-information {
         uses fm-fpc-state-information-block;
       }
     }
   }
   rpc get-fm-bandwidth-degradation {
     description "Show FPC fabric bandwidth degradation information";
     junos:command "show chassis fabric degradation";
     input {
       uses command-forwarding;
     }
     output {
       container fm-bandwidth-degradation {
         uses fm-bandwidth-degradation-block;
       }
     }
   }
   rpc get-fm-degradation-information-details {
     description "Show fpc fabric degradation action history";
     junos:command "show chassis fabric degradation actions";
     input {
       uses command-forwarding;
     }
   }
   rpc get-fm-fabric-destinations-state {
     description "Show fabric destinations state for all FPCs";
     junos:command "show chassis fabric destinations";
     input {
       uses command-forwarding;
       leaf fpc {
         description "FPC slot number";
         type union {
           type string {
             pattern "<.*>|$.*";
           }
           type uint32;
         }
       }
     }
     output {
       container fm-fabric-destinations-state {
         uses fm-fabric-destinations-state-block;
       }
     }
   }
   rpc get-fm-plane-location-information {
     description "Show fabric plane location";
     junos:command "show chassis fabric plane-location";
     input {
       uses command-forwarding;
     }
     output {
       container fm-plane-location-information {
         uses fm-plane-location-information-block;
       }
     }
   }
   rpc get-fm-topology {
     description "Show fabric topology for plane";
     junos:command "show chassis fabric map";
     input {
       uses command-forwarding;
       leaf plane {
         description "Fabric plane number";
         type union {
           type string {
             pattern "<.*>|$.*";
           }
           type uint32;
         }
       }
     }
     output {
       container fm-topology {
         uses fm-topology-block;
       }
     }
   }
   rpc get-fm-plane-state-information {
     description "Show state of fabric management plane";
     junos:command "show chassis fabric plane";
     input {
       uses command-forwarding;
       leaf display {
         junos:cli-feature "nokeyword";
         type enumeration {
           enum "terse" {
             description "Show terse output";
           }
           enum "detail" {
             description "Show detail output";
           }
           enum "extensive" {
             description "Show extensive output";
           }
         }
       }
       leaf number {
         description "Fabric plane number";
         junos:cli-feature "nokeyword";
         type union {
           type string {
             pattern "<.*>|$.*";
           }
           type uint32 {
             range "0 .. 4";
           }
         }
       }
     }
     output {
       container fm-plane-state-information {
         uses fm-plane-state-information-block;
       }
     }
   }
   rpc get-fm-state-information {
     description "Show summary fabric management state";
     junos:command "show chassis fabric summary";
     input {
       uses command-forwarding;
     }
     output {
       container fm-state-information {
         uses fm-state-information-block;
       }
     }
   }
   rpc get-fm-ext-state-information {
     description "Show extended summary fabric management state";
     junos:command "show chassis fabric summary extended";
     input {
       uses command-forwarding;
     }
     output {
       container fm-ext-state-information {
         uses fm-ext-state-information-block;
       }
     }
   }
   rpc get-fm-state-legend {
     description "Show legend of fabric management states";
     junos:command "show chassis fabric legend";
     input {
       uses command-forwarding;
     }
     output {
       container fm-state-legend {
         uses fm-state-legend-block;
       }
     }
   }
   rpc get-fm-fabric-reachability-information {
     description "Show current status of fabric reachability";
     junos:command "show chassis fabric reachability";
     input {
       uses command-forwarding;
       leaf detail {
         description "Show reachability output in detail";
         type empty;
       }
     }
     output {
       container fm-fabric-reachability-information {
         uses fm-fabric-reachability-information-block;
       }
     }
   }
   rpc get-fm-fabric-events-information {
     description "Show current fabric events that are in progress";
     junos:command "show chassis fabric events queue";
     input {
       uses command-forwarding;
     }
     output {
       container fm-fabric-events-information {
         uses fm-fabric-events-information-block;
       }
     }
   }
   rpc get-fm-fabric-events-history {
     description "Show fabric events history.";
     junos:command "show chassis fabric events history";
     output {
       container fm-fabric-events-history {
         uses fm-fabric-events-history-block;
       }
     }
   }
   rpc get-fm-fpc-stream-information {
     description "Show FPC stream number information";
     junos:command "show chassis fabric stream-info";
     input {
       uses command-forwarding;
     }
     output {
       container fm-fpc-stream-information {
         uses fm-fpc-stream-information-block;
       }
     }
   }
   rpc get-chassis-inventory {
     description "Show installed hardware components";
     junos:command "show chassis hardware";
     input {
       uses command-forwarding;
       leaf verbosity {
         junos:cli-feature "nokeyword";
         type enumeration {
           enum "detail" {
             description "Include RAM and disk information in output";
           }
           enum "extensive" {
             description "Display ID EEPROM information";
           }
           enum "models" {
             description "Display serial number and model number for orderable FRUs";
           }
           enum "clei-models" {
             description "Display CLEI barcode and model number for orderable FRUs";
           }
         }
       }
     }
     output {
       container chassis-inventory {
         uses chassis-inventory-block;
       }
     }
   }
   rpc get-reswatch-config-information {
     description "Show rewatch configuration";
     junos:command "show chassis reswatch-config";
     input {
       uses command-forwarding;
     }
     output {
       container reswatch-config-information {
         uses reswatch-config-information-block;
       }
     }
   }
   rpc get-power-budget-information {
     description "Show power budget chassis information";
     junos:command "show chassis power-budget-statistics";
     input {
       uses command-forwarding;
     }
     output {
       container power-budget-information {
         uses power-budget-information-block;
       }
     }
   }
   rpc get-chassis-mac-addresses {
     description "Show media access control addresses";
     junos:command "show chassis mac-addresses";
     input {
       uses command-forwarding;
     }
     output {
       container chassis-mac-addresses {
         uses chassis-mac-addresses-block;
       }
     }
   }
   rpc get-raid-status {
     description "Show RAID status";
     junos:command "show chassis raid status";
     input {
       uses command-forwarding;
     }
     output {
       container raid-information {
         uses raid-information-block;
       }
     }
   }
   rpc get-raid-members {
     description "Show RAID members";
     junos:command "show chassis raid members";
     input {
       uses command-forwarding;
     }
     output {
       container raid-information {
         uses raid-information-block;
       }
     }
   }
   rpc get-route-engine-information {
     description "Show Routing Engine status";
     junos:command "show chassis routing-engine";
     input {
       uses command-forwarding;
       leaf slot {
         description "Routing Engine slot number";
         junos:cli-feature "nokeyword";
         type union {
           type string {
             pattern "<.*>|$.*";
           }
           type uint32;
         }
       }
     }
     output {
       container route-engine-information {
         uses route-engine-information-block;
       }
     }
   }
   rpc get-bios-version-information {
     description "Show BIOS firmware version";
     junos:command "show chassis routing-engine bios";
     input {
       uses command-forwarding;
     }
     output {
       container route-engine-information {
         uses route-engine-information-block;
       }
     }
   }
   rpc get-chassis-hard-disk-test {
     description "Show smartd self tests status on hard disks";
     junos:command "show chassis routing-engine hard-disk-test";
     input {
       leaf status {
         description "Display status of test";
         type empty;
         mandatory true;
       }
       leaf disk {
         description "Name of hard disk";
         type string;
         mandatory true;
       }
     }
     output {
       container raid-information {
         uses raid-information-block;
       }
     }
   }
   rpc get-chassis-routing-engine-errors {
     description "Show RE errors";
     junos:command "show chassis routing-engine errors";
     input {
       uses command-forwarding;
     }
     output {
       container route-engine-resiliency-information {
         uses route-engine-resiliency-information-block;
       }
     }
   }
   rpc get-fwdd-information {
     description "Show forwarding process (fwdd) status";
     junos:command "show chassis forwarding";
     input {
       uses command-forwarding;
     }
     output {
       container scb-information {
         uses scb-information-block;
       }
     }
   }
   rpc get-fan-information {
     description "Show fan and fan tray information";
     junos:command "show chassis fan";
     input {
       uses command-forwarding;
     }
     output {
       container fan-information {
         uses fan-information-block;
       }
     }
   }
   rpc get-chassis-location {
     description "Show physical location of chassis";
     junos:command "show chassis location";
     input {
       uses command-forwarding;
     }
     output {
       container chassis-location {
         uses chassis-location-block;
       }
     }
   }
   rpc get-temperature-threshold-information {
     description "Show chassis temperature threshold settings";
     junos:command "show chassis temperature-thresholds";
     input {
       uses command-forwarding;
     }
     output {
       container temperature-threshold-information {
         uses temperature-threshold-information-block;
       }
     }
   }
   rpc get-enh-temperature-threshold-information {
     description "Show chassis temperature threshold settings";
     junos:command "show chassis enhanced-temperature-thresholds";
     output {
       container enh-temperature-threshold-information {
         uses enh-temperature-threshold-information-block;
       }
     }
   }
   rpc get-power-management {
     description "Show power ratings for the router";
     junos:command "show chassis power-ratings";
     input {
       uses command-forwarding;
     }
     output {
       container power-management-information {
         uses power-management-information-block;
       }
     }
   }
   rpc get-dedicated-ukern-status {
     description "Show ukernel dedicated CPU core assignment status ";
     junos:command "show chassis dedicated-ukern-cpu";
     output {
       container dedicated-ukern-cpu {
         uses dedicated-ukern-cpu-block;
       }
     }
   }
   rpc get-realtime-ukern-status {
     description "Show ukernel realtime thread assignment status ";
     junos:command "show chassis realtime-ukern-thread";
   }
   rpc get-chassis-oss-map {
     description "Show Operation Supported System's translated model";
     junos:command "show chassis oss-map";
     output {
       container chassis-oss-map {
         uses chassis-oss-map-block;
       }
     }
   }
   rpc get-chassis-cluster-interfaces {
     description "Display chassis cluster interfaces";
     junos:command "show chassis cluster interfaces";
     output {
       container chassis-cluster-interface-statistics {
         uses chassis-cluster-interface-statistics-block;
       }
     }
   }
   rpc get-chassis-cluster-control-port-status {
     description "Display HA control port status";
     junos:command "show chassis cluster control-interface status";
     output {
       container chassis-cluster-control-port-status {
         uses chassis-cluster-control-port-status-block;
       }
     }
   }
   rpc get-chassis-cluster-control-plane-statistics {
     description "Display control-plane statistics";
     junos:command "show chassis cluster control-plane statistics";
     output {
       container chassis-cluster-statistics {
         uses chassis-cluster-statistics-block;
       }
     }
   }
   rpc get-chassis-cluster-data-plane-statistics {
     description "Display data-plane statistics";
     junos:command "show chassis cluster data-plane statistics";
     output {
       container services-synchronized {
         uses services-synchronized-block;
       }
     }
   }
   rpc get-chassis-cluster-data-plane-interfaces {
     description "Display data-plane interfaces";
     junos:command "show chassis cluster data-plane interfaces";
     output {
       container chassis-cluster-dataplane-interfaces {
         uses chassis-cluster-dataplane-interfaces-block;
       }
     }
   }
   rpc get-chassis-cluster-statistics {
     description "Display chassis cluster statistics";
     junos:command "show chassis cluster statistics";
     output {
       container chassis-cluster-statistics {
         uses chassis-cluster-statistics-block;
       }
     }
   }
   rpc get-chassis-cluster-status {
     description "Display chassis cluster status";
     junos:command "show chassis cluster status";
     input {
       leaf redundancy-group {
         description "Display chassis cluster status per redundancy-group";
         type union {
           type string {
             pattern "<.*>|$.*";
           }
           type uint8;
         }
       }
     }
     output {
       container chassis-cluster-status {
         uses chassis-cluster-status-block;
       }
     }
   }
   rpc get-chassis-cluster-information {
     description "Show chassis cluster information";
     junos:command "show chassis cluster information";
     input {
       uses command-forwarding;
     }
     output {
       container chassis-cluster-information {
         uses chassis-cluster-information-block;
       }
     }
   }
   rpc get-chassis-cluster-configuration-synchronization-information {
     description "Display configuration synchronization information";
     junos:command "show chassis cluster information configuration-synchronization";
     input {
       uses command-forwarding;
     }
     output {
       container configuration-synchronization-information {
         uses configuration-synchronization-information-block;
       }
     }
   }
   rpc get-chassis-cluster-issu-information {
     description "Display ISSU information";
     junos:command "show chassis cluster information issu";
     input {
       uses command-forwarding;
     }
     output {
       container issu-information {
         uses issu-information-block;
       }
     }
   }
   rpc get-chassis-cluster-detail-information {
     description "Display all chassis cluster information";
     junos:command "show chassis cluster information detail";
     input {
       uses command-forwarding;
       leaf redundancy-group {
         description "Display chassis cluster status per redundancy-group";
         type union {
           type string {
             pattern "<.*>|$.*";
           }
           type uint8;
         }
       }
     }
     output {
       container chassis-cluster-detail-information {
         uses chassis-cluster-detail-information-block;
       }
     }
   }
   rpc get-chassis-cluster-cold-synchronization-information {
     description "Display coldsync information";
     junos:command "show chassis cluster information detail coldsync";
     input {
       uses command-forwarding;
     }
     output {
       container cold-synchronization-monitoring-information {
         uses cold-synchronization-monitoring-information-block;
       }
     }
   }
   rpc get-chassis-cluster-spu-information {
     description "Display SPU information";
     junos:command "show chassis cluster information detail spu";
     input {
       uses command-forwarding;
     }
     output {
       container spu-monitoring-information {
         uses spu-monitoring-information-block;
       }
     }
   }
   rpc get-chassis-cluster-loopback-information {
     description "Display loopback monitoring information";
     junos:command "show chassis cluster information detail loopback";
     input {
       uses command-forwarding;
     }
     output {
       container loopback-information {
         uses loopback-information-block;
       }
     }
   }
   rpc get-chassis-cluster-hardware-monitoring-information {
     description "Display hardware monitoring information";
     junos:command "show chassis cluster information detail hardware-monitor";
     input {
       uses command-forwarding;
     }
     output {
       container hardware-monitoring-information {
         uses hardware-monitoring-information-block;
       }
     }
   }
   rpc get-chassis-cluster-schedule-monitoring-information {
     description "Display schedule monitoring information";
     junos:command "show chassis cluster information detail schedule-monitor";
     input {
       uses command-forwarding;
     }
     output {
       container schedule-monitoring-information {
         uses schedule-monitoring-information-block;
       }
     }
   }
   rpc get-chassis-cluster-interface-monitoring-information {
     description "Display interface monitoring information";
     junos:command "show chassis cluster information detail interface-monitor";
     input {
       uses command-forwarding;
     }
     output {
       container interface-monitoring-information {
         uses interface-monitoring-information-block;
       }
     }
   }
   rpc get-chassis-cluster-control-link-information {
     description "Display control link information";
     junos:command "show chassis cluster information detail control-link";
     input {
       uses command-forwarding;
     }
     output {
       container control-link-information {
         uses control-link-information-block;
       }
     }
   }
   rpc get-chassis-cluster-fabric-link-information {
     description "Display fabric link information";
     junos:command "show chassis cluster information detail fabric-link";
     input {
       uses command-forwarding;
     }
     output {
       container fabric-link-information {
         uses fabric-link-information-block;
       }
     }
   }
   rpc get-chassis-cluster-command-history-information {
     description "Display command history";
     junos:command "show chassis cluster information detail command-history";
     input {
       uses command-forwarding;
     }
     output {
       container command-history-information {
         uses command-history-information-block;
       }
     }
   }
   rpc get-chassis-cluster-ip-monitoring-status {
     description "Display IP monitoring status";
     junos:command "show chassis cluster ip-monitoring status";
     input {
       uses command-forwarding;
     }
     output {
       container chassis-cluster-ip-monitoring {
         uses chassis-cluster-ip-monitoring-block;
       }
     }
   }
   rpc get-chassis-cluster-ip-monitoring-status-redundancy-group {
     description "Show IP monitoring status of a specific redundancy-group";
     junos:command "show chassis cluster ip-monitoring status redundancy-group";
     input {
       uses command-forwarding;
       leaf redundancy-group-identifier {
         description "Redundancy-group identifier";
         junos:cli-feature "nokeyword";
         type union {
           type string {
             pattern "<.*>|$.*";
           }
           type uint8;
         }
         mandatory true;
       }
     }
     output {
       container chassis-cluster-ip-monitoring {
         uses chassis-cluster-ip-monitoring-block;
       }
     }
   }
   rpc get-chassis-cluster-ethernet-switching-status {
     description "Display chassis cluster ethernet switching status";
     junos:command "show chassis cluster ethernet-switching status";
     output {
       container chassis-cluster-ethernet-switching-status {
         uses chassis-cluster-ethernet-switching-status-block;
       }
     }
   }
   rpc get-chassis-cluster-switch-fabric-probe-statistics {
     description "Display chassis cluster switch fabric probe statistics";
     junos:command "show chassis cluster ethernet-switching statistics";
     output {
       container chassis-cluster-ethernet-switching-statistics {
         uses chassis-cluster-ethernet-switching-statistics-block;
       }
     }
   }
   rpc get-chassis-cluster-switch-fabric-link-interfaces {
     description "Display chassis cluster switch fabric link interfaces";
     junos:command "show chassis cluster ethernet-switching interfaces";
     output {
       container chassis-cluster-ethernet-switching-interfaces {
         uses chassis-cluster-ethernet-switching-interfaces-block;
       }
     }
   }
   rpc get-chassis-high-availability-information {
     description "Display high-availability information";
     junos:command "show chassis high-availability information";
     output {
       container chassis-high-availability-info {
         uses chassis-high-availability-info-block;
       }
     }
   }
   rpc get-chassis-high-availability-detail-information {
     description "Display detailed high-availability info";
     junos:command "show chassis high-availability information detail";
     input {
       leaf services-redundancy-group {
         description "Service redundancy-group identifier";
         type union {
           type string {
             pattern "<.*>|$.*";
           }
           type uint8 {
             range "0 .. 20";
           }
         }
       }
     }
     output {
       container chassis-high-availability-detail-information {
         uses chassis-high-availability-detail-information-block;
       }
     }
   }
   rpc get-chassis-high-availability-peer-information {
     description "Display high-availability peer information";
     junos:command "show chassis high-availability peer-info";
     output {
       container chassis-high-availability-peer-info-detail {
         uses chassis-high-availability-peer-info-detail-block;
       }
     }
   }
   rpc get-chassis-ha-data-plane-statistics {
     description "Display data-plane statistics";
     junos:command "show chassis high-availability data-plane statistics";
     output {
       container services-synchronized {
         uses services-synchronized-block;
       }
     }
   }
   rpc get-chassis-high-availability-srg-information {
     description "Show specific service-redundancy-group terse information";
     junos:command "show chassis high-availability services-redundancy-group";
     input {
       leaf services-redundancy-group-id {
         description "Service redundancy-group identifier";
         junos:cli-feature "nokeyword";
         type union {
           type string {
             pattern "<.*>|$.*";
           }
           type uint8 {
             range "0 .. 20";
           }
         }
         mandatory true;
       }
       leaf monitor-object {
         description "SRG monitored object name";
         type string;
       }
     }
     output {
       container chassis-high-availability-srg-terse-info {
         uses chassis-high-availability-srg-terse-info-block;
       }
     }
   }
   rpc get-chassis-high-availability-prefix-information {
     description "Show ip prefix to srg mapping information";
     junos:command "show chassis high-availability prefix-srgid-table";
     output {
       container chassis-high-availability-prefix-information {
         uses chassis-high-availability-prefix-information-block;
       }
     }
   }
   rpc get-chassis-high-availability-prefix-ip-information {
     description "IP to be queried for prefix-srgid mapping";
     junos:command "show chassis high-availability prefix-srgid-table query-ip";
     input {
       leaf ip-address {
         description "IP address";
         junos:cli-feature "nokeyword";
         type jt:ipaddr;
         mandatory true;
       }
       leaf routing-table {
         description "Routing table (e.g. - default)";
         type string;
         mandatory true;
       }
     }
     output {
       container chassis-high-availability-prefix-ip-information {
         uses chassis-high-availability-prefix-ip-information-block;
       }
     }
   }
   rpc get-chassis-high-availability-prefix-srgid-information {
     description "SRG id to be queried for prefix-srgid mapping";
     junos:command "show chassis high-availability prefix-srgid-table query-srgid";
     input {
       leaf srg-id {
         description "Service redundancy-group identifier";
         junos:cli-feature "nokeyword";
         type union {
           type string {
             pattern "<.*>|$.*";
           }
           type uint8 {
             range "0 .. 20";
           }
         }
         mandatory true;
       }
     }
     output {
       container chassis-high-availability-prefix-srgid-information {
         uses chassis-high-availability-prefix-srgid-information-block;
       }
     }
   }
   rpc get-chassis-high-availability-prefix-policy-information {
     description "Show policy table information";
     junos:command "show chassis high-availability prefix-srgid-table prefix-policy-table";
     output {
       container chassis-high-availability-prefix-policy-information {
         uses chassis-high-availability-prefix-policy-information-block;
       }
     }
   }
   grouping command-forwarding {
     leaf no-forwarding {
       description "No forwarding";
       type empty;
     }
     choice chassis-selector {
       case case_1 {
         leaf all-chassis {
           description "All chassis";
           type empty;
         }
       }
       case case_2 {
         leaf all-lcc {
           description "All LCC chassis";
           type empty;
         }
       }
       case case_3 {
         leaf scc {
           description "SCC";
           type empty;
         }
       }
       case case_4 {
         leaf sfc {
           description "SFC";
           type union {
             type string {
               pattern "<.*>|$.*";
             }
             type uint32;
           }
         }
       }
       case case_5 {
         leaf lcc {
           description "Specific LCC";
           type union {
             type string {
               pattern "<.*>|$.*";
             }
             type uint32;
           }
         }
       }
       case case_6 {
         leaf node {
           description "Specific node";
           type string;
         }
       }
       case case_7 {
         leaf bsys {
           description "Base system";
           type empty;
         }
       }
       case case_8 {
         leaf gnf {
           description "Specific guest network function";
           type union {
             type string {
               pattern "<.*>|$.*";
             }
             type uint32 {
               range "1 .. 10";
             }
           }
         }
       }
       case case_9 {
         leaf all-gnfs {
           description "All guest network functions";
           type empty;
         }
       }
       case case_10 {
         leaf all-system {
           description "All system (BSYS and GNFs)";
           type empty;
         }
       }
       case case_11 {
         leaf server {
           description "Specific server slot";
           type union {
             type string {
               pattern "<.*>|$.*";
             }
             type uint32 {
               range "0 .. 1";
             }
           }
         }
       }
       case case_12 {
         leaf all-servers {
           description "All servers";
           type empty;
         }
       }
       case case_13 {
         leaf vnf {
           description "Specific virtual-network-function";
           type string;
         }
       }
       case case_14 {
         leaf all-vnfs {
           description "All virtual-network-functions";
           type empty;
         }
       }
     }
     choice re-selector {
       case case_1 {
         leaf re0 {
           description "RE0";
           type empty;
         }
       }
       case case_2 {
         leaf re1 {
           description "RE1";
           type empty;
         }
       }
       case case_3 {
         leaf routing-engine {
           description "Specific routing engine";
           type enumeration {
             enum "local" {
               description "Local routing engine";
             }
             enum "other" {
               description "Other routing engine";
             }
             enum "master" {
               description "Master routing engine";
             }
             enum "backup" {
               description "Backup routing engine";
             }
             enum "both" {
               description "Both routing engines";
             }
           }
         }
       }
     }
     choice lr-selector {
       case case_1 {
         leaf logical-system {
           description "Name of logical system, or 'all'";
           type string;
         }
       }
     }
     choice tenant-selector {
       case case_1 {
         leaf tenant {
           description "Name of tenant, or 'all'";
           type string;
         }
       }
     }
     choice vc-selector {
       case case_1 {
         leaf local {
           description "Local virtual chassis member";
           type empty;
         }
       }
       case case_2 {
         leaf all-members {
           description "All virtual chassis members";
           type empty;
         }
       }
       case case_3 {
         leaf member {
           description "Specific virtual chassis member which is master";
           type union {
             type string {
               pattern "<.*>|$.*";
             }
             type uint32;
           }
         }
       }
     }
   }
   grouping chassis-scb-ha-port-block {
     container chassis-scb-ha-port-eeprom {
       description "Information about Switch Control Board HA control port ideeprom data";
       leaf scb-port-number {
         type int32;
         description "Port number on the PIC";
       }
       leaf scb-cable-type {
         type string;
         description "Port cable type";
       }
       leaf scb-fiber-mode {
         type string;
         description "Single or multi-mode";
       }
       leaf scb-sfp-vendor-name {
         type string;
         description "SFP vendor name";
       }
       leaf scb-sfp-vendor-pno {
         type string;
         description "SFP vendor part number";
       }
       leaf scb-wavelength {
         type string;
         description "Wavelength of the optical transceiver";
       }
       leaf scb-sfp-vendor-fw-ver {
         type string;
         description "Vendor firmware version";
       }
       leaf scb-sfp-jnpr-ver {
         type string;
         description "Juniper revision";
       }
       leaf scb-sfp-msa-version {
         type string;
         description "Multi-Source Agreement version";
       }
     }
     container chassis-scb-ha-port-diag {
       description "Information about Switch Control Board HA control port diagnostics data";
       leaf port-index {
         type int32;
       }
       leaf current {
         type string;
       }
       leaf output-powers {
         type string;
       }
       leaf temp {
         type string;
       }
       leaf-list voltage {
         type string;
       }
       leaf receiver-power {
         type string;
       }
       leaf alarm-warning-flags {
         type string;
       }
       leaf current-high-alarm {
         type string;
       }
       leaf current-low-alarm {
         type string;
       }
       leaf current-high-warning {
         type string;
       }
       leaf current-low-warning {
         type string;
       }
       leaf output-power-high-alarm {
         type string;
       }
       leaf output-power-low-alarm {
         type string;
       }
       leaf output-power-high-warning {
         type string;
       }
       leaf output-power-low-warning {
         type string;
       }
       leaf temperature-high-alarm {
         type string;
       }
       leaf temperature-low-alarm {
         type string;
       }
       leaf temperature-high-warning {
         type string;
       }
       leaf temperature-low-warning {
         type string;
       }
       leaf voltage-high-alarm {
         type string;
       }
       leaf voltage-low-alarm {
         type string;
       }
       leaf voltage-high-warning {
         type string;
       }
       leaf voltage-low-warning {
         type string;
       }
       leaf rx-power-high-alarm {
         type string;
       }
       leaf rx-power-low-alarm {
         type string;
       }
       leaf rx-power-high-warning {
         type string;
       }
       leaf rx-power-low-warning {
         type string;
       }
       leaf current-high-alarm-threshold {
         type string;
       }
       leaf current-low-alarm-threshold {
         type string;
       }
       leaf current-high-warning-threshold {
         type string;
       }
       leaf current-low-warning-threshold {
         type string;
       }
       leaf output-power-high-alarm-threshold {
         type string;
       }
       leaf output-power-low-alarm-threshold {
         type string;
       }
       leaf output-power-high-warning-threshold {
         type string;
       }
       leaf output-power-low-warning-threshold {
         type string;
       }
       leaf temperature-high-alarm-threshold {
         type string;
       }
       leaf temperature-low-alarm-threshold {
         type string;
       }
       leaf temperature-high-warning-threshold {
         type string;
       }
       leaf temperature-low-warning-threshold {
         type string;
       }
       leaf voltage-high-alarm-threshold {
         type string;
       }
       leaf voltage-low-alarm-threshold {
         type string;
       }
       leaf voltage-high-warning-threshold {
         type string;
       }
       leaf voltage-low-warning-threshold {
         type string;
       }
       leaf rx-power-high-alarm-threshold {
         type string;
       }
       leaf rx-power-low-alarm-threshold {
         type string;
       }
       leaf rx-power-high-warning-threshold {
         type string;
       }
       leaf rx-power-low-warning-threshold {
         type string;
       }
     }
   }
   grouping power-usage-information-block {
     leaf capacity-actual {
       type uint32;
       description "Actual capacity in volt";
     }
     leaf capacity-max {
       type uint32;
       description "Maximum capacity in volt";
     }
     leaf capacity-allocated {
       type uint32;
       description "Allocated capacity in volt";
     }
     leaf capacity-remaining {
       type uint32;
       description "Remaining capacity in volt";
     }
     leaf capacity-actual-usage {
       type uint32;
       description "Actual usage in volt";
     }
     leaf capacity-load {
       type uint32;
       description "Percentage usage";
     }
     leaf zone {
       type uint32;
       description "Power zone";
     }
     leaf str-zone {
       type string;
       description "Power zone";
     }
     container power-usage-item {
       leaf name {
         type string;
         description "Name of this component";
       }
       leaf status {
         type string;
         description "Status of clock synchronization source";
       }
       leaf state {
         type string;
         description "Status of the component";
       }
       container ac-input-detail {
         leaf ac-input {
           type string;
           description "AC input state";
         }
         leaf ac-expect-feed {
           type uint32;
           description "Expect power input feed";
         }
         leaf ac-actual-feed {
           type uint32;
           description "Actual power input feed";
         }
       }
       container ac-input-detail2 {
         leaf ac-input_status {
           type string;
           description "AC input status";
         }
         leaf str-ac-expect-feed {
           type string;
           description "Expect power input feed";
         }
         leaf str-ac-actual-feed {
           type string;
           description "Actual power input feed";
         }
         leaf ac-feed0-voltage {
           type string;
           description "AC feed0 voltage";
         }
         leaf ac-feed0-current {
           type string;
           description "AC feed0 current";
         }
         leaf ac-feed0-power {
           type string;
           description "AC feed0 power";
         }
         leaf ac-feed1-voltage {
           type string;
           description "AC feed1 voltage";
         }
         leaf ac-feed1-current {
           type string;
           description "AC feed1 current";
         }
         leaf ac-feed1-power {
           type string;
           description "AC feed1 power";
         }
       }
       container dc-input-detail {
         leaf dc-input {
           type string;
           description "DC input state";
         }
         leaf dc-expect-feed {
           type uint32;
           description "Expect power input feed";
         }
         leaf dc-actual-feed {
           type uint32;
           description "Actual power input feed";
         }
         leaf reference-voltage {
           type string;
           description "Voltage of the item in Volts";
         }
         leaf actual-voltage {
           type int32;
           description "Voltage of the item in mVlots";
         }
       }
       container dc-input-detail2 {
         leaf dc-input-status {
           type string;
           description "DC input status";
         }
         leaf str-dc-expect-feed {
           type string;
           description "Expect power input feed";
         }
         leaf str-dc-actual-feed {
           type string;
           description "Actual power input feed";
         }
         leaf dc-feed0-voltage {
           type string;
           description "DC feed0 voltage";
         }
         leaf dc-feed0-current {
           type string;
           description "DC feed0 current";
         }
         leaf dc-feed0-power {
           type string;
           description "DC feed0 power";
         }
         leaf dc-feed1-voltage {
           type string;
           description "DC feed1 voltage";
         }
         leaf dc-feed1-current {
           type string;
           description "DC feed1 current";
         }
         leaf dc-feed1-power {
           type string;
           description "DC feed1 power";
         }
       }
       container dc-output-detail {
         leaf dc-power {
           type uint32;
         }
         leaf zone {
           type uint32;
           description "Power zone";
         }
         leaf dc-current {
           type uint32;
         }
         leaf dc-voltage {
           type uint32;
         }
         leaf dc-load {
           type uint32;
         }
         leaf str3-dc-current {
           type string;
         }
         leaf str3-dc-voltage {
           type string;
         }
       }
       container dc-output-detail2 {
         leaf str-dc-power {
           type string;
         }
         leaf str-zone {
           type string;
           description "Power zone";
         }
         leaf str-dc-current {
           type string;
         }
         leaf str-dc-voltage {
           type string;
         }
         leaf str-dc-load {
           type string;
         }
       }
       container dc-output-detail3 {
         leaf str2-dc-power {
           type string;
         }
         leaf str2-dc-current {
           type string;
         }
         leaf str2-dc-voltage {
           type string;
         }
         leaf str2-dc-load {
           type string;
         }
       }
       container pem-capacity-detail {
         leaf capacity-actual {
           type uint32;
           description "Actual capacity in volt";
         }
         leaf capacity-max {
           type uint32;
           description "Maximum capacity in volt";
         }
       }
       container dc-output-detail4 {
         leaf dc-power1 {
           type uint32;
         }
         leaf zone1 {
           type uint32;
         }
         leaf str4-dc-current {
           type string;
         }
         leaf str4-dc-voltage {
           type string;
         }
         leaf dc-load-integer {
           type uint32;
         }
         leaf str-dip-switch-input {
           type string;
         }
       }
       container input-mode-detail {
         leaf feed-number {
           type uint32;
           description "Index of the Feed";
         }
         leaf feed-type {
           type string;
           description "Type of input given to the feed";
         }
       }
     }
     container power-usage-system {
       leaf capacity-res-power {
         type uint32;
       }
       leaf capacity-sys-actual {
         type uint32;
       }
       leaf capacity-sys-max {
         type uint32;
       }
       leaf capacity-sys-remaining {
         type uint32;
       }
       container power-usage-zone-information {
         leaf zone {
           type uint32;
           description "Power zone";
         }
         leaf str-zone {
           type string;
           description "Power zone";
         }
         leaf capacity-actual {
           type uint32;
           description "Actual capacity in volt";
         }
         leaf capacity-max {
           type uint32;
           description "Maximum capacity in volt";
         }
         leaf capacity-allocated {
           type uint32;
           description "Allocated capacity in volt";
         }
         leaf capacity-remaining {
           type uint32;
           description "Remaining capacity in volt";
         }
         leaf capacity-actual-usage {
           type uint32;
           description "Actual usage in volt";
         }
       }
       container power-mode-system-information {
         leaf power-mode {
           type string;
           description "Power mode";
         }
       }
     }
     container power-usage-system2 {
       container power-usage-zone-information2 {
         leaf capacity-actual {
           type uint32;
           description "Actual capacity in volt";
         }
         leaf capacity-max {
           type uint32;
           description "Maximum capacity in volt";
         }
         leaf capacity-allocated {
           type uint32;
           description "Allocated capacity in volt";
         }
         leaf capacity-remaining {
           type uint32;
           description "Remaining capacity in volt";
         }
         leaf capacity-actual-usage {
           type uint32;
           description "Actual usage in volt";
         }
       }
     }
     container power-usage-total {
       leaf dc-power {
         type uint32;
       }
     }
     container power-usage-voltage-total {
       leaf dc-power {
         type uint32;
       }
     }
     container power-usage-pdu-item {
       leaf slot {
         type int32;
       }
       leaf dc-power {
         type uint32;
       }
       container power-usage-psm-item {
         leaf slot {
           type int32;
         }
         container power-usage-psm-input {
           leaf name {
             type string;
             description "Name of this component";
           }
           leaf dc-voltage {
             type uint32;
           }
           leaf dc-power {
             type uint32;
           }
         }
         leaf state {
           type string;
           description "Status of the component";
         }
         container power-usage-psm-detail {
           leaf capacity-actual {
             type uint32;
             description "Actual capacity in volt";
           }
           leaf capacity-max {
             type uint32;
             description "Maximum capacity in volt";
           }
         }
       }
     }
     container power-usage-psm-item1 {
       leaf slot {
         type int32;
       }
       container power-usage-psm-input1 {
         leaf name {
           type string;
           description "Name of this component";
         }
         leaf dc-voltage {
           type uint32;
         }
         leaf dc-power {
           type uint32;
         }
         container power-usage-psm-a-feed {
           leaf feed-a-num {
             type uint32;
           }
           leaf dc-vin-a {
             type uint32;
           }
         }
         container power-usage-psm-b-feed {
           leaf feed-b-num {
             type uint32;
           }
           leaf dc-vin-b {
             type uint32;
           }
         }
         container power-usage-psm-ac-feed {
           leaf name {
             type string;
             description "Name of this component";
           }
           leaf ac-voltage {
             type uint32;
           }
           leaf ac-power {
             type uint32;
           }
         }
         container power-usage-psm-dc-feed {
           leaf name {
             type string;
             description "Name of this component";
           }
           leaf dc-voltage {
             type uint32;
           }
           leaf dc-power {
             type uint32;
           }
         }
       }
       leaf name {
         type string;
         description "Name of this component";
       }
       leaf state {
         type string;
         description "Status of the component";
       }
       container power-usage-psm-info {
         leaf psm-type {
           type string;
           description "Psm type";
         }
         leaf psm-feed {
           type string;
           description "Psm feed";
         }
       }
       container power-usage-psm-output {
         leaf name {
           type string;
           description "Name of this component";
         }
         leaf dc-voltage {
           type uint32;
         }
         leaf dc-power {
           type uint32;
         }
         leaf input-source {
           type string;
           description "Input source";
         }
       }
       container power-usage-psm-detail1 {
         leaf capacity-actual {
           type uint32;
           description "Actual capacity in volt";
         }
         leaf capacity-max {
           type uint32;
           description "Maximum capacity in volt";
         }
       }
       container power-usage-psm-detail2 {
         leaf capacity-used {
           type uint32;
           description "Capacity used percentage";
         }
         leaf conversion-efficiency {
           type uint32;
           description "Conversion efficiency";
         }
       }
     }
     container power-usage-fru-item {
       leaf name {
         type string;
         description "Name of this component";
       }
       leaf dc-power {
         type uint32;
       }
       container sub-components {
         list sub-component {
           leaf comp-name {
             type string;
           }
           leaf comp-power {
             type uint32;
           }
         }
       }
     }
     leaf percent-capacity-allocated {
       type uint32;
       description "Percentage of maximum capacity allocated";
     }
     leaf power-mode {
       type string;
       description "Power mode";
     }
     container power-usage-system3 {
       leaf capacity-max {
         type uint32;
         description "Maximum capacity in volt";
       }
       leaf capacity-allocated {
         type uint32;
         description "Allocated capacity in volt";
       }
       leaf percent-capacity-allocated {
         type uint32;
         description "Percentage of maximum capacity allocated";
       }
       leaf capacity-remaining {
         type uint32;
         description "Remaining capacity in volt";
       }
       leaf capacity-actual-usage {
         type uint32;
         description "Actual usage in volt";
       }
     }
     container power-usage-voltage-total1 {
       leaf dc-power {
         type uint32;
       }
     }
     container sub-components {
     }
     container power-usage-component {
       leaf name {
         type string;
         description "Name of this component";
       }
       leaf dc-power {
         type uint32;
       }
     }
     container power-usage-max-fru-item {
       leaf name {
         type string;
         description "Name of this component";
       }
       leaf dc-power {
         type uint32;
       }
       leaf max-power {
         type uint32;
       }
     }
   }
   grouping fru-power-on-sequence-block {
     leaf sequence {
       type string;
     }
   }
   grouping alarm-information-block {
     container alarm-summary {
       description "Number of alarms currently active";
       leaf active-alarm-count {
         type int32;
         description "Number of active alarms";
       }
       leaf active-fpc-slot {
         type int32;
         description "FPC slot with active alarms";
       }
       leaf no-active-alarms {
         type empty;
         description "No active alarms";
       }
       leaf no-active-fpc-slot {
         type int32;
         description "FPC slot with non active alarms";
       }
     }
     list alarm-detail {
       description "Detailed information about an active alarm";
       leaf alarm-time {
         type string;
         description "Time of the alarm";
       }
       leaf alarm-class {
         type string;
         description "Class of the alarm";
       }
       leaf alarm-description {
         type string;
         description "Description of the alarm";
       }
       leaf alarm-short-description {
         type string;
         description "Short description of the alarm";
       }
       leaf alarm-type {
         type string;
         description "Type (class) of the alarm";
       }
     }
   }
   grouping ambient-temperature-block {
     container ambient-temperature-information {
       leaf name {
         type string;
         description "Name of this component";
       }
     }
   }
   grouping satellite-device-list-block {
     list satellite-device {
       leaf slot {
         type int32;
       }
       leaf description {
         type string;
         description "Description of this component";
       }
       leaf ip-address {
         type jt:ipaddr;
       }
       leaf target-mode {
         type string;
       }
       leaf mac-address-base {
         type jt:mac-addr;
       }
       leaf mac-address-count {
         type int32;
       }
       leaf-list cascade-port {
         type string;
       }
     }
   }
   grouping craft-information-block {
     leaf-list output {
       type string;
       description "Formatted ASCII output displayed by the CLI";
     }
     container front-panel {
       description "Information from the craft interface";
       container display-panel {
         description "Text currently appearing on the craft interface display";
         leaf-list display-line {
           type string;
           description "Single line of text currently appearing on the craft interface display";
         }
       }
       container re-panel {
         description "State of status LEDs on the craft interface for one or more Routing Engines. The front panel of each Routing Engine has the same LEDs.";
         list re {
           description "State of status LEDs on the craft interface for a Routing Engine. The front panel of the Routing Engine has the same LEDs.";
           leaf slot {
             type int32;
           }
           leaf ok-led {
             type empty;
             description "OK LED is lit";
           }
           leaf fail-led {
             type empty;
             description "Fail LED is lit";
           }
           leaf master-led {
             type empty;
             description "Master LED is lit";
           }
         }
       }
       container alarm-indicators {
         description "Information about alarms from the craft interface";
         leaf red-led {
           type empty;
           description "Red LED is lit";
         }
         leaf yellow-led {
           type empty;
           description "Yellow LED is lit";
         }
         leaf major-alarm-relay {
           type empty;
           description "Major (red) alarm relay is active";
         }
         leaf minor-alarm-relay {
           type empty;
           description "Minor (yellow) alarm relay is active";
         }
       }
       container fpc-panel {
         description "State of status LEDs on the craft interface for Flexible PIC Concentrators";
         list fpccraft {
           description "State of status LEDs on the craft interface for Flexible PICConcentrators.";
           leaf slot {
             type int32;
           }
           leaf red-led {
             type empty;
             description "Red LED is lit";
           }
           leaf green-led {
             type empty;
             description "Green LED is lit";
           }
         }
       }
       container sib-panel {
         description "State of the status LEDs on the faceplate of one or more Switch Interface Boards. Some of the LEDs also appear on the craft interface.";
         container sib {
           leaf ok-led {
             type empty;
             description "OK LED is lit";
           }
           leaf fail-led {
             type empty;
             description "Fail LED is lit";
           }
           leaf active-led {
             type empty;
             description "Active LED is lit";
           }
         }
       }
       container ccg-panel {
         description "State of the status LEDs on the faceplate of one or more SONET ClockGenerators";
         container ccg {
           description "State of the CCG status LEDs on the craft interface";
           leaf slot {
             type int32;
           }
           leaf ok-led {
             type empty;
             description "OK LED is lit";
           }
           leaf fail-led {
             type empty;
             description "Fail LED is lit";
           }
           leaf master-led {
             type empty;
             description "Master LED is lit";
           }
         }
       }
       container cb-panel {
         description "State of status LEDs on one or more Control Boards";
         list cb {
           description "State of status LEDs on a Control Board";
           leaf slot {
             type int32;
           }
           leaf amber-led {
             type empty;
             description "Amber LED is lit";
           }
           leaf green-led {
             type empty;
             description "Green LED is lit";
           }
           leaf blue-led {
             type empty;
             description "Blue LED is lit";
           }
         }
       }
       container fan-tray-panel {
         description "State of status LEDs on the craft interface for Fan Trays";
         container fan-tray {
           description "State of the status LEDs on the craft interface for a fan tray";
           leaf slot {
             type int32;
           }
           leaf red-led {
             type empty;
             description "Red LED is lit";
           }
           leaf green-led {
             type empty;
             description "Green LED is lit";
           }
         }
       }
       container power-supply-panel {
         description "State of the status LEDs on the faceplate of one or more power supplies";
         list power-supply {
           description "State of the status LEDs on the faceplate of a power supply";
           leaf slot {
             type int32;
           }
           leaf amber-led {
             type empty;
             description "Amber LED is lit";
           }
           leaf green-led {
             type empty;
             description "Green LED is lit";
           }
           leaf blue-led {
             type empty;
             description "Blue LED is lit";
           }
         }
         container pdu {
           description "State of the PDU status LEDs on the craft interface";
           leaf slot {
             type int32;
           }
           leaf red-led {
             type empty;
             description "Red LED is lit";
           }
           leaf green-led {
             type empty;
             description "Green LED is lit";
           }
           container psm {
             description "State of the PSM status LEDs on the craft interface";
             leaf slot {
               type int32;
             }
             leaf red-led {
               type empty;
               description "Red LED is lit";
             }
             leaf green-led {
               type empty;
               description "Green LED is lit";
             }
           }
         }
       }
     }
     container recb-panel {
       description "Information about LEDs from the craft interface";
       container ha-led {
         description "State of the HA LED on the craft interface";
         leaf red-led {
           type empty;
           description "Red LED is lit";
         }
         leaf yellow-led {
           type empty;
           description "Yellow LED is lit";
         }
         leaf amber-led {
           type empty;
           description "Amber LED is lit";
         }
       }
       container rps-led {
         description "State of the RPS LED on the craft interface";
         leaf red-led {
           type empty;
           description "Red LED is lit";
         }
         leaf green-led {
           type empty;
           description "Green LED is lit";
         }
         leaf led-off {
           type empty;
           description "LED is off";
         }
       }
       container mpim1-led {
         description "State of the MPIM1 LED on the craft interface";
         leaf green-led {
           type empty;
           description "Green LED is lit";
         }
         leaf led-off {
           type empty;
           description "LED is off";
         }
       }
       container mpim2-led {
         description "State of the MPIM2 LED on the craft interface";
         leaf green-led {
           type empty;
           description "Green LED is lit";
         }
         leaf led-off {
           type empty;
           description "LED is off";
         }
       }
       container storage-led {
         description "State of the external storage LED on the craft interface";
         leaf green-led {
           type empty;
           description "Green LED is lit";
         }
         leaf led-off {
           type empty;
           description "LED is off";
         }
       }
       container sfb-led {
         description "State of the SFB LED on the craft interface";
         leaf red-led {
           type empty;
           description "Red LED is lit";
         }
         leaf yellow-led {
           type empty;
           description "Yellow LED is lit";
         }
         leaf amber-led {
           type empty;
           description "Amber LED is lit";
         }
         leaf blink-led {
           type empty;
           description "LED is blinking";
         }
       }
       container cfm-ok-fail-led {
         description "State of the CFM Ok/Fail LED on the craft interface";
         leaf red-led {
           type empty;
           description "Red LED is lit";
         }
         leaf yellow-led {
           type empty;
           description "Yellow LED is lit";
         }
         leaf amber-led {
           type empty;
           description "Amber LED is lit";
         }
       }
       container cfm-service-led {
         description "State of the CFM Service LED on the craft interface";
         leaf red-led {
           type empty;
           description "Red LED is lit";
         }
         leaf yellow-led {
           type empty;
           description "Yellow LED is lit";
         }
         leaf amber-led {
           type empty;
           description "Amber LED is lit";
         }
       }
       container sysio-status-led {
         description "State of the SYSIO Status LED on the craft interface";
         leaf red-led {
           type empty;
           description "Red LED is lit";
         }
         leaf yellow-led {
           type empty;
           description "Yellow LED is lit";
         }
         leaf amber-led {
           type empty;
           description "Amber LED is lit";
         }
         leaf blink-led {
           type empty;
           description "LED is blinking";
         }
       }
     }
     container mcs-panel {
       description "State of the status LEDs on the faceplate of one or more Miscellaneous Control Subsystems";
       container mcs {
         description "State of the status LEDs on the faceplate of a Miscellaneous Control Subsystem";
         leaf slot {
           type int32;
         }
         leaf amber-led {
           type empty;
           description "Amber LED is lit";
         }
         leaf green-led {
           type empty;
           description "Green LED is lit";
         }
         leaf blue-led {
           type empty;
           description "Blue LED is lit";
         }
       }
     }
     container sfm-panel {
       description "State of the status LEDs on the faceplate of one or more Switching and Forwarding Modules";
       container sfm {
         description "State of the status LEDs on the faceplate of a Switching andForwarding Module";
         leaf slot {
           type int32;
         }
         leaf amber-led {
           type empty;
           description "Amber LED is lit";
         }
         leaf green-led {
           type empty;
           description "Green LED is lit";
         }
         leaf blue-led {
           type empty;
           description "Blue LED is lit";
         }
       }
     }
     container pcg-panel {
       description "State of the status LEDs on the faceplate of one or more Packet Forwarding Engine Clock Generators";
       container pcg {
         description "State of the status LEDs on the faceplate of a Packet Forwarding Engine Clock Generator";
         leaf slot {
           type int32;
         }
         leaf amber-led {
           type empty;
           description "Amber LED is lit";
         }
         leaf green-led {
           type empty;
           description "Green LED is lit";
         }
         leaf blue-led {
           type empty;
           description "Blue LED is lit";
         }
       }
     }
     container cb-panel {
       description "State of status LEDs on one or more Control Boards";
       list cb {
         description "State of status LEDs on a Control Board";
         leaf slot {
           type int32;
         }
         leaf amber-led {
           type empty;
           description "Amber LED is lit";
         }
         leaf green-led {
           type empty;
           description "Green LED is lit";
         }
         leaf blue-led {
           type empty;
           description "Blue LED is lit";
         }
       }
     }
     container sib-panel {
       description "State of the status LEDs on the faceplate of one or more Switch Interface Boards. Some of the LEDs also appear on the craft interface.";
       container sib {
         leaf ok-led {
           type empty;
           description "OK LED is lit";
         }
         leaf fail-led {
           type empty;
           description "Fail LED is lit";
         }
         leaf active-led {
           type empty;
           description "Active LED is lit";
         }
       }
     }
     container scg-panel {
       description "State of the status LEDs on the faceplate of one or more SONET ClockGenerators";
       container scg {
         description "State of the status LEDs on the faceplate of a SONET Clock Generator";
         leaf slot {
           type int32;
         }
         leaf amber-led {
           type empty;
           description "Amber LED is lit";
         }
         leaf green-led {
           type empty;
           description "Green LED is lit";
         }
         leaf blue-led {
           type empty;
           description "Blue LED is lit";
         }
       }
     }
     container feb-panel {
       description "State of the status LEDs on the faceplate of one or more Forwarding Engine Boards";
       container feb {
         description "State of the status LEDs on the faceplate of a Forwarding Engine Board";
         leaf slot {
           type int32;
         }
         leaf ok-led {
           type empty;
           description "OK LED is lit";
         }
         leaf fail-led {
           type empty;
           description "Fail LED is lit";
         }
         leaf active-led {
           type empty;
           description "Active LED is lit";
         }
       }
     }
     container power-supply-panel {
       description "State of the status LEDs on the faceplate of one or more power supplies";
       list power-supply {
         description "State of the status LEDs on the faceplate of a power supply";
         leaf slot {
           type int32;
         }
         leaf amber-led {
           type empty;
           description "Amber LED is lit";
         }
         leaf green-led {
           type empty;
           description "Green LED is lit";
         }
         leaf blue-led {
           type empty;
           description "Blue LED is lit";
         }
       }
       container pdu {
         description "State of the PDU status LEDs on the craft interface";
         leaf slot {
           type int32;
         }
         leaf red-led {
           type empty;
           description "Red LED is lit";
         }
         leaf green-led {
           type empty;
           description "Green LED is lit";
         }
         container psm {
           description "State of the PSM status LEDs on the craft interface";
           leaf slot {
             type int32;
           }
           leaf red-led {
             type empty;
             description "Red LED is lit";
           }
           leaf green-led {
             type empty;
             description "Green LED is lit";
           }
         }
       }
     }
     container fan-tray-panel {
       description "State of status LEDs on the craft interface for Fan Trays";
       container fan-tray {
         description "State of the status LEDs on the craft interface for a fan tray";
         leaf slot {
           type int32;
         }
         leaf red-led {
           type empty;
           description "Red LED is lit";
         }
         leaf green-led {
           type empty;
           description "Green LED is lit";
         }
       }
     }
   }
   grouping ethernet-switch-information-block {
     leaf summary {
       type string;
     }
     list link-info {
       leaf admin-status {
         type string;
       }
       leaf interface-name {
         type string;
       }
       leaf port-number {
         type int32;
         description "Port number on the PIC";
       }
       leaf connected-to {
         type string;
       }
       leaf speed {
         type string;
       }
       leaf duplex {
         type string;
       }
       leaf autonegotiate {
         type string;
       }
       leaf flow-control-tx {
         type string;
       }
       leaf flow-control-rx {
         type string;
       }
       leaf-list error-message {
         type string;
       }
     }
   }
   grouping ethernet-switch-statistics-information-block {
     leaf summary {
       type string;
     }
     list link-up-info {
       leaf ge-summary {
         type string;
       }
       leaf gt-64 {
         type uint64;
       }
       leaf gt-127 {
         type uint64;
       }
       leaf gt-255 {
         type uint64;
       }
       leaf gt-511 {
         type uint64;
       }
       leaf gt-1023 {
         type uint64;
       }
       leaf gt-1518 {
         type uint64;
       }
       leaf gt-2047 {
         type uint64;
       }
       leaf gt-4095 {
         type uint64;
       }
       leaf gt-9216 {
         type uint64;
       }
       leaf gt-mgv {
         type uint64;
       }
       leaf gt-pkt {
         type uint64;
       }
       leaf gt-mca {
         type uint64;
       }
       leaf gt-bca {
         type uint64;
       }
       leaf gt-scl {
         type uint64;
       }
       leaf gt-mcl {
         type uint64;
       }
       leaf gt-lcl {
         type uint64;
       }
       leaf gt-xcl {
         type uint64;
       }
       leaf gt-ncl {
         type uint64;
       }
       leaf gt-xpf {
         type uint64;
       }
       leaf gt-xcf {
         type uint64;
       }
       leaf gt-dfr {
         type uint64;
       }
       leaf gt-edf {
         type uint64;
       }
       leaf gt-ovr {
         type uint64;
       }
       leaf gt-jbr {
         type uint64;
       }
       leaf gt-fcs {
         type uint64;
       }
       leaf gt-frg {
         type uint64;
       }
       leaf gt-byt {
         type uint64;
       }
       leaf gr-64 {
         type uint64;
       }
       leaf gr-127 {
         type uint64;
       }
       leaf gr-255 {
         type uint64;
       }
       leaf gr-511 {
         type uint64;
       }
       leaf gr-1023 {
         type uint64;
       }
       leaf gr-1518 {
         type uint64;
       }
       leaf gr-2047 {
         type uint64;
       }
       leaf gr-4095 {
         type uint64;
       }
       leaf gr-9216 {
         type uint64;
       }
       leaf gr-pkt {
         type uint64;
       }
       leaf gr-mca {
         type uint64;
       }
       leaf gr-bca {
         type uint64;
       }
       leaf gr-fcs {
         type uint64;
       }
       leaf gr-aln {
         type uint64;
       }
       leaf gr-frg {
         type uint64;
       }
       leaf gr-cde {
         type uint64;
       }
       leaf gr-xuo {
         type uint64;
       }
       leaf gr-flr {
         type uint64;
       }
       leaf gr-fcr {
         type uint64;
       }
       leaf gr-und {
         type uint64;
       }
       leaf gr-ovr {
         type uint64;
       }
       leaf gr-jbr {
         type uint64;
       }
       leaf gr-mgv {
         type uint64;
       }
       leaf gr-mtue {
         type uint64;
       }
       leaf gr-xcf {
         type uint64;
       }
       leaf gr-xpf {
         type uint64;
       }
       leaf gr-byt {
         type uint64;
       }
       leaf xe-summary {
         type string;
       }
       leaf it-64 {
         type uint64;
       }
       leaf it-127 {
         type uint64;
       }
       leaf it-255 {
         type uint64;
       }
       leaf it-511 {
         type uint64;
       }
       leaf it-1023 {
         type uint64;
       }
       leaf it-1518 {
         type uint64;
       }
       leaf it-2047 {
         type uint64;
       }
       leaf it-4095 {
         type uint64;
       }
       leaf it-9216 {
         type uint64;
       }
       leaf it-16383 {
         type uint64;
       }
       leaf it-pkt {
         type uint64;
       }
       leaf it-mca {
         type uint64;
       }
       leaf it-bca {
         type uint64;
       }
       leaf it-xpf {
         type uint64;
       }
       leaf it-ovr {
         type uint64;
       }
       leaf it-fcs {
         type uint64;
       }
       leaf it-frg {
         type uint64;
       }
       leaf it-byt {
         type uint64;
       }
       leaf ir-64 {
         type uint64;
       }
       leaf ir-127 {
         type uint64;
       }
       leaf ir-255 {
         type uint64;
       }
       leaf ir-511 {
         type uint64;
       }
       leaf ir-1023 {
         type uint64;
       }
       leaf ir-1518 {
         type uint64;
       }
       leaf ir-2047 {
         type uint64;
       }
       leaf ir-4095 {
         type uint64;
       }
       leaf ir-9216 {
         type uint64;
       }
       leaf ir-16383 {
         type uint64;
       }
       leaf ir-pkt {
         type uint64;
       }
       leaf ir-mca {
         type uint64;
       }
       leaf ir-bca {
         type uint64;
       }
       leaf ir-fcs {
         type uint64;
       }
       leaf ir-frg {
         type uint64;
       }
       leaf ir-xuo {
         type uint64;
       }
       leaf ir-flr {
         type uint64;
       }
       leaf ir-und {
         type uint64;
       }
       leaf ir-ovr {
         type uint64;
       }
       leaf ir-jbr {
         type uint64;
       }
       leaf ir-xcf {
         type uint64;
       }
       leaf ir-xpf {
         type uint64;
       }
       leaf ir-byt {
         type uint64;
       }
       leaf-list error-message {
         type string;
       }
     }
   }
   grouping ethernet-switch-error-information-block {
     leaf summary {
       type string;
     }
     leaf mlt3 {
       type int32;
     }
     leaf lock {
       type int32;
     }
     leaf xmit {
       type int32;
     }
     leaf esd {
       type int32;
     }
     leaf false-carrier {
       type int32;
     }
     leaf disconnects {
       type int32;
     }
     leaf fx-mode {
       type int32;
     }
     leaf-list error-message {
       type string;
     }
   }
   grouping ioc-npc-connectivity-block {
     list ioc-npc-connectivity-item {
       description "NPC connectivity information for an IOC";
       leaf ioc-slot {
         type int32;
       }
       leaf ioc-type {
         type string;
         description "IOC type";
       }
       leaf ioc-state {
         type string;
         description "IOC state";
       }
       leaf npc-slot {
         type int32;
       }
       leaf no-npc-slot {
         type empty;
       }
       leaf npc-state {
         type string;
       }
       leaf fpc-link-status {
         type string;
         description "FPC link status";
       }
     }
   }
   grouping environment-information-block {
     list environment-item {
       leaf class {
         type string;
       }
       leaf name {
         type string;
         description "Name of this component";
       }
       leaf status {
         type string;
         description "Status of clock synchronization source";
       }
       leaf temperature {
         type string;
         description "Temperature of the item";
       }
       leaf comment {
         type string;
       }
       leaf humidity {
         type string;
       }
     }
   }
   grouping environment-component-information-block {
     list environment-component-item {
       description "Chassis environment component";
       leaf name {
         type string;
         description "Name of this component";
       }
       leaf state {
         type string;
         description "Status of the component";
       }
       leaf bus-revision {
         type int32;
         description "Bus revision";
       }
       leaf cmb-revision {
         type int32;
         description "CMB revision";
       }
       leaf fpga-revision {
         type int32;
         description "FPGA revision";
       }
       leaf ac-feed0-voltage {
         type string;
         description "AC feed0 voltage";
       }
       leaf ac-feed0-current {
         type string;
         description "AC feed0 current";
       }
       leaf ac-feed0-power {
         type string;
         description "AC feed0 power";
       }
       leaf ac-feed1-voltage {
         type string;
         description "AC feed1 voltage";
       }
       leaf ac-feed1-current {
         type string;
         description "AC feed1 current";
       }
       leaf ac-feed1-power {
         type string;
         description "AC feed1 power";
       }
       leaf reason {
         type string;
         description "Reason";
       }
       leaf frequency {
         type string;
         description "Frequency";
       }
       leaf slave-revision {
         type uint32;
         description "Slave revision";
       }
       leaf load {
         type string;
         description "Load";
       }
       leaf time-used {
         type string;
         description "Length of time this component has been used";
       }
       leaf check-input1-alarm {
         type string;
         description "Check input1 alarm";
       }
       leaf check-input2-alarm {
         type string;
         description "Check input2 alarm";
       }
       leaf ac-input_status {
         type string;
         description "AC input status";
       }
       container temperature-reading {
         leaf temperature-name {
           type string;
         }
         leaf temperature {
           type string;
           description "Temperature of the item";
         }
       }
       container fan-speed-reading {
         leaf fan-name {
           type string;
         }
         leaf fan-speed {
           type string;
           description "Fan speed in RPM";
         }
       }
       container fpga-revision-detail {
         description "FPGA revision in detail";
         leaf fpga-revision-name {
           type string;
         }
         leaf fpga-revision-value {
           type string;
         }
       }
       container revision {
         leaf revision-name {
           type string;
           description "Revision Name";
         }
         leaf revision-number {
           type uint32;
           description "Revision Number";
         }
       }
       container slave-registers-information {
         leaf slave-registers-title {
           type string;
           description "Title for the dump of slave registers";
         }
         container slave-registers {
           description "Slave register values";
           leaf slave-registers-name {
             type string;
           }
           leaf slave-registers-value {
             type string;
           }
           leaf slave-registers-desc {
             type string;
           }
         }
       }
       container fpga-registers {
         description "FPGA register values";
         leaf fpga-registers-type {
           type string;
         }
         leaf fpga-registers-name {
           type string;
         }
         leaf fpga-registers-value {
           type string;
         }
       }
       container power-information {
         leaf voltage-title {
           type string;
           description "Title for the display of voltage";
         }
         leaf max-power-consumption-ambient-temp {
           type int32;
         }
         leaf psm-hours-used {
           type uint32;
           description "Hours used for this component";
         }
         container power-title {
           leaf power-type {
             type string;
             description "Title for the display of power";
           }
           leaf power-state {
             type string;
             description "State of power";
           }
         }
         container voltage {
           leaf reference-voltage {
             type string;
             description "Voltage of the item in Volts";
           }
           leaf actual-voltage {
             type int32;
             description "Voltage of the item in mVlots";
           }
         }
         container current {
           leaf reference-curr {
             type string;
             description "Current of the item in Amps";
           }
           leaf actual-curr {
             type int32;
             description "Current of the item in mAmps";
           }
         }
         container voltage-current {
           leaf reference-volt-string {
             type string;
             description "Voltage of the item in Volts";
           }
           leaf actual-volt-in {
             type int32;
             description "Voltage in of the item in mVolts";
           }
           leaf actual-current-in {
             type int32;
             description "Current of the item in mAmps";
           }
         }
         container voltage-power {
           leaf reference-volt {
             type string;
             description "Voltage of the item in Volts";
           }
           leaf actual-volt {
             type int32;
             description "Voltage of the item in mVlots";
           }
           leaf actual-current {
             type int32;
             description "Current of the item in mAmps";
           }
           leaf actual-power {
             type int32;
             description "Power of the item in mWatts";
           }
         }
         list voltage-power-temperature-only {
           leaf voltage-string {
             type string;
             description "Name of the component";
           }
           leaf actual-temperature {
             type int32;
             description "Temperature of the item in degree (C)";
           }
         }
         container voltage-power-volt-only {
           leaf reference-volt-only {
             type string;
             description "Voltage of the item in Volts";
           }
           leaf actual-volt-only {
             type int32;
             description "Voltage of the item in mVlots";
           }
         }
       }
       container pcg-frequency {
         description "PCG Frequency";
         leaf pcg-frequency-setting {
           type string;
         }
         leaf pcg-frequency-measurement {
           type string;
         }
       }
       container dc-information {
         leaf dc-feed0-voltage {
           type string;
           description "DC feed0 voltage";
         }
         leaf dc-feed0-current {
           type string;
           description "DC feed0 current";
         }
         leaf dc-feed0-power {
           type string;
           description "DC feed0 power";
         }
         leaf dc-feed1-voltage {
           type string;
           description "DC feed1 voltage";
         }
         leaf dc-feed1-current {
           type string;
           description "DC feed1 current";
         }
         leaf dc-feed1-power {
           type string;
           description "DC feed1 power";
         }
         leaf dc-input {
           type string;
           description "DC input state";
         }
         leaf dc-output {
           type string;
           description "DC output state";
         }
         leaf ac-input {
           type string;
           description "AC input state";
         }
         leaf ac-output {
           type string;
           description "AC output state";
         }
         leaf dc-input-status {
           type string;
           description "DC input status";
         }
         leaf dc-input1 {
           type string;
           description "DC input1 state";
         }
         leaf dc-input2 {
           type string;
           description "DC input2 state";
         }
         leaf ac-input1 {
           type string;
           description "AC input1 state";
         }
         leaf ac-input2 {
           type string;
           description "AC input2 state";
         }
         container dc-detail {
           description "Detailed DC information";
           leaf dc-device {
             type string;
           }
           leaf dc-voltage {
             type uint32;
           }
           leaf dc-current {
             type uint32;
           }
           leaf dc-power {
             type uint32;
           }
           leaf dc-load {
             type uint32;
           }
           leaf str-dc-voltage {
             type string;
           }
           leaf str-dc-current {
             type string;
           }
           leaf str-dc-power {
             type string;
           }
           leaf str-dc-load {
             type string;
           }
           leaf str2-dc-voltage {
             type string;
           }
           leaf str2-dc-current {
             type string;
           }
           leaf str2-dc-power {
             type string;
           }
           leaf str2-dc-load {
             type string;
           }
           leaf str3-dc-voltage {
             type string;
           }
           leaf str3-dc-current {
             type string;
           }
           leaf max-power {
             type uint32;
           }
         }
         container dc-in-detail2 {
           description "Detailed DC input information";
           leaf dc-in-device2 {
             type string;
           }
           leaf dc-in-voltage-string {
             type string;
           }
           leaf dc-in-current-string {
             type string;
           }
           leaf dc-in-power-string {
             type string;
           }
           leaf dc-in-load-string {
             type string;
           }
         }
         container dc-detail2 {
           description "Detailed DC information";
           leaf dc-device2 {
             type string;
           }
           leaf dc-voltage-string {
             type string;
           }
           leaf dc-current-string {
             type string;
           }
           leaf dc-power-string {
             type string;
           }
           leaf dc-load-string {
             type string;
           }
         }
         leaf dc-inp0 {
           type string;
           description "DC input0 state";
         }
         leaf dc-inp1 {
           type string;
           description "DC input1 state";
         }
         leaf dc2-input-a0 {
           type string;
           description "DC2 input a0 state";
         }
         leaf dc2-input-b0 {
           type string;
           description "DC2 input b0 state";
         }
         leaf dc2-input-a1 {
           type string;
           description "DC2 input a1 state";
         }
         leaf dc2-input-b1 {
           type string;
           description "DC2 input b1 state";
         }
         leaf ac-inp0 {
           type string;
           description "AC input0 state";
         }
         leaf ac-inp1 {
           type string;
           description "AC input1 state";
         }
       }
       container pmbus-table {
         container pmbus-table-entry {
           description "Power Management Bus Device information";
           leaf pmbus-device-name {
             type string;
           }
           leaf pmbus-expected-voltage {
             type uint32;
           }
           leaf pmbus-actual-voltage {
             type uint32;
           }
           leaf pmbus-actual-current {
             type uint32;
           }
           leaf pmbus-calculated-power {
             type uint32;
           }
         }
       }
       container airflow-direction {
         leaf airflow {
           type string;
         }
         leaf direction {
           type string;
           description "Airflow direction";
         }
       }
       container input-voltage {
         leaf voltage-name {
           type string;
           description "Input voltage";
         }
         leaf voltage-value {
           type uint32;
         }
       }
       container output-detail {
         description "Detailed power output information";
         leaf output-voltage {
           type uint32;
         }
         leaf output-current {
           type uint32;
           description "Output Current in Ampere(A)";
         }
       }
       container pdu-information {
         leaf hours-used {
           type uint32;
           description "Hours used for this component";
         }
         leaf pdu-status {
           type string;
         }
         container efuse {
           description "PDU efuse information";
           leaf name {
             type string;
             description "Name of this component";
           }
           leaf state {
             type string;
             description "Status of the component";
           }
         }
         container pdu-firmware {
           description "PDU firmware information";
           leaf firmware-name {
             type string;
             description "Name of this component";
           }
           leaf firmware-version {
             type string;
             description "Firmware version string for this component";
           }
         }
         container pdu-component {
           description "PDU specific component information";
           leaf component-name {
             type string;
             description "PDU component name";
           }
           leaf component-state {
             type string;
             description "PDU component state";
           }
         }
       }
       container psm-information {
         leaf temperature {
           type string;
           description "Temperature of the item";
         }
         leaf hours-used {
           type uint32;
           description "Hours used for this component";
         }
         leaf firmware-version {
           type string;
           description "Firmware version string for this component";
         }
         container psm-status {
           leaf fans {
             type string;
             description "Fan status for this component";
           }
           leaf dc-input {
             type string;
             description "DC input state";
           }
           leaf dc-input1 {
             type string;
             description "DC input1 state";
           }
           leaf dc-input2 {
             type string;
             description "DC input2 state";
           }
           leaf ac-input {
             type string;
             description "AC input state";
           }
           leaf ac-input1 {
             type string;
             description "AC input1 state";
           }
           leaf ac-input2 {
             type string;
             description "AC input2 state";
           }
           leaf check-input1-alarm {
             type string;
             description "Check input1 alarm";
           }
           leaf check-input2-alarm {
             type string;
             description "Check input2 alarm";
           }
           leaf dc-output {
             type string;
             description "DC output state";
           }
           leaf ac-output {
             type string;
             description "AC output state";
           }
           leaf psm-health-check-status {
             type string;
             description "Show health check status of all PSMs";
           }
           leaf dc-inp0 {
             type string;
             description "DC input0 state";
           }
           leaf dc-inp1 {
             type string;
             description "DC input1 state";
           }
           leaf dc2-input-a0 {
             type string;
             description "DC2 input a0 state";
           }
           leaf dc2-input-b0 {
             type string;
             description "DC2 input b0 state";
           }
           leaf dc2-input-a1 {
             type string;
             description "DC2 input a1 state";
           }
           leaf dc2-input-b1 {
             type string;
             description "DC2 input b1 state";
           }
           leaf ac-inp0 {
             type string;
             description "AC input0 state";
           }
           leaf ac-inp1 {
             type string;
             description "AC input1 state";
           }
           leaf check-input-a0-alarm {
             type string;
             description "Check input a0 alarm";
           }
           leaf check-input-b0-alarm {
             type string;
             description "Check input b0 alarm";
           }
           leaf check-input-a1-alarm {
             type string;
             description "Check input a1 alarm";
           }
           leaf check-input-b1-alarm {
             type string;
             description "Check input b1 alarm";
           }
           list psm-input-status {
             leaf psm-input-feed-name {
               type string;
             }
             leaf psm-input-feed-status {
               type string;
             }
           }
           list psm-input-alarm {
             leaf input-feed-alarm-name {
               type string;
             }
             leaf input-feed-alarm-status {
               type string;
             }
           }
         }
         leaf fan-status {
           type string;
           description "Fan status for this component";
         }
         leaf firmware-primary-mcu {
           type string;
         }
         leaf firmware-secondary-mcu {
           type string;
         }
         leaf firmware-communication-mcu {
           type string;
         }
         leaf firmware-led-mcu {
           type string;
         }
         leaf firmware-version-psm {
           type string;
         }
         leaf hvdc-mode {
           type string;
           description "HVDC mode";
         }
         leaf temperature-name {
           type string;
         }
         container fan-speed-reading-psm {
           leaf fan1-speed {
             type string;
           }
           leaf fan2-speed {
             type string;
           }
         }
       }
       container pem-information {
         leaf fpc-slot {
           type int32;
           description "FPC slot";
         }
         leaf pem-slot {
           type uint32;
         }
         leaf pem-state {
           type string;
           description "State of power supply unit";
         }
         leaf pem-temperature {
           type uint32;
           description "Temperature in (C)";
         }
         leaf input-current {
           type uint32;
           description "Input Current in Ampere(A)";
         }
         leaf input-volt {
           type uint32;
           description "Input Volt in Volt(V)";
         }
         leaf input-power {
           type uint32;
           description "Input Power in Watt(W)";
         }
         leaf output-current {
           type uint32;
           description "Output Current in Ampere(A)";
         }
         leaf output-volt {
           type uint32;
           description "Output Volt in Volt(V)";
         }
         leaf output-power {
           type uint32;
           description "Output Power in Watt(W)";
         }
       }
       leaf ac-input-state {
         type string;
         description "Input type";
       }
       leaf dc-input-state {
         type string;
         description "Input type";
       }
       leaf check-input-a0-alarm {
         type string;
         description "Check input a0 alarm";
       }
       leaf check-input-b0-alarm {
         type string;
         description "Check input b0 alarm";
       }
       leaf check-input-a1-alarm {
         type string;
         description "Check input a1 alarm";
       }
       leaf check-input-b1-alarm {
         type string;
         description "Check input b1 alarm";
       }
       container feed-info {
         leaf feed-name {
           type string;
         }
         leaf feed-state {
           type string;
         }
       }
       container cowra-registers-information {
         leaf cowra-registers-title {
           type string;
           description "Title for the dump of cowra registers";
         }
         container cowra-registers {
           description "Cowra register values";
           leaf cowra-registers-name {
             type string;
           }
           leaf cowra-registers-value {
             type string;
           }
         }
       }
       list firmware {
         description "Firmware version";
         leaf firmware-name {
           type string;
           description "Name of this component";
         }
         leaf firmware-version {
           type string;
           description "Firmware version string for this component";
         }
         leaf firmware-version-psm {
           type string;
         }
         leaf firmware-primary-mcu {
           type string;
         }
         leaf firmware-secondary-mcu {
           type string;
         }
         leaf firmware-communication-mcu {
           type string;
         }
         leaf firmware-led-mcu {
           type string;
         }
       }
       container input-detail2 {
         leaf input-feed-name {
           type string;
           description "Input Feed Name";
         }
         leaf input-feed-volt {
           type string;
           description "Input Feed Voltage";
         }
         leaf input-feed-current {
           type string;
           description "Input Feed Current";
         }
         leaf input-feed-power {
           type string;
           description "Input Feed Power";
         }
       }
       container ac-pem-input-detail {
         leaf ac-pem-input-volt {
           type string;
           description "Input Voltage";
         }
         leaf ac-pem-input-current {
           type string;
           description "Input Current";
         }
         leaf ac-pem-input-power {
           type string;
           description "Input Power";
         }
       }
       container dc-pem-input-detail {
         leaf dc-pem-input-volt {
           type string;
           description "Input Voltage";
         }
         leaf dc-pem-input-current {
           type string;
           description "Input Current";
         }
         leaf dc-pem-input-power {
           type string;
           description "Input Power";
         }
       }
       container psm-health-check-detail {
         leaf health-check-status {
           type string;
         }
         leaf health-check-state-str {
           type string;
           description "Current Health Check State";
         }
         leaf health-check-last-result-str {
           type string;
           description "Result of Last Execution";
         }
         leaf health-check-last-exec-str {
           type string;
           description "Time of Last Health Check Test Execution";
         }
         leaf health-check-next-sched-run-str {
           type string;
           description "Time of Next Scheduled Health Check Test";
         }
       }
     }
   }
   grouping firmware-information-block {
     container chassis {
       description "Hardware inventory of this chassis";
       leaf name {
         type string;
         description "Name of this component";
       }
       leaf version {
         type string;
         description "Version of this component";
       }
       leaf part-number {
         type string;
         description "Part number of this component";
       }
       leaf serial-number {
         type string;
         description "Serial number of this component";
       }
       leaf description {
         type string;
         description "Description of this component";
       }
       leaf hardware-incomplete {
         type empty;
       }
       leaf model-number {
         type string;
         description "Model number of this component";
       }
       leaf clei-code {
         type string;
         description "Common Language Equipment Identifier code of this component";
       }
       container i2c-information {
         leaf jedec-code {
           type string;
         }
         leaf eeprom-version {
           type string;
         }
         leaf part-number {
           type string;
           description "Part number of this component";
         }
         leaf serial-number {
           type string;
           description "Serial number of this component";
         }
         leaf assembly-identifier {
           type string;
         }
         leaf assembly-version {
           type string;
         }
         leaf manufacture-date {
           type string;
           description "Date this component was manufactured";
         }
         leaf assembly-flags {
           type string;
         }
         leaf i2c-version {
           type string;
         }
         leaf clei-code {
           type string;
           description "Common Language Equipment Identifier code of this component";
         }
         leaf i2c-identifier {
           type string;
         }
         leaf model-number {
           type string;
           description "Model number of this component";
         }
         leaf board-information-record {
           type string;
           description "Hex dump of board information record";
         }
         leaf i2c-data {
           type string;
           description "Hex dump of I2C data";
         }
       }
       list chassis-module {
         leaf name {
           type string;
           description "Name of this component";
         }
         leaf version {
           type string;
           description "Version of this component";
         }
         leaf part-number {
           type string;
           description "Part number of this component";
         }
         leaf serial-number {
           type string;
           description "Serial number of this component";
         }
         leaf description {
           type string;
           description "Description of this component";
         }
         leaf ir-mode {
           type string;
           description "R/IR mode configured";
         }
         container i2c-information {
           leaf jedec-code {
             type string;
           }
           leaf eeprom-version {
             type string;
           }
           leaf part-number {
             type string;
             description "Part number of this component";
           }
           leaf serial-number {
             type string;
             description "Serial number of this component";
           }
           leaf assembly-identifier {
             type string;
           }
           leaf assembly-version {
             type string;
           }
           leaf manufacture-date {
             type string;
             description "Date this component was manufactured";
           }
           leaf assembly-flags {
             type string;
           }
           leaf i2c-version {
             type string;
           }
           leaf clei-code {
             type string;
             description "Common Language Equipment Identifier code of this component";
           }
           leaf i2c-identifier {
             type string;
           }
           leaf model-number {
             type string;
             description "Model number of this component";
           }
           leaf board-information-record {
             type string;
             description "Hex dump of board information record";
           }
           leaf i2c-data {
             type string;
             description "Hex dump of I2C data";
           }
         }
         list firmware {
           leaf firmware-version-psm {
             type string;
           }
           leaf firmware-primary-mcu {
             type string;
           }
           leaf firmware-secondary-mcu {
             type string;
           }
           leaf firmware-communication-mcu {
             type string;
           }
           leaf firmware-led-mcu {
             type string;
           }
           leaf type {
             type string;
             description "Type of this component";
           }
           leaf firmware-version {
             type string;
             description "Firmware version string for this component";
           }
         }
         list chassis-sub-module {
           leaf name {
             type string;
             description "Name of this component";
           }
           leaf version {
             type string;
             description "Version of this component";
           }
           leaf part-number {
             type string;
             description "Part number of this component";
           }
           leaf serial-number {
             type string;
             description "Serial number of this component";
           }
           leaf description {
             type string;
             description "Description of this component";
           }
           container i2c-information {
             leaf jedec-code {
               type string;
             }
             leaf eeprom-version {
               type string;
             }
             leaf part-number {
               type string;
               description "Part number of this component";
             }
             leaf serial-number {
               type string;
               description "Serial number of this component";
             }
             leaf assembly-identifier {
               type string;
             }
             leaf assembly-version {
               type string;
             }
             leaf manufacture-date {
               type string;
               description "Date this component was manufactured";
             }
             leaf assembly-flags {
               type string;
             }
             leaf i2c-version {
               type string;
             }
             leaf clei-code {
               type string;
               description "Common Language Equipment Identifier code of this component";
             }
             leaf i2c-identifier {
               type string;
             }
             leaf model-number {
               type string;
               description "Model number of this component";
             }
             leaf board-information-record {
               type string;
               description "Hex dump of board information record";
             }
             leaf i2c-data {
               type string;
               description "Hex dump of I2C data";
             }
           }
           list firmware {
             leaf firmware-version-psm {
               type string;
             }
             leaf firmware-primary-mcu {
               type string;
             }
             leaf firmware-secondary-mcu {
               type string;
             }
             leaf firmware-communication-mcu {
               type string;
             }
             leaf firmware-led-mcu {
               type string;
             }
           }
           list chassis-sub-sub-module {
             leaf name {
               type string;
               description "Name of this component";
             }
             leaf version {
               type string;
               description "Version of this component";
             }
             leaf part-number {
               type string;
               description "Part number of this component";
             }
             leaf serial-number {
               type string;
               description "Serial number of this component";
             }
             leaf description {
               type string;
               description "Description of this component";
             }
             leaf model-number {
               type string;
               description "Model number of this component";
             }
             leaf clei-code {
               type string;
               description "Common Language Equipment Identifier code of this component";
             }
             list chassis-sub-sub-sub-module {
               leaf name {
                 type string;
                 description "Name of this component";
               }
               leaf version {
                 type string;
                 description "Version of this component";
               }
               leaf part-number {
                 type string;
                 description "Part number of this component";
               }
               leaf serial-number {
                 type string;
                 description "Serial number of this component";
               }
               leaf description {
                 type string;
                 description "Description of this component";
               }
               leaf model-number {
                 type string;
                 description "Model number of this component";
               }
               leaf clei-code {
                 type string;
                 description "Common Language Equipment Identifier code of this component";
               }
             }
           }
           leaf model-number {
             type string;
             description "Model number of this component";
           }
           leaf clei-code {
             type string;
             description "Common Language Equipment Identifier code of this component";
           }
         }
         list chassis-re-disk-module {
           leaf name {
             type string;
             description "Name of this component";
           }
           leaf disk-size {
             type int32;
             description "Disk size (megabytes)";
           }
           leaf model {
             type string;
           }
           leaf serial-number {
             type string;
             description "Serial number of this component";
           }
           leaf description {
             type string;
             description "Description of this component";
           }
         }
         list chassis-re-usb-module {
           leaf name {
             type string;
             description "Name of this component";
           }
           leaf product {
             type string;
           }
           leaf product-number {
             type int32;
           }
           leaf vendor {
             type string;
           }
           leaf description {
             type string;
             description "Description of this component";
           }
         }
         list chassis-re-dimm-module {
           leaf name {
             type string;
             description "Name of this component";
           }
           leaf part-number {
             type string;
             description "Part number of this component";
           }
           leaf die-rev {
             type string;
             description " DIE revision of the DIMM";
           }
           leaf pcb-rev {
             type string;
             description "PCB revision ";
           }
           leaf mfr-id {
             type string;
             description "Manufacture Id of the DIMM";
           }
         }
         list chassis-compute-node-disk-module {
           leaf name {
             type string;
             description "Name of this component";
           }
           leaf disk-size {
             type int32;
             description "Disk size (megabytes)";
           }
           leaf model {
             type string;
           }
           leaf serial-number {
             type string;
             description "Serial number of this component";
           }
           leaf description {
             type string;
             description "Description of this component";
           }
         }
         leaf license-mode {
           type string;
           description "PTX R/IR mode configured";
         }
         leaf model-number {
           type string;
           description "Model number of this component";
         }
         leaf clei-code {
           type string;
           description "Common Language Equipment Identifier code of this component";
         }
       }
     }
     list system-firmware {
       container system-module {
         leaf firmware-name {
           type string;
           description "Name of this component";
         }
         container firmware-state {
           leaf firmware-type {
             type string;
             description "Type of this component";
           }
           leaf firmware-status {
             type string;
             description "Firmware status for this component";
           }
         }
       }
       container system-sub-module-firmware-list {
         list system-sub-module-firmware {
           leaf firmware-name {
             type string;
             description "Name of this component";
           }
           leaf firmware-type {
             type string;
             description "Type of this component";
           }
           leaf firmware-tag {
             type int32;
             description "Multiple firmware per FRU delimiter";
           }
           leaf firmware-revision {
             type string;
             description "Firmware version for this component";
           }
           leaf firmware-revision-available {
             type string;
             description "Firmware version available on disk for this component";
           }
           leaf firmware-status {
             type string;
             description "Firmware status for this component";
           }
         }
       }
       leaf firmware-name {
         type string;
         description "Name of this component";
       }
       leaf firmware-type {
         type string;
         description "Type of this component";
       }
       leaf firmware-tag {
         type int32;
         description "Multiple firmware per FRU delimiter";
       }
       leaf firmware-revision {
         type string;
         description "Firmware version for this component";
       }
       leaf firmware-revision-available {
         type string;
         description "Firmware version available on disk for this component";
       }
       leaf firmware-status {
         type string;
         description "Firmware status for this component";
       }
     }
   }
   grouping fpc-information-block {
     list fpc {
       leaf slot {
         type int32;
       }
       leaf state {
         type string;
         description "Status of the component";
       }
       leaf comment {
         type string;
       }
       leaf temperature {
         type string;
         description "Temperature of the item";
       }
       leaf memory-rldram-size {
         type int32;
         description "RLDRAM";
       }
       leaf memory-xr2-size {
         type int32;
         description "XR2";
       }
       leaf memory-ddr-dram-size {
         type int32;
         description "DDR DRAM";
       }
       container pic-detail {
         container port-information {
           container port {
             leaf port-number {
               type int32;
               description "Port number on the PIC";
             }
             leaf cable-type {
               type string;
               description "Port cable type";
             }
             leaf fiber-mode {
               type string;
               description "Single or multi-mode";
             }
             leaf sfp-vendor-name {
               type string;
               description "SFP vendor name";
             }
             leaf sfp-vendor-pno {
               type string;
               description "SFP vendor part number";
             }
             leaf wavelength {
               type string;
               description "Wavelength of the optical transceiver";
             }
             leaf sfp-vendor-fw-ver {
               type string;
               description "Vendor firmware version";
             }
             leaf sfp-jnpr-ver {
               type string;
               description "Juniper revision";
             }
             leaf sfp-msa-version {
               type string;
               description "MSA version";
             }
             leaf short-long-port {
               type string;
               description "Short or long Port";
             }
           }
         }
         container package-information {
           container package {
             leaf package-name {
               type string;
             }
           }
         }
         container port-profile-speed-information {
           leaf active-portprofile-cfg {
             type string;
             description "Current Port Profile Config";
           }
           container profile-port {
             leaf profile-port-number {
               type int32;
               description "PIC port profile port number";
             }
             leaf current-speed {
               type string;
               description "PIC port current speed";
             }
             leaf default-speed {
               type string;
               description "PIC port default speed";
             }
             leaf port-profile-speed-capability {
               type string;
               description "Port profile speed capabilities";
             }
           }
           container port-profile-note-information {
             leaf note-speed {
               type string;
               description "PIC Note";
             }
           }
           container port-profile-channel-note-information {
             leaf note-channel-speed {
               type string;
               description "PIC channel Note";
             }
           }
         }
         container port-group-speed-information {
           container port1 {
             leaf port-number2 {
               type int32;
               description "PIC pg port number";
             }
             leaf pfe-number1 {
               type int32;
               description "PIC pg PFE number";
             }
             leaf pg-number {
               type int32;
               description "PIC port group number";
             }
             leaf speed-capability1 {
               type string;
               description "Port speed capabilities";
             }
           }
         }
         container port-speed-information {
           list port {
             leaf port-number1 {
               type int32;
               description "PIC port number";
             }
             leaf pfe-number {
               type int32;
               description "PIC PFE number";
             }
             leaf speed-capability {
               type string;
               description "Port speed capabilities";
             }
           }
         }
         container pic-error-information {
           container error {
             leaf errnumber {
               type int32;
               description "Serial No";
             }
             leaf errmsg {
               type string;
               description "Configuration Errors";
             }
           }
         }
         container fec-error-information {
           container error {
             leaf errnumber {
               type int32;
               description "Serial No";
             }
             leaf errmsg {
               type string;
               description "Configuration Errors";
             }
           }
         }
         leaf slot {
           type int32;
         }
         leaf pic-slot {
           type int32;
         }
         leaf pic-type {
           type string;
         }
         leaf comment {
           type string;
         }
         leaf asic-type {
           type string;
           description "Type of ASIC on the PIC";
         }
         leaf account-layer2-overhead {
           type string;
           description "Account Layer2 Overhead Knob Status";
         }
         leaf state {
           type string;
           description "Status of the component";
         }
         leaf pic-version {
           type string;
           description "PIC hardware version";
         }
         leaf cpu-sw-version {
           type string;
           description "Version of operating system running on the PIC";
         }
         leaf cpu-rom-version {
           type string;
           description "PIC ROM version";
         }
         leaf cpu-total {
           type int32;
           description "Percentage of CPU utilized";
         }
         leaf cpu-interrupt {
           type int32;
           description "Percentage of CPU utilized by interrupt processing";
         }
         leaf memory-dram-size {
           type string;
           description "DRAM";
         }
         leaf memory-buffer-utilization {
           type int32;
           description "Percentage of buffer memory utilized";
         }
         leaf memory-heap-utilization {
           type int32;
           description "Percentage of heap memory utilized";
         }
         leaf up-time {
           type string;
           description "Length of time this component has been operational";
         }
         leaf pic-package {
           type string;
         }
         leaf pic-clock-sync {
           type string;
           description "PIC Clock Synchronization";
         }
         leaf pic-multirate-mode {
           type string;
         }
         leaf pic-channelization-mode {
           type string;
           description "PIC Channelization Mode";
         }
         leaf configured-mode {
           type string;
         }
         leaf control-cores {
           type int32;
         }
         leaf data-cores {
           type int32;
         }
         leaf object-cache-size {
           type int32;
         }
         leaf policy-db-size {
           type int32;
         }
         leaf forwarding-db-size {
           type int32;
         }
         leaf wired-process-mem-size {
           type int32;
         }
         leaf wired-max-processes {
           type int32;
         }
         container pic-transport-information {
           leaf pic-transport-admin-state {
             type string;
           }
           leaf pic-transport-oper-state {
             type string;
           }
         }
         leaf slc-slot {
           type int32;
           description "SLC id number";
         }
       }
       list mic {
         leaf-list comment {
           type string;
         }
         leaf mic-slot {
           type int32;
         }
         leaf mic-state {
           type string;
         }
         leaf mic-type {
           type string;
         }
       }
       list pfe-info-values {
         leaf ppfe-id {
           type string;
         }
         leaf pfe-instance {
           type int32;
         }
         leaf pfeid {
           type int32;
         }
         leaf pfe-state {
           type string;
         }
         leaf pfe-temp-perf-throt {
           type string;
         }
         leaf pfe-temp-volt-reduction {
           type string;
         }
       }
       list pfeid-info-values {
         leaf pfe-instance {
           type int32;
         }
         leaf ppfe-id {
           type string;
         }
         leaf pfe-state {
           type string;
         }
         leaf pfe-temp-perf-throt {
           type string;
         }
         leaf pfe-temp-volt-reduction {
           type string;
         }
         leaf pfeid {
           type int32;
         }
       }
       list scope-level {
       }
       container fpc-slc-error-information {
         list scope-level {
         }
       }
       list fpc-error {
         list fpc-error-group-detail {
           leaf fpc-error-group-name {
             type string;
           }
           leaf fpc-error-group-occurred {
             type int32;
           }
           leaf fpc-error-group-cleared {
             type int32;
           }
           leaf fpc-error-group-error-id {
             type int32;
           }
         }
       }
       leaf cpu-total {
         type int32;
         description "Percentage of CPU utilized";
       }
       leaf cpu-interrupt {
         type int32;
         description "Percentage of CPU utilized by interrupt processing";
       }
       leaf cpu-1min-avg {
         type int32;
         description "Percentage of one min average CPU utilized";
       }
       leaf cpu-5min-avg {
         type int32;
         description "Percentage of five min average CPU utilized";
       }
       leaf cpu-15min-avg {
         type int32;
         description "Percentage of fifteen min average CPU utilized";
       }
       leaf memory-dram-size {
         type string;
         description "DRAM";
       }
       leaf memory-heap-utilization {
         type int32;
         description "Percentage of heap memory utilized";
       }
       leaf memory-buffer-utilization {
         type int32;
         description "Percentage of buffer memory utilized";
       }
       leaf error-code {
         type int32;
         description "Code resulting from major or minor error";
       }
       leaf logical-slot {
         type int32;
       }
       leaf cpu-less-info-str {
         type string;
         description "Flexible PIC Concentrator (FPC) without CPU";
       }
       leaf memory-sram-size {
         type int32;
         description "SRAM";
       }
       leaf memory-sdram-size {
         type int32;
         description "SDRAM";
       }
       leaf memory-notification-sdram-size {
         type int32;
         description "Notification SDRAM";
       }
       leaf asic-information {
         type string;
       }
       leaf start-time {
         type string;
         description "Time this component was started";
       }
       leaf up-time {
         type string;
         description "Length of time this component has been operational";
       }
       leaf max-power-consumption {
         type int32;
       }
       leaf memory-hbm-size {
         type int32;
         description "HBM";
       }
       leaf last-reboot-reason {
         type string;
         description "Last reboot reason of routing engine";
       }
       leaf max-mpc-base-power-consumption {
         type int32;
       }
       leaf max-mic0-power-consumption {
         type int32;
       }
       leaf max-mic1-power-consumption {
         type int32;
       }
       leaf max-mic2-power-consumption {
         type int32;
       }
       leaf max-mic3-power-consumption {
         type int32;
       }
       leaf max-mpc-total-power-consumption {
         type int32;
       }
       leaf fips-capable {
         type string;
         description "Does the FPC support FIPS";
       }
       leaf fips-mode {
         type string;
         description "Is the FPC in FIPS mode";
       }
       leaf configured-bandwidth {
         type int32;
       }
       leaf operating-bandwidth {
         type int32;
       }
       leaf high-performance-mode-support {
         type string;
         description "Is high-performance mode supported";
       }
       leaf pics-in-high-performance-mode {
         type string;
         description "PFEs in high-performance mode";
       }
       leaf fpc-pfe-type {
         type string;
       }
       list fpc-pfe-information {
         leaf fpc-pfe-num {
           type int32;
         }
         leaf fpc-pfe-power-state {
           type string;
         }
         leaf fpc-pfe-bandwidth {
           type string;
         }
         leaf fpc-pfe-slc {
           type int32;
           description "SLC id number";
         }
       }
       container fpc-slc-information {
         leaf fpc-slc-slot {
           type int32;
           description "SLC id number";
         }
         leaf fpc-slc-state {
           type string;
           description "SLC state";
         }
         leaf fpc-slc-error-code {
           type int32;
           description "Code resulting from major or minor error";
         }
         leaf fpc-slc-version {
           type string;
         }
         leaf fpc-slc-cpu-cores {
           type int32;
           description "Cpu cores assigned to SLC";
         }
         leaf fpc-slc-memory-dram-size {
           type string;
           description "DRAM";
         }
         leaf fpc-slc-memory-rldram-size {
           type int32;
           description "RLDRAM";
         }
         leaf fpc-slc-memory-xr2-size {
           type int32;
           description "XR2";
         }
         leaf fpc-slc-memory-ddr-dram-size {
           type int32;
           description "DDR DRAM";
         }
         leaf fpc-slc-memory-hbm-size {
           type int32;
           description "HBM";
         }
         leaf fpc-slc-start-time {
           type string;
           description "Time this component was started";
         }
         leaf fpc-slc-up-time {
           type string;
           description "Length of time this component has been operational";
         }
         leaf fpc-slc-comment {
           type string;
         }
         leaf fpc-slc-configured-bandwidth {
           type int32;
         }
         leaf fpc-slc-operating-bandwidth {
           type int32;
         }
         leaf fpc-slot {
           type int32;
           description "FPC slot";
         }
         leaf fpc-slc-temperature {
           type int32;
           description "Temperature in (C)";
         }
         leaf fpc-slc-cpu-total {
           type int32;
           description "Percentage of CPU utilized";
         }
         leaf fpc-slc-cpu-interrupt {
           type int32;
           description "Percentage of CPU utilized by interrupt processing";
         }
         leaf fpc-slc-cpu-1min-avg {
           type int32;
           description "Percentage of one min average CPU utilized";
         }
         leaf fpc-slc-cpu-5min-avg {
           type int32;
           description "Percentage of five min average CPU utilized";
         }
         leaf fpc-slc-cpu-15min-avg {
           type int32;
           description "Percentage of fifteen min average CPU utilized";
         }
         leaf fpc-slc-memory-heap-utilization {
           type int32;
           description "Percentage of heap memory utilized";
         }
         leaf fpc-slc-memory-buffer-utilization {
           type int32;
           description "Percentage of buffer memory utilized";
         }
         leaf fpc-slc-gnf-id {
           type string;
           description "Gnf id assigned to SLC";
         }
       }
       leaf description {
         type string;
         description "Description of this component";
       }
       list pic {
         leaf pic-slot {
           type int32;
         }
         leaf pic-state {
           type string;
         }
         leaf pic-type {
           type string;
         }
         leaf comment {
           type string;
         }
       }
       leaf gnf-id {
         type string;
       }
       container slc {
         leaf slc-id {
           type int32;
           description "SLC id number";
         }
         leaf slc-state {
           type string;
           description "SLC state";
         }
         leaf slc-info {
           type string;
           description "SLC config info";
         }
         leaf slc-gnf-id {
           type int32;
           description "Gnf id assigned to SLC";
         }
       }
     }
     leaf fpc-slot {
       type int32;
       description "FPC slot";
     }
     leaf fpc-status {
       type string;
       description "FPC status";
     }
     leaf fpc-power-limit {
       type string;
       description "FPC power limit";
     }
     leaf fpc-power {
       type string;
       description "Total FPC power consumption";
     }
     leaf fpc-priority {
       type string;
       description "Priority options";
     }
     leaf fpc-firmware-version {
       type string;
       description "POE firmware version";
     }
   }
   grouping fpc-ether-types-information-block {
     list ether {
       leaf slot {
         type int32;
       }
       leaf ether-slot {
         type int32;
       }
       leaf ether-type-default {
         type int32;
       }
       leaf ether-type-configurable {
         type string;
       }
       leaf ether-type-active {
         type int32;
       }
       leaf-list comment {
         type string;
       }
     }
   }
   grouping fpc-port-information-block {
     list fpc {
       leaf slot {
         type int32;
       }
       leaf port-num {
         type int32;
       }
       leaf port-config-map {
         type string;
       }
       leaf port-map {
         type string;
       }
       list mic {
         leaf-list comment {
           type string;
         }
       }
       container pic-detail {
         container port-information {
         }
         container port-profile-speed-information {
         }
         container package-information {
           container package {
             leaf package-name {
               type string;
             }
           }
         }
         container port-group-speed-information {
         }
         container port-speed-information {
         }
         container pic-error-information {
         }
         container fec-error-information {
         }
       }
       list pfe-info-values {
         leaf ppfe-id {
           type string;
         }
       }
       list pfeid-info-values {
         leaf pfe-instance {
           type int32;
         }
         leaf ppfe-id {
           type string;
         }
         leaf pfe-state {
           type string;
         }
         leaf pfe-temp-perf-throt {
           type string;
         }
         leaf pfe-temp-volt-reduction {
           type string;
         }
       }
       list scope-level {
       }
       container fpc-slc-error-information {
         list scope-level {
         }
       }
       list fpc-error {
         list fpc-error-group-detail {
           leaf fpc-error-group-name {
             type string;
           }
           leaf fpc-error-group-occurred {
             type int32;
           }
           leaf fpc-error-group-cleared {
             type int32;
           }
           leaf fpc-error-group-error-id {
             type int32;
           }
         }
       }
     }
   }
   grouping fpc-error-information-block {
     list fpc {
       leaf slot {
         type int32;
       }
       leaf minor-level-occured {
         type int32;
       }
       leaf minor-level-cleared {
         type int32;
       }
       leaf minor-level-threshold {
         type int32;
       }
       leaf minor-level-action-taken {
         type int32;
       }
       leaf minor-level-action {
         type string;
       }
       leaf major-level-occured {
         type int32;
       }
       leaf major-level-cleared {
         type int32;
       }
       leaf major-level-threshold {
         type int32;
       }
       leaf major-level-action-taken {
         type int32;
       }
       leaf major-level-action {
         type string;
       }
       leaf fatal-level-occured {
         type int32;
       }
       leaf fatal-level-cleared {
         type int32;
       }
       leaf fatal-level-threshold {
         type int32;
       }
       leaf fatal-level-action-taken {
         type int32;
       }
       leaf fatal-level-action {
         type string;
       }
       leaf fpc-pfe-state {
         type string;
       }
       leaf memory-rldram-size {
         type int32;
         description "RLDRAM";
       }
       leaf memory-xr2-size {
         type int32;
         description "XR2";
       }
       leaf memory-ddr-dram-size {
         type int32;
         description "DDR DRAM";
       }
       container pic-detail {
         container port-information {
         }
         container package-information {
           container package {
             leaf package-name {
               type string;
             }
           }
         }
         container port-profile-speed-information {
         }
         container port-group-speed-information {
         }
         container port-speed-information {
         }
         container pic-error-information {
         }
         container fec-error-information {
         }
       }
       list mic {
         leaf-list comment {
           type string;
         }
       }
       list pfe-info-values {
         leaf ppfe-id {
           type string;
         }
       }
       list pfeid-info-values {
         leaf pfe-instance {
           type int32;
         }
         leaf ppfe-id {
           type string;
         }
         leaf pfe-state {
           type string;
         }
         leaf pfe-temp-perf-throt {
           type string;
         }
         leaf pfe-temp-volt-reduction {
           type string;
         }
       }
       list scope-level {
         leaf scope {
           type string;
           description "Error scope";
         }
         list category-level {
           leaf category {
             type string;
             description "Error category";
           }
           leaf minor-level-occurred {
             type uint32;
           }
           leaf minor-level-cleared {
             type uint32;
           }
           leaf minor-level-threshold {
             type uint32;
           }
           leaf minor-level-action-taken {
             type uint32;
           }
           leaf minor-level-action {
             type string;
           }
           leaf major-level-occurred {
             type uint32;
           }
           leaf major-level-cleared {
             type uint32;
           }
           leaf major-level-threshold {
             type uint32;
           }
           leaf major-level-action-taken {
             type uint32;
           }
           leaf major-level-action {
             type string;
           }
           leaf fatal-level-occurred {
             type uint32;
           }
           leaf fatal-level-cleared {
             type uint32;
           }
           leaf fatal-level-threshold {
             type uint32;
           }
           leaf fatal-level-action-taken {
             type uint32;
           }
           leaf fatal-level-action {
             type string;
           }
         }
       }
       container fpc-slc-error-information {
         leaf slot {
           type int32;
         }
         leaf fpc-slc-error-slot {
           type int32;
           description "SLC id number";
         }
         leaf slc-fpc-pfe-state {
           type string;
         }
         list scope-level {
           leaf scope {
             type string;
             description "Error scope";
           }
           list category-level {
             leaf category {
               type string;
               description "Error category";
             }
             leaf minor-level-occurred {
               type uint32;
             }
             leaf minor-level-cleared {
               type uint32;
             }
             leaf minor-level-threshold {
               type uint32;
             }
             leaf minor-level-action-taken {
               type uint32;
             }
             leaf minor-level-action {
               type string;
             }
             leaf major-level-occurred {
               type uint32;
             }
             leaf major-level-cleared {
               type uint32;
             }
             leaf major-level-threshold {
               type uint32;
             }
             leaf major-level-action-taken {
               type uint32;
             }
             leaf major-level-action {
               type string;
             }
             leaf fatal-level-occurred {
               type uint32;
             }
             leaf fatal-level-cleared {
               type uint32;
             }
             leaf fatal-level-threshold {
               type uint32;
             }
             leaf fatal-level-action-taken {
               type uint32;
             }
             leaf fatal-level-action {
               type string;
             }
           }
         }
       }
       list fpc-error {
         list fpc-error-group-detail {
           leaf fpc-error-group-name {
             type string;
           }
           leaf fpc-error-group-occurred {
             type int32;
           }
           leaf fpc-error-group-cleared {
             type int32;
           }
           leaf fpc-error-group-error-id {
             type int32;
           }
           leaf fpc-error-group-description {
             type string;
           }
           leaf fpc-error-group-threshold {
             type int32;
           }
         }
         leaf pfe-id {
           type string;
         }
         list fpc-error-group {
           leaf fpc-error-group-name {
             type string;
           }
           leaf fpc-error-group-occurred {
             type int32;
           }
           leaf fpc-error-group-cleared {
             type int32;
           }
           leaf fpc-error-group-action {
             type string;
           }
           leaf fpc-error-group-threshold {
             type int32;
           }
           leaf fpc-error-group-error-id {
             type int32;
           }
         }
       }
     }
   }
   grouping jnu-satellites-information-block {
     list satellite-information {
       leaf satellite-ip {
         type string;
         description "Satellite name or ip";
       }
       leaf alive {
         type string;
         description "Ping";
       }
       leaf satellite-model {
         type string;
         description "Satellite model";
       }
       leaf satellite-version {
         type string;
         description "Junos version";
       }
     }
   }
   grouping jnu-role-information-block {
     leaf role {
       type string;
       description "JNU Role";
     }
   }
   grouping fm-fpc-state-information-block {
     list fm-fpc-ln {
       list fm-pfe-ln {
         list fm-sib-ln {
           leaf sib-slot {
             type int32;
             description "SIB slot number";
           }
           leaf sib-core {
             type int32;
           }
           leaf sib-plane {
             type int32;
           }
           leaf pfe-core-link-state {
             type string;
           }
           leaf sib-fm-state {
             type string;
           }
           leaf sib-asic {
             type int32;
           }
           leaf ln-name {
             type string;
           }
         }
         leaf pfe-slot {
           type int32;
         }
         container fm-plane-ln {
           leaf plane-slot {
             type uint32;
           }
           leaf plane-fm-state {
             type string;
           }
         }
         container fm-link-ln {
           leaf link {
             type uint32;
           }
           leaf link-fm-state {
             type string;
           }
         }
       }
       leaf slot {
         type int32;
       }
     }
     list fm-fpc-ln1 {
       leaf fpc-slot1 {
         type int32;
       }
       list fm-pfe-ln1 {
         leaf pfe-slot1 {
           type int32;
         }
         list fm-pfe-core-ln {
           leaf sib-slot {
             type int32;
             description "SIB slot number";
           }
           leaf sib-core {
             type int32;
           }
           leaf sib-plane {
             type int32;
           }
           leaf pfe-core-link-state {
             type string;
           }
           leaf sib-asic {
             type int32;
           }
           leaf ln-name {
             type string;
           }
         }
         list fm-pfe-core-ln-extended {
           leaf sib-slot {
             type int32;
             description "SIB slot number";
           }
           leaf sib-core {
             type int32;
           }
           leaf sib-asic {
             type int32;
           }
           leaf sib-plane {
             type int32;
           }
           leaf pfe-core-link-state {
             type string;
           }
           leaf ln-name {
             type string;
           }
         }
       }
     }
     leaf comment {
       type string;
     }
   }
   grouping fm-bandwidth-degradation-block {
     container fm-bandwidth-degradation-line {
       leaf slot {
         type int32;
       }
       leaf state {
         type string;
         description "Status of the component";
       }
       leaf comment {
         type string;
       }
       leaf planes-for-line-rate {
         type uint32;
       }
       leaf configured-degradation {
         type string;
       }
       leaf current-degradation {
         type string;
       }
       leaf time-degrad-triggered {
         type string;
       }
       leaf sublc-slot {
         type string;
       }
     }
   }
   grouping fm-fabric-destinations-state-block {
     list fm-dest-fpc-ln {
       leaf fm-slot {
         type uint32;
         description "FPC slot";
       }
       list fm-dest-pfe-ln {
         leaf fm-pfe-slot {
           type uint32;
           description "PFE slot";
         }
         list fm-dest-plane-ln {
           leaf fm-plane-slot {
             type uint32;
             description "Plane slot";
           }
           container fm-dest-fabric-destinations-ln {
             leaf fm-fabric-destination-status {
               type string;
               description "Destinations status information";
             }
           }
         }
       }
     }
   }
   grouping fm-plane-location-information-block {
     container fm-plane-location {
       leaf plane {
         type string;
         description "Plane information";
       }
       leaf sib-f13-slot {
         type string;
         description "F13 SIB information";
       }
       leaf sib-f2-slot {
         type string;
         description "F2 SIB information";
       }
       leaf sib-l-slot {
         type string;
         description "LCC SIB information";
       }
       leaf plane-slot {
         type uint32;
       }
       leaf cb-slot {
         type uint32;
       }
       leaf sfb-plane {
         type uint32;
       }
       leaf sfb-slot {
         type uint32;
       }
       leaf sib-slot {
         type int32;
         description "SIB slot number";
       }
       leaf planes {
         type string;
         description "Planes associated with the SIB";
       }
       leaf plane-number {
         type uint32;
         description "Planes number";
       }
       leaf fab-fru-slot {
         type int32;
         description "Fabric FRU slot number";
       }
     }
   }
   grouping fm-topology-block {
     container fm-topo-link-src-des {
       leaf fm-topo-link-msg {
         type string;
       }
       container fm-topo-link-src {
         leaf fm-topo-link-src-in {
           type string;
         }
         leaf fm-topo-link-src-out {
           type string;
         }
         leaf hsl2-state-src {
           type string;
         }
       }
       container fm-topo-link-des {
         leaf fm-topo-link-des-in {
           type string;
         }
         leaf fm-topo-link-des-out {
           type string;
         }
         leaf hsl2-state-des {
           type string;
         }
       }
     }
     container fm-topo-link-io {
       leaf fm-topo-link-header-message {
         type string;
         description "Header messages for this command";
       }
       container fm-topo-link-sib {
         leaf fm-topo-link-sibnum {
           type int32;
           description "SIB number";
         }
         leaf fm-topo-link-sib-message {
           type string;
           description "SIB messages";
         }
         container fm-topo-link-fchip {
           leaf fm-topo-link-fchipnum {
             type int32;
             description "FCHIP number";
           }
           container fm-topo-link-fcore {
             leaf fm-topo-link-fcorenum {
               type int32;
               description "FCORE number";
             }
             leaf fm-topo-link-detail-message {
               type string;
               description "Link detail messages";
             }
             container fm-topo-link-source {
               leaf fm-topo-link-in {
                 type string;
                 description "In-link name";
               }
               leaf link-state-source {
                 type string;
                 description "In-link state";
               }
             }
             container fm-topo-link-destination {
               leaf fm-topo-link-out {
                 type string;
                 description "Out-link name";
               }
               leaf link-state-destination {
                 type string;
                 description "Out-link state";
               }
             }
             list fm-topo-link-entry {
               description "Link entry";
               container fm-topo-link-source {
                 description "Source link detail";
                 leaf fm-topo-link-in {
                   type string;
                   description "In-link name";
                 }
                 leaf link-state-source {
                   type string;
                   description "In-link state";
                 }
               }
               container fm-topo-link-destination {
                 description "Destination link detail";
                 leaf fm-topo-link-out {
                   type string;
                   description "Out-link name";
                 }
                 leaf link-state-destination {
                   type string;
                   description "Out-link state";
                 }
               }
             }
           }
         }
       }
     }
     container fm-topo-link {
       leaf fm-topo-sib {
         type string;
         description "SIB information";
       }
       leaf fm-topo-dbl-line {
         type string;
         description "Under line of the header";
       }
       leaf fm-topo-fail-msg {
         type string;
         description "Details of the failure";
       }
       container fm-topo-link-details {
         leaf fm-topo-link-type {
           type string;
           description "Type of the link";
         }
         leaf fm-topo-sib-source {
           type string;
           description "Source sib";
         }
         leaf fm-topo-sib-dest {
           type string;
           description "Destination sib";
         }
         leaf source-pfe-xc-link {
           type string;
           description "Source pfe link";
         }
         leaf dest-pfe-xc-link {
           type string;
           description "Destination pfe link";
         }
         leaf vcsel-status {
           type string;
           description "VCSEL status";
         }
         leaf hsl2-channel {
           type string;
           description "HSL2 channel number";
         }
         leaf hsl2-status {
           type string;
           description "HSL2 channel status";
         }
         container fm-topo-link-in-out {
           leaf fm-topo-link-type {
             type string;
             description "Type of the link";
           }
         }
         container fm-topo-link-details-head-lcc {
           leaf fm-topo-sib-source {
             type string;
             description "Source sib";
           }
           leaf fm-topo-sib-dest {
             type string;
             description "Destination sib";
           }
         }
         container fm-topo-link-details-lcc {
           leaf source-pfe-xc-link {
             type string;
             description "Source pfe link";
           }
           leaf dest-pfe-xc-link {
             type string;
             description "Destination pfe link";
           }
           leaf vcsel-status {
             type string;
             description "VCSEL status";
           }
           leaf hsl2-channel {
             type string;
             description "HSL2 channel number";
           }
           leaf hsl2-status {
             type string;
             description "HSL2 channel status";
           }
         }
         container fm-topo-link-details-head-sfc {
           leaf fm-topo-sib-source {
             type string;
             description "Source sib";
           }
           leaf fm-topo-sib-dest {
             type string;
             description "Destination sib";
           }
         }
         container fm-topo-link-details-sfc {
           leaf source-pfe-xc-link {
             type string;
             description "Source pfe link";
           }
           leaf dest-pfe-xc-link {
             type string;
             description "Destination pfe link";
           }
           leaf vcsel-status {
             type string;
             description "VCSEL status";
           }
           leaf hsl2-channel {
             type string;
             description "HSL2 channel number";
           }
           leaf hsl2-status {
             type string;
             description "HSL2 channel status";
           }
         }
       }
       container fm-topo-link-information {
         leaf fm-topo-sib {
           type string;
           description "SIB information";
         }
         leaf fm-topo-dbl-line {
           type string;
           description "Under line of the header";
         }
         container fm-topo-link-fail {
           leaf fm-topo-sib {
             type string;
             description "SIB information";
           }
           leaf fm-topo-fail-msg {
             type string;
             description "Details of the failure";
           }
         }
         container fm-topo-link-details {
           leaf fm-topo-link-type {
             type string;
             description "Type of the link";
           }
           leaf fm-topo-sib-source {
             type string;
             description "Source sib";
           }
           leaf fm-topo-sib-dest {
             type string;
             description "Destination sib";
           }
           leaf source-pfe-xc-link {
             type string;
             description "Source pfe link";
           }
           leaf dest-pfe-xc-link {
             type string;
             description "Destination pfe link";
           }
           leaf vcsel-status {
             type string;
             description "VCSEL status";
           }
           leaf hsl2-channel {
             type string;
             description "HSL2 channel number";
           }
           leaf hsl2-status {
             type string;
             description "HSL2 channel status";
           }
           container fm-topo-link-in-out {
             leaf fm-topo-link-type {
               type string;
               description "Type of the link";
             }
           }
           container fm-topo-link-details-head-lcc {
             leaf fm-topo-sib-source {
               type string;
               description "Source sib";
             }
             leaf fm-topo-sib-dest {
               type string;
               description "Destination sib";
             }
           }
           container fm-topo-link-details-lcc {
             leaf source-pfe-xc-link {
               type string;
               description "Source pfe link";
             }
             leaf dest-pfe-xc-link {
               type string;
               description "Destination pfe link";
             }
             leaf vcsel-status {
               type string;
               description "VCSEL status";
             }
             leaf hsl2-channel {
               type string;
               description "HSL2 channel number";
             }
             leaf hsl2-status {
               type string;
               description "HSL2 channel status";
             }
           }
           container fm-topo-link-details-head-sfc {
             leaf fm-topo-sib-source {
               type string;
               description "Source sib";
             }
             leaf fm-topo-sib-dest {
               type string;
               description "Destination sib";
             }
           }
           container fm-topo-link-details-sfc {
             leaf source-pfe-xc-link {
               type string;
               description "Source pfe link";
             }
             leaf dest-pfe-xc-link {
               type string;
               description "Destination pfe link";
             }
             leaf vcsel-status {
               type string;
               description "VCSEL status";
             }
             leaf hsl2-channel {
               type string;
               description "HSL2 channel number";
             }
             leaf hsl2-status {
               type string;
               description "HSL2 channel status";
             }
           }
         }
       }
       container fm-topo-link-information-sgl {
         container fm-topo-link-fail-sgl {
           leaf fm-topo-sib {
             type string;
             description "SIB information";
           }
           leaf fm-topo-fail-msg {
             type string;
             description "Details of the failure";
           }
         }
         container fm-topo-link-details {
           leaf fm-topo-link-type {
             type string;
             description "Type of the link";
           }
           leaf fm-topo-sib-source {
             type string;
             description "Source sib";
           }
           leaf fm-topo-sib-dest {
             type string;
             description "Destination sib";
           }
           leaf source-pfe-xc-link {
             type string;
             description "Source pfe link";
           }
           leaf dest-pfe-xc-link {
             type string;
             description "Destination pfe link";
           }
           leaf vcsel-status {
             type string;
             description "VCSEL status";
           }
           leaf hsl2-channel {
             type string;
             description "HSL2 channel number";
           }
           leaf hsl2-status {
             type string;
             description "HSL2 channel status";
           }
           container fm-topo-link-in-out {
             leaf fm-topo-link-type {
               type string;
               description "Type of the link";
             }
           }
           container fm-topo-link-details-head-lcc {
             leaf fm-topo-sib-source {
               type string;
               description "Source sib";
             }
             leaf fm-topo-sib-dest {
               type string;
               description "Destination sib";
             }
           }
           container fm-topo-link-details-lcc {
             leaf source-pfe-xc-link {
               type string;
               description "Source pfe link";
             }
             leaf dest-pfe-xc-link {
               type string;
               description "Destination pfe link";
             }
             leaf vcsel-status {
               type string;
               description "VCSEL status";
             }
             leaf hsl2-channel {
               type string;
               description "HSL2 channel number";
             }
             leaf hsl2-status {
               type string;
               description "HSL2 channel status";
             }
           }
           container fm-topo-link-details-head-sfc {
             leaf fm-topo-sib-source {
               type string;
               description "Source sib";
             }
             leaf fm-topo-sib-dest {
               type string;
               description "Destination sib";
             }
           }
           container fm-topo-link-details-sfc {
             leaf source-pfe-xc-link {
               type string;
               description "Source pfe link";
             }
             leaf dest-pfe-xc-link {
               type string;
               description "Destination pfe link";
             }
             leaf vcsel-status {
               type string;
               description "VCSEL status";
             }
             leaf hsl2-channel {
               type string;
               description "HSL2 channel number";
             }
             leaf hsl2-status {
               type string;
               description "HSL2 channel status";
             }
           }
         }
       }
     }
     container fm-topo-map {
       container fm-topo-map-ln {
         leaf fm-fpc-slot {
           type uint32;
         }
         leaf fm-pfe-slot {
           type uint32;
           description "PFE slot";
         }
         leaf fm-cb-slot {
           type uint32;
         }
         leaf port {
           type uint32;
         }
         leaf link-state {
           type string;
         }
       }
     }
     container fm-topo-link-io-b2b {
       leaf fm-topo-link-header-message {
         type string;
         description "Header messages for this command";
       }
       container fm-topo-link-fpc {
         leaf fm-topo-link-fpcnum {
           type int32;
           description "FPC number";
         }
         leaf fm-topo-link-fpc-message {
           type string;
           description "FPC messages";
         }
         container fm-topo-link-fpfe {
           leaf fm-topo-link-fpfenum {
             type int32;
             description "FPFE number";
           }
           container fm-topo-link-fcore {
             leaf fm-topo-link-detail-message {
               type string;
               description "Link detail messages";
             }
             list fm-topo-link-entry {
               description "Link entry";
               container fm-topo-link-source {
                 description "Source link detail";
                 leaf fm-topo-link-in {
                   type string;
                   description "In-link name";
                 }
                 leaf link-state-source {
                   type string;
                   description "In-link state";
                 }
               }
               container fm-topo-link-destination {
                 description "Destination link detail";
                 leaf fm-topo-link-out {
                   type string;
                   description "Out-link name";
                 }
                 leaf link-state-destination {
                   type string;
                   description "Out-link state";
                 }
               }
             }
           }
         }
       }
     }
   }
   grouping fm-plane-state-information-block {
     leaf comment {
       type string;
     }
     container fmp-plane {
       leaf slot {
         type int32;
       }
       leaf state {
         type string;
         description "Status of the component";
       }
       leaf fru-name {
         type string;
       }
       leaf fru-slot {
         type int32;
         description "FRU slot number";
       }
       leaf pfe-slot {
         type int32;
       }
       leaf pfe-link-status {
         type string;
         description "PFE link status information";
       }
       leaf lcc-adc-slot {
         type int32;
         description "ADC slot number";
       }
       container fru-plane-info {
         leaf fru-name {
           type string;
         }
         leaf fru-slot {
           type int32;
           description "FRU slot number";
         }
         container pfe-plane-info {
           leaf pfe-slot {
             type int32;
           }
           leaf pfe-link-status {
             type string;
             description "PFE link status information";
           }
         }
       }
       leaf link-error {
         type string;
         description "Link error count";
       }
       leaf destination-error {
         type string;
         description "Destination error count";
       }
       leaf up-time {
         type string;
         description "Length of time this component has been operational";
       }
       leaf plane-cable-errors {
         type string;
         description "Number of cable errors in the plane";
       }
       leaf plane-state {
         type string;
         description "Plane state information";
       }
       leaf sib-name {
         type string;
         description "SIB name";
       }
       leaf sibs-slot {
         type string;
         description "Chassis SIB slot number";
       }
       leaf sib-f13-name {
         type string;
         description "F13 SIB name";
       }
       leaf f13-slot {
         type int32;
         description "F13 slot number";
       }
       leaf even-odd {
         type string;
         description "Even or Odd part of SIB F13";
       }
       leaf lcc-slot {
         type int32;
         description "LCC slot number";
       }
       leaf sibl-slot {
         type int32;
         description "LCC SIB slot number";
       }
       leaf sibl-link-state {
         type string;
         description "LCC SIB link state information";
       }
       leaf sgasic-number {
         type int32;
         description "SG number on SFC";
       }
       leaf sgasic-port-number {
         type int32;
         description "SG port number on SFC";
       }
       leaf sgasic-port-link-state {
         type string;
         description "SG port link status on SFC";
       }
       leaf sibs-lcc-pfe-slot {
         type int32;
         description "SFC PFE slot number";
       }
       leaf sibs-lcc-pfe-link-state {
         type string;
         description "SFC PFE link state information";
       }
       leaf sib-f2-name {
         type string;
         description "F2 SIB name";
       }
       leaf sibs2-slot {
         type string;
         description "Chassis F2 SIB slot number";
       }
       leaf f2-link-state {
         type string;
         description "F2 link state information";
       }
       leaf lcc-sib-link-state {
         type string;
         description "LCC SIB link state information";
       }
       leaf lcc-sgasic-number {
         type int32;
         description "SG number on LCC";
       }
       leaf lcc-sgasic-port-number {
         type int32;
         description "SG port number on LCC";
       }
       leaf lcc-sgasic-port-link-state {
         type string;
         description "SG port link status on LCC";
       }
       leaf sibl-lcc-pfe-slot {
         type int32;
         description "LCC PFE slot number";
       }
       leaf sibl-lcc-pfe-link-state {
         type string;
         description "LCC PFE link state information";
       }
       leaf lcc-fpc-slot {
         type int32;
         description "FPC slot number";
       }
       leaf lcc-pfe-slot {
         type int32;
         description "PFE slot number";
       }
       leaf lcc-pfe-link-state {
         type string;
         description "PFE link state information";
       }
     }
     leaf fabric-header {
       type string;
       description "Fabric header";
     }
   }
   grouping fm-state-information-block {
     leaf comment {
       type string;
     }
     container fm-state-item {
       leaf plane-slot {
         type uint32;
       }
       leaf state {
         type string;
         description "Status of the component";
       }
       leaf up-time {
         type string;
         description "Length of time this component has been operational";
       }
     }
     container fm-summary-state-default-junos {
       leaf-list comment {
         type string;
       }
       list fm-state-item {
         leaf plane-slot {
           type uint32;
         }
         leaf state {
           type string;
           description "Status of the component";
         }
         leaf up-time {
           type string;
           description "Length of time this component has been operational";
         }
       }
     }
     container fm-summary-state-default-evo {
       leaf-list comment {
         type string;
       }
       list fm-state-item {
         leaf plane-slot {
           type uint32;
         }
         leaf state {
           type string;
           description "Status of the component";
         }
         leaf link-error {
           type string;
           description "Link error count";
         }
         leaf link-tf {
           type string;
           description "Count of training failure links";
         }
         leaf local-reachability-error {
           type string;
           description "Local Reachability error count";
         }
         leaf remote-reachability-error {
           type string;
           description "Remote Reachability error count";
         }
         leaf up-time {
           type string;
           description "Length of time this component has been operational";
         }
       }
     }
   }
   grouping fm-ext-state-information-block {
     leaf comment {
       type string;
     }
     container fm-ext-state-item {
       leaf plane-slot {
         type uint32;
       }
       leaf state {
         type string;
         description "Status of the component";
       }
       leaf link-error {
         type string;
         description "Link error count";
       }
       leaf link-tf {
         type string;
         description "Count of training failure links";
       }
       leaf destination-error {
         type string;
         description "Destination error count";
       }
       leaf up-time {
         type string;
         description "Length of time this component has been operational";
       }
       leaf local-destination-error {
         type string;
         description "Local Destination error count";
       }
       leaf remote-destination-error {
         type string;
         description "Remote Destination error count";
       }
     }
   }
   grouping fm-state-legend-block {
     leaf comment {
       type string;
     }
   }
   grouping fm-fabric-reachability-information-block {
     leaf fab-reach-status {
       type string;
     }
     leaf fab-reach-resolute {
       type string;
     }
     container fab-reachability-detect {
       leaf unreach-dests {
         type string;
       }
       leaf detect-time {
         type string;
         description "Time of unreachability detection";
       }
       leaf unreachability-reason {
         type string;
       }
     }
     container fab-reachability-action {
       leaf plane-restart-phase-status {
         type string;
       }
       leaf plane-restart-start-time {
         type string;
         description "Plane restart start time";
       }
       leaf plane-restart-list {
         type string;
       }
       leaf plane-timeout-list {
         type string;
         description "Planes timed out on event";
       }
       leaf plane-restart-planes-offline {
         type string;
       }
       leaf plane-restart-planes-offline-time {
         type string;
         description "Time plane made offline";
       }
       leaf plane-restart-planes-online {
         type string;
       }
       leaf plane-restart-planes-online-time {
         type string;
         description "Time plane made online";
       }
       leaf plane-restart-end-time {
         type string;
         description "Plane restart end time";
       }
       leaf pfe-offline-current {
         type string;
         description "PFEs being disabled";
       }
       leaf pfe-restart-action-list {
         type string;
       }
       leaf pfe-restart-offline-current {
         type string;
       }
       leaf pfe-restart-online-current {
         type string;
       }
       leaf pfe-restart-offline-start-time {
         type string;
         description "Offline PFE stage start time";
       }
       leaf pfe-restart-offline-end-time {
         type string;
         description "PFE restart offline stage end time";
       }
       leaf pfe-restart-online-start-time {
         type string;
         description "Offline PFE stage start time";
       }
       leaf pfe-restart-online-end-time {
         type string;
         description "PFE restart online end time";
       }
       leaf plane-fpc-restart-phase-status {
         type string;
       }
       leaf plane-fpc-restart-start-time {
         type string;
         description "Plane and FPC restart phase start time";
       }
       leaf fpc-offline-start-time {
         type string;
         description "Offline FPC stage start time";
       }
       leaf fpc-action-list {
         type string;
       }
       leaf fpc-offline-timeout-list {
         type string;
         description "FPCs timed out on offline event";
       }
       leaf fpc-offline-current {
         type int32;
       }
       leaf fpc-offline-time {
         type string;
         description "Time FPC made offline";
       }
       leaf fpc-offline-end-time {
         type string;
         description "Offline FPC stage end time";
       }
       leaf fpc-online-start-time {
         type string;
         description "FPC online stage start time";
       }
       leaf fpc-online-list {
         type string;
       }
       leaf fpc-online-timeout-list {
         type string;
         description "FPCs timed out on online event";
       }
       leaf fpc-online-current {
         type int32;
       }
       leaf fpc-online-time {
         type string;
         description "Time FPC made online";
       }
       leaf fpc-online-end-time {
         type string;
         description "FPC online stage end time";
       }
       leaf fpc-restart-list {
         type string;
         description "FPCs restart list";
       }
       leaf fpc-restart-time {
         type string;
         description "FPC restart time";
       }
       leaf plane-fpc-restart-phase-end-time {
         type string;
         description "Plane and FPC restart phase end time";
       }
       leaf fpc-offline-list {
         type string;
       }
       leaf fpc-offline-phase-status {
         type string;
       }
       leaf fpc-offline-phase-start-time {
         type string;
         description "FPC offline phase start time";
       }
       leaf fpc-offline-phase-end-time {
         type string;
         description "FPC offline phase end time";
       }
       leaf plane-skipped-list {
         type string;
       }
       leaf fpc-restart-phase-status {
         type string;
         description "Status of FPC restart phase";
       }
       leaf fpc-restart-phase-start-time {
         type string;
         description "FPC restart phase start time";
       }
       leaf fpc-timeout-list {
         type string;
         description "FPCs timed out";
       }
       leaf fpc-skipped-list {
         type string;
         description "FPCs skipped restart";
       }
       leaf fpc-restart-phase-end-time {
         type string;
         description "FPC restart phase end time";
       }
       leaf pfe-offline-phase-status {
         type string;
         description "Status of PFE offline phase";
       }
       leaf pfe-offline-phase-start-time {
         type string;
         description "PFE disable phase start time";
       }
       leaf pfe-disable-start-time {
         type string;
         description "PFE disable action start time";
       }
       leaf ifd-disable-start-time {
         type string;
         description "IFD disable action start time";
       }
       leaf pfe-offline-phase-fpc-offline {
         type string;
         description "FPC slots for which PFEs are being disabled";
       }
       leaf pfe-offline-phase-end-time {
         type string;
         description "PFE disable phase end time";
       }
       leaf pfe-restart-phase-status {
         type string;
         description "Status of PFE restart phase";
       }
       leaf pfe-restart-phase-start-time {
         type string;
         description "PFE restart phase start time";
       }
       leaf pfe-restart-list {
         type string;
         description "PFE restart list";
       }
       leaf pfe-restart-timeout-list {
         type string;
         description "PFE timed out";
       }
       leaf pfe-restart-skipped-list {
         type string;
         description "PFEs skipped restart";
       }
       leaf pfe-restart-offline-list {
         type string;
         description "PFE restart offline list";
       }
       leaf pfe-restart-offline-time {
         type string;
         description "PFE restart offline end time";
       }
       leaf pfe-restart-online-list {
         type string;
         description "PFE restart online list";
       }
       leaf pfe-restart-online-time {
         type string;
         description "Time PFE made online";
       }
       leaf pfe-restart-offline-online-list {
         type string;
         description "PFE restart offline/online list";
       }
       leaf pfe-restart-phase-end-time {
         type string;
         description "FPC restart phase end time";
       }
       leaf current-act {
         type string;
       }
       leaf act-reason {
         type string;
       }
       leaf init-phase {
         type string;
       }
       leaf current-phase {
         type string;
       }
       leaf current-phase-status {
         type string;
       }
       leaf act-start-time {
         type string;
         description "Fabric reachability action started";
       }
       leaf act-end-time {
         type string;
         description "Time fabric reachability action completed";
       }
     }
   }
   grouping fm-fabric-events-information-block {
     list fabric-events-q {
       leaf evt-msg {
         type string;
       }
       list evt-line {
         leaf evt-type {
           type string;
         }
         leaf evt-slot {
           type string;
         }
         leaf evt-aux-slot {
           type string;
         }
         leaf evt-sub-slot {
           type string;
         }
       }
     }
   }
   grouping fm-fabric-events-history-block {
     list event-line {
       leaf event-type {
         type string;
       }
       leaf event-fpc-slot {
         type string;
       }
       leaf event-stage {
         type string;
       }
       leaf event-aux-slot {
         type string;
       }
       leaf event-sub-slot {
         type string;
       }
       leaf event-time {
         type string;
         description "Event timestamp";
       }
     }
   }
   grouping fm-fpc-stream-information-block {
     list header-info-line {
       leaf header-info {
         type string;
       }
     }
     list fpc-low-stream-info-line {
       leaf slot {
         type int32;
       }
       leaf low-stream-info {
         type string;
       }
     }
     list high-stream-info-line {
       leaf high-stream-info {
         type string;
       }
     }
   }
   grouping chassis-inventory-block {
     container chassis {
       description "Hardware inventory of this chassis";
       leaf name {
         type string;
         description "Name of this component";
       }
       leaf version {
         type string;
         description "Version of this component";
       }
       leaf part-number {
         type string;
         description "Part number of this component";
       }
       leaf serial-number {
         type string;
         description "Serial number of this component";
       }
       leaf description {
         type string;
         description "Description of this component";
       }
       leaf hardware-incomplete {
         type empty;
       }
       leaf model-number {
         type string;
         description "Model number of this component";
       }
       leaf clei-code {
         type string;
         description "Common Language Equipment Identifier code of this component";
       }
       container i2c-information {
         leaf jedec-code {
           type string;
         }
         leaf eeprom-version {
           type string;
         }
         leaf part-number {
           type string;
           description "Part number of this component";
         }
         leaf serial-number {
           type string;
           description "Serial number of this component";
         }
         leaf assembly-identifier {
           type string;
         }
         leaf assembly-version {
           type string;
         }
         leaf manufacture-date {
           type string;
           description "Date this component was manufactured";
         }
         leaf assembly-flags {
           type string;
         }
         leaf i2c-version {
           type string;
         }
         leaf clei-code {
           type string;
           description "Common Language Equipment Identifier code of this component";
         }
         leaf i2c-identifier {
           type string;
         }
         leaf model-number {
           type string;
           description "Model number of this component";
         }
         leaf board-information-record {
           type string;
           description "Hex dump of board information record";
         }
         leaf i2c-data {
           type string;
           description "Hex dump of I2C data";
         }
       }
       list chassis-module {
         leaf name {
           type string;
           description "Name of this component";
         }
         leaf version {
           type string;
           description "Version of this component";
         }
         leaf part-number {
           type string;
           description "Part number of this component";
         }
         leaf serial-number {
           type string;
           description "Serial number of this component";
         }
         leaf description {
           type string;
           description "Description of this component";
         }
         leaf ir-mode {
           type string;
           description "R/IR mode configured";
         }
         container i2c-information {
           leaf jedec-code {
             type string;
           }
           leaf eeprom-version {
             type string;
           }
           leaf part-number {
             type string;
             description "Part number of this component";
           }
           leaf serial-number {
             type string;
             description "Serial number of this component";
           }
           leaf assembly-identifier {
             type string;
           }
           leaf assembly-version {
             type string;
           }
           leaf manufacture-date {
             type string;
             description "Date this component was manufactured";
           }
           leaf assembly-flags {
             type string;
           }
           leaf i2c-version {
             type string;
           }
           leaf clei-code {
             type string;
             description "Common Language Equipment Identifier code of this component";
           }
           leaf i2c-identifier {
             type string;
           }
           leaf model-number {
             type string;
             description "Model number of this component";
           }
           leaf board-information-record {
             type string;
             description "Hex dump of board information record";
           }
           leaf i2c-data {
             type string;
             description "Hex dump of I2C data";
           }
         }
         list firmware {
           leaf firmware-version-psm {
             type string;
           }
           leaf firmware-primary-mcu {
             type string;
           }
           leaf firmware-secondary-mcu {
             type string;
           }
           leaf firmware-communication-mcu {
             type string;
           }
           leaf firmware-led-mcu {
             type string;
           }
           leaf type {
             type string;
             description "Type of this component";
           }
           leaf firmware-version {
             type string;
             description "Firmware version string for this component";
           }
         }
         list chassis-sub-module {
           leaf name {
             type string;
             description "Name of this component";
           }
           leaf version {
             type string;
             description "Version of this component";
           }
           leaf part-number {
             type string;
             description "Part number of this component";
           }
           leaf serial-number {
             type string;
             description "Serial number of this component";
           }
           leaf description {
             type string;
             description "Description of this component";
           }
           container i2c-information {
             leaf jedec-code {
               type string;
             }
             leaf eeprom-version {
               type string;
             }
             leaf part-number {
               type string;
               description "Part number of this component";
             }
             leaf serial-number {
               type string;
               description "Serial number of this component";
             }
             leaf assembly-identifier {
               type string;
             }
             leaf assembly-version {
               type string;
             }
             leaf manufacture-date {
               type string;
               description "Date this component was manufactured";
             }
             leaf assembly-flags {
               type string;
             }
             leaf i2c-version {
               type string;
             }
             leaf clei-code {
               type string;
               description "Common Language Equipment Identifier code of this component";
             }
             leaf i2c-identifier {
               type string;
             }
             leaf model-number {
               type string;
               description "Model number of this component";
             }
             leaf board-information-record {
               type string;
               description "Hex dump of board information record";
             }
             leaf i2c-data {
               type string;
               description "Hex dump of I2C data";
             }
           }
           list firmware {
             leaf firmware-version-psm {
               type string;
             }
             leaf firmware-primary-mcu {
               type string;
             }
             leaf firmware-secondary-mcu {
               type string;
             }
             leaf firmware-communication-mcu {
               type string;
             }
             leaf firmware-led-mcu {
               type string;
             }
           }
           list chassis-sub-sub-module {
             leaf name {
               type string;
               description "Name of this component";
             }
             leaf version {
               type string;
               description "Version of this component";
             }
             leaf part-number {
               type string;
               description "Part number of this component";
             }
             leaf serial-number {
               type string;
               description "Serial number of this component";
             }
             leaf description {
               type string;
               description "Description of this component";
             }
             leaf model-number {
               type string;
               description "Model number of this component";
             }
             leaf clei-code {
               type string;
               description "Common Language Equipment Identifier code of this component";
             }
             list chassis-sub-sub-sub-module {
               leaf name {
                 type string;
                 description "Name of this component";
               }
               leaf version {
                 type string;
                 description "Version of this component";
               }
               leaf part-number {
                 type string;
                 description "Part number of this component";
               }
               leaf serial-number {
                 type string;
                 description "Serial number of this component";
               }
               leaf description {
                 type string;
                 description "Description of this component";
               }
               leaf model-number {
                 type string;
                 description "Model number of this component";
               }
               leaf clei-code {
                 type string;
                 description "Common Language Equipment Identifier code of this component";
               }
             }
           }
           leaf model-number {
             type string;
             description "Model number of this component";
           }
           leaf clei-code {
             type string;
             description "Common Language Equipment Identifier code of this component";
           }
         }
         list chassis-re-disk-module {
           leaf name {
             type string;
             description "Name of this component";
           }
           leaf disk-size {
             type int32;
             description "Disk size (megabytes)";
           }
           leaf model {
             type string;
           }
           leaf serial-number {
             type string;
             description "Serial number of this component";
           }
           leaf description {
             type string;
             description "Description of this component";
           }
         }
         list chassis-re-usb-module {
           leaf name {
             type string;
             description "Name of this component";
           }
           leaf product {
             type string;
           }
           leaf product-number {
             type int32;
           }
           leaf vendor {
             type string;
           }
           leaf description {
             type string;
             description "Description of this component";
           }
         }
         list chassis-re-dimm-module {
           leaf name {
             type string;
             description "Name of this component";
           }
           leaf part-number {
             type string;
             description "Part number of this component";
           }
           leaf die-rev {
             type string;
             description " DIE revision of the DIMM";
           }
           leaf pcb-rev {
             type string;
             description "PCB revision ";
           }
           leaf mfr-id {
             type string;
             description "Manufacture Id of the DIMM";
           }
         }
         list chassis-compute-node-disk-module {
           leaf name {
             type string;
             description "Name of this component";
           }
           leaf disk-size {
             type int32;
             description "Disk size (megabytes)";
           }
           leaf model {
             type string;
           }
           leaf serial-number {
             type string;
             description "Serial number of this component";
           }
           leaf description {
             type string;
             description "Description of this component";
           }
         }
         leaf license-mode {
           type string;
           description "PTX R/IR mode configured";
         }
         leaf model-number {
           type string;
           description "Model number of this component";
         }
         leaf clei-code {
           type string;
           description "Common Language Equipment Identifier code of this component";
         }
       }
     }
   }
   grouping reswatch-config-information-block {
     leaf reswatch-enable {
       type string;
     }
     leaf reswatch-cpu-statistics-count {
       type string;
     }
     leaf reswatch-jkl-statistics-count {
       type string;
     }
     leaf reswatch-red-enable {
       type string;
     }
     leaf reswatch-red-cpu-threshold {
       type string;
     }
     leaf reswatch-red-jkl-threshold {
       type string;
     }
     leaf reswatch-red-snmp-enable {
       type string;
     }
     leaf reswatch-orange-enable {
       type string;
     }
     leaf reswatch-orange-threshold {
       type string;
     }
   }
   grouping power-budget-information-block {
     leaf psu-slot {
       type int32;
       description "PSU slot";
     }
     leaf-list psu-type {
       type string;
       description "PSU type";
     }
     leaf power-supplied-psu {
       type int32;
       description "Power supplied by that PSU";
     }
     leaf power-supply-state {
       type string;
       description "State of PSU";
     }
     leaf total-power-supplied {
       type int32;
       description "Total Power supplied by all Online PSUs";
     }
     leaf-list psu-redundancy-config {
       type string;
       description "PSU redundancy Config";
     }
     leaf base-power {
       type int32;
       description "Reserved Power for the chassis";
     }
     leaf line-card-slot {
       type int32;
       description "Line card slot";
     }
     leaf-list line-card-type {
       type string;
       description "Line card type";
     }
     leaf line-card-power {
       type int32;
       description "Power used by that line card";
     }
     leaf line-card-poe-power {
       type int32;
       description "Power allocated for PoE per FPC";
     }
     leaf line-card-priority {
       type int32;
       description "Priority of the FPC";
     }
     leaf actual-power-used {
       type int32;
       description "Actual Power consumed by the chassis";
     }
     leaf total-poe-power-allocated {
       type int32;
       description "Total power allocated for Power over Ethernet(PoE)";
     }
     leaf power-available-redundant-case {
       type int32;
       description "Power available for use in redundant (N+1) case";
     }
     leaf total-power-available {
       type int32;
       description "Power available for use in non redundant (N) case";
     }
     list power-budget {
       leaf total-power-supplied {
         type int32;
         description "Total Power supplied by all Online PSUs";
       }
       leaf-list psu-redundancy-config {
         type string;
         description "PSU redundancy Config";
       }
       leaf base-power {
         type int32;
         description "Reserved Power for the chassis";
       }
       leaf line-card-slot {
         type int32;
         description "Line card slot";
       }
       leaf-list line-card-type {
         type string;
         description "Line card type";
       }
       leaf line-card-power {
         type int32;
         description "Power used by that line card";
       }
       leaf line-card-poe-power {
         type int32;
         description "Power allocated for PoE per FPC";
       }
       leaf line-card-priority {
         type int32;
         description "Priority of the FPC";
       }
       leaf actual-power-used {
         type int32;
         description "Actual Power consumed by the chassis";
       }
       leaf total-poe-power-allocated {
         type int32;
         description "Total power allocated for Power over Ethernet(PoE)";
       }
       leaf power-available-redundant-case {
         type int32;
         description "Power available for use in redundant (N+1) case";
       }
       leaf total-power-available {
         type int32;
         description "Power available for use in non redundant (N) case";
       }
       list power-supply {
         leaf psu-slot {
           type int32;
           description "PSU slot";
         }
         leaf-list psu-type {
           type string;
           description "PSU type";
         }
         leaf power-supplied-psu {
           type int32;
           description "Power supplied by that PSU";
         }
         leaf power-supply-state {
           type string;
           description "State of PSU";
         }
         leaf slot {
           type int32;
         }
         leaf amber-led {
           type empty;
           description "Amber LED is lit";
         }
         leaf green-led {
           type empty;
           description "Green LED is lit";
         }
         leaf blue-led {
           type empty;
           description "Blue LED is lit";
         }
       }
       leaf fan-tray-slot {
         type int32;
         description "Fan Tray slot";
       }
       leaf-list fan-tray-type {
         type string;
         description "Fan Tray type";
       }
       leaf fan-tray-base-power {
         type int32;
         description "Fan Tray base power";
       }
       leaf fan-tray-actual-power {
         type empty;
         description "Actual Power consumed by Fan Tray";
       }
       leaf line-card-actual-power {
         type empty;
         description "Power actually used by that line card";
       }
       leaf actual-poe-power-used {
         type int32;
         description "Power used for Power over Ethernet (PoE)";
       }
       leaf total-poe-power-available {
         type int32;
         description "Total power available for Power over Ethernet (PoE)";
       }
     }
     leaf fan-tray-slot {
       type int32;
       description "Fan Tray slot";
     }
     leaf-list fan-tray-type {
       type string;
       description "Fan Tray type";
     }
     leaf fan-tray-base-power {
       type int32;
       description "Fan Tray base power";
     }
     leaf fan-tray-actual-power {
       type empty;
       description "Actual Power consumed by Fan Tray";
     }
     leaf line-card-actual-power {
       type empty;
       description "Power actually used by that line card";
     }
     leaf actual-poe-power-used {
       type int32;
       description "Power used for Power over Ethernet (PoE)";
     }
     leaf total-poe-power-available {
       type int32;
       description "Total power available for Power over Ethernet (PoE)";
     }
   }
   grouping chassis-mac-addresses-block {
     list chassis-mac-addresses-edge-info {
       container re-mac-address {
         leaf re-fc-mac-base {
           type string;
         }
         leaf re-fc-mac-count {
           type string;
         }
         leaf re-vlan-mac {
           type string;
         }
       }
       list fpc-mac-address {
         leaf name {
           type string;
           description "Name of this component";
         }
         leaf fpc-mac-base {
           type string;
         }
         leaf fpc-mac-count {
           type string;
         }
       }
     }
     list mac-address-information {
       leaf public-base-address {
         type string;
       }
       leaf public-count {
         type string;
       }
       leaf private-base-address {
         type string;
       }
       leaf private-count {
         type string;
       }
     }
     container external-mac-address-information {
       leaf external-base-address {
         type string;
       }
       leaf external-count {
         type string;
       }
       leaf external-available {
         type string;
       }
     }
   }
   grouping raid-information-block {
     leaf raid-status {
       type string;
     }
     list raid-members {
       leaf raid-member-device {
         type string;
       }
       leaf raid-member-format {
         type string;
       }
       leaf raid-member-name {
         type string;
       }
       leaf raid-member-type {
         type string;
       }
       leaf raid-member-status {
         type string;
       }
       leaf raid-member-size {
         type string;
       }
       leaf raid-member-offset {
         type string;
       }
     }
   }
   grouping route-engine-information-block {
     list route-engine {
       leaf slot {
         type int32;
       }
       leaf physical-slot {
         type int32;
       }
       leaf mastership-state {
         type string;
         description "Current state of mastership on this Routing Engine";
       }
       leaf mastership-priority {
         type string;
         description "Configured priority for mastership on this Routing Engine";
       }
       leaf temperature {
         type string;
         description "Temperature of the item";
       }
       leaf cpu-temperature {
         type string;
       }
       leaf memory-dram-size {
         type string;
         description "DRAM";
       }
       leaf memory-installed-size {
         type string;
         description "Installed RAM";
       }
       leaf memory-buffer-utilization {
         type int32;
         description "Percentage of buffer memory utilized";
       }
       leaf memory-system-total {
         type int32;
         description "Display the total system memory";
       }
       leaf memory-system-total-used {
         type int32;
         description "Display overall utilization of system memory";
       }
       leaf memory-system-total-util {
         type int32;
         description "Display overall %utilization of system memory";
       }
       leaf memory-control-plane {
         type int32;
         description "Display the total memory with control plane";
       }
       leaf memory-control-plane-used {
         type int32;
         description "Display the memory utilization of control plane mem";
       }
       leaf memory-control-plane-util {
         type int32;
         description "Display the %memory utilization of control plane mem";
       }
       leaf memory-data-plane {
         type int32;
         description "Display the total memory preallocated for data plane";
       }
       leaf memory-data-plane-used {
         type int32;
         description "Display the memory utilization of data plane mem";
       }
       leaf memory-data-plane-util {
         type int32;
         description "Display the %memory utilization of data plane mem";
       }
       leaf control-plane-cpu-count {
         type int32;
         description "Display the number of CPUS dedicated for control-plane";
       }
       leaf data-plane-cpu-count {
         type int32;
         description "Display the number of CPUS dedicated for data-plane";
       }
       leaf cpu-user {
         type int32;
         description "Percentage of CPU utilized by user processes";
       }
       leaf cpu-real-time {
         type int32;
         description "Percentage of CPU utilized by real-time threads";
       }
       leaf cpu-background {
         type int32;
         description "Percentage of CPU utilized by background processes";
       }
       leaf cpu-system {
         type int32;
         description "Percentage of CPU utilized by the kernel";
       }
       leaf cpu-interrupt {
         type int32;
         description "Percentage of CPU utilized by interrupt processing";
       }
       leaf cpu-idle {
         type int32;
         description "Percentage of CPU idle time";
       }
       leaf cpu-user1 {
         type int32;
         description "Percentage of CPU utilized by user processes";
       }
       leaf cpu-background1 {
         type int32;
         description "Percentage of CPU utilized by background processes";
       }
       leaf cpu-system1 {
         type int32;
         description "Percentage of CPU utilized by the kernel";
       }
       leaf cpu-interrupt1 {
         type int32;
         description "Percentage of CPU utilized by the Interrupt";
       }
       leaf cpu-idle1 {
         type int32;
         description "Percentage of CPU idle time";
       }
       leaf cpu-user2 {
         type int32;
         description "Percentage of CPU utilized by user processes";
       }
       leaf cpu-background2 {
         type int32;
         description "Percentage of CPU utilized by background processes";
       }
       leaf cpu-system2 {
         type int32;
         description "Percentage of CPU utilized by the kernel";
       }
       leaf cpu-interrupt2 {
         type int32;
         description "Percentage of CPU utilized by the Interrupt";
       }
       leaf cpu-idle2 {
         type int32;
         description "Percentage of CPU idle time";
       }
       leaf cpu-user3 {
         type int32;
         description "Percentage of CPU utilized by user processes";
       }
       leaf cpu-background3 {
         type int32;
         description "Percentage of CPU utilized by background processes";
       }
       leaf cpu-system3 {
         type int32;
         description "Percentage of CPU utilized by the kernel";
       }
       leaf cpu-interrupt3 {
         type int32;
         description "Percentage of CPU utilized by the Interrupt";
       }
       leaf cpu-idle3 {
         type int32;
         description "Percentage of CPU idle time";
       }
       leaf model {
         type string;
       }
       leaf serial-number {
         type string;
         description "Serial number of this component";
       }
       leaf start-time {
         type string;
         description "Time this component was started";
       }
       leaf up-time {
         type string;
         description "Length of time this component has been operational";
       }
       leaf last-reboot-reason {
         type string;
         description "Last reboot reason of routinge engine";
       }
       leaf load-average-one {
         type string;
       }
       leaf load-average-five {
         type string;
       }
       leaf load-average-fifteen {
         type string;
       }
       leaf bios-version {
         type string;
         description "Routing engine BIOS version";
       }
       leaf bios-date {
         type string;
         description "Routing engine BIOS date";
       }
       leaf bios-id {
         type string;
         description "Routing engine BIOS ID";
       }
       leaf description {
         type string;
         description "Description of this component";
       }
       leaf status {
         type string;
         description "Status of clock synchronization source";
       }
       leaf loader-name {
         type string;
         description "Routing engine Loader name";
       }
       leaf loader-version {
         type string;
         description "Routing engine Loader version";
       }
       leaf icrt-version {
         type string;
         description "Routing engine iCRT version";
       }
     }
   }
   grouping route-engine-resiliency-information-block {
     list route-engine-resiliency-entry {
       leaf reerror-module-name {
         type string;
         description "Module_name";
       }
       leaf reerror-error-id {
         type uint64;
         description "Error_id";
       }
       leaf reerror-threshold {
         type int32;
         description "Threshold";
       }
       leaf reerror-count {
         type int32;
         description "Count";
       }
       leaf reerror-occured {
         type int32;
         description "Occured";
       }
       leaf reerror-cleared {
         type int32;
         description "Cleared";
       }
       leaf reerror-errdesc {
         type string;
         description "Desc";
       }
       leaf reerror-timestamp {
         type int32;
         description "Timestamp";
       }
       leaf reerror-module-id {
         type int32;
         description "Module_id";
       }
     }
   }
   grouping scb-information-block {
     leaf cross-connect {
       type string;
     }
     leaf packet-scheduling {
       type string;
       description "Packet scheduling knob status";
     }
     list scb {
       leaf slot {
         type int32;
       }
       leaf state {
         type string;
         description "Status of the component";
       }
       leaf comment {
         type string;
       }
       leaf temperature {
         type string;
         description "Temperature of the item";
       }
       leaf cpu-total {
         type int32;
         description "Percentage of CPU utilized";
       }
       leaf cpu-interrupt {
         type int32;
         description "Percentage of CPU utilized by interrupt processing";
       }
       leaf memory-dram-size {
         type string;
         description "DRAM";
       }
       leaf memory-heap-utilization {
         type int32;
         description "Percentage of heap memory utilized";
       }
       leaf memory-buffer-utilization {
         type int32;
         description "Percentage of buffer memory utilized";
       }
       leaf failover-count {
         type int32;
       }
       leaf intake-temperature {
         type string;
       }
       leaf exhaust-temperature {
         type string;
       }
       leaf exhaust-a-temperature {
         type string;
         description "Exhaust A temperature";
       }
       leaf exhaust-b-temperature {
         type string;
         description "Exhaust B temperature";
       }
       leaf spp-temperature {
         type string;
       }
       leaf spr-temperature {
         type string;
       }
       leaf cpu-total-ukern {
         type int32;
       }
       leaf cpu-total-rt {
         type int32;
       }
       leaf memory-sram-size {
         type int32;
         description "SRAM";
       }
       leaf memory-rldram-size {
         type int32;
         description "RLDRAM";
       }
       leaf memory-xr2-size {
         type int32;
         description "XR2";
       }
       leaf memory-ddr-dram-size {
         type int32;
         description "DDR DRAM";
       }
       leaf asic-name {
         type string;
       }
       leaf asic-information {
         type string;
       }
       leaf start-time {
         type string;
         description "Time this component was started";
       }
       leaf up-time {
         type string;
         description "Length of time this component has been operational";
       }
       leaf activate-count {
         type int32;
       }
       leaf reset-count {
         type int32;
       }
       leaf max-power-consumption {
         type int32;
       }
       leaf max-mpc-base-power-consumption {
         type int32;
       }
       leaf max-mic0-power-consumption {
         type int32;
       }
       leaf max-mic1-power-consumption {
         type int32;
       }
       leaf max-mpc-total-power-consumption {
         type int32;
       }
       leaf memory-hbm-size {
         type int32;
         description "HBM";
       }
       leaf configured-bandwidth {
         type int32;
       }
       leaf operating-bandwidth {
         type int32;
       }
     }
     leaf scb-type {
       type string;
     }
   }
   grouping fan-information-block {
     leaf name {
       type string;
       description "Name of this component";
     }
     leaf status {
       type string;
       description "Status of clock synchronization source";
     }
     leaf rpm {
       type string;
       description "Fan speed in RPM";
     }
     leaf rpm-percent {
       type string;
       description "Fan speed in % RPM";
     }
     leaf comment {
       type string;
     }
     container fan-information-rpm-item {
       leaf name {
         type string;
         description "Name of this component";
       }
       leaf status {
         type string;
         description "Status of clock synchronization source";
       }
       leaf rpm {
         type string;
         description "Fan speed in RPM";
       }
       leaf comment {
         type string;
       }
     }
     container fan-information-percent-rpm-item {
       leaf name {
         type string;
         description "Name of this component";
       }
       leaf status {
         type string;
         description "Status of clock synchronization source";
       }
       leaf rpm-percent {
         type string;
         description "Fan speed in % RPM";
       }
       leaf comment {
         type string;
       }
     }
   }
   grouping chassis-location-block {
     list chassis-location-information {
       leaf country-code {
         type string;
         description "Country code";
       }
       leaf postal-code {
         type string;
         description "Postal code";
       }
       leaf npa-nxx {
         type string;
         description "Six digits of the phone number";
       }
       leaf altitude {
         type int32;
         description "Feet above (or below) sea level";
       }
       leaf lata {
         type string;
         description "Long distance service area";
       }
       leaf latitude {
         type string;
         description "Latitude";
       }
       leaf longitude {
         type string;
         description "Longitude";
       }
       leaf vcoord {
         type string;
         description "Bellcore vertical coordinate";
       }
       leaf hcoord {
         type string;
         description "Bellcore horizontal coordinate";
       }
       leaf building {
         type string;
         description "Building information";
       }
       leaf floor {
         type uint32;
         description "Floor in building";
       }
       leaf rack {
         type uint32;
         description "Rack";
       }
     }
   }
   grouping temperature-threshold-information-block {
     list temperature-threshold {
       description "Temperature threshold information for a component on the routing platform.";
       leaf name {
         type string;
         description "Name of this component";
       }
       leaf fan-normal-speed {
         type string;
         description "Temperature above which fans are set to normal speed";
       }
       leaf fan-high-speed {
         type string;
         description "Temperature above which fans are set to high speed";
       }
       leaf yellow-alarm {
         type string;
         description "Temperature above which yellow alarm is raised";
       }
       leaf bad-fan-yellow-alarm {
         type string;
         description "Temperature above which yellow alarm is raised if one or more fans are bad";
       }
       leaf red-alarm {
         type string;
         description "Temperature above which red alarm is raised";
       }
       leaf bad-fan-red-alarm {
         type string;
         description "Temperature above which red alarm is raised if one or more fans are bad";
       }
       leaf fire-shutdown {
         type string;
         description "Temperature above which fire-shutdown occurs";
       }
     }
   }
   grouping enh-temperature-threshold-information-block {
     list enh-temperature-threshold {
       description "Temperature threshold information for a component on the routing platform.";
       leaf name {
         type string;
         description "Name of this component";
       }
       leaf enh-fan-normal-speed {
         type string;
         description "Temperature above which fans are set to normal speed";
       }
       leaf enh-fan-high-speed {
         type string;
         description "Temperature above which fans are set to high speed";
       }
       leaf enh-fan-full-speed {
         type string;
         description "Temperature above which fans are set to full speed";
       }
       leaf enh-bad-fan-full-speed {
         type string;
         description "Temperature above which fans are set to high speed";
       }
       leaf enh-yellow-alarm {
         type string;
         description "Temperature above which yellow alarm is raised";
       }
       leaf enh-bad-fan-yellow-alarm {
         type string;
         description "Temperature above which yellow alarm is raised if one or more fans are bad";
       }
       leaf enh-red-alarm {
         type string;
         description "Temperature above which red alarm is raised";
       }
       leaf enh-bad-fan-red-alarm {
         type string;
         description "Temperature above which red alarm is raised if one or more fans are bad";
       }
       leaf enh-fire-shutdown {
         type string;
         description "Temperature above which fire-shutdown occurs";
       }
       leaf enh-state {
         type string;
         description "Temperature sensor EM policy state";
       }
     }
   }
   grouping power-management-information-block {
     list power-management {
       description "Information about JSeries Power Management";
       leaf power-mgmt-device {
         type string;
         description "Type of device";
       }
       leaf power-mgmt-low-power {
         type int32;
         description "Low power Rating tokens";
       }
       leaf power-mgmt-high-power {
         type int32;
         description "High power Rating tokens";
       }
       leaf power-mgmt-heat {
         type int32;
         description "Heat Rating tokens";
       }
       leaf power-mgmt-state {
         type string;
         description "Ratings exceed Chassis limits or not";
       }
     }
   }
   grouping dedicated-ukern-cpu-block {
     leaf dedicated-ukern-cpu-enabled {
       type string;
     }
   }
   grouping chassis-oss-map-block {
     leaf chassis-model {
       type string;
       description "Actual chassis model";
     }
     leaf oss-map {
       type string;
       description "Configured OSS chassis model";
     }
   }
   grouping chassis-cluster-interface-statistics-block {
     leaf control-interface-status {
       type string;
       description "Chassis cluster control interface status";
     }
     leaf dataplane-interface-status {
       type string;
       description "Chassis cluster fabric interface status";
     }
     container control-link-interfaces {
       list control-information {
         leaf control-link-interface-index {
           type uint32;
           description "Chassis cluster control interface index";
         }
         leaf control-link-interface-name {
           type string;
           description "Chassis cluster control interface name";
         }
         leaf control-link-interface-status {
           type string;
           description "Chassis cluster control interface status";
         }
         leaf control-link-interface-internal-sa-status {
           type string;
           description "Chassis cluster control interface internal SA status";
         }
         leaf control-link-interface-security-status {
           type string;
           description "Chassis cluster control interface security status";
         }
       }
     }
     container dataplane-interfaces {
       container fabric-information {
         leaf fabric-interface-index {
           type string;
           description "Chassis cluster fabric interface index";
         }
         leaf fabric-child-interface-name {
           type string;
           description "Child interface name";
         }
         leaf fabric-child-interface-status {
           type string;
           description "Connection status of child interface";
         }
         leaf fabric-link-interface-security-status {
           type string;
           description "Security status of child interface";
         }
       }
     }
     container reth {
       leaf reth-name {
         type string;
         description "Redundant ethernet interface name";
       }
       leaf reth-status {
         type string;
         description "Redundant ethernet interface status";
       }
       leaf redundancy-group-id-for-reth {
         type string;
         description "Redundancy-group ID of redundant ethernet interface";
       }
     }
     container interface-monitoring {
       leaf interface-name-for-monitoring {
         type string;
         description "Interface name for monitoring";
       }
       leaf weight {
         type int32;
         description "Weight assigned to this interface";
       }
       leaf status {
         type string;
         description "Interface administrative status";
       }
       leaf redundancy-group-for-interface {
         type int32;
         description "Redundancy-group for interface";
       }
     }
     container pseudo-if {
       leaf name {
         type string;
         description "Pseudo interface name";
       }
       leaf status {
         type string;
         description "Interface administrative status";
       }
       leaf redundancy-group-id {
         type int32;
         description "Redundancy-group id";
       }
     }
   }
   grouping chassis-cluster-control-port-status-block {
     list chassis-cluster-ctrl-intf-link-status {
       description "Information about Chassis Cluster control interface link status";
       leaf port-number {
         type int32;
         description "Control port number";
       }
       leaf line-side {
         type string;
         description "Control port line-side link status";
       }
     }
     list chassis-cluster-ctrl-port-eeprom {
       description "Information about Chassis Cluster control port ideeprom data";
       leaf port-number {
         type int32;
         description "Control port number";
       }
       leaf cable-type {
         type string;
         description "Port cable type";
       }
       leaf fiber-mode {
         type string;
         description "Single or multi-mode";
       }
       leaf sfp-vendor-name {
         type string;
         description "SFP vendor name";
       }
       leaf sfp-vendor-pno {
         type string;
         description "SFP vendor part number";
       }
       leaf wavelength {
         type string;
         description "Wavelength of the optical transceiver";
       }
       leaf sfp-vendor-fw-ver {
         type string;
         description "Vendor firmware version";
       }
       leaf sfp-jnpr-ver {
         type string;
         description "Juniper revision";
       }
       leaf sfp-msa-version {
         type string;
         description "Multi-Source Agreement version";
       }
     }
     list chassis-cluster-ctrl-port-diag {
       description "Information about Chassis Cluster control port diagnostics data";
       leaf port-index {
         type int32;
       }
       leaf current {
         type string;
       }
       leaf output-powers {
         type string;
       }
       leaf temp {
         type string;
       }
       leaf voltage {
         type string;
       }
       leaf receiver-power {
         type string;
       }
       leaf alarm-warning-flags {
         type string;
       }
       leaf current-high-alarm {
         type string;
       }
       leaf current-low-alarm {
         type string;
       }
       leaf current-high-warning {
         type string;
       }
       leaf current-low-warning {
         type string;
       }
       leaf output-power-high-alarm {
         type string;
       }
       leaf output-power-low-alarm {
         type string;
       }
       leaf output-power-high-warning {
         type string;
       }
       leaf output-power-low-warning {
         type string;
       }
       leaf temperature-high-alarm {
         type string;
       }
       leaf temperature-low-alarm {
         type string;
       }
       leaf temperature-high-warning {
         type string;
       }
       leaf temperature-low-warning {
         type string;
       }
       leaf voltage-high-alarm {
         type string;
       }
       leaf voltage-low-alarm {
         type string;
       }
       leaf voltage-high-warning {
         type string;
       }
       leaf voltage-low-warning {
         type string;
       }
       leaf rx-power-high-alarm {
         type string;
       }
       leaf rx-power-low-alarm {
         type string;
       }
       leaf rx-power-high-warning {
         type string;
       }
       leaf rx-power-low-warning {
         type string;
       }
       leaf current-high-alarm-threshold {
         type string;
       }
       leaf current-low-alarm-threshold {
         type string;
       }
       leaf current-high-warning-threshold {
         type string;
       }
       leaf current-low-warning-threshold {
         type string;
       }
       leaf output-power-high-alarm-threshold {
         type string;
       }
       leaf output-power-low-alarm-threshold {
         type string;
       }
       leaf output-power-high-warning-threshold {
         type string;
       }
       leaf output-power-low-warning-threshold {
         type string;
       }
       leaf temperature-high-alarm-threshold {
         type string;
       }
       leaf temperature-low-alarm-threshold {
         type string;
       }
       leaf temperature-high-warning-threshold {
         type string;
       }
       leaf temperature-low-warning-threshold {
         type string;
       }
       leaf voltage-high-alarm-threshold {
         type string;
       }
       leaf voltage-low-alarm-threshold {
         type string;
       }
       leaf voltage-high-warning-threshold {
         type string;
       }
       leaf voltage-low-warning-threshold {
         type string;
       }
       leaf rx-power-high-alarm-threshold {
         type string;
       }
       leaf rx-power-low-alarm-threshold {
         type string;
       }
       leaf rx-power-high-warning-threshold {
         type string;
       }
       leaf rx-power-low-warning-threshold {
         type string;
       }
     }
   }
   grouping chassis-cluster-statistics-block {
     container chassis-cluster-interfaces {
       container chassis-cluster-control {
         leaf control-interface-index {
           type uint32;
           description "Chassis cluster control interface index";
         }
         leaf heartbeat-sent {
           type string;
           description "Heartbeat packets sent on control link";
         }
         leaf heartbeat-received {
           type string;
           description "Heartbeat packets received on control link";
         }
         leaf heartbeat-errors {
           type string;
           description "Heartbeat packets dropped due to errors";
         }
       }
       list offload-heartbeat-statistics {
         description "Offloaded HA heartbeat statistics";
         leaf control-interface-index {
           type uint32;
           description "Chassis cluster control interface index";
         }
         leaf offload-heartbeat-connection {
           type string;
           description "HA offload mode connection status";
         }
         leaf offload-heartbeat-sent {
           type string;
           description "HA offload heartbeat sent";
         }
         leaf offload-heartbeat-received {
           type string;
           description "HA offload heartbeat received";
         }
         leaf offload-heartbeat-sent-jitter {
           type string;
           description "HA offload heartbeat sent jitter";
         }
         leaf offload-heartbeat-received-jitter {
           type string;
           description "HA offload heartbeat received jitter";
         }
       }
       container chassis-cluster-fabric {
         leaf rto-packets {
           type uint32;
           description "RTO packets";
         }
         leaf forwarded-packets {
           type uint32;
           description "Forwarded packets";
         }
         container fabric-child {
           leaf fabric-child-index {
             type uint32;
             description "Fabric child index";
           }
           leaf fabric-hello-sent {
             type uint32;
             description "Fabric hello packets sent";
           }
           leaf fabric-hello-received {
             type uint32;
             description "Fabric hello packets received";
           }
           leaf fabric-hello-error {
             type uint32;
             description "Fabric hello packets with error";
           }
         }
       }
     }
   }
   grouping services-synchronized-block {
     leaf service-name {
       type string;
       description "Name of the service";
     }
     leaf rtos-sent {
       type uint32;
       description "RTOs sent";
     }
     leaf rtos-received {
       type uint32;
       description "RTOs received";
     }
   }
   grouping chassis-cluster-dataplane-interfaces-block {
     leaf fabric-interface-index {
       type string;
       description "Chassis cluster fabric interface index";
     }
     container fabric-information {
       leaf fabric-child-interface-name {
         type string;
         description "Child interface name";
       }
       leaf fabric-child-interface-status {
         type string;
         description "Connection status of child interface";
       }
     }
   }
   grouping chassis-cluster-status-block {
     leaf cluster-id {
       type int32;
       description "Cluster id";
     }
     container redundancy-group {
       description "Redundancy group for IP monitoring";
       leaf redundancy-group-id {
         type int32;
         description "Redundancy-group id";
       }
       leaf redundancy-group-failover-count {
         type int32;
         description "No of transitions between primary and secondary states";
       }
       list device-stats {
         leaf device-name {
           type string;
           description "Node name";
         }
         leaf device-priority {
           type int32;
           description "Configured priority of the device";
         }
         leaf redundancy-group-status {
           type string;
           description "Status of the redundancy group";
         }
         leaf preempt {
           type string;
           description "Preempt configuration for the redundancy group";
         }
         leaf failover-mode {
           type string;
           description "Manual failover mode for the redundancy group";
         }
         leaf monitor-failures {
           type string;
           description "Monitoring failures for the redundancy group";
         }
       }
     }
   }
   grouping chassis-cluster-information-block {
     container chassis-cluster-redundancy-mode {
       description "Chassis cluster configured and operational redundancy modes";
       leaf configured {
         type string;
         description "Configured";
       }
       leaf operational {
         type string;
         description "Operational";
       }
       leaf mode-mismatch-warning {
         type string;
         description "Chassis cluster redundancy mode mismatch warning";
       }
     }
     container chassis-cluster-redundancy-group-information {
       description "Display redundancy group information";
       container redundancy-group-list {
         description "Display each redundancy group information";
         leaf redundancy-group-id {
           type int32;
           description "Redundancy-group id";
         }
         leaf redundancy-group-status {
           type string;
           description "Status of the redundancy group";
         }
         leaf redundancy-group-weight {
           type int32;
           description "Weight of redundancy group to indicate health status";
         }
         container redundancy-group-state-transition-record {
           description "Display each state transition";
           leaf transition-time {
             type string;
             description "Time of the transistion";
           }
           leaf from-state {
             type string;
             description "Previous state";
           }
           leaf to-state {
             type string;
             description "Current state";
           }
           leaf transition-reason {
             type string;
             description "Reason of the transition";
           }
         }
       }
     }
     container chassis-cluster-led-information {
       description "Chassis cluster LED related information";
       leaf current-led-color {
         type string;
         description "Current color of the chassis cluster LED";
       }
       leaf last-change-reason {
         type string;
         description "Reason for last change of state/color of the chassis cluster LED";
       }
     }
     container chassis-cluster-heartbeat-offload-information {
       description "Chassis cluster HA heartbeat offload mode information";
       leaf chassis-cluster-heartbeat-offload-status {
         type string;
         description "Chassis cluster HA heartbeat offload mode status";
       }
     }
     container chassis-cluster-hld-information {
       description "Chassis cluster HA HLD connection information";
       leaf chassis-cluster-hld-status {
         type string;
         description "Chassis cluster HA HLD connection details";
       }
     }
     container control-link-vlan-information {
       description "Control port traffic tagging with vlan(4094) enabled or disabled";
       leaf control-link-vlan-status {
         type string;
         description "Control port tagging enabled or disabled";
       }
     }
     container chassis-cluster-monitoring-failure-information {
       description "Display monitoring failure information";
       leaf monitoring-failure-title {
         type string;
         description "Display the title";
       }
       container spu-monitoring-failure-information {
         description "Display spu monitoring failure information";
         container spu-monitoring-failure-statistics {
           leaf spu-total-number {
             type int32;
             description "Statistics of total spus";
           }
           leaf npc-total-number {
             type int32;
             description "Statistics of total npcs";
           }
           leaf spu-up-number {
             type int32;
             description "Statistics of up spus";
           }
           leaf npc-up-number {
             type int32;
             description "Statistics of up npcs";
           }
           leaf spu-down-number {
             type int32;
             description "Statistics of down spus";
           }
           leaf npc-down-number {
             type int32;
             description "Statistics of down npcs";
           }
         }
         container spu-monitoring-failure-pic-state {
           description "Display monitoring pic state";
           leaf pfe-name {
             type string;
             description "Name of the PFE";
           }
           leaf pic-state {
             type string;
             description "State of each PIC";
           }
           leaf report-time {
             type string;
             description "Time of receiving report";
           }
         }
       }
       container ip-monitoring-failure-information {
         description "Display ip monitoring failure information";
         leaf redundancy-group-id {
           type int32;
           description "Redundancy-group id";
         }
         leaf redundancy-group-ip-monitoring-status {
           type string;
           description "IP monitoring status of each redundancy group";
         }
         leaf ip-address {
           type jt:ipaddr;
           description "IPv4 address that is being monitored";
         }
         leaf ip-reachability-status {
           type string;
           description "IP address reachability status";
         }
         leaf ip-unreachable-reason {
           type string;
           description "Reason for IP reachability failure";
         }
       }
       container interface-monitoring-failure-information {
         description "Display interface monitoring failure information";
         leaf redundancy-group-id {
           type int32;
           description "Redundancy-group id";
         }
         leaf interface-monitoring-status {
           type string;
           description "Monitoring status of each redundancy group";
         }
         leaf monitoring-interface-name {
           type string;
           description "Name of monitored interface";
         }
         leaf monitoring-interface-status {
           type string;
           description "Status of monitored interface";
         }
         leaf monitoring-child-interface-name {
           type string;
           description "Name of child interface belong to monitored interface";
         }
         leaf monitoring-child-interface-status {
           type string;
           description "Status of child interface belong to monitored interface";
         }
       }
       container coldsync-monitoring-failure-information {
         description "Display coldsync monitoring failure information";
         container coldsync-monitoring-statistics {
           description "Display statistics information of coldsync";
           leaf coldsync-total-spu {
             type int32;
             description "The number of spu that need to do coldsync";
           }
           leaf coldsync-completed-spu {
             type int32;
             description "The number of spu that coldsync completed";
           }
           leaf coldsync-not-complete-spu {
             type int32;
             description "The number of spu that coldsync not complete";
           }
         }
         container coldsync-monitoring-spu-list {
           description "List each spu coldsync state";
           leaf pfe-name {
             type string;
             description "Name of the PFE";
           }
           leaf coldsync-state {
             type string;
             description "Spu coldsync state";
           }
           leaf report-time {
             type string;
             description "Time of receiving report";
           }
         }
       }
       container hardware-monitoring-failure-information {
         description "Display hardware monitoring failure information";
         leaf hardware-monitoring-failure-redundancy-group {
           type string;
           description "Redundancy group of hardware monitoring failure";
         }
         leaf report-time {
           type string;
           description "Time of receiving report";
         }
       }
       container loopback-monitoring-failure-information {
         description "Display loopback, mbuf and nexthop monitoring information";
         leaf pfe-name {
           type string;
           description "Name of the PFE";
         }
         leaf loopback-monitoring-status {
           type string;
           description "Result of loopback monitoring";
         }
         leaf nexthop-monitoring-status {
           type string;
           description "Result of nexthop monitoring";
         }
         leaf mbuf-monitoring-status {
           type string;
           description "Result of mbuf monitoring";
         }
       }
       container fabric-link-failure-information {
         description "Display fabric link failure information";
         container fabric-link-interface-status {
           description "Status of fabric link interfaces";
           leaf fabric-link-interface-index {
             type int32;
             description "Index of fabric link interface";
           }
           container fabric-link-child-interface-status {
             description "Status of fabric link child interfaces";
             leaf fabric-link-child-interface-name {
               type string;
               description "Child interface name of fabric link";
             }
             leaf fabric-link-child-interface-physical-status {
               type string;
               description "Child interface ifd status of fabric link";
             }
             leaf fabric-link-child-interface-monitored-status {
               type string;
               description "Child interface monitored status of fabric link";
             }
           }
         }
       }
       container control-link-failure-information {
         description "Display control link failure information";
         leaf control-link-status {
           type string;
           description "Status of control link";
         }
         leaf dual-control-link-status {
           type string;
           description "Enable or disabled dual control link";
         }
         container control-link-interface-state {
           leaf control-link-interface-name {
             type string;
             description "Chassis cluster control interface name";
           }
           leaf control-link-interface-physical-status {
             type string;
             description "Ifd status of control link interface";
           }
           leaf control-link-interface-monitored-status {
             type string;
             description "Monitored status of control link interface";
           }
         }
       }
       container schedule-monitoring-failure-information {
         description "Display schedule monitoring failure information";
         leaf schedule-monitoring-failure-status {
           type string;
           description "Status of schedule monitoring failure";
         }
         leaf schedule-monitoring-failure-clear-time {
           type uint32;
           description "Time to clear the failure";
         }
       }
     }
   }
   grouping configuration-synchronization-information-block {
     leaf configuration-synchronization-information-header {
       type string;
       description "Configuration synchronization header";
     }
     container configuration-synchronization-status {
       leaf configuration-synchronization-activation-status {
         type string;
         description "Configuration synchronization is enabled/disabled";
       }
       leaf configuration-synchronization-last-operation {
         type string;
         description "Last configuration synchronization operation";
       }
       leaf configuration-synchronization-last-result {
         type string;
         description "Configuration synchronization result";
       }
       container configuration-synchronization-mgd-messages {
         description "Configuration synchronization messages from mgd daemon";
         leaf configuration-synchronization-mgd-messages-header {
           type string;
           description "Configuration synchronization mgd messages header";
         }
         leaf configuration-synchronization-mgd-messages-item {
           type string;
           description "Configuration synchronization message from mgd daemon";
         }
       }
     }
     container configuration-synchronization-events {
       description "List of configuration synchronization events";
       leaf-list configuration-synchronization-event {
         type string;
         description "Recorded configuration synchronization events";
       }
     }
   }
   grouping issu-information-block {
     leaf-list cold-synchronization-progress {
       type string;
       description "Cold synchronization progress";
     }
     leaf-list chassis-cluster-issu-event {
       type string;
       description "ISSU events";
     }
   }
   grouping chassis-cluster-detail-information-block {
     container chassis-cluster-redundancy-mode {
       description "Chassis cluster configured and operational redundancy modes";
       leaf configured {
         type string;
         description "Configured";
       }
       leaf operational {
         type string;
         description "Operational";
       }
       leaf mode-mismatch-warning {
         type string;
         description "Chassis cluster redundancy mode mismatch warning";
       }
     }
     container chassis-cluster-configuration-information {
       description "Cluster configured information";
       leaf heartbeat-interval {
         type uint32;
         description "Heartbeat interval in ms";
       }
       leaf heartbeat-threshold {
         type uint32;
         description "Heartbeat threshold";
       }
       leaf control-link-recovery {
         type string;
         description "Control link recovery";
       }
       leaf fabric-link-timeout {
         type uint32;
         description "Fabric link down timeout value";
       }
       leaf ha-heartbeat-offload-disable {
         type string;
         description "HA heartbeat offload disable";
       }
     }
     container chassis-cluster-node-health {
       leaf local-node-health {
         type string;
         description "Health of current node";
       }
       leaf remote-node-health {
         type string;
         description "Health of remote node";
       }
     }
     container chassis-cluster-internal-statistics {
       container chassis-cluster-control-statistics {
         leaf control-interface-index {
           type uint32;
           description "Chassis cluster control interface index";
         }
         leaf heartbeat-sent {
           type string;
           description "Heartbeat packets sent on control link";
         }
         leaf heartbeat-received {
           type string;
           description "Heartbeat packets received on control link";
         }
         leaf heartbeat-errors {
           type string;
           description "Heartbeat packets dropped due to errors";
         }
         leaf heartbeat-duplicates {
           type string;
           description "Duplicate heartbeat packets received on control link";
         }
         leaf control-link-recovery-packet-count {
           type string;
           description "Hearbeat packet count to identify control link recovery";
         }
         leaf last-heartbeat-id-sent {
           type string;
           description "Sequence number of last heartbeat packet sent on control link";
         }
         leaf last-heartbeat-id-received {
           type string;
           description "Sequence number of last heartbeat packet received on control link";
         }
       }
       list offload-heartbeat-statistics {
         description "Offloaded HA heartbeat statistics";
         leaf control-interface-index {
           type uint32;
           description "Chassis cluster control interface index";
         }
         leaf offload-heartbeat-connection {
           type string;
           description "HA offload mode connection status";
         }
         leaf offload-heartbeat-sent {
           type string;
           description "HA offload heartbeat sent";
         }
         leaf offload-heartbeat-received {
           type string;
           description "HA offload heartbeat received";
         }
         leaf offload-heartbeat-sent-jitter {
           type string;
           description "HA offload heartbeat sent jitter";
         }
         leaf offload-heartbeat-received-jitter {
           type string;
           description "HA offload heartbeat received jitter";
         }
       }
       container chassis-cluster-fabric-statistics {
         container fabric-child {
           leaf fabric-child-index {
             type uint32;
             description "Fabric child index";
           }
           leaf fabric-hello-sent {
             type uint32;
             description "Fabric hello packets sent";
           }
           leaf fabric-hello-received {
             type uint32;
             description "Fabric hello packets received";
           }
           leaf fabric-hello-error {
             type uint32;
             description "Fabric hello packets with error";
           }
         }
       }
       container chassis-cluster-swfabric-statistics {
         leaf swfabric-probe-state {
           type string;
           description "Swfabric probe state";
         }
         leaf swfabric-link-heartbeat-packets-sent {
           type uint64;
           description "Fabric probes sent";
         }
         leaf swfabric-link-heartbeat-packets-received {
           type uint64;
           description "Fabric probes received";
         }
         leaf swfabric-probe-recv-errors {
           type uint64;
           description "Fabric probes dropped due to errors";
         }
         leaf swfabric-probe-send-errors {
           type uint64;
           description "Fabric probes not sent due to errors";
         }
         leaf swfabric-probe-recv-dropped {
           type uint64;
           description "Fabric probes not processed due to errors";
         }
         leaf swfabric-last-probe-id-sent {
           type uint64;
           description "Sequence number of last probe sent on swfabric link";
         }
         leaf swfabric-last-probe-id-rcvd {
           type uint64;
           description "Sequence number of last probe received on swfabric link";
         }
       }
     }
     container chassis-cluster-led-information {
       description "Chassis cluster LED related information";
       leaf current-led-color {
         type string;
         description "Current color of the chassis cluster LED";
       }
       leaf last-change-reason {
         type string;
         description "Reason for last change of state/color of the chassis cluster LED";
       }
     }
     container chassis-cluster-heartbeat-offload-information {
       description "Chassis cluster HA heartbeat offload mode information";
       leaf chassis-cluster-heartbeat-offload-status {
         type string;
         description "Chassis cluster HA heartbeat offload mode status";
       }
     }
     container chassis-cluster-hld-information {
       description "Chassis cluster HA HLD connection information";
       leaf chassis-cluster-hld-status {
         type string;
         description "Chassis cluster HA HLD connection details";
       }
     }
     container control-link-vlan-information {
       description "Control port traffic tagging with vlan(4094) enabled or disabled";
       leaf control-link-vlan-status {
         type string;
         description "Control port tagging enabled or disabled";
       }
     }
     container control-link-secure-login-information {
       description "Control link secure login is enabled or disabled";
       leaf control-link-secure-login-status {
         type string;
         description "Control link secure login is enabled or disabled";
       }
     }
     container redundancy-group-information-list {
       list redundancy-group-information {
         description "Redundancy group related information";
         leaf redundancy-group-id {
           type int32;
           description "Redundancy-group id";
         }
         container redundancy-group-monitoring-information {
           leaf redundancy-group-threshold {
             type uint32;
             description "Current redundancy group weight";
           }
           leaf monitoring-failure-string {
             type string;
             description "List of current monitoring failures";
           }
         }
         container redundancy-group-state-transition-events {
           description "Redundancy group state transition details";
           leaf-list redundancy-group-state-transition-event {
             type string;
             description "State transition old state - > new state";
           }
         }
       }
     }
     container spu-monitoring-information {
       description "SPU monitoring related information";
       container spu-monitoring-status {
         description "SPU monitoring related status information";
         leaf spu-monitoring-state {
           type string;
           description "SPU current monitoring mode Disabled/Enabled/Active";
         }
         leaf spu-monitoring-weight {
           type uint32;
           description "Current SPU monitoring weight";
         }
         list spu-monitoring-spu-state {
           description "Each SPU current state";
           container spu-monitoring-spu-state-list {
             description "Each SPU current state in list";
             leaf pfe-name {
               type string;
               description "Name of the PFE";
             }
             leaf pic-state {
               type string;
               description "State of each PIC";
             }
           }
         }
       }
       container spu-monitoring-statistics {
         description "Detailed statistics of SPU monitoring";
         leaf spu-up-count {
           type uint32;
           description "Number of SPUs that are up";
         }
         leaf spu-down-count {
           type uint32;
           description "Number of SPUs that are down";
         }
         leaf npc-up-count {
           type uint32;
           description "Number of NPCs that are up";
         }
         leaf npc-down-count {
           type uint32;
           description "Number of NPCs that are down";
         }
         leaf chinfo-blob-error-count {
           type uint32;
           description "Error count reading chinfo blob";
         }
       }
       container spu-monitoring-events {
         description "List of SPU monitoring events";
         leaf-list spu-monitoring-event {
           type string;
           description "Recorded SPU monitoring events";
         }
       }
     }
     list loopback-information {
       description "Loopback information";
       container loopback-information-list {
         description "Display loopback information list";
         leaf pfe-name {
           type string;
           description "Name of the PFE";
         }
         leaf loopback-status {
           type string;
           description "Loopback status of each PIC";
         }
         leaf nexthop-status {
           type string;
           description "Nexthop status of each PIC";
         }
         leaf mbuf-status {
           type string;
           description "Mbuf status of each PIC";
         }
       }
     }
     container cold-synchronization-monitoring-information {
       description "Cold sync monitoring related information";
       leaf-list cold-synchronization-progress {
         type string;
         description "Cold synchronization progress";
       }
       container cold-synchronization-status-information {
         description "Cold synchronization related status information";
         leaf cold-synchronization-completed {
           type string;
           description "List of PFE's which have completed cold synchnronization";
         }
         leaf cold-synchronization-not-completed {
           type string;
           description "List of PFE's which have failed cold synchnronization";
         }
         leaf cold-synchronization-unknown {
           type string;
           description "List of PFE's for which cold synchnronization statusupdate is not received";
         }
         leaf cold-synchronization-weight {
           type uint32;
           description "Current Cold Synchronization weight";
         }
       }
       container cold-synchronization-statistics {
         description "Cold synchronization statistics";
         leaf current-cold-synchronization-completed {
           type uint32;
           description "Cold synchronization completed for current jsrpd session";
         }
         leaf current-cold-synchronization-failed {
           type uint32;
           description "Cold synchronization failed for current jsrpd session";
         }
         list cold-synchronization-pfe-statistics {
           description "Cold synchroniizaton statistics for each PFE";
           leaf pfe-name {
             type string;
             description "Name of the PFE";
           }
           leaf cold-synchronization-pfe-completed {
             type uint32;
             description "Cold synchronization complete instances for a given PFE";
           }
           leaf cold-synchronization-pfe-failed {
             type uint32;
             description "Cold synchronization complete instances for a given PFE";
           }
         }
       }
       container cold-synchronization-events {
         description "List of cold synchronization events";
         leaf-list cold-synchronization-event {
           type string;
           description "Recorded cold sync complete/failure for a PFE";
         }
       }
     }
     container interface-monitoring-information {
       description "Interface monitoring related information";
       container interface-monitoring-statistics {
         description "Interface monitoring related statistics";
         leaf monitored-interface-failover-count {
           type uint32;
           description "Total count of monitored interface failure";
         }
       }
       container interface-monitoring-events {
         description "List of interface monitoring events";
         leaf-list interface-monitoring-event {
           type string;
           description "Recorded interface monitoring events";
         }
       }
     }
     container fabric-link-information {
       description "Displays complete fabric link information for debugging purposes";
       container fabric-monitoring-information {
         description "Fabric monitoring related information";
         container fabric-monitoring-status {
           description "Fabric monitoring status";
           leaf fabric-monitoring-state {
             type string;
             description "Fabric monitoring is enabled/disabled";
           }
           leaf fabric-monitoring-activation-status {
             type string;
             description "Fabric monitoring is active/suspended";
           }
           leaf fabric-monitoring-data-plane-notified-status {
             type string;
             description "Fabric monitoring status from data plane";
           }
           leaf fabric-monitoring-internal-status {
             type string;
             description "JSRPD internal fabric monitoring status";
           }
         }
       }
       container fabric-link-events {
         description "List of fabric link events";
         leaf-list fabric-link-event {
           type string;
           description "Recorded fabric link events";
         }
       }
       container fabric-link-hb-events {
         description "List of fabric link heartbeat and jitter events";
         leaf-list fabric-link-hb-event {
           type string;
           description "Recorded fabric link heartbeat events";
         }
       }
     }
     container control-link-information {
       description "Displays complete control link information for debugging purposes";
       leaf control-interface-status {
         type string;
         description "Chassis cluster control interface status";
       }
       container control-link-server-information {
         description "Control link server information";
         leaf server-status {
           type string;
           description "Control link server status";
         }
         leaf-list server-connections {
           type string;
           description "Information of clients connected to the server";
         }
       }
       container control-link-client-information {
         description "Control link client information";
         leaf client-status {
           type string;
           description "Control link client status";
         }
         leaf client-connections {
           type string;
           description "Information of server to which the connection is established";
         }
       }
       container control-link-events {
         description "List of control link events";
         leaf-list control-link-event {
           type string;
           description "Recorded control link events";
         }
       }
       container control-link-hb-events {
         description "List of control link monitoring heartbeat and jitter events";
         leaf-list control-link-hb-event {
           type string;
           description "Recorded control link monitoring heartbeat events";
         }
       }
     }
     container hardware-monitoring-information {
       description "Displays complete hardware monitoring information for debugging purposes";
       container hardware-monitoring-status-information {
         leaf hardware-monitoring-activation-status {
           type string;
           description "Hardware monitoring is enabled/disabled";
         }
         leaf hardware-monitoring-rg0-failover {
           type int32;
           description "Hardware monitoring redundancy group 0 failover";
         }
         leaf hardware-monitoring-rg0-errors {
           type int32;
           description "Hardware monitoring redundancy group 0 errors";
         }
         leaf hardware-monitoring-rg1-errors {
           type int32;
           description "Hardware monitoring redundancy group 1 errors";
         }
       }
       container hardware-monitoring-events {
         description "List of hardware monitoring events";
         leaf-list hardware-monitoring-event {
           type string;
           description "Recorded hardware monitoring events";
         }
       }
     }
     container issu-information {
       description "Displays complete ISSU information for debugging purposes";
       leaf-list cold-synchronization-progress {
         type string;
         description "Cold synchronization progress";
       }
       leaf-list chassis-cluster-issu-event {
         type string;
         description "ISSU events";
       }
     }
     container command-history-information {
       description "Displays command history information for debugging purposes";
       leaf-list chassis-cluster-command-history-event {
         type string;
         description "Command history ";
       }
     }
   }
   grouping cold-synchronization-monitoring-information-block {
     leaf-list cold-synchronization-progress {
       type string;
       description "Cold synchronization progress";
     }
     container cold-synchronization-status-information {
       description "Cold synchronization related status information";
       leaf cold-synchronization-completed {
         type string;
         description "List of PFE's which have completed cold synchnronization";
       }
       leaf cold-synchronization-not-completed {
         type string;
         description "List of PFE's which have failed cold synchnronization";
       }
       leaf cold-synchronization-unknown {
         type string;
         description "List of PFE's for which cold synchnronization statusupdate is not received";
       }
       leaf cold-synchronization-weight {
         type uint32;
         description "Current Cold Synchronization weight";
       }
     }
     container cold-synchronization-statistics {
       description "Cold synchronization statistics";
       leaf current-cold-synchronization-completed {
         type uint32;
         description "Cold synchronization completed for current jsrpd session";
       }
       leaf current-cold-synchronization-failed {
         type uint32;
         description "Cold synchronization failed for current jsrpd session";
       }
       list cold-synchronization-pfe-statistics {
         description "Cold synchroniizaton statistics for each PFE";
         leaf pfe-name {
           type string;
           description "Name of the PFE";
         }
         leaf cold-synchronization-pfe-completed {
           type uint32;
           description "Cold synchronization complete instances for a given PFE";
         }
         leaf cold-synchronization-pfe-failed {
           type uint32;
           description "Cold synchronization complete instances for a given PFE";
         }
       }
     }
     container cold-synchronization-events {
       description "List of cold synchronization events";
       leaf-list cold-synchronization-event {
         type string;
         description "Recorded cold sync complete/failure for a PFE";
       }
     }
   }
   grouping spu-monitoring-information-block {
     list spu-utilization-statistics {
       container fpc {
         description "FPC";
         leaf fpc-number {
           type uint32;
           description "FPC number";
         }
         leaf session-cps {
           type uint32;
           description "Session creation per second (for last 96 seconds on average)";
         }
         leaf session-cps-ipv4 {
           type uint32;
           description "IPv4 Session creation per second (for last 96 seconds on average)";
         }
         leaf session-cps-ipv6 {
           type uint32;
           description "IPv6 Session creation per second (for last 96 seconds on average)";
         }
         leaf session-cps2 {
           type uint32;
           description "Session creation per second (for last 96 seconds on average)";
         }
         leaf session-cps2-ipv4 {
           type uint32;
           description "IPv4 Session creation per second (for last 96 seconds on average)";
         }
         leaf session-cps2-ipv6 {
           type uint32;
           description "IPv6 Session creation per second (for last 96 seconds on average)";
         }
         container pic {
           description "PIC stats";
           leaf pic-number {
             type uint32;
             description "PIC number";
           }
           leaf spu-cpu-utilization {
             type uint32;
             description "SPU CPU utilization in percentage";
           }
           leaf spu-memory-utilization {
             type uint32;
             description "SPU memory utilization in percentage";
           }
           leaf spu-current-flow-session {
             type uint32;
             description "SPU current flow session";
           }
           leaf spu-current-flow-session-ipv4 {
             type uint32;
             description "SPU current IPv4 flow session";
           }
           leaf spu-current-flow-session-ipv6 {
             type uint32;
             description "SPU current IPv6 flow session";
           }
           leaf spu-max-flow-session {
             type uint32;
             description "SPU max flow session";
           }
           leaf spu-current-cp-session {
             type uint32;
             description "SPU current cp session";
           }
           leaf spu-current-cp-session-ipv4 {
             type uint32;
             description "SPU current IPv4 cp session";
           }
           leaf spu-current-cp-session-ipv6 {
             type uint32;
             description "SPU current IPv6 cp session";
           }
           leaf spu-max-cp-session {
             type uint32;
             description "SPU max cp session";
           }
         }
       }
     }
     container spu-monitoring-status {
       description "SPU monitoring related status information";
       leaf spu-monitoring-state {
         type string;
         description "SPU current monitoring mode Disabled/Enabled/Active";
       }
       leaf spu-monitoring-weight {
         type uint32;
         description "Current SPU monitoring weight";
       }
       list spu-monitoring-spu-state {
         description "Each SPU current state";
         container spu-monitoring-spu-state-list {
           description "Each SPU current state in list";
           leaf pfe-name {
             type string;
             description "Name of the PFE";
           }
           leaf pic-state {
             type string;
             description "State of each PIC";
           }
         }
       }
     }
     container spu-monitoring-statistics {
       description "Detailed statistics of SPU monitoring";
       leaf spu-up-count {
         type uint32;
         description "Number of SPUs that are up";
       }
       leaf spu-down-count {
         type uint32;
         description "Number of SPUs that are down";
       }
       leaf npc-up-count {
         type uint32;
         description "Number of NPCs that are up";
       }
       leaf npc-down-count {
         type uint32;
         description "Number of NPCs that are down";
       }
       leaf chinfo-blob-error-count {
         type uint32;
         description "Error count reading chinfo blob";
       }
     }
     container spu-monitoring-events {
       description "List of SPU monitoring events";
       leaf-list spu-monitoring-event {
         type string;
         description "Recorded SPU monitoring events";
       }
     }
   }
   grouping loopback-information-block {
     container loopback-information-list {
       description "Display loopback information list";
       leaf pfe-name {
         type string;
         description "Name of the PFE";
       }
       leaf loopback-status {
         type string;
         description "Loopback status of each PIC";
       }
       leaf nexthop-status {
         type string;
         description "Nexthop status of each PIC";
       }
       leaf mbuf-status {
         type string;
         description "Mbuf status of each PIC";
       }
     }
   }
   grouping hardware-monitoring-information-block {
     container hardware-monitoring-status-information {
       leaf hardware-monitoring-activation-status {
         type string;
         description "Hardware monitoring is enabled/disabled";
       }
       leaf hardware-monitoring-rg0-failover {
         type int32;
         description "Hardware monitoring redundancy group 0 failover";
       }
       leaf hardware-monitoring-rg0-errors {
         type int32;
         description "Hardware monitoring redundancy group 0 errors";
       }
       leaf hardware-monitoring-rg1-errors {
         type int32;
         description "Hardware monitoring redundancy group 1 errors";
       }
     }
     container hardware-monitoring-events {
       description "List of hardware monitoring events";
       leaf-list hardware-monitoring-event {
         type string;
         description "Recorded hardware monitoring events";
       }
     }
   }
   grouping schedule-monitoring-information-block {
     leaf schedule-monitoring-information-header {
       type string;
       description "Schedule monitoring header";
     }
     container schedule-monitoring-status {
       leaf schedule-monitoring-activation-status {
         type string;
         description "Schedule monitoring is enabled/disabled";
       }
       leaf schedule-monitoring-slip-detected {
         type string;
         description "Schedule slip detection status";
       }
       leaf schedule-monitoring-timers-ignored {
         type string;
         description "Ignore timer flag status";
       }
     }
     container schedule-monitoring-statistics {
       description "Statistics of slip duration and count";
       leaf schedule-monitoring-total-slip-count {
         type uint32;
         description "Total count of slip detected";
       }
       leaf schedule-monitoring-max-slip-duration {
         type uint32;
         description "The longest slip duration";
       }
     }
     container schedule-monitoring-events {
       description "List of schedule monitoring events";
       leaf-list schedule-monitoring-event {
         type string;
         description "Recorded schedule monitoring events";
       }
     }
   }
   grouping interface-monitoring-information-block {
     container interface-monitoring-statistics {
       description "Interface monitoring related statistics";
       leaf monitored-interface-failover-count {
         type uint32;
         description "Total count of monitored interface failure";
       }
     }
     container interface-monitoring-events {
       description "List of interface monitoring events";
       leaf-list interface-monitoring-event {
         type string;
         description "Recorded interface monitoring events";
       }
     }
   }
   grouping control-link-information-block {
     leaf control-interface-status {
       type string;
       description "Chassis cluster control interface status";
     }
     container control-link-server-information {
       description "Control link server information";
       leaf server-status {
         type string;
         description "Control link server status";
       }
       leaf-list server-connections {
         type string;
         description "Information of clients connected to the server";
       }
     }
     container control-link-client-information {
       description "Control link client information";
       leaf client-status {
         type string;
         description "Control link client status";
       }
       leaf client-connections {
         type string;
         description "Information of server to which the connection is established";
       }
     }
     container control-link-events {
       description "List of control link events";
       leaf-list control-link-event {
         type string;
         description "Recorded control link events";
       }
     }
     container control-link-hb-events {
       description "List of control link monitoring heartbeat and jitter events";
       leaf-list control-link-hb-event {
         type string;
         description "Recorded control link monitoring heartbeat events";
       }
     }
   }
   grouping fabric-link-information-block {
     container fabric-monitoring-information {
       description "Fabric monitoring related information";
       container fabric-monitoring-status {
         description "Fabric monitoring status";
         leaf fabric-monitoring-state {
           type string;
           description "Fabric monitoring is enabled/disabled";
         }
         leaf fabric-monitoring-activation-status {
           type string;
           description "Fabric monitoring is active/suspended";
         }
         leaf fabric-monitoring-data-plane-notified-status {
           type string;
           description "Fabric monitoring status from data plane";
         }
         leaf fabric-monitoring-internal-status {
           type string;
           description "JSRPD internal fabric monitoring status";
         }
       }
     }
     container fabric-link-events {
       description "List of fabric link events";
       leaf-list fabric-link-event {
         type string;
         description "Recorded fabric link events";
       }
     }
     container fabric-link-hb-events {
       description "List of fabric link heartbeat and jitter events";
       leaf-list fabric-link-hb-event {
         type string;
         description "Recorded fabric link heartbeat events";
       }
     }
   }
   grouping command-history-information-block {
     leaf-list chassis-cluster-command-history-event {
       type string;
       description "Command history ";
     }
   }
   grouping chassis-cluster-ip-monitoring-block {
     leaf redundancy-group {
       type int32;
       description "Redundancy group for IP monitoring";
     }
     leaf ip-monitoring-global-weight {
       type int32;
       description "Global weight for the IP monitoring";
     }
     leaf ip-monitoring-global-threshold {
       type int32;
       description "Global threshold of IP-monitoring";
     }
     leaf ip-monitoring-current-threshold {
       type int32;
       description "Current threshold of IP-monitoring";
     }
     leaf ip-address {
       type jt:ipaddr;
       description "IPv4 address that is being monitored";
     }
     leaf ip-reachability-status {
       type string;
       description "IP address reachability status";
     }
     leaf failure-count {
       type uint32;
       description "Indicates the number of times an IP became unreachable";
     }
     leaf ip-monitoring-weight {
       type int32;
       description "Weight associated with this IP";
     }
     leaf ip-unreachable-reason {
       type string;
       description "Reason for IP reachability failure";
     }
   }
   grouping chassis-cluster-ethernet-switching-status-block {
     leaf ethernet-switching-status {
       type string;
       description "Ethernet switching status";
     }
     list chassis-cluster-status {
       leaf cluster-id {
         type int32;
         description "Cluster id";
       }
       container redundancy-group {
         description "Redundancy group for IP monitoring";
         leaf redundancy-group-id {
           type int32;
           description "Redundancy-group id";
         }
         leaf redundancy-group-failover-count {
           type int32;
           description "No of transitions between primary and secondary states";
         }
         list device-stats {
           leaf device-name {
             type string;
             description "Node name";
           }
           leaf device-priority {
             type int32;
             description "Configured priority of the device";
           }
           leaf redundancy-group-status {
             type string;
             description "Status of the redundancy group";
           }
           leaf preempt {
             type string;
             description "Preempt configuration for the redundancy group";
           }
           leaf failover-mode {
             type string;
             description "Manual failover mode for the redundancy group";
           }
           leaf monitor-failures {
             type string;
             description "Monitoring failures for the redundancy group";
           }
         }
       }
     }
   }
   grouping chassis-cluster-ethernet-switching-statistics-block {
     list chassis-cluster-swfabric {
       leaf swfabric-probe-state {
         type string;
         description "Swfabric probe state";
       }
       leaf swfabric-link-heartbeat-packets-sent {
         type uint64;
         description "Fabric probes sent";
       }
       leaf swfabric-link-heartbeat-packets-received {
         type uint64;
         description "Fabric probes received";
       }
       leaf swfabric-probe-recv-errors {
         type uint64;
         description "Fabric probes dropped due to errors";
       }
       leaf swfabric-probe-send-errors {
         type uint64;
         description "Fabric probes not sent due to errors";
       }
     }
   }
   grouping chassis-cluster-ethernet-switching-interfaces-block {
     leaf swfabric-interface-index {
       type uint32;
       description "Chassis cluster switch fabric interface index";
     }
     container swfabric-information {
       leaf swfab-child-interface-name {
         type string;
         description "Child interface name";
       }
       leaf swfab-child-interface-status {
         type string;
         description "Connection status of child interface";
       }
     }
   }
   grouping chassis-high-availability-info-block {
     leaf node-status {
       type string;
       description "Status of the current node";
     }
     leaf grid-id {
       type int32;
       description "Grid identifier";
     }
     leaf local-id {
       type int32;
       description "Local node identifier";
     }
     leaf local-ip {
       type jt:ipaddr;
       description "Local node IPv4 address";
     }
     leaf local-fwd-ip {
       type jt:ipaddr;
       description "Local Forwarding IP address";
     }
     container chassis-high-availability-info-mnha {
       description "Displays 4 node mnha info";
       container chassis-mnha-local-domain-info {
         description "Displays high-availability peer related info";
         leaf node-status {
           type string;
           description "Status of the current node";
         }
         leaf local-domain-id {
           type int32;
           description "Local-domain-id";
         }
         leaf local-id {
           type int32;
           description "Local node identifier";
         }
         leaf local-ip {
           type jt:ipaddr;
           description "Local node IPv4 address";
         }
         leaf high-availability-peer-desc {
           type string;
           description "Peer description";
         }
         leaf high-availability-peer-id {
           type int32;
           description "Peer identifier that is configured";
         }
         leaf high-availability-peer-ip-address {
           type jt:ipaddr;
           description "Peer remote IPv4 address that is configured";
         }
         leaf-list high-availability-local-interface {
           type string;
           description "Local interface";
         }
         leaf high-availability-peer-rt-instance {
           type string;
           description "Routing Instance name for HA peer";
         }
         leaf high-availability-peer-encryption-status {
           type string;
           description "Encryption status of the current node";
         }
         leaf high-availability-peer-icl-bfd-status {
           type string;
           description "ICL BFD Status of the current node";
         }
         leaf high-availability-peer-detect-time {
           type string;
           description "Configured Peer BFD detection time";
         }
         leaf cold-sync-status {
           type string;
           description "Cold synchronization status";
         }
         leaf rtt-result {
           type string;
           description "RTT result";
         }
         leaf srg0-cold-sync-status {
           type string;
           description "SRG0 cold sync status";
         }
         leaf local-fwd-ip {
           type jt:ipaddr;
           description "Local Forwarding IP address";
         }
         leaf peer-hw-incompatible {
           type string;
           description "Peer hardware compatible status";
         }
         leaf high-availability-peer-fwd-ip-address {
           type jt:ipaddr;
           description "Peer forwarding remote IP address";
         }
         leaf high-availability-local-fwd-interface {
           type string;
           description "Local forwarding interface";
         }
         leaf high-availability-peer-fwd-bfd-status {
           type string;
           description "BFD forwarding status of the current node";
         }
       }
       container chassis-mnha-peer-domain-info {
         description "Displays mnha peer domain info";
         leaf peer-domain-info {
           type string;
           description "Peer-domain-info";
         }
         leaf peer-domain-id {
           type int32;
           description "Peer-domain-id";
         }
         leaf-list peer-local-ip {
           type jt:ipaddr;
           description "Peer node IPv4 address";
         }
         container chassis-high-availability-default-srg-info {
           description "Displays high-availability services redundancy group 0 info";
           leaf current-state {
             type string;
             description "SRG 0 current state";
           }
           leaf peer-id {
             type int32;
             description "Peer identifier";
           }
           leaf node-priority {
             type int32;
             description "Node-priority";
           }
           leaf peer-domain-id {
             type int32;
             description "Peer-domain-id";
           }
           list srg-peer-domain-peer-id-info {
             description "Idl peer node Id";
             leaf idl-peer-id {
               type int32;
               description "IDL Peer identifier";
             }
           }
           container high-availability-srg-signal-rt-info {
             description "  SRG Signal route Info";
             container ha-srg-signal-rt-list {
               description "Display each signal route information";
               leaf ha-srg-signal-rt-type {
                 type string;
                 description "  SRG  Signal route type";
               }
               leaf ha-srg-signal-rt-ipaddr {
                 type string;
                 description "IP address configured as SRG active signal route";
               }
               leaf ha-srg-signal-rt-rt {
                 type string;
                 description "Routing table configured for active signal route";
               }
               leaf ha-srg-signal-rt-status {
                 type string;
                 description " SRG signal Route installation status";
               }
             }
           }
           list chassis-high-availability-shutdown-interface {
             description "Display high-availability shutdown interface list";
             leaf high-availability-shutdown-interface-name {
               type string;
               description "Interface name for monitoring";
             }
           }
           container chassis-high-availability-srg-ipmon {
             description "SRG IP monitoring Info";
             leaf ha-srg-ipmon-status {
               type string;
               description "SRG overall IP-monitoring status";
             }
             container chassis-high-availability-srg-ipmon-list {
               description " Display each IP monitoring entry";
               leaf ha-srg-ipmon-dst-ipaddr {
                 type string;
                 description "Destination IP address configured for HA ip-monitoring";
               }
               leaf ha-srg-ipmon-rt {
                 type string;
                 description "Routing instance configured for HA ip-monitoring";
               }
               leaf ha-ipmon-status {
                 type string;
                 description "HA ip-monitoring status";
               }
               leaf ha-srg-ipmon-reason {
                 type string;
                 description "HA ip-monitoring failure reason";
               }
             }
           }
           container chassis-high-availability-srg-bfdmon {
             description " SRG BFD mon information ";
             leaf ha-srg-bfdmon-status {
               type string;
               description "HA overall bfd-monitoring status";
             }
             container chassis-high-availability-srg-bfdmon-list {
               description " Display each BFD mon entry Information";
               leaf ha-srg-bfdmon-src-ipaddr {
                 type string;
                 description "Source IP address configured for HA bfd-monitoring";
               }
               leaf ha-srg-bfdmon-dst-ipaddr {
                 type string;
                 description "Destination IP address configured for HA bfd-monitoring";
               }
               leaf ha-srg-bfdmon-rt {
                 type string;
                 description "Routing instance configured for HA bfd-monitoring";
               }
               leaf ha-srg-bfdmon-type {
                 type string;
                 description "HA bfd-monitoring type";
               }
               leaf ha-srg-bfdmon-ifl-name {
                 type string;
                 description "HA bfd-monitoring IFL name";
               }
               leaf ha-srg-bfdmon-state {
                 type string;
                 description "HA bfd-monitoring state";
               }
             }
           }
           container chassis-high-availability-srg-ifmon {
             description "SRG Interface monitoring Info";
             leaf ha-srg-ifmon-status {
               type string;
               description "HA overall Interface-monitoring status";
             }
             container chassis-high-availability-srg-ifmon-list {
               description " Display each Interface monitoring entry";
               leaf ha-srg-ifmon-if-name {
                 type string;
                 description "HA Interface-monitoring IF name";
               }
               leaf ha-srg-ifmon-state {
                 type string;
                 description "HA Interface-monitoring state";
               }
             }
           }
           container chassis-high-availability-srg-mon-info {
             description "SRG global threshold info";
             leaf ha-srg-mon-status {
               type string;
               description "SRG monitor status";
             }
             leaf ha-srg-mon-threshold {
               type int32;
               description "SRG monitor threshold";
             }
             leaf ha-srg-mon-weight {
               type int32;
               description "SRG monitor weight";
             }
             leaf ha-srg-mon-failed-objects {
               type int32;
               description "SRG monitor failed objects";
             }
           }
           container chassis-high-availability-srg-obj-info {
             description "SRG monitor-object info";
             leaf ha-srg-obj-name {
               type string;
               description "SRG monitor object name";
             }
             leaf ha-srg-obj-status {
               type string;
               description "SRG monitor object status";
             }
             leaf ha-srg-obj-entries {
               type string;
               description "SRG monitor object monitored entries";
             }
             leaf ha-srg-obj-failure {
               type string;
               description "SRG monitor object monitored failures";
             }
             leaf ha-srg-obj-threshold {
               type int32;
               description "SRG monitor object threshold";
             }
             leaf ha-srg-obj-weight {
               type int32;
               description "SRG monitor object current weight";
             }
           }
           container chassis-high-availability-srg-obj-ipmon {
             description "SRG monitor object IP monitoring Info";
             leaf ha-srg-obj-ipmon-threshold {
               type int32;
               description "SRG monitor object IP-monitoring threshold";
             }
             leaf ha-srg-obj-ipmon-weight {
               type int32;
               description "SRG monitor object IP-monitoring weight";
             }
             leaf ha-srg-obj-ipmon-status {
               type string;
               description "SRG monitor object IP-monitoring global status";
             }
             container chassis-high-availability-srg-obj-ipmon-list {
               description " Display each monitor object IP monitoring entry status";
               leaf ha-srg-obj-ipmon-entry-status {
                 type string;
                 description "HA SRG monitor object ip-monitoring state";
               }
               leaf ha-srg-obj-ipmon-entry-weight {
                 type int32;
                 description "HA SRG monitor object ip-monitoring weight";
               }
               leaf ha-srg-obj-ipmon-entry-dst-ipaddr {
                 type string;
                 description "Destination IP address configured for HA ip-monitoring";
               }
             }
           }
           container chassis-high-availability-srg-obj-ipmon-detail {
             description "SRG monitor object IP monitoring detail Info";
             container chassis-high-availability-srg-ipmon-list {
               description " Display each IP monitoring entry";
               leaf ha-srg-ipmon-dst-ipaddr {
                 type string;
                 description "Destination IP address configured for HA ip-monitoring";
               }
               leaf ha-srg-ipmon-rt {
                 type string;
                 description "Routing instance configured for HA ip-monitoring";
               }
               leaf ha-ipmon-status {
                 type string;
                 description "HA ip-monitoring status";
               }
               leaf ha-srg-ipmon-reason {
                 type string;
                 description "HA ip-monitoring failure reason";
               }
             }
           }
           container chassis-high-availability-srg-obj-bfdmon {
             description "SRG monitor object BFD monitoring Info";
             leaf ha-srg-obj-bfdmon-threshold {
               type int32;
               description "SRG monitor object BFD-monitoring threshold";
             }
             leaf ha-srg-obj-bfdmon-weight {
               type int32;
               description "SRG monitor object BFD-monitoring weight";
             }
             leaf ha-srg-obj-bfdmon-status {
               type string;
               description "SRG monitor object BFD-monitoring global status";
             }
             container chassis-high-availability-srg-obj-bfdmon-list {
               description "Display each monitor object BFD monitoring entry status";
               leaf ha-srg-obj-bfdmon-entry-status {
                 type string;
                 description "HA SRG monitor object BFD-monitoring state";
               }
               leaf ha-srg-obj-bfdmon-entry-weight {
                 type int32;
                 description "HA SRG monitor object BFD-monitoring weight";
               }
               leaf ha-srg-obj-bfdmon-entry-dst-bfdaddr {
                 type string;
                 description "Destination BFD address configured for HA BFD-monitoring";
               }
             }
           }
           container chassis-high-availability-srg-obj-bfdmon-detail {
             description "SRG monitor object BFD mon information ";
             container chassis-high-availability-srg-bfdmon-list {
               description " Display each BFD mon entry Information";
               leaf ha-srg-bfdmon-src-ipaddr {
                 type string;
                 description "Source IP address configured for HA bfd-monitoring";
               }
               leaf ha-srg-bfdmon-dst-ipaddr {
                 type string;
                 description "Destination IP address configured for HA bfd-monitoring";
               }
               leaf ha-srg-bfdmon-rt {
                 type string;
                 description "Routing instance configured for HA bfd-monitoring";
               }
               leaf ha-srg-bfdmon-type {
                 type string;
                 description "HA bfd-monitoring type";
               }
               leaf ha-srg-bfdmon-ifl-name {
                 type string;
                 description "HA bfd-monitoring IFL name";
               }
               leaf ha-srg-bfdmon-state {
                 type string;
                 description "HA bfd-monitoring state";
               }
             }
           }
           container chassis-high-availability-srg-obj-ifmon {
             description "SRG monitor object IF monitoring Info";
             leaf ha-srg-obj-ifmon-threshold {
               type int32;
               description "SRG monitor object IF-monitoring threshold";
             }
             leaf ha-srg-obj-ifmon-weight {
               type int32;
               description "SRG monitor object IF-monitoring current weight";
             }
             leaf ha-srg-ifmon-status {
               type string;
               description "HA overall Interface-monitoring status";
             }
             container chassis-high-availability-srg-obj-ifmon-list {
               description "Display each monitor object IF monitoring entry status";
               leaf ha-srg-ifmon-entry-status {
                 type string;
                 description "HA SRG monitor object IF-monitoring entry status";
               }
               leaf ha-srg-obj-ifmon-entry-weight {
                 type int32;
                 description "HA SRG monitor object IF-monitoring entry weight";
               }
               leaf ha-srg-ifmon-if-name {
                 type string;
                 description "HA Interface-monitoring IF name";
               }
             }
           }
         }
         list chassis-mnha-peer-node-info {
           description "Displays mnha peer node related info";
           leaf-list peer-local-ip {
             type jt:ipaddr;
             description "Peer node IPv4 address";
           }
           leaf high-availability-peer-desc {
             type string;
             description "Peer description";
           }
           leaf high-availability-peer-id {
             type int32;
             description "Peer identifier that is configured";
           }
           leaf high-availability-peer-ip-address {
             type jt:ipaddr;
             description "Peer remote IPv4 address that is configured";
           }
           leaf-list high-availability-local-interface {
             type string;
             description "Local interface";
           }
           leaf high-availability-peer-rt-instance {
             type string;
             description "Routing Instance name for HA peer";
           }
           leaf high-availability-peer-encryption-status {
             type string;
             description "Encryption status of the current node";
           }
           leaf high-availability-peer-idl-bfd-status {
             type string;
             description "IDL BFD Status of the current node";
           }
           leaf high-availability-peer-detect-time {
             type string;
             description "Configured Peer BFD detection time";
           }
           leaf cold-sync-status {
             type string;
             description "Cold synchronization status";
           }
           leaf rtt-result {
             type string;
             description "RTT result";
           }
           leaf srg0-cold-sync-status {
             type string;
             description "SRG0 cold sync status";
           }
           leaf peer-hw-incompatible {
             type string;
             description "Peer hardware compatible status";
           }
           leaf high-availability-peer-fwd-ip-address {
             type jt:ipaddr;
             description "Peer forwarding remote IP address";
           }
           leaf high-availability-local-fwd-interface {
             type string;
             description "Local forwarding interface";
           }
           leaf high-availability-peer-fwd-bfd-status {
             type string;
             description "BFD forwarding status of the current node";
           }
           container chassis-high-availability-default-srg-info {
             description "Displays high-availability services redundancy group 0 info";
             leaf current-state {
               type string;
               description "SRG 0 current state";
             }
             leaf peer-id {
               type int32;
               description "Peer identifier";
             }
             leaf node-priority {
               type int32;
               description "Node-priority";
             }
             leaf peer-domain-id {
               type int32;
               description "Peer-domain-id";
             }
             list srg-peer-domain-peer-id-info {
               description "Idl peer node Id";
               leaf idl-peer-id {
                 type int32;
                 description "IDL Peer identifier";
               }
             }
             container high-availability-srg-signal-rt-info {
               description "  SRG Signal route Info";
               container ha-srg-signal-rt-list {
                 description "Display each signal route information";
                 leaf ha-srg-signal-rt-type {
                   type string;
                   description "  SRG  Signal route type";
                 }
                 leaf ha-srg-signal-rt-ipaddr {
                   type string;
                   description "IP address configured as SRG active signal route";
                 }
                 leaf ha-srg-signal-rt-rt {
                   type string;
                   description "Routing table configured for active signal route";
                 }
                 leaf ha-srg-signal-rt-status {
                   type string;
                   description " SRG signal Route installation status";
                 }
               }
             }
             list chassis-high-availability-shutdown-interface {
               description "Display high-availability shutdown interface list";
               leaf high-availability-shutdown-interface-name {
                 type string;
                 description "Interface name for monitoring";
               }
             }
             container chassis-high-availability-srg-ipmon {
               description "SRG IP monitoring Info";
               leaf ha-srg-ipmon-status {
                 type string;
                 description "SRG overall IP-monitoring status";
               }
               container chassis-high-availability-srg-ipmon-list {
                 description " Display each IP monitoring entry";
                 leaf ha-srg-ipmon-dst-ipaddr {
                   type string;
                   description "Destination IP address configured for HA ip-monitoring";
                 }
                 leaf ha-srg-ipmon-rt {
                   type string;
                   description "Routing instance configured for HA ip-monitoring";
                 }
                 leaf ha-ipmon-status {
                   type string;
                   description "HA ip-monitoring status";
                 }
                 leaf ha-srg-ipmon-reason {
                   type string;
                   description "HA ip-monitoring failure reason";
                 }
               }
             }
             container chassis-high-availability-srg-bfdmon {
               description " SRG BFD mon information ";
               leaf ha-srg-bfdmon-status {
                 type string;
                 description "HA overall bfd-monitoring status";
               }
               container chassis-high-availability-srg-bfdmon-list {
                 description " Display each BFD mon entry Information";
                 leaf ha-srg-bfdmon-src-ipaddr {
                   type string;
                   description "Source IP address configured for HA bfd-monitoring";
                 }
                 leaf ha-srg-bfdmon-dst-ipaddr {
                   type string;
                   description "Destination IP address configured for HA bfd-monitoring";
                 }
                 leaf ha-srg-bfdmon-rt {
                   type string;
                   description "Routing instance configured for HA bfd-monitoring";
                 }
                 leaf ha-srg-bfdmon-type {
                   type string;
                   description "HA bfd-monitoring type";
                 }
                 leaf ha-srg-bfdmon-ifl-name {
                   type string;
                   description "HA bfd-monitoring IFL name";
                 }
                 leaf ha-srg-bfdmon-state {
                   type string;
                   description "HA bfd-monitoring state";
                 }
               }
             }
             container chassis-high-availability-srg-ifmon {
               description "SRG Interface monitoring Info";
               leaf ha-srg-ifmon-status {
                 type string;
                 description "HA overall Interface-monitoring status";
               }
               container chassis-high-availability-srg-ifmon-list {
                 description " Display each Interface monitoring entry";
                 leaf ha-srg-ifmon-if-name {
                   type string;
                   description "HA Interface-monitoring IF name";
                 }
                 leaf ha-srg-ifmon-state {
                   type string;
                   description "HA Interface-monitoring state";
                 }
               }
             }
             container chassis-high-availability-srg-mon-info {
               description "SRG global threshold info";
               leaf ha-srg-mon-status {
                 type string;
                 description "SRG monitor status";
               }
               leaf ha-srg-mon-threshold {
                 type int32;
                 description "SRG monitor threshold";
               }
               leaf ha-srg-mon-weight {
                 type int32;
                 description "SRG monitor weight";
               }
               leaf ha-srg-mon-failed-objects {
                 type int32;
                 description "SRG monitor failed objects";
               }
             }
             container chassis-high-availability-srg-obj-info {
               description "SRG monitor-object info";
               leaf ha-srg-obj-name {
                 type string;
                 description "SRG monitor object name";
               }
               leaf ha-srg-obj-status {
                 type string;
                 description "SRG monitor object status";
               }
               leaf ha-srg-obj-entries {
                 type string;
                 description "SRG monitor object monitored entries";
               }
               leaf ha-srg-obj-failure {
                 type string;
                 description "SRG monitor object monitored failures";
               }
               leaf ha-srg-obj-threshold {
                 type int32;
                 description "SRG monitor object threshold";
               }
               leaf ha-srg-obj-weight {
                 type int32;
                 description "SRG monitor object current weight";
               }
             }
             container chassis-high-availability-srg-obj-ipmon {
               description "SRG monitor object IP monitoring Info";
               leaf ha-srg-obj-ipmon-threshold {
                 type int32;
                 description "SRG monitor object IP-monitoring threshold";
               }
               leaf ha-srg-obj-ipmon-weight {
                 type int32;
                 description "SRG monitor object IP-monitoring weight";
               }
               leaf ha-srg-obj-ipmon-status {
                 type string;
                 description "SRG monitor object IP-monitoring global status";
               }
               container chassis-high-availability-srg-obj-ipmon-list {
                 description " Display each monitor object IP monitoring entry status";
                 leaf ha-srg-obj-ipmon-entry-status {
                   type string;
                   description "HA SRG monitor object ip-monitoring state";
                 }
                 leaf ha-srg-obj-ipmon-entry-weight {
                   type int32;
                   description "HA SRG monitor object ip-monitoring weight";
                 }
                 leaf ha-srg-obj-ipmon-entry-dst-ipaddr {
                   type string;
                   description "Destination IP address configured for HA ip-monitoring";
                 }
               }
             }
             container chassis-high-availability-srg-obj-ipmon-detail {
               description "SRG monitor object IP monitoring detail Info";
               container chassis-high-availability-srg-ipmon-list {
                 description " Display each IP monitoring entry";
                 leaf ha-srg-ipmon-dst-ipaddr {
                   type string;
                   description "Destination IP address configured for HA ip-monitoring";
                 }
                 leaf ha-srg-ipmon-rt {
                   type string;
                   description "Routing instance configured for HA ip-monitoring";
                 }
                 leaf ha-ipmon-status {
                   type string;
                   description "HA ip-monitoring status";
                 }
                 leaf ha-srg-ipmon-reason {
                   type string;
                   description "HA ip-monitoring failure reason";
                 }
               }
             }
             container chassis-high-availability-srg-obj-bfdmon {
               description "SRG monitor object BFD monitoring Info";
               leaf ha-srg-obj-bfdmon-threshold {
                 type int32;
                 description "SRG monitor object BFD-monitoring threshold";
               }
               leaf ha-srg-obj-bfdmon-weight {
                 type int32;
                 description "SRG monitor object BFD-monitoring weight";
               }
               leaf ha-srg-obj-bfdmon-status {
                 type string;
                 description "SRG monitor object BFD-monitoring global status";
               }
               container chassis-high-availability-srg-obj-bfdmon-list {
                 description "Display each monitor object BFD monitoring entry status";
                 leaf ha-srg-obj-bfdmon-entry-status {
                   type string;
                   description "HA SRG monitor object BFD-monitoring state";
                 }
                 leaf ha-srg-obj-bfdmon-entry-weight {
                   type int32;
                   description "HA SRG monitor object BFD-monitoring weight";
                 }
                 leaf ha-srg-obj-bfdmon-entry-dst-bfdaddr {
                   type string;
                   description "Destination BFD address configured for HA BFD-monitoring";
                 }
               }
             }
             container chassis-high-availability-srg-obj-bfdmon-detail {
               description "SRG monitor object BFD mon information ";
               container chassis-high-availability-srg-bfdmon-list {
                 description " Display each BFD mon entry Information";
                 leaf ha-srg-bfdmon-src-ipaddr {
                   type string;
                   description "Source IP address configured for HA bfd-monitoring";
                 }
                 leaf ha-srg-bfdmon-dst-ipaddr {
                   type string;
                   description "Destination IP address configured for HA bfd-monitoring";
                 }
                 leaf ha-srg-bfdmon-rt {
                   type string;
                   description "Routing instance configured for HA bfd-monitoring";
                 }
                 leaf ha-srg-bfdmon-type {
                   type string;
                   description "HA bfd-monitoring type";
                 }
                 leaf ha-srg-bfdmon-ifl-name {
                   type string;
                   description "HA bfd-monitoring IFL name";
                 }
                 leaf ha-srg-bfdmon-state {
                   type string;
                   description "HA bfd-monitoring state";
                 }
               }
             }
             container chassis-high-availability-srg-obj-ifmon {
               description "SRG monitor object IF monitoring Info";
               leaf ha-srg-obj-ifmon-threshold {
                 type int32;
                 description "SRG monitor object IF-monitoring threshold";
               }
               leaf ha-srg-obj-ifmon-weight {
                 type int32;
                 description "SRG monitor object IF-monitoring current weight";
               }
               leaf ha-srg-ifmon-status {
                 type string;
                 description "HA overall Interface-monitoring status";
               }
               container chassis-high-availability-srg-obj-ifmon-list {
                 description "Display each monitor object IF monitoring entry status";
                 leaf ha-srg-ifmon-entry-status {
                   type string;
                   description "HA SRG monitor object IF-monitoring entry status";
                 }
                 leaf ha-srg-obj-ifmon-entry-weight {
                   type int32;
                   description "HA SRG monitor object IF-monitoring entry weight";
                 }
                 leaf ha-srg-ifmon-if-name {
                   type string;
                   description "HA Interface-monitoring IF name";
                 }
               }
             }
           }
         }
       }
       container chassis-high-availability-default-srg-info {
         description "Displays high-availability services redundancy group 0 info";
         leaf current-state {
           type string;
           description "SRG 0 current state";
         }
         leaf peer-id {
           type int32;
           description "Peer identifier";
         }
         leaf node-priority {
           type int32;
           description "Node-priority";
         }
         leaf peer-domain-id {
           type int32;
           description "Peer-domain-id";
         }
         list srg-peer-domain-peer-id-info {
           description "Idl peer node Id";
           leaf idl-peer-id {
             type int32;
             description "IDL Peer identifier";
           }
         }
         container high-availability-srg-signal-rt-info {
           description "  SRG Signal route Info";
           container ha-srg-signal-rt-list {
             description "Display each signal route information";
             leaf ha-srg-signal-rt-type {
               type string;
               description "  SRG  Signal route type";
             }
             leaf ha-srg-signal-rt-ipaddr {
               type string;
               description "IP address configured as SRG active signal route";
             }
             leaf ha-srg-signal-rt-rt {
               type string;
               description "Routing table configured for active signal route";
             }
             leaf ha-srg-signal-rt-status {
               type string;
               description " SRG signal Route installation status";
             }
           }
         }
         list chassis-high-availability-shutdown-interface {
           description "Display high-availability shutdown interface list";
           leaf high-availability-shutdown-interface-name {
             type string;
             description "Interface name for monitoring";
           }
         }
         container chassis-high-availability-srg-ipmon {
           description "SRG IP monitoring Info";
           leaf ha-srg-ipmon-status {
             type string;
             description "SRG overall IP-monitoring status";
           }
           container chassis-high-availability-srg-ipmon-list {
             description " Display each IP monitoring entry";
             leaf ha-srg-ipmon-dst-ipaddr {
               type string;
               description "Destination IP address configured for HA ip-monitoring";
             }
             leaf ha-srg-ipmon-rt {
               type string;
               description "Routing instance configured for HA ip-monitoring";
             }
             leaf ha-ipmon-status {
               type string;
               description "HA ip-monitoring status";
             }
             leaf ha-srg-ipmon-reason {
               type string;
               description "HA ip-monitoring failure reason";
             }
           }
         }
         container chassis-high-availability-srg-bfdmon {
           description " SRG BFD mon information ";
           leaf ha-srg-bfdmon-status {
             type string;
             description "HA overall bfd-monitoring status";
           }
           container chassis-high-availability-srg-bfdmon-list {
             description " Display each BFD mon entry Information";
             leaf ha-srg-bfdmon-src-ipaddr {
               type string;
               description "Source IP address configured for HA bfd-monitoring";
             }
             leaf ha-srg-bfdmon-dst-ipaddr {
               type string;
               description "Destination IP address configured for HA bfd-monitoring";
             }
             leaf ha-srg-bfdmon-rt {
               type string;
               description "Routing instance configured for HA bfd-monitoring";
             }
             leaf ha-srg-bfdmon-type {
               type string;
               description "HA bfd-monitoring type";
             }
             leaf ha-srg-bfdmon-ifl-name {
               type string;
               description "HA bfd-monitoring IFL name";
             }
             leaf ha-srg-bfdmon-state {
               type string;
               description "HA bfd-monitoring state";
             }
           }
         }
         container chassis-high-availability-srg-ifmon {
           description "SRG Interface monitoring Info";
           leaf ha-srg-ifmon-status {
             type string;
             description "HA overall Interface-monitoring status";
           }
           container chassis-high-availability-srg-ifmon-list {
             description " Display each Interface monitoring entry";
             leaf ha-srg-ifmon-if-name {
               type string;
               description "HA Interface-monitoring IF name";
             }
             leaf ha-srg-ifmon-state {
               type string;
               description "HA Interface-monitoring state";
             }
           }
         }
         container chassis-high-availability-srg-mon-info {
           description "SRG global threshold info";
           leaf ha-srg-mon-status {
             type string;
             description "SRG monitor status";
           }
           leaf ha-srg-mon-threshold {
             type int32;
             description "SRG monitor threshold";
           }
           leaf ha-srg-mon-weight {
             type int32;
             description "SRG monitor weight";
           }
           leaf ha-srg-mon-failed-objects {
             type int32;
             description "SRG monitor failed objects";
           }
         }
         container chassis-high-availability-srg-obj-info {
           description "SRG monitor-object info";
           leaf ha-srg-obj-name {
             type string;
             description "SRG monitor object name";
           }
           leaf ha-srg-obj-status {
             type string;
             description "SRG monitor object status";
           }
           leaf ha-srg-obj-entries {
             type string;
             description "SRG monitor object monitored entries";
           }
           leaf ha-srg-obj-failure {
             type string;
             description "SRG monitor object monitored failures";
           }
           leaf ha-srg-obj-threshold {
             type int32;
             description "SRG monitor object threshold";
           }
           leaf ha-srg-obj-weight {
             type int32;
             description "SRG monitor object current weight";
           }
         }
         container chassis-high-availability-srg-obj-ipmon {
           description "SRG monitor object IP monitoring Info";
           leaf ha-srg-obj-ipmon-threshold {
             type int32;
             description "SRG monitor object IP-monitoring threshold";
           }
           leaf ha-srg-obj-ipmon-weight {
             type int32;
             description "SRG monitor object IP-monitoring weight";
           }
           leaf ha-srg-obj-ipmon-status {
             type string;
             description "SRG monitor object IP-monitoring global status";
           }
           container chassis-high-availability-srg-obj-ipmon-list {
             description " Display each monitor object IP monitoring entry status";
             leaf ha-srg-obj-ipmon-entry-status {
               type string;
               description "HA SRG monitor object ip-monitoring state";
             }
             leaf ha-srg-obj-ipmon-entry-weight {
               type int32;
               description "HA SRG monitor object ip-monitoring weight";
             }
             leaf ha-srg-obj-ipmon-entry-dst-ipaddr {
               type string;
               description "Destination IP address configured for HA ip-monitoring";
             }
           }
         }
         container chassis-high-availability-srg-obj-ipmon-detail {
           description "SRG monitor object IP monitoring detail Info";
           container chassis-high-availability-srg-ipmon-list {
             description " Display each IP monitoring entry";
             leaf ha-srg-ipmon-dst-ipaddr {
               type string;
               description "Destination IP address configured for HA ip-monitoring";
             }
             leaf ha-srg-ipmon-rt {
               type string;
               description "Routing instance configured for HA ip-monitoring";
             }
             leaf ha-ipmon-status {
               type string;
               description "HA ip-monitoring status";
             }
             leaf ha-srg-ipmon-reason {
               type string;
               description "HA ip-monitoring failure reason";
             }
           }
         }
         container chassis-high-availability-srg-obj-bfdmon {
           description "SRG monitor object BFD monitoring Info";
           leaf ha-srg-obj-bfdmon-threshold {
             type int32;
             description "SRG monitor object BFD-monitoring threshold";
           }
           leaf ha-srg-obj-bfdmon-weight {
             type int32;
             description "SRG monitor object BFD-monitoring weight";
           }
           leaf ha-srg-obj-bfdmon-status {
             type string;
             description "SRG monitor object BFD-monitoring global status";
           }
           container chassis-high-availability-srg-obj-bfdmon-list {
             description "Display each monitor object BFD monitoring entry status";
             leaf ha-srg-obj-bfdmon-entry-status {
               type string;
               description "HA SRG monitor object BFD-monitoring state";
             }
             leaf ha-srg-obj-bfdmon-entry-weight {
               type int32;
               description "HA SRG monitor object BFD-monitoring weight";
             }
             leaf ha-srg-obj-bfdmon-entry-dst-bfdaddr {
               type string;
               description "Destination BFD address configured for HA BFD-monitoring";
             }
           }
         }
         container chassis-high-availability-srg-obj-bfdmon-detail {
           description "SRG monitor object BFD mon information ";
           container chassis-high-availability-srg-bfdmon-list {
             description " Display each BFD mon entry Information";
             leaf ha-srg-bfdmon-src-ipaddr {
               type string;
               description "Source IP address configured for HA bfd-monitoring";
             }
             leaf ha-srg-bfdmon-dst-ipaddr {
               type string;
               description "Destination IP address configured for HA bfd-monitoring";
             }
             leaf ha-srg-bfdmon-rt {
               type string;
               description "Routing instance configured for HA bfd-monitoring";
             }
             leaf ha-srg-bfdmon-type {
               type string;
               description "HA bfd-monitoring type";
             }
             leaf ha-srg-bfdmon-ifl-name {
               type string;
               description "HA bfd-monitoring IFL name";
             }
             leaf ha-srg-bfdmon-state {
               type string;
               description "HA bfd-monitoring state";
             }
           }
         }
         container chassis-high-availability-srg-obj-ifmon {
           description "SRG monitor object IF monitoring Info";
           leaf ha-srg-obj-ifmon-threshold {
             type int32;
             description "SRG monitor object IF-monitoring threshold";
           }
           leaf ha-srg-obj-ifmon-weight {
             type int32;
             description "SRG monitor object IF-monitoring current weight";
           }
           leaf ha-srg-ifmon-status {
             type string;
             description "HA overall Interface-monitoring status";
           }
           container chassis-high-availability-srg-obj-ifmon-list {
             description "Display each monitor object IF monitoring entry status";
             leaf ha-srg-ifmon-entry-status {
               type string;
               description "HA SRG monitor object IF-monitoring entry status";
             }
             leaf ha-srg-obj-ifmon-entry-weight {
               type int32;
               description "HA SRG monitor object IF-monitoring entry weight";
             }
             leaf ha-srg-ifmon-if-name {
               type string;
               description "HA Interface-monitoring IF name";
             }
           }
         }
       }
     }
     list chassis-high-availability-peer-info {
       description "Displays high-availability peer related info";
       leaf high-availability-peer-desc {
         type string;
         description "Peer description";
       }
       leaf high-availability-peer-id {
         type int32;
         description "Peer identifier that is configured";
       }
       leaf high-availability-peer-ip-address {
         type jt:ipaddr;
         description "Peer remote IPv4 address that is configured";
       }
       leaf-list high-availability-local-interface {
         type string;
         description "Local interface";
       }
       leaf high-availability-peer-rt-instance {
         type string;
         description "Routing Instance name for HA peer";
       }
       leaf high-availability-peer-encryption-status {
         type string;
         description "Encryption status of the current node";
       }
       leaf high-availability-peer-bfd-status {
         type string;
         description "BFD Status of the current node";
       }
       leaf high-availability-peer-detect-time {
         type string;
         description "Configured Peer BFD detection time";
       }
       leaf cold-sync-status {
         type string;
         description "Cold synchronization status";
       }
       leaf peer-hw-incompatible {
         type string;
         description "Peer hardware compatible status";
       }
       leaf high-availability-peer-fwd-ip-address {
         type jt:ipaddr;
         description "Peer forwarding remote IP address";
       }
       leaf high-availability-local-fwd-interface {
         type string;
         description "Local forwarding interface";
       }
       leaf high-availability-peer-fwd-bfd-status {
         type string;
         description "BFD forwarding status of the current node";
       }
     }
     container chassis-high-availability-default-srg-info {
       description "Displays high-availability services redundancy group 0 info";
       leaf current-state {
         type string;
         description "SRG 0 current state";
       }
       leaf peer-id {
         type int32;
         description "Peer identifier";
       }
       leaf node-priority {
         type int32;
         description "Node-priority";
       }
       leaf peer-domain-id {
         type int32;
         description "Peer-domain-id";
       }
       list srg-peer-domain-peer-id-info {
         description "Idl peer node Id";
         leaf idl-peer-id {
           type int32;
           description "IDL Peer identifier";
         }
       }
       container high-availability-srg-signal-rt-info {
         description "  SRG Signal route Info";
         container ha-srg-signal-rt-list {
           description "Display each signal route information";
           leaf ha-srg-signal-rt-type {
             type string;
             description "  SRG  Signal route type";
           }
           leaf ha-srg-signal-rt-ipaddr {
             type string;
             description "IP address configured as SRG active signal route";
           }
           leaf ha-srg-signal-rt-rt {
             type string;
             description "Routing table configured for active signal route";
           }
           leaf ha-srg-signal-rt-status {
             type string;
             description " SRG signal Route installation status";
           }
         }
       }
       list chassis-high-availability-shutdown-interface {
         description "Display high-availability shutdown interface list";
         leaf high-availability-shutdown-interface-name {
           type string;
           description "Interface name for monitoring";
         }
       }
       container chassis-high-availability-srg-ipmon {
         description "SRG IP monitoring Info";
         leaf ha-srg-ipmon-status {
           type string;
           description "SRG overall IP-monitoring status";
         }
         container chassis-high-availability-srg-ipmon-list {
           description " Display each IP monitoring entry";
           leaf ha-srg-ipmon-dst-ipaddr {
             type string;
             description "Destination IP address configured for HA ip-monitoring";
           }
           leaf ha-srg-ipmon-rt {
             type string;
             description "Routing instance configured for HA ip-monitoring";
           }
           leaf ha-ipmon-status {
             type string;
             description "HA ip-monitoring status";
           }
           leaf ha-srg-ipmon-reason {
             type string;
             description "HA ip-monitoring failure reason";
           }
         }
       }
       container chassis-high-availability-srg-bfdmon {
         description " SRG BFD mon information ";
         leaf ha-srg-bfdmon-status {
           type string;
           description "HA overall bfd-monitoring status";
         }
         container chassis-high-availability-srg-bfdmon-list {
           description " Display each BFD mon entry Information";
           leaf ha-srg-bfdmon-src-ipaddr {
             type string;
             description "Source IP address configured for HA bfd-monitoring";
           }
           leaf ha-srg-bfdmon-dst-ipaddr {
             type string;
             description "Destination IP address configured for HA bfd-monitoring";
           }
           leaf ha-srg-bfdmon-rt {
             type string;
             description "Routing instance configured for HA bfd-monitoring";
           }
           leaf ha-srg-bfdmon-type {
             type string;
             description "HA bfd-monitoring type";
           }
           leaf ha-srg-bfdmon-ifl-name {
             type string;
             description "HA bfd-monitoring IFL name";
           }
           leaf ha-srg-bfdmon-state {
             type string;
             description "HA bfd-monitoring state";
           }
         }
       }
       container chassis-high-availability-srg-ifmon {
         description "SRG Interface monitoring Info";
         leaf ha-srg-ifmon-status {
           type string;
           description "HA overall Interface-monitoring status";
         }
         container chassis-high-availability-srg-ifmon-list {
           description " Display each Interface monitoring entry";
           leaf ha-srg-ifmon-if-name {
             type string;
             description "HA Interface-monitoring IF name";
           }
           leaf ha-srg-ifmon-state {
             type string;
             description "HA Interface-monitoring state";
           }
         }
       }
       container chassis-high-availability-srg-mon-info {
         description "SRG global threshold info";
         leaf ha-srg-mon-status {
           type string;
           description "SRG monitor status";
         }
         leaf ha-srg-mon-threshold {
           type int32;
           description "SRG monitor threshold";
         }
         leaf ha-srg-mon-weight {
           type int32;
           description "SRG monitor weight";
         }
         leaf ha-srg-mon-failed-objects {
           type int32;
           description "SRG monitor failed objects";
         }
       }
       container chassis-high-availability-srg-obj-info {
         description "SRG monitor-object info";
         leaf ha-srg-obj-name {
           type string;
           description "SRG monitor object name";
         }
         leaf ha-srg-obj-status {
           type string;
           description "SRG monitor object status";
         }
         leaf ha-srg-obj-entries {
           type string;
           description "SRG monitor object monitored entries";
         }
         leaf ha-srg-obj-failure {
           type string;
           description "SRG monitor object monitored failures";
         }
         leaf ha-srg-obj-threshold {
           type int32;
           description "SRG monitor object threshold";
         }
         leaf ha-srg-obj-weight {
           type int32;
           description "SRG monitor object current weight";
         }
       }
       container chassis-high-availability-srg-obj-ipmon {
         description "SRG monitor object IP monitoring Info";
         leaf ha-srg-obj-ipmon-threshold {
           type int32;
           description "SRG monitor object IP-monitoring threshold";
         }
         leaf ha-srg-obj-ipmon-weight {
           type int32;
           description "SRG monitor object IP-monitoring weight";
         }
         leaf ha-srg-obj-ipmon-status {
           type string;
           description "SRG monitor object IP-monitoring global status";
         }
         container chassis-high-availability-srg-obj-ipmon-list {
           description " Display each monitor object IP monitoring entry status";
           leaf ha-srg-obj-ipmon-entry-status {
             type string;
             description "HA SRG monitor object ip-monitoring state";
           }
           leaf ha-srg-obj-ipmon-entry-weight {
             type int32;
             description "HA SRG monitor object ip-monitoring weight";
           }
           leaf ha-srg-obj-ipmon-entry-dst-ipaddr {
             type string;
             description "Destination IP address configured for HA ip-monitoring";
           }
         }
       }
       container chassis-high-availability-srg-obj-ipmon-detail {
         description "SRG monitor object IP monitoring detail Info";
         container chassis-high-availability-srg-ipmon-list {
           description " Display each IP monitoring entry";
           leaf ha-srg-ipmon-dst-ipaddr {
             type string;
             description "Destination IP address configured for HA ip-monitoring";
           }
           leaf ha-srg-ipmon-rt {
             type string;
             description "Routing instance configured for HA ip-monitoring";
           }
           leaf ha-ipmon-status {
             type string;
             description "HA ip-monitoring status";
           }
           leaf ha-srg-ipmon-reason {
             type string;
             description "HA ip-monitoring failure reason";
           }
         }
       }
       container chassis-high-availability-srg-obj-bfdmon {
         description "SRG monitor object BFD monitoring Info";
         leaf ha-srg-obj-bfdmon-threshold {
           type int32;
           description "SRG monitor object BFD-monitoring threshold";
         }
         leaf ha-srg-obj-bfdmon-weight {
           type int32;
           description "SRG monitor object BFD-monitoring weight";
         }
         leaf ha-srg-obj-bfdmon-status {
           type string;
           description "SRG monitor object BFD-monitoring global status";
         }
         container chassis-high-availability-srg-obj-bfdmon-list {
           description "Display each monitor object BFD monitoring entry status";
           leaf ha-srg-obj-bfdmon-entry-status {
             type string;
             description "HA SRG monitor object BFD-monitoring state";
           }
           leaf ha-srg-obj-bfdmon-entry-weight {
             type int32;
             description "HA SRG monitor object BFD-monitoring weight";
           }
           leaf ha-srg-obj-bfdmon-entry-dst-bfdaddr {
             type string;
             description "Destination BFD address configured for HA BFD-monitoring";
           }
         }
       }
       container chassis-high-availability-srg-obj-bfdmon-detail {
         description "SRG monitor object BFD mon information ";
         container chassis-high-availability-srg-bfdmon-list {
           description " Display each BFD mon entry Information";
           leaf ha-srg-bfdmon-src-ipaddr {
             type string;
             description "Source IP address configured for HA bfd-monitoring";
           }
           leaf ha-srg-bfdmon-dst-ipaddr {
             type string;
             description "Destination IP address configured for HA bfd-monitoring";
           }
           leaf ha-srg-bfdmon-rt {
             type string;
             description "Routing instance configured for HA bfd-monitoring";
           }
           leaf ha-srg-bfdmon-type {
             type string;
             description "HA bfd-monitoring type";
           }
           leaf ha-srg-bfdmon-ifl-name {
             type string;
             description "HA bfd-monitoring IFL name";
           }
           leaf ha-srg-bfdmon-state {
             type string;
             description "HA bfd-monitoring state";
           }
         }
       }
       container chassis-high-availability-srg-obj-ifmon {
         description "SRG monitor object IF monitoring Info";
         leaf ha-srg-obj-ifmon-threshold {
           type int32;
           description "SRG monitor object IF-monitoring threshold";
         }
         leaf ha-srg-obj-ifmon-weight {
           type int32;
           description "SRG monitor object IF-monitoring current weight";
         }
         leaf ha-srg-ifmon-status {
           type string;
           description "HA overall Interface-monitoring status";
         }
         container chassis-high-availability-srg-obj-ifmon-list {
           description "Display each monitor object IF monitoring entry status";
           leaf ha-srg-ifmon-entry-status {
             type string;
             description "HA SRG monitor object IF-monitoring entry status";
           }
           leaf ha-srg-obj-ifmon-entry-weight {
             type int32;
             description "HA SRG monitor object IF-monitoring entry weight";
           }
           leaf ha-srg-ifmon-if-name {
             type string;
             description "HA Interface-monitoring IF name";
           }
         }
       }
     }
     container chassis-high-availability-srg-info {
       description "Displays high-availability services redundancy group info";
       container chassis-high-availability-srg-info-list {
         description "Displays each services redundancy group info";
         leaf srg-id {
           type int32;
           description "Current services redundancy group identifier";
         }
         leaf deployment-type {
           type string;
           description "Deployment Type";
         }
         leaf node-role {
           type string;
           description "Local node role";
         }
         leaf activeness-priority {
           type int32;
           description "SRG activeness priority";
         }
         leaf preemption {
           type string;
           description "Preemption enable flag Status";
         }
         leaf process-pkt-in-bkp-state {
           type string;
           description "SRG backup state pkt processing info";
         }
         leaf control-plane {
           type string;
           description "Control plane status";
         }
         leaf system-integrity-check {
           type string;
           description "Status of system integrity check";
         }
         leaf failure-events {
           type string;
           description "List of failure events";
         }
         leaf peer-id {
           type int32;
           description "Peer identifier";
         }
         leaf peer-node-role {
           type string;
           description "Peer node role";
         }
         leaf health-status {
           type string;
           description "Peer health status";
         }
         leaf failover-readiness {
           type string;
           description "SRG failover readiness";
         }
       }
     }
   }
   grouping chassis-high-availability-detail-information-block {
     container chassis-mnha-node-level-info {
       description "Display high-availability node level information";
       leaf node-status {
         type string;
         description "Status of the current node";
       }
       leaf local-domain-id {
         type int32;
         description "Local-domain-id";
       }
       leaf local-id {
         type int32;
         description "Local node identifier";
       }
       leaf local-ip {
         type jt:ipaddr;
         description "Local node IPv4 address";
       }
       leaf local-fwd-ip {
         type jt:ipaddr;
         description "Local Forwarding IP address";
       }
     }
     container chassis-mnha-local-domain-info-detail {
       description "Displays mnha local domain related info";
       leaf local-ip {
         type jt:ipaddr;
         description "Local node IPv4 address";
       }
       list high-availability-hw-upgrade-events {
         description "List of HA hardware upgrade events";
         leaf-list high-availability-hw-upgrade-event {
           type string;
           description "Recorded HA hardware upgrade event";
         }
       }
       list chassis-high-availability-shutdown-interface {
         description "Display high-availability shutdown interface list";
         leaf high-availability-shutdown-interface-name {
           type string;
           description "Interface name for monitoring";
         }
       }
       container chassis-mnha-icl-peer-info {
         description "Displays mnha icl peer related info";
         leaf high-availability-peer-desc {
           type string;
           description "Peer description";
         }
         leaf peer-domain-id {
           type int32;
           description "Peer-domain-id";
         }
         leaf high-availability-peer-id {
           type int32;
           description "Peer identifier that is configured";
         }
         leaf high-availability-peer-ip-address {
           type jt:ipaddr;
           description "Peer remote IPv4 address that is configured";
         }
         leaf-list high-availability-local-interface {
           type string;
           description "Local interface";
         }
         leaf high-availability-peer-rt-instance {
           type string;
           description "Routing Instance name for HA peer";
         }
         leaf high-availability-peer-encryption-status {
           type string;
           description "Encryption status of the current node";
         }
         leaf high-availability-peer-bfd-status {
           type string;
           description "BFD Status of the current node";
         }
         leaf cold-sync-status {
           type string;
           description "Cold synchronization status";
         }
         leaf peer-hw-incompatible {
           type string;
           description "Peer hardware compatible status";
         }
         leaf peer-internal-interface {
           type string;
           description "Peer internal interface";
         }
         leaf peer-internal-local-ip {
           type jt:ipaddr;
           description "Internal local IPv4 address";
         }
         leaf peer-internal-peer-ip {
           type jt:ipaddr;
           description "Internal peer IPv4 address";
         }
         leaf peer-internal-routing-instance {
           type string;
           description "Peer internal routing instance";
         }
         leaf high-availability-peer-detect-time {
           type string;
           description "Configured Peer BFD detection time";
         }
         leaf srg0-cold-sync-status {
           type string;
           description "SRG0 cold sync status";
         }
         container chassis-mnha-local-node-idl-info {
           description "Displays high-availability local node IDL BFD and CS state";
           leaf states-from-domain-id {
             type int32;
             description "States from domain id";
           }
           leaf states-from-node-id {
             type int32;
             description "States from node id";
           }
           leaf domain-id {
             type int32;
             description "Domain-id";
           }
           leaf peer-id {
             type int32;
             description "Peer identifier";
           }
           leaf conn-state {
             type string;
             description "Conn state";
           }
           leaf rtt-result {
             type string;
             description "RTT result";
           }
           leaf cold-sync-status {
             type string;
             description "Cold synchronization status";
           }
           leaf srg0-idl-status {
             type string;
             description "SRG0 idl status";
           }
         }
         container chassis-mnha-peer-node-icl-info {
           description "Displays high-availability icl info";
           leaf states-from-domain-id {
             type int32;
             description "States from domain id";
           }
           leaf states-from-node-id {
             type int32;
             description "States from node id";
           }
           leaf icl-conn-state {
             type string;
             description "ICL Conn state";
           }
           leaf cold-sync-status {
             type string;
             description "Cold synchronization status";
           }
         }
         container chassis-mnha-peer-node-idl-info {
           description "Displays high-availability peer node IDL BFD and CS state";
           leaf states-from-domain-id {
             type int32;
             description "States from domain id";
           }
           leaf states-from-node-id {
             type int32;
             description "States from node id";
           }
           leaf domain-id {
             type int32;
             description "Domain-id";
           }
           leaf peer-id {
             type int32;
             description "Peer identifier";
           }
           leaf conn-state {
             type string;
             description "Conn state";
           }
           leaf rtt-result {
             type string;
             description "RTT result";
           }
           leaf cold-sync-status {
             type string;
             description "Cold synchronization status";
           }
           leaf srg0-idl-status {
             type string;
             description "SRG0 idl status";
           }
         }
         list high-availability-peer-packet-stats {
           description "Peer Packet Stats";
           leaf packet-send-err-cnt {
             type int32;
             description "Peer packet send error cnt";
           }
           leaf packet-recv-err-cnt {
             type int32;
             description "Peer packet recv error cnt";
           }
           list peer-packet-send-rcv-stats {
             description "Peer Packet Send receive Stats";
             list peer-packet-stats-list {
               description "Stats for each peer packet type";
               leaf peer-packet-type {
                 type string;
                 description "Peer packet Type";
               }
               leaf peer-packet-send-cnt {
                 type int32;
                 description "Peer packet sent count";
               }
               leaf peer-packet-rcv-cnt {
                 type int32;
                 description "Peer packet rcv cnt";
               }
             }
           }
         }
       }
       container cold-synchronization-monitoring-information {
         description "Cold sync monitoring related information";
         leaf-list cold-synchronization-progress {
           type string;
           description "Cold synchronization progress";
         }
         container cold-synchronization-status-information {
           description "Cold synchronization related status information";
           leaf cold-synchronization-completed {
             type string;
             description "List of PFE's which have completed cold synchnronization";
           }
           leaf cold-synchronization-not-completed {
             type string;
             description "List of PFE's which have failed cold synchnronization";
           }
           leaf cold-synchronization-unknown {
             type string;
             description "List of PFE's for which cold synchnronization statusupdate is not received";
           }
           leaf cold-synchronization-weight {
             type uint32;
             description "Current Cold Synchronization weight";
           }
         }
         container cold-synchronization-statistics {
           description "Cold synchronization statistics";
           leaf current-cold-synchronization-completed {
             type uint32;
             description "Cold synchronization completed for current jsrpd session";
           }
           leaf current-cold-synchronization-failed {
             type uint32;
             description "Cold synchronization failed for current jsrpd session";
           }
           list cold-synchronization-pfe-statistics {
             description "Cold synchroniizaton statistics for each PFE";
             leaf pfe-name {
               type string;
               description "Name of the PFE";
             }
             leaf cold-synchronization-pfe-completed {
               type uint32;
               description "Cold synchronization complete instances for a given PFE";
             }
             leaf cold-synchronization-pfe-failed {
               type uint32;
               description "Cold synchronization complete instances for a given PFE";
             }
           }
         }
         container cold-synchronization-events {
           description "List of cold synchronization events";
           leaf-list cold-synchronization-event {
             type string;
             description "Recorded cold sync complete/failure for a PFE";
           }
         }
       }
       container spu-monitoring-information {
         description "SPU monitoring related information";
         container spu-monitoring-status {
           description "SPU monitoring related status information";
           leaf spu-monitoring-state {
             type string;
             description "SPU current monitoring mode Disabled/Enabled/Active";
           }
           leaf spu-monitoring-weight {
             type uint32;
             description "Current SPU monitoring weight";
           }
           list spu-monitoring-spu-state {
             description "Each SPU current state";
             container spu-monitoring-spu-state-list {
               description "Each SPU current state in list";
               leaf pfe-name {
                 type string;
                 description "Name of the PFE";
               }
               leaf pic-state {
                 type string;
                 description "State of each PIC";
               }
             }
           }
         }
         container spu-monitoring-statistics {
           description "Detailed statistics of SPU monitoring";
           leaf spu-up-count {
             type uint32;
             description "Number of SPUs that are up";
           }
           leaf spu-down-count {
             type uint32;
             description "Number of SPUs that are down";
           }
           leaf npc-up-count {
             type uint32;
             description "Number of NPCs that are up";
           }
           leaf npc-down-count {
             type uint32;
             description "Number of NPCs that are down";
           }
           leaf chinfo-blob-error-count {
             type uint32;
             description "Error count reading chinfo blob";
           }
         }
         container spu-monitoring-events {
           description "List of SPU monitoring events";
           leaf-list spu-monitoring-event {
             type string;
             description "Recorded SPU monitoring events";
           }
         }
       }
       list loopback-information {
         description "Loopback information";
         container loopback-information-list {
           description "Display loopback information list";
           leaf pfe-name {
             type string;
             description "Name of the PFE";
           }
           leaf loopback-status {
             type string;
             description "Loopback status of each PIC";
           }
           leaf nexthop-status {
             type string;
             description "Nexthop status of each PIC";
           }
           leaf mbuf-status {
             type string;
             description "Mbuf status of each PIC";
           }
         }
       }
       container high-availability-hardware-monitoring-information {
         description "Displays complete high-availability hardware monitoring information for debugging purposes";
         container high-availability-hardware-monitoring-status-information {
           leaf high-availability-hardware-monitoring-activation-status {
             type string;
             description "Hardware monitoring is enabled/disabled";
           }
           leaf high-availability-hardware-monitoring-ctrl-plane-errors {
             type int32;
             description "Hardware monitoring Ctrl plane errors";
           }
           leaf high-availability-hardware-monitoring-data-plane-errors {
             type int32;
             description "Hardware monitoring Data plane errors";
           }
         }
       }
       container chassis-high-availability-default-srg-info {
         description "Displays high-availability services redundancy group 0 info";
         leaf current-state {
           type string;
           description "SRG 0 current state";
         }
         leaf peer-id {
           type int32;
           description "Peer identifier";
         }
         leaf node-priority {
           type int32;
           description "Node-priority";
         }
         leaf peer-domain-id {
           type int32;
           description "Peer-domain-id";
         }
         list srg-peer-domain-peer-id-info {
           description "Idl peer node Id";
           leaf idl-peer-id {
             type int32;
             description "IDL Peer identifier";
           }
         }
         container high-availability-srg-signal-rt-info {
           description "  SRG Signal route Info";
           container ha-srg-signal-rt-list {
             description "Display each signal route information";
             leaf ha-srg-signal-rt-type {
               type string;
               description "  SRG  Signal route type";
             }
             leaf ha-srg-signal-rt-ipaddr {
               type string;
               description "IP address configured as SRG active signal route";
             }
             leaf ha-srg-signal-rt-rt {
               type string;
               description "Routing table configured for active signal route";
             }
             leaf ha-srg-signal-rt-status {
               type string;
               description " SRG signal Route installation status";
             }
           }
         }
         list chassis-high-availability-shutdown-interface {
           description "Display high-availability shutdown interface list";
           leaf high-availability-shutdown-interface-name {
             type string;
             description "Interface name for monitoring";
           }
         }
         container chassis-high-availability-srg-ipmon {
           description "SRG IP monitoring Info";
           leaf ha-srg-ipmon-status {
             type string;
             description "SRG overall IP-monitoring status";
           }
           container chassis-high-availability-srg-ipmon-list {
             description " Display each IP monitoring entry";
             leaf ha-srg-ipmon-dst-ipaddr {
               type string;
               description "Destination IP address configured for HA ip-monitoring";
             }
             leaf ha-srg-ipmon-rt {
               type string;
               description "Routing instance configured for HA ip-monitoring";
             }
             leaf ha-ipmon-status {
               type string;
               description "HA ip-monitoring status";
             }
             leaf ha-srg-ipmon-reason {
               type string;
               description "HA ip-monitoring failure reason";
             }
           }
         }
         container chassis-high-availability-srg-bfdmon {
           description " SRG BFD mon information ";
           leaf ha-srg-bfdmon-status {
             type string;
             description "HA overall bfd-monitoring status";
           }
           container chassis-high-availability-srg-bfdmon-list {
             description " Display each BFD mon entry Information";
             leaf ha-srg-bfdmon-src-ipaddr {
               type string;
               description "Source IP address configured for HA bfd-monitoring";
             }
             leaf ha-srg-bfdmon-dst-ipaddr {
               type string;
               description "Destination IP address configured for HA bfd-monitoring";
             }
             leaf ha-srg-bfdmon-rt {
               type string;
               description "Routing instance configured for HA bfd-monitoring";
             }
             leaf ha-srg-bfdmon-type {
               type string;
               description "HA bfd-monitoring type";
             }
             leaf ha-srg-bfdmon-ifl-name {
               type string;
               description "HA bfd-monitoring IFL name";
             }
             leaf ha-srg-bfdmon-state {
               type string;
               description "HA bfd-monitoring state";
             }
           }
         }
         container chassis-high-availability-srg-ifmon {
           description "SRG Interface monitoring Info";
           leaf ha-srg-ifmon-status {
             type string;
             description "HA overall Interface-monitoring status";
           }
           container chassis-high-availability-srg-ifmon-list {
             description " Display each Interface monitoring entry";
             leaf ha-srg-ifmon-if-name {
               type string;
               description "HA Interface-monitoring IF name";
             }
             leaf ha-srg-ifmon-state {
               type string;
               description "HA Interface-monitoring state";
             }
           }
         }
         container chassis-high-availability-srg-mon-info {
           description "SRG global threshold info";
           leaf ha-srg-mon-status {
             type string;
             description "SRG monitor status";
           }
           leaf ha-srg-mon-threshold {
             type int32;
             description "SRG monitor threshold";
           }
           leaf ha-srg-mon-weight {
             type int32;
             description "SRG monitor weight";
           }
           leaf ha-srg-mon-failed-objects {
             type int32;
             description "SRG monitor failed objects";
           }
         }
         container chassis-high-availability-srg-obj-info {
           description "SRG monitor-object info";
           leaf ha-srg-obj-name {
             type string;
             description "SRG monitor object name";
           }
           leaf ha-srg-obj-status {
             type string;
             description "SRG monitor object status";
           }
           leaf ha-srg-obj-entries {
             type string;
             description "SRG monitor object monitored entries";
           }
           leaf ha-srg-obj-failure {
             type string;
             description "SRG monitor object monitored failures";
           }
           leaf ha-srg-obj-threshold {
             type int32;
             description "SRG monitor object threshold";
           }
           leaf ha-srg-obj-weight {
             type int32;
             description "SRG monitor object current weight";
           }
         }
         container chassis-high-availability-srg-obj-ipmon {
           description "SRG monitor object IP monitoring Info";
           leaf ha-srg-obj-ipmon-threshold {
             type int32;
             description "SRG monitor object IP-monitoring threshold";
           }
           leaf ha-srg-obj-ipmon-weight {
             type int32;
             description "SRG monitor object IP-monitoring weight";
           }
           leaf ha-srg-obj-ipmon-status {
             type string;
             description "SRG monitor object IP-monitoring global status";
           }
           container chassis-high-availability-srg-obj-ipmon-list {
             description " Display each monitor object IP monitoring entry status";
             leaf ha-srg-obj-ipmon-entry-status {
               type string;
               description "HA SRG monitor object ip-monitoring state";
             }
             leaf ha-srg-obj-ipmon-entry-weight {
               type int32;
               description "HA SRG monitor object ip-monitoring weight";
             }
             leaf ha-srg-obj-ipmon-entry-dst-ipaddr {
               type string;
               description "Destination IP address configured for HA ip-monitoring";
             }
           }
         }
         container chassis-high-availability-srg-obj-ipmon-detail {
           description "SRG monitor object IP monitoring detail Info";
           container chassis-high-availability-srg-ipmon-list {
             description " Display each IP monitoring entry";
             leaf ha-srg-ipmon-dst-ipaddr {
               type string;
               description "Destination IP address configured for HA ip-monitoring";
             }
             leaf ha-srg-ipmon-rt {
               type string;
               description "Routing instance configured for HA ip-monitoring";
             }
             leaf ha-ipmon-status {
               type string;
               description "HA ip-monitoring status";
             }
             leaf ha-srg-ipmon-reason {
               type string;
               description "HA ip-monitoring failure reason";
             }
           }
         }
         container chassis-high-availability-srg-obj-bfdmon {
           description "SRG monitor object BFD monitoring Info";
           leaf ha-srg-obj-bfdmon-threshold {
             type int32;
             description "SRG monitor object BFD-monitoring threshold";
           }
           leaf ha-srg-obj-bfdmon-weight {
             type int32;
             description "SRG monitor object BFD-monitoring weight";
           }
           leaf ha-srg-obj-bfdmon-status {
             type string;
             description "SRG monitor object BFD-monitoring global status";
           }
           container chassis-high-availability-srg-obj-bfdmon-list {
             description "Display each monitor object BFD monitoring entry status";
             leaf ha-srg-obj-bfdmon-entry-status {
               type string;
               description "HA SRG monitor object BFD-monitoring state";
             }
             leaf ha-srg-obj-bfdmon-entry-weight {
               type int32;
               description "HA SRG monitor object BFD-monitoring weight";
             }
             leaf ha-srg-obj-bfdmon-entry-dst-bfdaddr {
               type string;
               description "Destination BFD address configured for HA BFD-monitoring";
             }
           }
         }
         container chassis-high-availability-srg-obj-bfdmon-detail {
           description "SRG monitor object BFD mon information ";
           container chassis-high-availability-srg-bfdmon-list {
             description " Display each BFD mon entry Information";
             leaf ha-srg-bfdmon-src-ipaddr {
               type string;
               description "Source IP address configured for HA bfd-monitoring";
             }
             leaf ha-srg-bfdmon-dst-ipaddr {
               type string;
               description "Destination IP address configured for HA bfd-monitoring";
             }
             leaf ha-srg-bfdmon-rt {
               type string;
               description "Routing instance configured for HA bfd-monitoring";
             }
             leaf ha-srg-bfdmon-type {
               type string;
               description "HA bfd-monitoring type";
             }
             leaf ha-srg-bfdmon-ifl-name {
               type string;
               description "HA bfd-monitoring IFL name";
             }
             leaf ha-srg-bfdmon-state {
               type string;
               description "HA bfd-monitoring state";
             }
           }
         }
         container chassis-high-availability-srg-obj-ifmon {
           description "SRG monitor object IF monitoring Info";
           leaf ha-srg-obj-ifmon-threshold {
             type int32;
             description "SRG monitor object IF-monitoring threshold";
           }
           leaf ha-srg-obj-ifmon-weight {
             type int32;
             description "SRG monitor object IF-monitoring current weight";
           }
           leaf ha-srg-ifmon-status {
             type string;
             description "HA overall Interface-monitoring status";
           }
           container chassis-high-availability-srg-obj-ifmon-list {
             description "Display each monitor object IF monitoring entry status";
             leaf ha-srg-ifmon-entry-status {
               type string;
               description "HA SRG monitor object IF-monitoring entry status";
             }
             leaf ha-srg-obj-ifmon-entry-weight {
               type int32;
               description "HA SRG monitor object IF-monitoring entry weight";
             }
             leaf ha-srg-ifmon-if-name {
               type string;
               description "HA Interface-monitoring IF name";
             }
           }
         }
       }
       list chassis-high-availability-srg-info-detail {
         description "Displays high-availability services redundancy group detail info";
         list srg-info-detail {
           leaf srg-id {
             type int32;
             description "Current services redundancy group identifier";
           }
           leaf deployment-type {
             type string;
             description "Deployment Type";
           }
           leaf node-role {
             type string;
             description "Local node role";
           }
           leaf activeness-priority {
             type int32;
             description "SRG activeness priority";
           }
           leaf hold-timer {
             type int32;
             description "SRG hold down timer";
           }
           leaf peer-ids {
             type int32;
             description "List of peer ids";
           }
           leaf process-pkt-in-bkp-state {
             type string;
             description "SRG backup state pkt processing info";
           }
           leaf service-names {
             type string;
             description "SRG service names";
           }
           leaf control-plane {
             type string;
             description "Control plane status";
           }
           leaf system-integrity-check {
             type string;
             description "Status of system integrity check";
           }
           leaf peer-id {
             type int32;
             description "Peer identifier";
           }
           leaf peer-node-role {
             type string;
             description "Peer node role";
           }
           leaf health-status {
             type string;
             description "Peer health status";
           }
           leaf failover-readiness {
             type string;
             description "SRG failover readiness";
           }
           leaf failure-events {
             type string;
             description "List of failure events";
           }
           leaf preempt {
             type string;
             description "Preempt configuration for the redundancy group";
           }
           container high-availability-srg-signal-rt-info {
             description "  SRG Signal route Info";
             container ha-srg-signal-rt-list {
               description "Display each signal route information";
               leaf ha-srg-signal-rt-type {
                 type string;
                 description "  SRG  Signal route type";
               }
               leaf ha-srg-signal-rt-ipaddr {
                 type string;
                 description "IP address configured as SRG active signal route";
               }
               leaf ha-srg-signal-rt-rt {
                 type string;
                 description "Routing table configured for active signal route";
               }
               leaf ha-srg-signal-rt-status {
                 type string;
                 description " SRG signal Route installation status";
               }
             }
           }
           container high-availability-srg-vip-info {
             description "  SRG Virtual IP Info";
             container ha-srg-vip-list {
               description "Display each Virtual IP information";
               leaf ha-srg-vip-index {
                 type string;
                 description "  SRG  Signal Virtual IP Index";
               }
               leaf ha-srg-virtual-ipaddr {
                 type string;
                 description "IP address configured as SRG virtual IP";
               }
               leaf ha-srg-virtual-mac-address {
                 type string;
                 description "MAC address for the virtual IP.";
               }
               leaf ha-srg-vip-if-name {
                 type string;
                 description "Interface for the virtual IP assignment";
               }
               leaf ha-srg-vip-status {
                 type string;
                 description " SRG Virtual IP assignmentstatus";
               }
             }
           }
           list high-availability-srg-state-events {
             description "List of service redundancy group state change events";
             leaf-list high-availability-srg-state-event {
               type string;
               description "Recorded service redundancy group state change event";
             }
           }
           list high-availability-peer-status-events {
             description "List of HA Peer Conn events";
             leaf-list high-availability-peer-status-event {
               type string;
               description "Recorded HA Peer Conn event";
             }
           }
           list high-availability-hw-upgrade-events {
             description "List of HA hardware upgrade events";
             leaf-list high-availability-hw-upgrade-event {
               type string;
               description "Recorded HA hardware upgrade event";
             }
           }
           container chassis-high-availability-srg-probe {
             description "SRG split brain prevention probe info";
             leaf ha-srg-probe-dst-ipaddr {
               type string;
               description "Destination IP address used for probing";
             }
             leaf ha-srg-probe-src-ipaddr {
               type string;
               description "Source IP address used for probing";
             }
             leaf ha-srg-vip-if-name {
               type string;
               description "Interface for the virtual IP assignment";
             }
             leaf ha-srg-probe-rt {
               type string;
               description "Routing instance used for probing";
             }
             leaf ha-srg-probe-type {
               type string;
               description "Probing type";
             }
             leaf ha-probe-interval {
               type int32;
               description "HA probe interval in ms";
             }
             leaf ha-probe-multiplier {
               type int32;
               description "HA probe multiplier";
             }
             leaf ha-probe-status {
               type string;
               description "Probing status";
             }
             leaf ha-probe-result {
               type string;
               description "Probing result";
             }
             leaf ha-srg-probe-fail-reason {
               type string;
               description "Probing failure reason";
             }
           }
           container chassis-high-availability-srg-mon-info {
             description "SRG global threshold info";
             leaf ha-srg-mon-status {
               type string;
               description "SRG monitor status";
             }
             leaf ha-srg-mon-threshold {
               type int32;
               description "SRG monitor threshold";
             }
             leaf ha-srg-mon-weight {
               type int32;
               description "SRG monitor weight";
             }
             leaf ha-srg-mon-failed-objects {
               type int32;
               description "SRG monitor failed objects";
             }
           }
           container chassis-high-availability-srg-obj-info {
             description "SRG monitor-object info";
             leaf ha-srg-obj-name {
               type string;
               description "SRG monitor object name";
             }
             leaf ha-srg-obj-status {
               type string;
               description "SRG monitor object status";
             }
             leaf ha-srg-obj-entries {
               type string;
               description "SRG monitor object monitored entries";
             }
             leaf ha-srg-obj-failure {
               type string;
               description "SRG monitor object monitored failures";
             }
             leaf ha-srg-obj-threshold {
               type int32;
               description "SRG monitor object threshold";
             }
             leaf ha-srg-obj-weight {
               type int32;
               description "SRG monitor object current weight";
             }
           }
           container chassis-high-availability-srg-bfdmon {
             description " SRG BFD mon information ";
             leaf ha-srg-bfdmon-status {
               type string;
               description "HA overall bfd-monitoring status";
             }
             container chassis-high-availability-srg-bfdmon-list {
               description " Display each BFD mon entry Information";
               leaf ha-srg-bfdmon-src-ipaddr {
                 type string;
                 description "Source IP address configured for HA bfd-monitoring";
               }
               leaf ha-srg-bfdmon-dst-ipaddr {
                 type string;
                 description "Destination IP address configured for HA bfd-monitoring";
               }
               leaf ha-srg-bfdmon-rt {
                 type string;
                 description "Routing instance configured for HA bfd-monitoring";
               }
               leaf ha-srg-bfdmon-type {
                 type string;
                 description "HA bfd-monitoring type";
               }
               leaf ha-srg-bfdmon-ifl-name {
                 type string;
                 description "HA bfd-monitoring IFL name";
               }
               leaf ha-srg-bfdmon-state {
                 type string;
                 description "HA bfd-monitoring state";
               }
             }
           }
           list high-availability-bfdmon-status-events {
             description "List of BFD-monitoring status events";
             leaf-list high-availability-bfdmon-status-event {
               type string;
               description "Recorded BFD-monitoring status event";
             }
           }
           container chassis-high-availability-srg-ipmon {
             description "SRG IP monitoring Info";
             leaf ha-srg-ipmon-status {
               type string;
               description "SRG overall IP-monitoring status";
             }
             container chassis-high-availability-srg-ipmon-list {
               description " Display each IP monitoring entry";
               leaf ha-srg-ipmon-dst-ipaddr {
                 type string;
                 description "Destination IP address configured for HA ip-monitoring";
               }
               leaf ha-srg-ipmon-rt {
                 type string;
                 description "Routing instance configured for HA ip-monitoring";
               }
               leaf ha-ipmon-status {
                 type string;
                 description "HA ip-monitoring status";
               }
               leaf ha-srg-ipmon-reason {
                 type string;
                 description "HA ip-monitoring failure reason";
               }
             }
           }
           container chassis-high-availability-srg-obj-ipmon {
             description "SRG monitor object IP monitoring Info";
             leaf ha-srg-obj-ipmon-threshold {
               type int32;
               description "SRG monitor object IP-monitoring threshold";
             }
             leaf ha-srg-obj-ipmon-weight {
               type int32;
               description "SRG monitor object IP-monitoring weight";
             }
             leaf ha-srg-obj-ipmon-status {
               type string;
               description "SRG monitor object IP-monitoring global status";
             }
             container chassis-high-availability-srg-obj-ipmon-list {
               description " Display each monitor object IP monitoring entry status";
               leaf ha-srg-obj-ipmon-entry-status {
                 type string;
                 description "HA SRG monitor object ip-monitoring state";
               }
               leaf ha-srg-obj-ipmon-entry-weight {
                 type int32;
                 description "HA SRG monitor object ip-monitoring weight";
               }
               leaf ha-srg-obj-ipmon-entry-dst-ipaddr {
                 type string;
                 description "Destination IP address configured for HA ip-monitoring";
               }
             }
           }
           container chassis-high-availability-srg-obj-ipmon-detail {
             description "SRG monitor object IP monitoring detail Info";
             container chassis-high-availability-srg-ipmon-list {
               description " Display each IP monitoring entry";
               leaf ha-srg-ipmon-dst-ipaddr {
                 type string;
                 description "Destination IP address configured for HA ip-monitoring";
               }
               leaf ha-srg-ipmon-rt {
                 type string;
                 description "Routing instance configured for HA ip-monitoring";
               }
               leaf ha-ipmon-status {
                 type string;
                 description "HA ip-monitoring status";
               }
               leaf ha-srg-ipmon-reason {
                 type string;
                 description "HA ip-monitoring failure reason";
               }
             }
           }
           list high-availability-ipmon-status-events {
             description "List of ip-monitoring status events";
             leaf-list high-availability-ipmon-status-event {
               type string;
               description "Recorded ip-monitoring status event";
             }
           }
           list high-availability-probe-status-events {
             description "List of activeness probe status events";
             leaf-list high-availability-probe-status-event {
               type string;
               description "Recorded activeness probe status event";
             }
           }
         }
       }
     }
     container chassis-mnha-peer-domain-info-detail {
       description "Displays high-availability peer related info";
       leaf peer-domain-info {
         type string;
         description "Peer-domain-info";
       }
       leaf peer-domain-id {
         type int32;
         description "Peer-domain-id";
       }
       leaf-list peer-local-ip {
         type jt:ipaddr;
         description "Peer node IPv4 address";
       }
       list high-availability-hw-upgrade-events {
         description "List of HA hardware upgrade events";
         leaf-list high-availability-hw-upgrade-event {
           type string;
           description "Recorded HA hardware upgrade event";
         }
       }
       list chassis-mnha-idl-peer-info {
         description "Displays mnha idl peer related info";
         leaf high-availability-peer-desc {
           type string;
           description "Peer description";
         }
         leaf peer-domain-id {
           type int32;
           description "Peer-domain-id";
         }
         leaf high-availability-peer-id {
           type int32;
           description "Peer identifier that is configured";
         }
         leaf high-availability-peer-ip-address {
           type jt:ipaddr;
           description "Peer remote IPv4 address that is configured";
         }
         leaf-list high-availability-local-interface {
           type string;
           description "Local interface";
         }
         leaf high-availability-peer-rt-instance {
           type string;
           description "Routing Instance name for HA peer";
         }
         leaf high-availability-peer-encryption-status {
           type string;
           description "Encryption status of the current node";
         }
         leaf high-availability-peer-idl-bfd-status {
           type string;
           description "IDL BFD Status of the current node";
         }
         leaf cold-sync-status {
           type string;
           description "Cold synchronization status";
         }
         leaf peer-hw-incompatible {
           type string;
           description "Peer hardware compatible status";
         }
         leaf peer-internal-interface {
           type string;
           description "Peer internal interface";
         }
         leaf peer-internal-local-ip {
           type jt:ipaddr;
           description "Internal local IPv4 address";
         }
         leaf peer-internal-peer-ip {
           type jt:ipaddr;
           description "Internal peer IPv4 address";
         }
         leaf peer-internal-routing-instance {
           type string;
           description "Peer internal routing instance";
         }
         leaf high-availability-peer-detect-time {
           type string;
           description "Configured Peer BFD detection time";
         }
         container chassis-mnha-peer-node-icl-info {
           description "Displays high-availability icl info";
           leaf states-from-domain-id {
             type int32;
             description "States from domain id";
           }
           leaf states-from-node-id {
             type int32;
             description "States from node id";
           }
           leaf icl-conn-state {
             type string;
             description "ICL Conn state";
           }
           leaf cold-sync-status {
             type string;
             description "Cold synchronization status";
           }
         }
         container chassis-mnha-peer-domain-idl-info {
           description "Displays high-availability peer domain IDL BFD and CS state";
           leaf states-from-domain-id {
             type int32;
             description "States from domain id";
           }
           leaf states-from-node-id {
             type int32;
             description "States from node id";
           }
           leaf domain-id {
             type int32;
             description "Domain-id";
           }
           leaf peer-id {
             type int32;
             description "Peer identifier";
           }
           leaf conn-state {
             type string;
             description "Conn state";
           }
           leaf rtt-result {
             type string;
             description "RTT result";
           }
           leaf cold-sync-status {
             type string;
             description "Cold synchronization status";
           }
           leaf srg0-idl-status {
             type string;
             description "SRG0 idl status";
           }
         }
         list high-availability-peer-packet-stats {
           description "Peer Packet Stats";
           leaf packet-send-err-cnt {
             type int32;
             description "Peer packet send error cnt";
           }
           leaf packet-recv-err-cnt {
             type int32;
             description "Peer packet recv error cnt";
           }
           list peer-packet-send-rcv-stats {
             description "Peer Packet Send receive Stats";
             list peer-packet-stats-list {
               description "Stats for each peer packet type";
               leaf peer-packet-type {
                 type string;
                 description "Peer packet Type";
               }
               leaf peer-packet-send-cnt {
                 type int32;
                 description "Peer packet sent count";
               }
               leaf peer-packet-rcv-cnt {
                 type int32;
                 description "Peer packet rcv cnt";
               }
             }
           }
         }
       }
       container cold-synchronization-monitoring-information {
         description "Cold sync monitoring related information";
         leaf-list cold-synchronization-progress {
           type string;
           description "Cold synchronization progress";
         }
         container cold-synchronization-status-information {
           description "Cold synchronization related status information";
           leaf cold-synchronization-completed {
             type string;
             description "List of PFE's which have completed cold synchnronization";
           }
           leaf cold-synchronization-not-completed {
             type string;
             description "List of PFE's which have failed cold synchnronization";
           }
           leaf cold-synchronization-unknown {
             type string;
             description "List of PFE's for which cold synchnronization statusupdate is not received";
           }
           leaf cold-synchronization-weight {
             type uint32;
             description "Current Cold Synchronization weight";
           }
         }
         container cold-synchronization-statistics {
           description "Cold synchronization statistics";
           leaf current-cold-synchronization-completed {
             type uint32;
             description "Cold synchronization completed for current jsrpd session";
           }
           leaf current-cold-synchronization-failed {
             type uint32;
             description "Cold synchronization failed for current jsrpd session";
           }
           list cold-synchronization-pfe-statistics {
             description "Cold synchroniizaton statistics for each PFE";
             leaf pfe-name {
               type string;
               description "Name of the PFE";
             }
             leaf cold-synchronization-pfe-completed {
               type uint32;
               description "Cold synchronization complete instances for a given PFE";
             }
             leaf cold-synchronization-pfe-failed {
               type uint32;
               description "Cold synchronization complete instances for a given PFE";
             }
           }
         }
         container cold-synchronization-events {
           description "List of cold synchronization events";
           leaf-list cold-synchronization-event {
             type string;
             description "Recorded cold sync complete/failure for a PFE";
           }
         }
       }
       container spu-monitoring-information {
         description "SPU monitoring related information";
         container spu-monitoring-status {
           description "SPU monitoring related status information";
           leaf spu-monitoring-state {
             type string;
             description "SPU current monitoring mode Disabled/Enabled/Active";
           }
           leaf spu-monitoring-weight {
             type uint32;
             description "Current SPU monitoring weight";
           }
           list spu-monitoring-spu-state {
             description "Each SPU current state";
             container spu-monitoring-spu-state-list {
               description "Each SPU current state in list";
               leaf pfe-name {
                 type string;
                 description "Name of the PFE";
               }
               leaf pic-state {
                 type string;
                 description "State of each PIC";
               }
             }
           }
         }
         container spu-monitoring-statistics {
           description "Detailed statistics of SPU monitoring";
           leaf spu-up-count {
             type uint32;
             description "Number of SPUs that are up";
           }
           leaf spu-down-count {
             type uint32;
             description "Number of SPUs that are down";
           }
           leaf npc-up-count {
             type uint32;
             description "Number of NPCs that are up";
           }
           leaf npc-down-count {
             type uint32;
             description "Number of NPCs that are down";
           }
           leaf chinfo-blob-error-count {
             type uint32;
             description "Error count reading chinfo blob";
           }
         }
         container spu-monitoring-events {
           description "List of SPU monitoring events";
           leaf-list spu-monitoring-event {
             type string;
             description "Recorded SPU monitoring events";
           }
         }
       }
       list loopback-information {
         description "Loopback information";
         container loopback-information-list {
           description "Display loopback information list";
           leaf pfe-name {
             type string;
             description "Name of the PFE";
           }
           leaf loopback-status {
             type string;
             description "Loopback status of each PIC";
           }
           leaf nexthop-status {
             type string;
             description "Nexthop status of each PIC";
           }
           leaf mbuf-status {
             type string;
             description "Mbuf status of each PIC";
           }
         }
       }
       container high-availability-hardware-monitoring-information {
         description "Displays complete high-availability hardware monitoring information for debugging purposes";
         container high-availability-hardware-monitoring-status-information {
           leaf high-availability-hardware-monitoring-activation-status {
             type string;
             description "Hardware monitoring is enabled/disabled";
           }
           leaf high-availability-hardware-monitoring-ctrl-plane-errors {
             type int32;
             description "Hardware monitoring Ctrl plane errors";
           }
           leaf high-availability-hardware-monitoring-data-plane-errors {
             type int32;
             description "Hardware monitoring Data plane errors";
           }
         }
       }
       container chassis-high-availability-default-srg-info {
         description "Displays high-availability services redundancy group 0 info";
         leaf current-state {
           type string;
           description "SRG 0 current state";
         }
         leaf peer-id {
           type int32;
           description "Peer identifier";
         }
         leaf node-priority {
           type int32;
           description "Node-priority";
         }
         leaf peer-domain-id {
           type int32;
           description "Peer-domain-id";
         }
         list srg-peer-domain-peer-id-info {
           description "Idl peer node Id";
           leaf idl-peer-id {
             type int32;
             description "IDL Peer identifier";
           }
         }
         container high-availability-srg-signal-rt-info {
           description "  SRG Signal route Info";
           container ha-srg-signal-rt-list {
             description "Display each signal route information";
             leaf ha-srg-signal-rt-type {
               type string;
               description "  SRG  Signal route type";
             }
             leaf ha-srg-signal-rt-ipaddr {
               type string;
               description "IP address configured as SRG active signal route";
             }
             leaf ha-srg-signal-rt-rt {
               type string;
               description "Routing table configured for active signal route";
             }
             leaf ha-srg-signal-rt-status {
               type string;
               description " SRG signal Route installation status";
             }
           }
         }
         list chassis-high-availability-shutdown-interface {
           description "Display high-availability shutdown interface list";
           leaf high-availability-shutdown-interface-name {
             type string;
             description "Interface name for monitoring";
           }
         }
         container chassis-high-availability-srg-ipmon {
           description "SRG IP monitoring Info";
           leaf ha-srg-ipmon-status {
             type string;
             description "SRG overall IP-monitoring status";
           }
           container chassis-high-availability-srg-ipmon-list {
             description " Display each IP monitoring entry";
             leaf ha-srg-ipmon-dst-ipaddr {
               type string;
               description "Destination IP address configured for HA ip-monitoring";
             }
             leaf ha-srg-ipmon-rt {
               type string;
               description "Routing instance configured for HA ip-monitoring";
             }
             leaf ha-ipmon-status {
               type string;
               description "HA ip-monitoring status";
             }
             leaf ha-srg-ipmon-reason {
               type string;
               description "HA ip-monitoring failure reason";
             }
           }
         }
         container chassis-high-availability-srg-bfdmon {
           description " SRG BFD mon information ";
           leaf ha-srg-bfdmon-status {
             type string;
             description "HA overall bfd-monitoring status";
           }
           container chassis-high-availability-srg-bfdmon-list {
             description " Display each BFD mon entry Information";
             leaf ha-srg-bfdmon-src-ipaddr {
               type string;
               description "Source IP address configured for HA bfd-monitoring";
             }
             leaf ha-srg-bfdmon-dst-ipaddr {
               type string;
               description "Destination IP address configured for HA bfd-monitoring";
             }
             leaf ha-srg-bfdmon-rt {
               type string;
               description "Routing instance configured for HA bfd-monitoring";
             }
             leaf ha-srg-bfdmon-type {
               type string;
               description "HA bfd-monitoring type";
             }
             leaf ha-srg-bfdmon-ifl-name {
               type string;
               description "HA bfd-monitoring IFL name";
             }
             leaf ha-srg-bfdmon-state {
               type string;
               description "HA bfd-monitoring state";
             }
           }
         }
         container chassis-high-availability-srg-ifmon {
           description "SRG Interface monitoring Info";
           leaf ha-srg-ifmon-status {
             type string;
             description "HA overall Interface-monitoring status";
           }
           container chassis-high-availability-srg-ifmon-list {
             description " Display each Interface monitoring entry";
             leaf ha-srg-ifmon-if-name {
               type string;
               description "HA Interface-monitoring IF name";
             }
             leaf ha-srg-ifmon-state {
               type string;
               description "HA Interface-monitoring state";
             }
           }
         }
         container chassis-high-availability-srg-mon-info {
           description "SRG global threshold info";
           leaf ha-srg-mon-status {
             type string;
             description "SRG monitor status";
           }
           leaf ha-srg-mon-threshold {
             type int32;
             description "SRG monitor threshold";
           }
           leaf ha-srg-mon-weight {
             type int32;
             description "SRG monitor weight";
           }
           leaf ha-srg-mon-failed-objects {
             type int32;
             description "SRG monitor failed objects";
           }
         }
         container chassis-high-availability-srg-obj-info {
           description "SRG monitor-object info";
           leaf ha-srg-obj-name {
             type string;
             description "SRG monitor object name";
           }
           leaf ha-srg-obj-status {
             type string;
             description "SRG monitor object status";
           }
           leaf ha-srg-obj-entries {
             type string;
             description "SRG monitor object monitored entries";
           }
           leaf ha-srg-obj-failure {
             type string;
             description "SRG monitor object monitored failures";
           }
           leaf ha-srg-obj-threshold {
             type int32;
             description "SRG monitor object threshold";
           }
           leaf ha-srg-obj-weight {
             type int32;
             description "SRG monitor object current weight";
           }
         }
         container chassis-high-availability-srg-obj-ipmon {
           description "SRG monitor object IP monitoring Info";
           leaf ha-srg-obj-ipmon-threshold {
             type int32;
             description "SRG monitor object IP-monitoring threshold";
           }
           leaf ha-srg-obj-ipmon-weight {
             type int32;
             description "SRG monitor object IP-monitoring weight";
           }
           leaf ha-srg-obj-ipmon-status {
             type string;
             description "SRG monitor object IP-monitoring global status";
           }
           container chassis-high-availability-srg-obj-ipmon-list {
             description " Display each monitor object IP monitoring entry status";
             leaf ha-srg-obj-ipmon-entry-status {
               type string;
               description "HA SRG monitor object ip-monitoring state";
             }
             leaf ha-srg-obj-ipmon-entry-weight {
               type int32;
               description "HA SRG monitor object ip-monitoring weight";
             }
             leaf ha-srg-obj-ipmon-entry-dst-ipaddr {
               type string;
               description "Destination IP address configured for HA ip-monitoring";
             }
           }
         }
         container chassis-high-availability-srg-obj-ipmon-detail {
           description "SRG monitor object IP monitoring detail Info";
           container chassis-high-availability-srg-ipmon-list {
             description " Display each IP monitoring entry";
             leaf ha-srg-ipmon-dst-ipaddr {
               type string;
               description "Destination IP address configured for HA ip-monitoring";
             }
             leaf ha-srg-ipmon-rt {
               type string;
               description "Routing instance configured for HA ip-monitoring";
             }
             leaf ha-ipmon-status {
               type string;
               description "HA ip-monitoring status";
             }
             leaf ha-srg-ipmon-reason {
               type string;
               description "HA ip-monitoring failure reason";
             }
           }
         }
         container chassis-high-availability-srg-obj-bfdmon {
           description "SRG monitor object BFD monitoring Info";
           leaf ha-srg-obj-bfdmon-threshold {
             type int32;
             description "SRG monitor object BFD-monitoring threshold";
           }
           leaf ha-srg-obj-bfdmon-weight {
             type int32;
             description "SRG monitor object BFD-monitoring weight";
           }
           leaf ha-srg-obj-bfdmon-status {
             type string;
             description "SRG monitor object BFD-monitoring global status";
           }
           container chassis-high-availability-srg-obj-bfdmon-list {
             description "Display each monitor object BFD monitoring entry status";
             leaf ha-srg-obj-bfdmon-entry-status {
               type string;
               description "HA SRG monitor object BFD-monitoring state";
             }
             leaf ha-srg-obj-bfdmon-entry-weight {
               type int32;
               description "HA SRG monitor object BFD-monitoring weight";
             }
             leaf ha-srg-obj-bfdmon-entry-dst-bfdaddr {
               type string;
               description "Destination BFD address configured for HA BFD-monitoring";
             }
           }
         }
         container chassis-high-availability-srg-obj-bfdmon-detail {
           description "SRG monitor object BFD mon information ";
           container chassis-high-availability-srg-bfdmon-list {
             description " Display each BFD mon entry Information";
             leaf ha-srg-bfdmon-src-ipaddr {
               type string;
               description "Source IP address configured for HA bfd-monitoring";
             }
             leaf ha-srg-bfdmon-dst-ipaddr {
               type string;
               description "Destination IP address configured for HA bfd-monitoring";
             }
             leaf ha-srg-bfdmon-rt {
               type string;
               description "Routing instance configured for HA bfd-monitoring";
             }
             leaf ha-srg-bfdmon-type {
               type string;
               description "HA bfd-monitoring type";
             }
             leaf ha-srg-bfdmon-ifl-name {
               type string;
               description "HA bfd-monitoring IFL name";
             }
             leaf ha-srg-bfdmon-state {
               type string;
               description "HA bfd-monitoring state";
             }
           }
         }
         container chassis-high-availability-srg-obj-ifmon {
           description "SRG monitor object IF monitoring Info";
           leaf ha-srg-obj-ifmon-threshold {
             type int32;
             description "SRG monitor object IF-monitoring threshold";
           }
           leaf ha-srg-obj-ifmon-weight {
             type int32;
             description "SRG monitor object IF-monitoring current weight";
           }
           leaf ha-srg-ifmon-status {
             type string;
             description "HA overall Interface-monitoring status";
           }
           container chassis-high-availability-srg-obj-ifmon-list {
             description "Display each monitor object IF monitoring entry status";
             leaf ha-srg-ifmon-entry-status {
               type string;
               description "HA SRG monitor object IF-monitoring entry status";
             }
             leaf ha-srg-obj-ifmon-entry-weight {
               type int32;
               description "HA SRG monitor object IF-monitoring entry weight";
             }
             leaf ha-srg-ifmon-if-name {
               type string;
               description "HA Interface-monitoring IF name";
             }
           }
         }
       }
       list chassis-high-availability-srg-info-detail {
         description "Displays high-availability services redundancy group detail info";
         list srg-info-detail {
           leaf srg-id {
             type int32;
             description "Current services redundancy group identifier";
           }
           leaf deployment-type {
             type string;
             description "Deployment Type";
           }
           leaf node-role {
             type string;
             description "Local node role";
           }
           leaf activeness-priority {
             type int32;
             description "SRG activeness priority";
           }
           leaf hold-timer {
             type int32;
             description "SRG hold down timer";
           }
           leaf peer-ids {
             type int32;
             description "List of peer ids";
           }
           leaf process-pkt-in-bkp-state {
             type string;
             description "SRG backup state pkt processing info";
           }
           leaf service-names {
             type string;
             description "SRG service names";
           }
           leaf control-plane {
             type string;
             description "Control plane status";
           }
           leaf system-integrity-check {
             type string;
             description "Status of system integrity check";
           }
           leaf peer-id {
             type int32;
             description "Peer identifier";
           }
           leaf peer-node-role {
             type string;
             description "Peer node role";
           }
           leaf health-status {
             type string;
             description "Peer health status";
           }
           leaf failover-readiness {
             type string;
             description "SRG failover readiness";
           }
           leaf failure-events {
             type string;
             description "List of failure events";
           }
           leaf preempt {
             type string;
             description "Preempt configuration for the redundancy group";
           }
           container high-availability-srg-signal-rt-info {
             description "  SRG Signal route Info";
             container ha-srg-signal-rt-list {
               description "Display each signal route information";
               leaf ha-srg-signal-rt-type {
                 type string;
                 description "  SRG  Signal route type";
               }
               leaf ha-srg-signal-rt-ipaddr {
                 type string;
                 description "IP address configured as SRG active signal route";
               }
               leaf ha-srg-signal-rt-rt {
                 type string;
                 description "Routing table configured for active signal route";
               }
               leaf ha-srg-signal-rt-status {
                 type string;
                 description " SRG signal Route installation status";
               }
             }
           }
           container high-availability-srg-vip-info {
             description "  SRG Virtual IP Info";
             container ha-srg-vip-list {
               description "Display each Virtual IP information";
               leaf ha-srg-vip-index {
                 type string;
                 description "  SRG  Signal Virtual IP Index";
               }
               leaf ha-srg-virtual-ipaddr {
                 type string;
                 description "IP address configured as SRG virtual IP";
               }
               leaf ha-srg-virtual-mac-address {
                 type string;
                 description "MAC address for the virtual IP.";
               }
               leaf ha-srg-vip-if-name {
                 type string;
                 description "Interface for the virtual IP assignment";
               }
               leaf ha-srg-vip-status {
                 type string;
                 description " SRG Virtual IP assignmentstatus";
               }
             }
           }
           list high-availability-srg-state-events {
             description "List of service redundancy group state change events";
             leaf-list high-availability-srg-state-event {
               type string;
               description "Recorded service redundancy group state change event";
             }
           }
           list high-availability-peer-status-events {
             description "List of HA Peer Conn events";
             leaf-list high-availability-peer-status-event {
               type string;
               description "Recorded HA Peer Conn event";
             }
           }
           list high-availability-hw-upgrade-events {
             description "List of HA hardware upgrade events";
             leaf-list high-availability-hw-upgrade-event {
               type string;
               description "Recorded HA hardware upgrade event";
             }
           }
           container chassis-high-availability-srg-probe {
             description "SRG split brain prevention probe info";
             leaf ha-srg-probe-dst-ipaddr {
               type string;
               description "Destination IP address used for probing";
             }
             leaf ha-srg-probe-src-ipaddr {
               type string;
               description "Source IP address used for probing";
             }
             leaf ha-srg-vip-if-name {
               type string;
               description "Interface for the virtual IP assignment";
             }
             leaf ha-srg-probe-rt {
               type string;
               description "Routing instance used for probing";
             }
             leaf ha-srg-probe-type {
               type string;
               description "Probing type";
             }
             leaf ha-probe-interval {
               type int32;
               description "HA probe interval in ms";
             }
             leaf ha-probe-multiplier {
               type int32;
               description "HA probe multiplier";
             }
             leaf ha-probe-status {
               type string;
               description "Probing status";
             }
             leaf ha-probe-result {
               type string;
               description "Probing result";
             }
             leaf ha-srg-probe-fail-reason {
               type string;
               description "Probing failure reason";
             }
           }
           container chassis-high-availability-srg-mon-info {
             description "SRG global threshold info";
             leaf ha-srg-mon-status {
               type string;
               description "SRG monitor status";
             }
             leaf ha-srg-mon-threshold {
               type int32;
               description "SRG monitor threshold";
             }
             leaf ha-srg-mon-weight {
               type int32;
               description "SRG monitor weight";
             }
             leaf ha-srg-mon-failed-objects {
               type int32;
               description "SRG monitor failed objects";
             }
           }
           container chassis-high-availability-srg-obj-info {
             description "SRG monitor-object info";
             leaf ha-srg-obj-name {
               type string;
               description "SRG monitor object name";
             }
             leaf ha-srg-obj-status {
               type string;
               description "SRG monitor object status";
             }
             leaf ha-srg-obj-entries {
               type string;
               description "SRG monitor object monitored entries";
             }
             leaf ha-srg-obj-failure {
               type string;
               description "SRG monitor object monitored failures";
             }
             leaf ha-srg-obj-threshold {
               type int32;
               description "SRG monitor object threshold";
             }
             leaf ha-srg-obj-weight {
               type int32;
               description "SRG monitor object current weight";
             }
           }
           container chassis-high-availability-srg-bfdmon {
             description " SRG BFD mon information ";
             leaf ha-srg-bfdmon-status {
               type string;
               description "HA overall bfd-monitoring status";
             }
             container chassis-high-availability-srg-bfdmon-list {
               description " Display each BFD mon entry Information";
               leaf ha-srg-bfdmon-src-ipaddr {
                 type string;
                 description "Source IP address configured for HA bfd-monitoring";
               }
               leaf ha-srg-bfdmon-dst-ipaddr {
                 type string;
                 description "Destination IP address configured for HA bfd-monitoring";
               }
               leaf ha-srg-bfdmon-rt {
                 type string;
                 description "Routing instance configured for HA bfd-monitoring";
               }
               leaf ha-srg-bfdmon-type {
                 type string;
                 description "HA bfd-monitoring type";
               }
               leaf ha-srg-bfdmon-ifl-name {
                 type string;
                 description "HA bfd-monitoring IFL name";
               }
               leaf ha-srg-bfdmon-state {
                 type string;
                 description "HA bfd-monitoring state";
               }
             }
           }
           list high-availability-bfdmon-status-events {
             description "List of BFD-monitoring status events";
             leaf-list high-availability-bfdmon-status-event {
               type string;
               description "Recorded BFD-monitoring status event";
             }
           }
           container chassis-high-availability-srg-ipmon {
             description "SRG IP monitoring Info";
             leaf ha-srg-ipmon-status {
               type string;
               description "SRG overall IP-monitoring status";
             }
             container chassis-high-availability-srg-ipmon-list {
               description " Display each IP monitoring entry";
               leaf ha-srg-ipmon-dst-ipaddr {
                 type string;
                 description "Destination IP address configured for HA ip-monitoring";
               }
               leaf ha-srg-ipmon-rt {
                 type string;
                 description "Routing instance configured for HA ip-monitoring";
               }
               leaf ha-ipmon-status {
                 type string;
                 description "HA ip-monitoring status";
               }
               leaf ha-srg-ipmon-reason {
                 type string;
                 description "HA ip-monitoring failure reason";
               }
             }
           }
           container chassis-high-availability-srg-obj-ipmon {
             description "SRG monitor object IP monitoring Info";
             leaf ha-srg-obj-ipmon-threshold {
               type int32;
               description "SRG monitor object IP-monitoring threshold";
             }
             leaf ha-srg-obj-ipmon-weight {
               type int32;
               description "SRG monitor object IP-monitoring weight";
             }
             leaf ha-srg-obj-ipmon-status {
               type string;
               description "SRG monitor object IP-monitoring global status";
             }
             container chassis-high-availability-srg-obj-ipmon-list {
               description " Display each monitor object IP monitoring entry status";
               leaf ha-srg-obj-ipmon-entry-status {
                 type string;
                 description "HA SRG monitor object ip-monitoring state";
               }
               leaf ha-srg-obj-ipmon-entry-weight {
                 type int32;
                 description "HA SRG monitor object ip-monitoring weight";
               }
               leaf ha-srg-obj-ipmon-entry-dst-ipaddr {
                 type string;
                 description "Destination IP address configured for HA ip-monitoring";
               }
             }
           }
           container chassis-high-availability-srg-obj-ipmon-detail {
             description "SRG monitor object IP monitoring detail Info";
             container chassis-high-availability-srg-ipmon-list {
               description " Display each IP monitoring entry";
               leaf ha-srg-ipmon-dst-ipaddr {
                 type string;
                 description "Destination IP address configured for HA ip-monitoring";
               }
               leaf ha-srg-ipmon-rt {
                 type string;
                 description "Routing instance configured for HA ip-monitoring";
               }
               leaf ha-ipmon-status {
                 type string;
                 description "HA ip-monitoring status";
               }
               leaf ha-srg-ipmon-reason {
                 type string;
                 description "HA ip-monitoring failure reason";
               }
             }
           }
           list high-availability-ipmon-status-events {
             description "List of ip-monitoring status events";
             leaf-list high-availability-ipmon-status-event {
               type string;
               description "Recorded ip-monitoring status event";
             }
           }
           list high-availability-probe-status-events {
             description "List of activeness probe status events";
             leaf-list high-availability-probe-status-event {
               type string;
               description "Recorded activeness probe status event";
             }
           }
         }
       }
     }
     container chassis-high-availability-node-info {
       description "Display high-availability node level information";
       leaf node-status {
         type string;
         description "Status of the current node";
       }
       leaf local-id {
         type int32;
         description "Local node identifier";
       }
       leaf local-ip {
         type jt:ipaddr;
         description "Local node IPv4 address";
       }
       leaf local-fwd-ip {
         type jt:ipaddr;
         description "Local Forwarding IP address";
       }
       list chassis-high-availability-shutdown-interface {
         description "Display high-availability shutdown interface list";
         leaf high-availability-shutdown-interface-name {
           type string;
           description "Interface name for monitoring";
         }
       }
       container chassis-high-availability-peer-info-detail {
         description "Displays high-availability peer related detail info";
         leaf high-availability-peer-desc {
           type string;
           description "Peer description";
         }
         leaf high-availability-peer-id {
           type int32;
           description "Peer identifier that is configured";
         }
         leaf high-availability-peer-ip-address {
           type jt:ipaddr;
           description "Peer remote IPv4 address that is configured";
         }
         leaf-list high-availability-local-interface {
           type string;
           description "Local interface";
         }
         leaf high-availability-peer-rt-instance {
           type string;
           description "Routing Instance name for HA peer";
         }
         leaf high-availability-peer-encryption-status {
           type string;
           description "Encryption status of the current node";
         }
         leaf high-availability-peer-bfd-status {
           type string;
           description "BFD Status of the current node";
         }
         leaf cold-sync-status {
           type string;
           description "Cold synchronization status";
         }
         leaf peer-hw-incompatible {
           type string;
           description "Peer hardware compatible status";
         }
         leaf peer-internal-interface {
           type string;
           description "Peer internal interface";
         }
         leaf peer-internal-local-ip {
           type jt:ipaddr;
           description "Internal local IPv4 address";
         }
         leaf peer-internal-peer-ip {
           type jt:ipaddr;
           description "Internal peer IPv4 address";
         }
         leaf peer-internal-routing-instance {
           type string;
           description "Peer internal routing instance";
         }
         leaf high-availability-peer-fwd-ip-address {
           type jt:ipaddr;
           description "Peer forwarding remote IP address";
         }
         leaf high-availability-local-fwd-interface {
           type string;
           description "Local forwarding interface";
         }
         leaf high-availability-peer-fwd-bfd-status {
           type string;
           description "BFD forwarding status of the current node";
         }
         container chassis-mnha-icl-peer-info {
           description "Displays mnha icl peer related info";
           leaf high-availability-peer-desc {
             type string;
             description "Peer description";
           }
           leaf peer-domain-id {
             type int32;
             description "Peer-domain-id";
           }
           leaf high-availability-peer-id {
             type int32;
             description "Peer identifier that is configured";
           }
           leaf high-availability-peer-ip-address {
             type jt:ipaddr;
             description "Peer remote IPv4 address that is configured";
           }
           leaf-list high-availability-local-interface {
             type string;
             description "Local interface";
           }
           leaf high-availability-peer-rt-instance {
             type string;
             description "Routing Instance name for HA peer";
           }
           leaf high-availability-peer-encryption-status {
             type string;
             description "Encryption status of the current node";
           }
           leaf high-availability-peer-bfd-status {
             type string;
             description "BFD Status of the current node";
           }
           leaf cold-sync-status {
             type string;
             description "Cold synchronization status";
           }
           leaf peer-hw-incompatible {
             type string;
             description "Peer hardware compatible status";
           }
           leaf peer-internal-interface {
             type string;
             description "Peer internal interface";
           }
           leaf peer-internal-local-ip {
             type jt:ipaddr;
             description "Internal local IPv4 address";
           }
           leaf peer-internal-peer-ip {
             type jt:ipaddr;
             description "Internal peer IPv4 address";
           }
           leaf peer-internal-routing-instance {
             type string;
             description "Peer internal routing instance";
           }
           leaf high-availability-peer-detect-time {
             type string;
             description "Configured Peer BFD detection time";
           }
           leaf srg0-cold-sync-status {
             type string;
             description "SRG0 cold sync status";
           }
           container chassis-mnha-local-node-idl-info {
             description "Displays high-availability local node IDL BFD and CS state";
             leaf states-from-domain-id {
               type int32;
               description "States from domain id";
             }
             leaf states-from-node-id {
               type int32;
               description "States from node id";
             }
             leaf domain-id {
               type int32;
               description "Domain-id";
             }
             leaf peer-id {
               type int32;
               description "Peer identifier";
             }
             leaf conn-state {
               type string;
               description "Conn state";
             }
             leaf rtt-result {
               type string;
               description "RTT result";
             }
             leaf cold-sync-status {
               type string;
               description "Cold synchronization status";
             }
             leaf srg0-idl-status {
               type string;
               description "SRG0 idl status";
             }
           }
           container chassis-mnha-peer-node-icl-info {
             description "Displays high-availability icl info";
             leaf states-from-domain-id {
               type int32;
               description "States from domain id";
             }
             leaf states-from-node-id {
               type int32;
               description "States from node id";
             }
             leaf icl-conn-state {
               type string;
               description "ICL Conn state";
             }
             leaf cold-sync-status {
               type string;
               description "Cold synchronization status";
             }
           }
           container chassis-mnha-peer-node-idl-info {
             description "Displays high-availability peer node IDL BFD and CS state";
             leaf states-from-domain-id {
               type int32;
               description "States from domain id";
             }
             leaf states-from-node-id {
               type int32;
               description "States from node id";
             }
             leaf domain-id {
               type int32;
               description "Domain-id";
             }
             leaf peer-id {
               type int32;
               description "Peer identifier";
             }
             leaf conn-state {
               type string;
               description "Conn state";
             }
             leaf rtt-result {
               type string;
               description "RTT result";
             }
             leaf cold-sync-status {
               type string;
               description "Cold synchronization status";
             }
             leaf srg0-idl-status {
               type string;
               description "SRG0 idl status";
             }
           }
           list high-availability-peer-packet-stats {
             description "Peer Packet Stats";
             leaf packet-send-err-cnt {
               type int32;
               description "Peer packet send error cnt";
             }
             leaf packet-recv-err-cnt {
               type int32;
               description "Peer packet recv error cnt";
             }
             list peer-packet-send-rcv-stats {
               description "Peer Packet Send receive Stats";
               list peer-packet-stats-list {
                 description "Stats for each peer packet type";
                 leaf peer-packet-type {
                   type string;
                   description "Peer packet Type";
                 }
                 leaf peer-packet-send-cnt {
                   type int32;
                   description "Peer packet sent count";
                 }
                 leaf peer-packet-rcv-cnt {
                   type int32;
                   description "Peer packet rcv cnt";
                 }
               }
             }
           }
         }
         list chassis-mnha-idl-peer-info {
           description "Displays mnha idl peer related info";
           leaf high-availability-peer-desc {
             type string;
             description "Peer description";
           }
           leaf peer-domain-id {
             type int32;
             description "Peer-domain-id";
           }
           leaf high-availability-peer-id {
             type int32;
             description "Peer identifier that is configured";
           }
           leaf high-availability-peer-ip-address {
             type jt:ipaddr;
             description "Peer remote IPv4 address that is configured";
           }
           leaf-list high-availability-local-interface {
             type string;
             description "Local interface";
           }
           leaf high-availability-peer-rt-instance {
             type string;
             description "Routing Instance name for HA peer";
           }
           leaf high-availability-peer-encryption-status {
             type string;
             description "Encryption status of the current node";
           }
           leaf high-availability-peer-idl-bfd-status {
             type string;
             description "IDL BFD Status of the current node";
           }
           leaf cold-sync-status {
             type string;
             description "Cold synchronization status";
           }
           leaf peer-hw-incompatible {
             type string;
             description "Peer hardware compatible status";
           }
           leaf peer-internal-interface {
             type string;
             description "Peer internal interface";
           }
           leaf peer-internal-local-ip {
             type jt:ipaddr;
             description "Internal local IPv4 address";
           }
           leaf peer-internal-peer-ip {
             type jt:ipaddr;
             description "Internal peer IPv4 address";
           }
           leaf peer-internal-routing-instance {
             type string;
             description "Peer internal routing instance";
           }
           leaf high-availability-peer-detect-time {
             type string;
             description "Configured Peer BFD detection time";
           }
           container chassis-mnha-peer-node-icl-info {
             description "Displays high-availability icl info";
             leaf states-from-domain-id {
               type int32;
               description "States from domain id";
             }
             leaf states-from-node-id {
               type int32;
               description "States from node id";
             }
             leaf icl-conn-state {
               type string;
               description "ICL Conn state";
             }
             leaf cold-sync-status {
               type string;
               description "Cold synchronization status";
             }
           }
           container chassis-mnha-peer-domain-idl-info {
             description "Displays high-availability peer domain IDL BFD and CS state";
             leaf states-from-domain-id {
               type int32;
               description "States from domain id";
             }
             leaf states-from-node-id {
               type int32;
               description "States from node id";
             }
             leaf domain-id {
               type int32;
               description "Domain-id";
             }
             leaf peer-id {
               type int32;
               description "Peer identifier";
             }
             leaf conn-state {
               type string;
               description "Conn state";
             }
             leaf rtt-result {
               type string;
               description "RTT result";
             }
             leaf cold-sync-status {
               type string;
               description "Cold synchronization status";
             }
             leaf srg0-idl-status {
               type string;
               description "SRG0 idl status";
             }
           }
           list high-availability-peer-packet-stats {
             description "Peer Packet Stats";
             leaf packet-send-err-cnt {
               type int32;
               description "Peer packet send error cnt";
             }
             leaf packet-recv-err-cnt {
               type int32;
               description "Peer packet recv error cnt";
             }
             list peer-packet-send-rcv-stats {
               description "Peer Packet Send receive Stats";
               list peer-packet-stats-list {
                 description "Stats for each peer packet type";
                 leaf peer-packet-type {
                   type string;
                   description "Peer packet Type";
                 }
                 leaf peer-packet-send-cnt {
                   type int32;
                   description "Peer packet sent count";
                 }
                 leaf peer-packet-rcv-cnt {
                   type int32;
                   description "Peer packet rcv cnt";
                 }
               }
             }
           }
         }
         list high-availability-peer-packet-stats {
           description "Peer Packet Stats";
           leaf packet-send-err-cnt {
             type int32;
             description "Peer packet send error cnt";
           }
           leaf packet-recv-err-cnt {
             type int32;
             description "Peer packet recv error cnt";
           }
           list peer-packet-send-rcv-stats {
             description "Peer Packet Send receive Stats";
             list peer-packet-stats-list {
               description "Stats for each peer packet type";
               leaf peer-packet-type {
                 type string;
                 description "Peer packet Type";
               }
               leaf peer-packet-send-cnt {
                 type int32;
                 description "Peer packet sent count";
               }
               leaf peer-packet-rcv-cnt {
                 type int32;
                 description "Peer packet rcv cnt";
               }
             }
           }
         }
       }
     }
     container cold-synchronization-monitoring-information {
       description "Cold sync monitoring related information";
       leaf-list cold-synchronization-progress {
         type string;
         description "Cold synchronization progress";
       }
       container cold-synchronization-status-information {
         description "Cold synchronization related status information";
         leaf cold-synchronization-completed {
           type string;
           description "List of PFE's which have completed cold synchnronization";
         }
         leaf cold-synchronization-not-completed {
           type string;
           description "List of PFE's which have failed cold synchnronization";
         }
         leaf cold-synchronization-unknown {
           type string;
           description "List of PFE's for which cold synchnronization statusupdate is not received";
         }
         leaf cold-synchronization-weight {
           type uint32;
           description "Current Cold Synchronization weight";
         }
       }
       container cold-synchronization-statistics {
         description "Cold synchronization statistics";
         leaf current-cold-synchronization-completed {
           type uint32;
           description "Cold synchronization completed for current jsrpd session";
         }
         leaf current-cold-synchronization-failed {
           type uint32;
           description "Cold synchronization failed for current jsrpd session";
         }
         list cold-synchronization-pfe-statistics {
           description "Cold synchroniizaton statistics for each PFE";
           leaf pfe-name {
             type string;
             description "Name of the PFE";
           }
           leaf cold-synchronization-pfe-completed {
             type uint32;
             description "Cold synchronization complete instances for a given PFE";
           }
           leaf cold-synchronization-pfe-failed {
             type uint32;
             description "Cold synchronization complete instances for a given PFE";
           }
         }
       }
       container cold-synchronization-events {
         description "List of cold synchronization events";
         leaf-list cold-synchronization-event {
           type string;
           description "Recorded cold sync complete/failure for a PFE";
         }
       }
     }
     container spu-monitoring-information {
       description "SPU monitoring related information";
       container spu-monitoring-status {
         description "SPU monitoring related status information";
         leaf spu-monitoring-state {
           type string;
           description "SPU current monitoring mode Disabled/Enabled/Active";
         }
         leaf spu-monitoring-weight {
           type uint32;
           description "Current SPU monitoring weight";
         }
         list spu-monitoring-spu-state {
           description "Each SPU current state";
           container spu-monitoring-spu-state-list {
             description "Each SPU current state in list";
             leaf pfe-name {
               type string;
               description "Name of the PFE";
             }
             leaf pic-state {
               type string;
               description "State of each PIC";
             }
           }
         }
       }
       container spu-monitoring-statistics {
         description "Detailed statistics of SPU monitoring";
         leaf spu-up-count {
           type uint32;
           description "Number of SPUs that are up";
         }
         leaf spu-down-count {
           type uint32;
           description "Number of SPUs that are down";
         }
         leaf npc-up-count {
           type uint32;
           description "Number of NPCs that are up";
         }
         leaf npc-down-count {
           type uint32;
           description "Number of NPCs that are down";
         }
         leaf chinfo-blob-error-count {
           type uint32;
           description "Error count reading chinfo blob";
         }
       }
       container spu-monitoring-events {
         description "List of SPU monitoring events";
         leaf-list spu-monitoring-event {
           type string;
           description "Recorded SPU monitoring events";
         }
       }
     }
     list loopback-information {
       description "Loopback information";
       container loopback-information-list {
         description "Display loopback information list";
         leaf pfe-name {
           type string;
           description "Name of the PFE";
         }
         leaf loopback-status {
           type string;
           description "Loopback status of each PIC";
         }
         leaf nexthop-status {
           type string;
           description "Nexthop status of each PIC";
         }
         leaf mbuf-status {
           type string;
           description "Mbuf status of each PIC";
         }
       }
     }
     container high-availability-hardware-monitoring-information {
       description "Displays complete high-availability hardware monitoring information for debugging purposes";
       container high-availability-hardware-monitoring-status-information {
         leaf high-availability-hardware-monitoring-activation-status {
           type string;
           description "Hardware monitoring is enabled/disabled";
         }
         leaf high-availability-hardware-monitoring-ctrl-plane-errors {
           type int32;
           description "Hardware monitoring Ctrl plane errors";
         }
         leaf high-availability-hardware-monitoring-data-plane-errors {
           type int32;
           description "Hardware monitoring Data plane errors";
         }
       }
     }
     container chassis-high-availability-default-srg-info {
       description "Displays high-availability services redundancy group 0 info";
       leaf current-state {
         type string;
         description "SRG 0 current state";
       }
       leaf peer-id {
         type int32;
         description "Peer identifier";
       }
       leaf node-priority {
         type int32;
         description "Node-priority";
       }
       leaf peer-domain-id {
         type int32;
         description "Peer-domain-id";
       }
       list srg-peer-domain-peer-id-info {
         description "Idl peer node Id";
         leaf idl-peer-id {
           type int32;
           description "IDL Peer identifier";
         }
       }
       container high-availability-srg-signal-rt-info {
         description "  SRG Signal route Info";
         container ha-srg-signal-rt-list {
           description "Display each signal route information";
           leaf ha-srg-signal-rt-type {
             type string;
             description "  SRG  Signal route type";
           }
           leaf ha-srg-signal-rt-ipaddr {
             type string;
             description "IP address configured as SRG active signal route";
           }
           leaf ha-srg-signal-rt-rt {
             type string;
             description "Routing table configured for active signal route";
           }
           leaf ha-srg-signal-rt-status {
             type string;
             description " SRG signal Route installation status";
           }
         }
       }
       list chassis-high-availability-shutdown-interface {
         description "Display high-availability shutdown interface list";
         leaf high-availability-shutdown-interface-name {
           type string;
           description "Interface name for monitoring";
         }
       }
       container chassis-high-availability-srg-ipmon {
         description "SRG IP monitoring Info";
         leaf ha-srg-ipmon-status {
           type string;
           description "SRG overall IP-monitoring status";
         }
         container chassis-high-availability-srg-ipmon-list {
           description " Display each IP monitoring entry";
           leaf ha-srg-ipmon-dst-ipaddr {
             type string;
             description "Destination IP address configured for HA ip-monitoring";
           }
           leaf ha-srg-ipmon-rt {
             type string;
             description "Routing instance configured for HA ip-monitoring";
           }
           leaf ha-ipmon-status {
             type string;
             description "HA ip-monitoring status";
           }
           leaf ha-srg-ipmon-reason {
             type string;
             description "HA ip-monitoring failure reason";
           }
         }
       }
       container chassis-high-availability-srg-bfdmon {
         description " SRG BFD mon information ";
         leaf ha-srg-bfdmon-status {
           type string;
           description "HA overall bfd-monitoring status";
         }
         container chassis-high-availability-srg-bfdmon-list {
           description " Display each BFD mon entry Information";
           leaf ha-srg-bfdmon-src-ipaddr {
             type string;
             description "Source IP address configured for HA bfd-monitoring";
           }
           leaf ha-srg-bfdmon-dst-ipaddr {
             type string;
             description "Destination IP address configured for HA bfd-monitoring";
           }
           leaf ha-srg-bfdmon-rt {
             type string;
             description "Routing instance configured for HA bfd-monitoring";
           }
           leaf ha-srg-bfdmon-type {
             type string;
             description "HA bfd-monitoring type";
           }
           leaf ha-srg-bfdmon-ifl-name {
             type string;
             description "HA bfd-monitoring IFL name";
           }
           leaf ha-srg-bfdmon-state {
             type string;
             description "HA bfd-monitoring state";
           }
         }
       }
       container chassis-high-availability-srg-ifmon {
         description "SRG Interface monitoring Info";
         leaf ha-srg-ifmon-status {
           type string;
           description "HA overall Interface-monitoring status";
         }
         container chassis-high-availability-srg-ifmon-list {
           description " Display each Interface monitoring entry";
           leaf ha-srg-ifmon-if-name {
             type string;
             description "HA Interface-monitoring IF name";
           }
           leaf ha-srg-ifmon-state {
             type string;
             description "HA Interface-monitoring state";
           }
         }
       }
       container chassis-high-availability-srg-mon-info {
         description "SRG global threshold info";
         leaf ha-srg-mon-status {
           type string;
           description "SRG monitor status";
         }
         leaf ha-srg-mon-threshold {
           type int32;
           description "SRG monitor threshold";
         }
         leaf ha-srg-mon-weight {
           type int32;
           description "SRG monitor weight";
         }
         leaf ha-srg-mon-failed-objects {
           type int32;
           description "SRG monitor failed objects";
         }
       }
       container chassis-high-availability-srg-obj-info {
         description "SRG monitor-object info";
         leaf ha-srg-obj-name {
           type string;
           description "SRG monitor object name";
         }
         leaf ha-srg-obj-status {
           type string;
           description "SRG monitor object status";
         }
         leaf ha-srg-obj-entries {
           type string;
           description "SRG monitor object monitored entries";
         }
         leaf ha-srg-obj-failure {
           type string;
           description "SRG monitor object monitored failures";
         }
         leaf ha-srg-obj-threshold {
           type int32;
           description "SRG monitor object threshold";
         }
         leaf ha-srg-obj-weight {
           type int32;
           description "SRG monitor object current weight";
         }
       }
       container chassis-high-availability-srg-obj-ipmon {
         description "SRG monitor object IP monitoring Info";
         leaf ha-srg-obj-ipmon-threshold {
           type int32;
           description "SRG monitor object IP-monitoring threshold";
         }
         leaf ha-srg-obj-ipmon-weight {
           type int32;
           description "SRG monitor object IP-monitoring weight";
         }
         leaf ha-srg-obj-ipmon-status {
           type string;
           description "SRG monitor object IP-monitoring global status";
         }
         container chassis-high-availability-srg-obj-ipmon-list {
           description " Display each monitor object IP monitoring entry status";
           leaf ha-srg-obj-ipmon-entry-status {
             type string;
             description "HA SRG monitor object ip-monitoring state";
           }
           leaf ha-srg-obj-ipmon-entry-weight {
             type int32;
             description "HA SRG monitor object ip-monitoring weight";
           }
           leaf ha-srg-obj-ipmon-entry-dst-ipaddr {
             type string;
             description "Destination IP address configured for HA ip-monitoring";
           }
         }
       }
       container chassis-high-availability-srg-obj-ipmon-detail {
         description "SRG monitor object IP monitoring detail Info";
         container chassis-high-availability-srg-ipmon-list {
           description " Display each IP monitoring entry";
           leaf ha-srg-ipmon-dst-ipaddr {
             type string;
             description "Destination IP address configured for HA ip-monitoring";
           }
           leaf ha-srg-ipmon-rt {
             type string;
             description "Routing instance configured for HA ip-monitoring";
           }
           leaf ha-ipmon-status {
             type string;
             description "HA ip-monitoring status";
           }
           leaf ha-srg-ipmon-reason {
             type string;
             description "HA ip-monitoring failure reason";
           }
         }
       }
       container chassis-high-availability-srg-obj-bfdmon {
         description "SRG monitor object BFD monitoring Info";
         leaf ha-srg-obj-bfdmon-threshold {
           type int32;
           description "SRG monitor object BFD-monitoring threshold";
         }
         leaf ha-srg-obj-bfdmon-weight {
           type int32;
           description "SRG monitor object BFD-monitoring weight";
         }
         leaf ha-srg-obj-bfdmon-status {
           type string;
           description "SRG monitor object BFD-monitoring global status";
         }
         container chassis-high-availability-srg-obj-bfdmon-list {
           description "Display each monitor object BFD monitoring entry status";
           leaf ha-srg-obj-bfdmon-entry-status {
             type string;
             description "HA SRG monitor object BFD-monitoring state";
           }
           leaf ha-srg-obj-bfdmon-entry-weight {
             type int32;
             description "HA SRG monitor object BFD-monitoring weight";
           }
           leaf ha-srg-obj-bfdmon-entry-dst-bfdaddr {
             type string;
             description "Destination BFD address configured for HA BFD-monitoring";
           }
         }
       }
       container chassis-high-availability-srg-obj-bfdmon-detail {
         description "SRG monitor object BFD mon information ";
         container chassis-high-availability-srg-bfdmon-list {
           description " Display each BFD mon entry Information";
           leaf ha-srg-bfdmon-src-ipaddr {
             type string;
             description "Source IP address configured for HA bfd-monitoring";
           }
           leaf ha-srg-bfdmon-dst-ipaddr {
             type string;
             description "Destination IP address configured for HA bfd-monitoring";
           }
           leaf ha-srg-bfdmon-rt {
             type string;
             description "Routing instance configured for HA bfd-monitoring";
           }
           leaf ha-srg-bfdmon-type {
             type string;
             description "HA bfd-monitoring type";
           }
           leaf ha-srg-bfdmon-ifl-name {
             type string;
             description "HA bfd-monitoring IFL name";
           }
           leaf ha-srg-bfdmon-state {
             type string;
             description "HA bfd-monitoring state";
           }
         }
       }
       container chassis-high-availability-srg-obj-ifmon {
         description "SRG monitor object IF monitoring Info";
         leaf ha-srg-obj-ifmon-threshold {
           type int32;
           description "SRG monitor object IF-monitoring threshold";
         }
         leaf ha-srg-obj-ifmon-weight {
           type int32;
           description "SRG monitor object IF-monitoring current weight";
         }
         leaf ha-srg-ifmon-status {
           type string;
           description "HA overall Interface-monitoring status";
         }
         container chassis-high-availability-srg-obj-ifmon-list {
           description "Display each monitor object IF monitoring entry status";
           leaf ha-srg-ifmon-entry-status {
             type string;
             description "HA SRG monitor object IF-monitoring entry status";
           }
           leaf ha-srg-obj-ifmon-entry-weight {
             type int32;
             description "HA SRG monitor object IF-monitoring entry weight";
           }
           leaf ha-srg-ifmon-if-name {
             type string;
             description "HA Interface-monitoring IF name";
           }
         }
       }
     }
     list chassis-high-availability-srg-info-detail {
       description "Displays high-availability services redundancy group detail info";
       list srg-info-detail {
         leaf srg-id {
           type int32;
           description "Current services redundancy group identifier";
         }
         leaf deployment-type {
           type string;
           description "Deployment Type";
         }
         leaf node-role {
           type string;
           description "Local node role";
         }
         leaf activeness-priority {
           type int32;
           description "SRG activeness priority";
         }
         leaf hold-timer {
           type int32;
           description "SRG hold down timer";
         }
         leaf peer-ids {
           type int32;
           description "List of peer ids";
         }
         leaf process-pkt-in-bkp-state {
           type string;
           description "SRG backup state pkt processing info";
         }
         leaf service-names {
           type string;
           description "SRG service names";
         }
         leaf control-plane {
           type string;
           description "Control plane status";
         }
         leaf system-integrity-check {
           type string;
           description "Status of system integrity check";
         }
         leaf peer-id {
           type int32;
           description "Peer identifier";
         }
         leaf peer-node-role {
           type string;
           description "Peer node role";
         }
         leaf health-status {
           type string;
           description "Peer health status";
         }
         leaf failover-readiness {
           type string;
           description "SRG failover readiness";
         }
         leaf failure-events {
           type string;
           description "List of failure events";
         }
         leaf preempt {
           type string;
           description "Preempt configuration for the redundancy group";
         }
         container high-availability-srg-signal-rt-info {
           description "  SRG Signal route Info";
           container ha-srg-signal-rt-list {
             description "Display each signal route information";
             leaf ha-srg-signal-rt-type {
               type string;
               description "  SRG  Signal route type";
             }
             leaf ha-srg-signal-rt-ipaddr {
               type string;
               description "IP address configured as SRG active signal route";
             }
             leaf ha-srg-signal-rt-rt {
               type string;
               description "Routing table configured for active signal route";
             }
             leaf ha-srg-signal-rt-status {
               type string;
               description " SRG signal Route installation status";
             }
           }
         }
         container high-availability-srg-vip-info {
           description "  SRG Virtual IP Info";
           container ha-srg-vip-list {
             description "Display each Virtual IP information";
             leaf ha-srg-vip-index {
               type string;
               description "  SRG  Signal Virtual IP Index";
             }
             leaf ha-srg-virtual-ipaddr {
               type string;
               description "IP address configured as SRG virtual IP";
             }
             leaf ha-srg-virtual-mac-address {
               type string;
               description "MAC address for the virtual IP.";
             }
             leaf ha-srg-vip-if-name {
               type string;
               description "Interface for the virtual IP assignment";
             }
             leaf ha-srg-vip-status {
               type string;
               description " SRG Virtual IP assignmentstatus";
             }
           }
         }
         list high-availability-srg-state-events {
           description "List of service redundancy group state change events";
           leaf-list high-availability-srg-state-event {
             type string;
             description "Recorded service redundancy group state change event";
           }
         }
         list high-availability-peer-status-events {
           description "List of HA Peer Conn events";
           leaf-list high-availability-peer-status-event {
             type string;
             description "Recorded HA Peer Conn event";
           }
         }
         list high-availability-hw-upgrade-events {
           description "List of HA hardware upgrade events";
           leaf-list high-availability-hw-upgrade-event {
             type string;
             description "Recorded HA hardware upgrade event";
           }
         }
         container chassis-high-availability-srg-probe {
           description "SRG split brain prevention probe info";
           leaf ha-srg-probe-dst-ipaddr {
             type string;
             description "Destination IP address used for probing";
           }
           leaf ha-srg-probe-src-ipaddr {
             type string;
             description "Source IP address used for probing";
           }
           leaf ha-srg-vip-if-name {
             type string;
             description "Interface for the virtual IP assignment";
           }
           leaf ha-srg-probe-rt {
             type string;
             description "Routing instance used for probing";
           }
           leaf ha-srg-probe-type {
             type string;
             description "Probing type";
           }
           leaf ha-probe-interval {
             type int32;
             description "HA probe interval in ms";
           }
           leaf ha-probe-multiplier {
             type int32;
             description "HA probe multiplier";
           }
           leaf ha-probe-status {
             type string;
             description "Probing status";
           }
           leaf ha-probe-result {
             type string;
             description "Probing result";
           }
           leaf ha-srg-probe-fail-reason {
             type string;
             description "Probing failure reason";
           }
         }
         container chassis-high-availability-srg-mon-info {
           description "SRG global threshold info";
           leaf ha-srg-mon-status {
             type string;
             description "SRG monitor status";
           }
           leaf ha-srg-mon-threshold {
             type int32;
             description "SRG monitor threshold";
           }
           leaf ha-srg-mon-weight {
             type int32;
             description "SRG monitor weight";
           }
           leaf ha-srg-mon-failed-objects {
             type int32;
             description "SRG monitor failed objects";
           }
         }
         container chassis-high-availability-srg-obj-info {
           description "SRG monitor-object info";
           leaf ha-srg-obj-name {
             type string;
             description "SRG monitor object name";
           }
           leaf ha-srg-obj-status {
             type string;
             description "SRG monitor object status";
           }
           leaf ha-srg-obj-entries {
             type string;
             description "SRG monitor object monitored entries";
           }
           leaf ha-srg-obj-failure {
             type string;
             description "SRG monitor object monitored failures";
           }
           leaf ha-srg-obj-threshold {
             type int32;
             description "SRG monitor object threshold";
           }
           leaf ha-srg-obj-weight {
             type int32;
             description "SRG monitor object current weight";
           }
         }
         container chassis-high-availability-srg-bfdmon {
           description " SRG BFD mon information ";
           leaf ha-srg-bfdmon-status {
             type string;
             description "HA overall bfd-monitoring status";
           }
           container chassis-high-availability-srg-bfdmon-list {
             description " Display each BFD mon entry Information";
             leaf ha-srg-bfdmon-src-ipaddr {
               type string;
               description "Source IP address configured for HA bfd-monitoring";
             }
             leaf ha-srg-bfdmon-dst-ipaddr {
               type string;
               description "Destination IP address configured for HA bfd-monitoring";
             }
             leaf ha-srg-bfdmon-rt {
               type string;
               description "Routing instance configured for HA bfd-monitoring";
             }
             leaf ha-srg-bfdmon-type {
               type string;
               description "HA bfd-monitoring type";
             }
             leaf ha-srg-bfdmon-ifl-name {
               type string;
               description "HA bfd-monitoring IFL name";
             }
             leaf ha-srg-bfdmon-state {
               type string;
               description "HA bfd-monitoring state";
             }
           }
         }
         list high-availability-bfdmon-status-events {
           description "List of BFD-monitoring status events";
           leaf-list high-availability-bfdmon-status-event {
             type string;
             description "Recorded BFD-monitoring status event";
           }
         }
         container chassis-high-availability-srg-ipmon {
           description "SRG IP monitoring Info";
           leaf ha-srg-ipmon-status {
             type string;
             description "SRG overall IP-monitoring status";
           }
           container chassis-high-availability-srg-ipmon-list {
             description " Display each IP monitoring entry";
             leaf ha-srg-ipmon-dst-ipaddr {
               type string;
               description "Destination IP address configured for HA ip-monitoring";
             }
             leaf ha-srg-ipmon-rt {
               type string;
               description "Routing instance configured for HA ip-monitoring";
             }
             leaf ha-ipmon-status {
               type string;
               description "HA ip-monitoring status";
             }
             leaf ha-srg-ipmon-reason {
               type string;
               description "HA ip-monitoring failure reason";
             }
           }
         }
         container chassis-high-availability-srg-obj-ipmon {
           description "SRG monitor object IP monitoring Info";
           leaf ha-srg-obj-ipmon-threshold {
             type int32;
             description "SRG monitor object IP-monitoring threshold";
           }
           leaf ha-srg-obj-ipmon-weight {
             type int32;
             description "SRG monitor object IP-monitoring weight";
           }
           leaf ha-srg-obj-ipmon-status {
             type string;
             description "SRG monitor object IP-monitoring global status";
           }
           container chassis-high-availability-srg-obj-ipmon-list {
             description " Display each monitor object IP monitoring entry status";
             leaf ha-srg-obj-ipmon-entry-status {
               type string;
               description "HA SRG monitor object ip-monitoring state";
             }
             leaf ha-srg-obj-ipmon-entry-weight {
               type int32;
               description "HA SRG monitor object ip-monitoring weight";
             }
             leaf ha-srg-obj-ipmon-entry-dst-ipaddr {
               type string;
               description "Destination IP address configured for HA ip-monitoring";
             }
           }
         }
         container chassis-high-availability-srg-obj-ipmon-detail {
           description "SRG monitor object IP monitoring detail Info";
           container chassis-high-availability-srg-ipmon-list {
             description " Display each IP monitoring entry";
             leaf ha-srg-ipmon-dst-ipaddr {
               type string;
               description "Destination IP address configured for HA ip-monitoring";
             }
             leaf ha-srg-ipmon-rt {
               type string;
               description "Routing instance configured for HA ip-monitoring";
             }
             leaf ha-ipmon-status {
               type string;
               description "HA ip-monitoring status";
             }
             leaf ha-srg-ipmon-reason {
               type string;
               description "HA ip-monitoring failure reason";
             }
           }
         }
         list high-availability-ipmon-status-events {
           description "List of ip-monitoring status events";
           leaf-list high-availability-ipmon-status-event {
             type string;
             description "Recorded ip-monitoring status event";
           }
         }
         list high-availability-probe-status-events {
           description "List of activeness probe status events";
           leaf-list high-availability-probe-status-event {
             type string;
             description "Recorded activeness probe status event";
           }
         }
       }
     }
   }
   grouping chassis-high-availability-peer-info-detail-block {
     leaf high-availability-peer-desc {
       type string;
       description "Peer description";
     }
     leaf high-availability-peer-id {
       type int32;
       description "Peer identifier that is configured";
     }
     leaf high-availability-peer-ip-address {
       type jt:ipaddr;
       description "Peer remote IPv4 address that is configured";
     }
     leaf-list high-availability-local-interface {
       type string;
       description "Local interface";
     }
     leaf high-availability-peer-rt-instance {
       type string;
       description "Routing Instance name for HA peer";
     }
     leaf high-availability-peer-encryption-status {
       type string;
       description "Encryption status of the current node";
     }
     leaf high-availability-peer-bfd-status {
       type string;
       description "BFD Status of the current node";
     }
     leaf cold-sync-status {
       type string;
       description "Cold synchronization status";
     }
     leaf peer-hw-incompatible {
       type string;
       description "Peer hardware compatible status";
     }
     leaf peer-internal-interface {
       type string;
       description "Peer internal interface";
     }
     leaf peer-internal-local-ip {
       type jt:ipaddr;
       description "Internal local IPv4 address";
     }
     leaf peer-internal-peer-ip {
       type jt:ipaddr;
       description "Internal peer IPv4 address";
     }
     leaf peer-internal-routing-instance {
       type string;
       description "Peer internal routing instance";
     }
     leaf high-availability-peer-fwd-ip-address {
       type jt:ipaddr;
       description "Peer forwarding remote IP address";
     }
     leaf high-availability-local-fwd-interface {
       type string;
       description "Local forwarding interface";
     }
     leaf high-availability-peer-fwd-bfd-status {
       type string;
       description "BFD forwarding status of the current node";
     }
     container chassis-mnha-icl-peer-info {
       description "Displays mnha icl peer related info";
       leaf high-availability-peer-desc {
         type string;
         description "Peer description";
       }
       leaf peer-domain-id {
         type int32;
         description "Peer-domain-id";
       }
       leaf high-availability-peer-id {
         type int32;
         description "Peer identifier that is configured";
       }
       leaf high-availability-peer-ip-address {
         type jt:ipaddr;
         description "Peer remote IPv4 address that is configured";
       }
       leaf-list high-availability-local-interface {
         type string;
         description "Local interface";
       }
       leaf high-availability-peer-rt-instance {
         type string;
         description "Routing Instance name for HA peer";
       }
       leaf high-availability-peer-encryption-status {
         type string;
         description "Encryption status of the current node";
       }
       leaf high-availability-peer-bfd-status {
         type string;
         description "BFD Status of the current node";
       }
       leaf cold-sync-status {
         type string;
         description "Cold synchronization status";
       }
       leaf peer-hw-incompatible {
         type string;
         description "Peer hardware compatible status";
       }
       leaf peer-internal-interface {
         type string;
         description "Peer internal interface";
       }
       leaf peer-internal-local-ip {
         type jt:ipaddr;
         description "Internal local IPv4 address";
       }
       leaf peer-internal-peer-ip {
         type jt:ipaddr;
         description "Internal peer IPv4 address";
       }
       leaf peer-internal-routing-instance {
         type string;
         description "Peer internal routing instance";
       }
       leaf high-availability-peer-detect-time {
         type string;
         description "Configured Peer BFD detection time";
       }
       leaf srg0-cold-sync-status {
         type string;
         description "SRG0 cold sync status";
       }
       container chassis-mnha-local-node-idl-info {
         description "Displays high-availability local node IDL BFD and CS state";
         leaf states-from-domain-id {
           type int32;
           description "States from domain id";
         }
         leaf states-from-node-id {
           type int32;
           description "States from node id";
         }
         leaf domain-id {
           type int32;
           description "Domain-id";
         }
         leaf peer-id {
           type int32;
           description "Peer identifier";
         }
         leaf conn-state {
           type string;
           description "Conn state";
         }
         leaf rtt-result {
           type string;
           description "RTT result";
         }
         leaf cold-sync-status {
           type string;
           description "Cold synchronization status";
         }
         leaf srg0-idl-status {
           type string;
           description "SRG0 idl status";
         }
       }
       container chassis-mnha-peer-node-icl-info {
         description "Displays high-availability icl info";
         leaf states-from-domain-id {
           type int32;
           description "States from domain id";
         }
         leaf states-from-node-id {
           type int32;
           description "States from node id";
         }
         leaf icl-conn-state {
           type string;
           description "ICL Conn state";
         }
         leaf cold-sync-status {
           type string;
           description "Cold synchronization status";
         }
       }
       container chassis-mnha-peer-node-idl-info {
         description "Displays high-availability peer node IDL BFD and CS state";
         leaf states-from-domain-id {
           type int32;
           description "States from domain id";
         }
         leaf states-from-node-id {
           type int32;
           description "States from node id";
         }
         leaf domain-id {
           type int32;
           description "Domain-id";
         }
         leaf peer-id {
           type int32;
           description "Peer identifier";
         }
         leaf conn-state {
           type string;
           description "Conn state";
         }
         leaf rtt-result {
           type string;
           description "RTT result";
         }
         leaf cold-sync-status {
           type string;
           description "Cold synchronization status";
         }
         leaf srg0-idl-status {
           type string;
           description "SRG0 idl status";
         }
       }
       list high-availability-peer-packet-stats {
         description "Peer Packet Stats";
         leaf packet-send-err-cnt {
           type int32;
           description "Peer packet send error cnt";
         }
         leaf packet-recv-err-cnt {
           type int32;
           description "Peer packet recv error cnt";
         }
         list peer-packet-send-rcv-stats {
           description "Peer Packet Send receive Stats";
           list peer-packet-stats-list {
             description "Stats for each peer packet type";
             leaf peer-packet-type {
               type string;
               description "Peer packet Type";
             }
             leaf peer-packet-send-cnt {
               type int32;
               description "Peer packet sent count";
             }
             leaf peer-packet-rcv-cnt {
               type int32;
               description "Peer packet rcv cnt";
             }
           }
         }
       }
     }
     list chassis-mnha-idl-peer-info {
       description "Displays mnha idl peer related info";
       leaf high-availability-peer-desc {
         type string;
         description "Peer description";
       }
       leaf peer-domain-id {
         type int32;
         description "Peer-domain-id";
       }
       leaf high-availability-peer-id {
         type int32;
         description "Peer identifier that is configured";
       }
       leaf high-availability-peer-ip-address {
         type jt:ipaddr;
         description "Peer remote IPv4 address that is configured";
       }
       leaf-list high-availability-local-interface {
         type string;
         description "Local interface";
       }
       leaf high-availability-peer-rt-instance {
         type string;
         description "Routing Instance name for HA peer";
       }
       leaf high-availability-peer-encryption-status {
         type string;
         description "Encryption status of the current node";
       }
       leaf high-availability-peer-idl-bfd-status {
         type string;
         description "IDL BFD Status of the current node";
       }
       leaf cold-sync-status {
         type string;
         description "Cold synchronization status";
       }
       leaf peer-hw-incompatible {
         type string;
         description "Peer hardware compatible status";
       }
       leaf peer-internal-interface {
         type string;
         description "Peer internal interface";
       }
       leaf peer-internal-local-ip {
         type jt:ipaddr;
         description "Internal local IPv4 address";
       }
       leaf peer-internal-peer-ip {
         type jt:ipaddr;
         description "Internal peer IPv4 address";
       }
       leaf peer-internal-routing-instance {
         type string;
         description "Peer internal routing instance";
       }
       leaf high-availability-peer-detect-time {
         type string;
         description "Configured Peer BFD detection time";
       }
       container chassis-mnha-peer-node-icl-info {
         description "Displays high-availability icl info";
         leaf states-from-domain-id {
           type int32;
           description "States from domain id";
         }
         leaf states-from-node-id {
           type int32;
           description "States from node id";
         }
         leaf icl-conn-state {
           type string;
           description "ICL Conn state";
         }
         leaf cold-sync-status {
           type string;
           description "Cold synchronization status";
         }
       }
       container chassis-mnha-peer-domain-idl-info {
         description "Displays high-availability peer domain IDL BFD and CS state";
         leaf states-from-domain-id {
           type int32;
           description "States from domain id";
         }
         leaf states-from-node-id {
           type int32;
           description "States from node id";
         }
         leaf domain-id {
           type int32;
           description "Domain-id";
         }
         leaf peer-id {
           type int32;
           description "Peer identifier";
         }
         leaf conn-state {
           type string;
           description "Conn state";
         }
         leaf rtt-result {
           type string;
           description "RTT result";
         }
         leaf cold-sync-status {
           type string;
           description "Cold synchronization status";
         }
         leaf srg0-idl-status {
           type string;
           description "SRG0 idl status";
         }
       }
       list high-availability-peer-packet-stats {
         description "Peer Packet Stats";
         leaf packet-send-err-cnt {
           type int32;
           description "Peer packet send error cnt";
         }
         leaf packet-recv-err-cnt {
           type int32;
           description "Peer packet recv error cnt";
         }
         list peer-packet-send-rcv-stats {
           description "Peer Packet Send receive Stats";
           list peer-packet-stats-list {
             description "Stats for each peer packet type";
             leaf peer-packet-type {
               type string;
               description "Peer packet Type";
             }
             leaf peer-packet-send-cnt {
               type int32;
               description "Peer packet sent count";
             }
             leaf peer-packet-rcv-cnt {
               type int32;
               description "Peer packet rcv cnt";
             }
           }
         }
       }
     }
     list high-availability-peer-packet-stats {
       description "Peer Packet Stats";
       leaf packet-send-err-cnt {
         type int32;
         description "Peer packet send error cnt";
       }
       leaf packet-recv-err-cnt {
         type int32;
         description "Peer packet recv error cnt";
       }
       list peer-packet-send-rcv-stats {
         description "Peer Packet Send receive Stats";
         list peer-packet-stats-list {
           description "Stats for each peer packet type";
           leaf peer-packet-type {
             type string;
             description "Peer packet Type";
           }
           leaf peer-packet-send-cnt {
             type int32;
             description "Peer packet sent count";
           }
           leaf peer-packet-rcv-cnt {
             type int32;
             description "Peer packet rcv cnt";
           }
         }
       }
     }
   }
   grouping chassis-high-availability-srg-terse-info-block {
     container chassis-high-availability-srg-info {
       description "Displays high-availability services redundancy group info";
       container chassis-high-availability-srg-info-list {
         description "Displays each services redundancy group info";
         leaf srg-id {
           type int32;
           description "Current services redundancy group identifier";
         }
         leaf deployment-type {
           type string;
           description "Deployment Type";
         }
         leaf node-role {
           type string;
           description "Local node role";
         }
         leaf activeness-priority {
           type int32;
           description "SRG activeness priority";
         }
         leaf preemption {
           type string;
           description "Preemption enable flag Status";
         }
         leaf process-pkt-in-bkp-state {
           type string;
           description "SRG backup state pkt processing info";
         }
         leaf control-plane {
           type string;
           description "Control plane status";
         }
         leaf system-integrity-check {
           type string;
           description "Status of system integrity check";
         }
         leaf failure-events {
           type string;
           description "List of failure events";
         }
         leaf peer-id {
           type int32;
           description "Peer identifier";
         }
         leaf peer-node-role {
           type string;
           description "Peer node role";
         }
         leaf health-status {
           type string;
           description "Peer health status";
         }
         leaf failover-readiness {
           type string;
           description "SRG failover readiness";
         }
       }
     }
     container high-availability-srg-signal-rt-info {
       description "  SRG Signal route Info";
       container ha-srg-signal-rt-list {
         description "Display each signal route information";
         leaf ha-srg-signal-rt-type {
           type string;
           description "  SRG  Signal route type";
         }
         leaf ha-srg-signal-rt-ipaddr {
           type string;
           description "IP address configured as SRG active signal route";
         }
         leaf ha-srg-signal-rt-rt {
           type string;
           description "Routing table configured for active signal route";
         }
         leaf ha-srg-signal-rt-status {
           type string;
           description " SRG signal Route installation status";
         }
       }
     }
     container high-availability-srg-vip-info {
       description "  SRG Virtual IP Info";
       container ha-srg-vip-list {
         description "Display each Virtual IP information";
         leaf ha-srg-vip-index {
           type string;
           description "  SRG  Signal Virtual IP Index";
         }
         leaf ha-srg-virtual-ipaddr {
           type string;
           description "IP address configured as SRG virtual IP";
         }
         leaf ha-srg-virtual-mac-address {
           type string;
           description "MAC address for the virtual IP.";
         }
         leaf ha-srg-vip-if-name {
           type string;
           description "Interface for the virtual IP assignment";
         }
         leaf ha-srg-vip-status {
           type string;
           description " SRG Virtual IP assignmentstatus";
         }
       }
     }
     container chassis-high-availability-srg-probe {
       description "SRG split brain prevention probe info";
       leaf ha-srg-probe-dst-ipaddr {
         type string;
         description "Destination IP address used for probing";
       }
       leaf ha-srg-probe-src-ipaddr {
         type string;
         description "Source IP address used for probing";
       }
       leaf ha-srg-vip-if-name {
         type string;
         description "Interface for the virtual IP assignment";
       }
       leaf ha-srg-probe-rt {
         type string;
         description "Routing instance used for probing";
       }
       leaf ha-srg-probe-type {
         type string;
         description "Probing type";
       }
       leaf ha-probe-interval {
         type int32;
         description "HA probe interval in ms";
       }
       leaf ha-probe-multiplier {
         type int32;
         description "HA probe multiplier";
       }
       leaf ha-probe-status {
         type string;
         description "Probing status";
       }
       leaf ha-probe-result {
         type string;
         description "Probing result";
       }
       leaf ha-srg-probe-fail-reason {
         type string;
         description "Probing failure reason";
       }
     }
     container chassis-high-availability-srg-ipmon {
       description "SRG IP monitoring Info";
       leaf ha-srg-ipmon-status {
         type string;
         description "SRG overall IP-monitoring status";
       }
       container chassis-high-availability-srg-ipmon-list {
         description " Display each IP monitoring entry";
         leaf ha-srg-ipmon-dst-ipaddr {
           type string;
           description "Destination IP address configured for HA ip-monitoring";
         }
         leaf ha-srg-ipmon-rt {
           type string;
           description "Routing instance configured for HA ip-monitoring";
         }
         leaf ha-ipmon-status {
           type string;
           description "HA ip-monitoring status";
         }
         leaf ha-srg-ipmon-reason {
           type string;
           description "HA ip-monitoring failure reason";
         }
       }
     }
     container chassis-high-availability-srg-bfdmon {
       description " SRG BFD mon information ";
       leaf ha-srg-bfdmon-status {
         type string;
         description "HA overall bfd-monitoring status";
       }
       container chassis-high-availability-srg-bfdmon-list {
         description " Display each BFD mon entry Information";
         leaf ha-srg-bfdmon-src-ipaddr {
           type string;
           description "Source IP address configured for HA bfd-monitoring";
         }
         leaf ha-srg-bfdmon-dst-ipaddr {
           type string;
           description "Destination IP address configured for HA bfd-monitoring";
         }
         leaf ha-srg-bfdmon-rt {
           type string;
           description "Routing instance configured for HA bfd-monitoring";
         }
         leaf ha-srg-bfdmon-type {
           type string;
           description "HA bfd-monitoring type";
         }
         leaf ha-srg-bfdmon-ifl-name {
           type string;
           description "HA bfd-monitoring IFL name";
         }
         leaf ha-srg-bfdmon-state {
           type string;
           description "HA bfd-monitoring state";
         }
       }
     }
     container chassis-high-availability-srg-ifmon {
       description "SRG Interface monitoring Info";
       leaf ha-srg-ifmon-status {
         type string;
         description "HA overall Interface-monitoring status";
       }
       container chassis-high-availability-srg-ifmon-list {
         description " Display each Interface monitoring entry";
         leaf ha-srg-ifmon-if-name {
           type string;
           description "HA Interface-monitoring IF name";
         }
         leaf ha-srg-ifmon-state {
           type string;
           description "HA Interface-monitoring state";
         }
       }
     }
     list high-availability-srg-state-events {
       description "List of service redundancy group state change events";
       leaf-list high-availability-srg-state-event {
         type string;
         description "Recorded service redundancy group state change event";
       }
     }
     list chassis-high-availability-prefix-information {
       container chassis-high-availability-prefix-srgid-information {
         description "Display ip prefix and srgid mapping info";
         container chassis-high-availability-prefix-srgid-information-list {
           leaf ha-mnha-ip-prefix-srgid {
             type string;
             description "MNHA srg-id";
           }
           leaf ha-mnha-ip-prefix {
             type string;
             description "IP Prefix";
           }
           leaf ha-mnha-ip-vrf {
             type string;
             description "Routing Table";
           }
         }
       }
       container chassis-high-availability-prefix-ip-information {
         description "Display srgid id info given an ip address";
         container chassis-high-availability-prefix-ip-information-list {
           leaf ha-mnha-ip-srgid {
             type int32;
             description "MNHA srg-id";
           }
         }
       }
     }
     list chassis-high-availability-srg-mon-obj-info {
       container chassis-high-availability-srg-mon-info {
         description "SRG global threshold info";
         leaf ha-srg-mon-status {
           type string;
           description "SRG monitor status";
         }
         leaf ha-srg-mon-threshold {
           type int32;
           description "SRG monitor threshold";
         }
         leaf ha-srg-mon-weight {
           type int32;
           description "SRG monitor weight";
         }
         leaf ha-srg-mon-failed-objects {
           type int32;
           description "SRG monitor failed objects";
         }
       }
       container chassis-high-availability-srg-obj-info {
         description "SRG monitor-object info";
         leaf ha-srg-obj-name {
           type string;
           description "SRG monitor object name";
         }
         leaf ha-srg-obj-status {
           type string;
           description "SRG monitor object status";
         }
         leaf ha-srg-obj-entries {
           type string;
           description "SRG monitor object monitored entries";
         }
         leaf ha-srg-obj-failure {
           type string;
           description "SRG monitor object monitored failures";
         }
         leaf ha-srg-obj-threshold {
           type int32;
           description "SRG monitor object threshold";
         }
         leaf ha-srg-obj-weight {
           type int32;
           description "SRG monitor object current weight";
         }
       }
       container chassis-high-availability-srg-obj-ipmon {
         description "SRG monitor object IP monitoring Info";
         leaf ha-srg-obj-ipmon-threshold {
           type int32;
           description "SRG monitor object IP-monitoring threshold";
         }
         leaf ha-srg-obj-ipmon-weight {
           type int32;
           description "SRG monitor object IP-monitoring weight";
         }
         leaf ha-srg-obj-ipmon-status {
           type string;
           description "SRG monitor object IP-monitoring global status";
         }
         container chassis-high-availability-srg-obj-ipmon-list {
           description " Display each monitor object IP monitoring entry status";
           leaf ha-srg-obj-ipmon-entry-status {
             type string;
             description "HA SRG monitor object ip-monitoring state";
           }
           leaf ha-srg-obj-ipmon-entry-weight {
             type int32;
             description "HA SRG monitor object ip-monitoring weight";
           }
           leaf ha-srg-obj-ipmon-entry-dst-ipaddr {
             type string;
             description "Destination IP address configured for HA ip-monitoring";
           }
         }
       }
       container chassis-high-availability-srg-obj-ipmon-detail {
         description "SRG monitor object IP monitoring detail Info";
         container chassis-high-availability-srg-ipmon-list {
           description " Display each IP monitoring entry";
           leaf ha-srg-ipmon-dst-ipaddr {
             type string;
             description "Destination IP address configured for HA ip-monitoring";
           }
           leaf ha-srg-ipmon-rt {
             type string;
             description "Routing instance configured for HA ip-monitoring";
           }
           leaf ha-ipmon-status {
             type string;
             description "HA ip-monitoring status";
           }
           leaf ha-srg-ipmon-reason {
             type string;
             description "HA ip-monitoring failure reason";
           }
         }
       }
       container chassis-high-availability-srg-obj-bfdmon {
         description "SRG monitor object BFD monitoring Info";
         leaf ha-srg-obj-bfdmon-threshold {
           type int32;
           description "SRG monitor object BFD-monitoring threshold";
         }
         leaf ha-srg-obj-bfdmon-weight {
           type int32;
           description "SRG monitor object BFD-monitoring weight";
         }
         leaf ha-srg-obj-bfdmon-status {
           type string;
           description "SRG monitor object BFD-monitoring global status";
         }
         container chassis-high-availability-srg-obj-bfdmon-list {
           description "Display each monitor object BFD monitoring entry status";
           leaf ha-srg-obj-bfdmon-entry-status {
             type string;
             description "HA SRG monitor object BFD-monitoring state";
           }
           leaf ha-srg-obj-bfdmon-entry-weight {
             type int32;
             description "HA SRG monitor object BFD-monitoring weight";
           }
           leaf ha-srg-obj-bfdmon-entry-dst-bfdaddr {
             type string;
             description "Destination BFD address configured for HA BFD-monitoring";
           }
         }
       }
       container chassis-high-availability-srg-obj-bfdmon-detail {
         description "SRG monitor object BFD mon information ";
         container chassis-high-availability-srg-bfdmon-list {
           description " Display each BFD mon entry Information";
           leaf ha-srg-bfdmon-src-ipaddr {
             type string;
             description "Source IP address configured for HA bfd-monitoring";
           }
           leaf ha-srg-bfdmon-dst-ipaddr {
             type string;
             description "Destination IP address configured for HA bfd-monitoring";
           }
           leaf ha-srg-bfdmon-rt {
             type string;
             description "Routing instance configured for HA bfd-monitoring";
           }
           leaf ha-srg-bfdmon-type {
             type string;
             description "HA bfd-monitoring type";
           }
           leaf ha-srg-bfdmon-ifl-name {
             type string;
             description "HA bfd-monitoring IFL name";
           }
           leaf ha-srg-bfdmon-state {
             type string;
             description "HA bfd-monitoring state";
           }
         }
       }
       container chassis-high-availability-srg-obj-ifmon {
         description "SRG monitor object IF monitoring Info";
         leaf ha-srg-obj-ifmon-threshold {
           type int32;
           description "SRG monitor object IF-monitoring threshold";
         }
         leaf ha-srg-obj-ifmon-weight {
           type int32;
           description "SRG monitor object IF-monitoring current weight";
         }
         leaf ha-srg-ifmon-status {
           type string;
           description "HA overall Interface-monitoring status";
         }
         container chassis-high-availability-srg-obj-ifmon-list {
           description "Display each monitor object IF monitoring entry status";
           leaf ha-srg-ifmon-entry-status {
             type string;
             description "HA SRG monitor object IF-monitoring entry status";
           }
           leaf ha-srg-obj-ifmon-entry-weight {
             type int32;
             description "HA SRG monitor object IF-monitoring entry weight";
           }
           leaf ha-srg-ifmon-if-name {
             type string;
             description "HA Interface-monitoring IF name";
           }
         }
       }
     }
   }
   grouping chassis-high-availability-prefix-information-block {
     container chassis-high-availability-prefix-srgid-information {
       description "Display ip prefix and srgid mapping info";
       container chassis-high-availability-prefix-srgid-information-list {
         leaf ha-mnha-ip-prefix-srgid {
           type string;
           description "MNHA srg-id";
         }
         leaf ha-mnha-ip-prefix {
           type string;
           description "IP Prefix";
         }
         leaf ha-mnha-ip-vrf {
           type string;
           description "Routing Table";
         }
       }
     }
     container chassis-high-availability-prefix-ip-information {
       description "Display srgid id info given an ip address";
       container chassis-high-availability-prefix-ip-information-list {
         leaf ha-mnha-ip-srgid {
           type int32;
           description "MNHA srg-id";
         }
       }
     }
   }
   grouping chassis-high-availability-prefix-ip-information-block {
     container chassis-high-availability-prefix-ip-information-list {
       leaf ha-mnha-ip-srgid {
         type int32;
         description "MNHA srg-id";
       }
     }
   }
   grouping chassis-high-availability-prefix-srgid-information-block {
     container chassis-high-availability-prefix-srgid-information-list {
       leaf ha-mnha-ip-prefix-srgid {
         type string;
         description "MNHA srg-id";
       }
       leaf ha-mnha-ip-prefix {
         type string;
         description "IP Prefix";
       }
       leaf ha-mnha-ip-vrf {
         type string;
         description "Routing Table";
       }
     }
   }
   grouping chassis-high-availability-prefix-policy-information-block {
     container chassis-high-availability-ip-prefix {
       description "Display ip and policy prefix mapping info";
       container chassis-high-availability-ip-prefix-list {
         leaf ha-policy-ip {
           type string;
           description "IP Prefix";
         }
         leaf ha-policy-prefix {
           type string;
           description "Policy Prefix";
         }
       }
     }
     container chassis-high-availability-prefix-srgid {
       description "Display ip prefix and srgid mapping info";
       container chassis-high-availability-prefix-srgid-list {
         leaf ha-mnha-srgid {
           type string;
           description "MNHA srg-id";
         }
         leaf ha-mnha-prefix-vrf {
           type string;
           description "Routing Table";
         }
         leaf ha-mnha-prefix-name {
           type string;
           description "IP Prefix";
         }
       }
     }
   }
 }
