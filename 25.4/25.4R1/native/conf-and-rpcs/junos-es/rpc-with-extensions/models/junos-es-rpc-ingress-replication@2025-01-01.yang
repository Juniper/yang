/*
 * Copyright (c) 2025 Juniper Networks, Inc.
 * All rights reserved.
 */
 module junos-es-rpc-ingress-replication {
   namespace "http://yang.juniper.net/junos-es/rpc/ingress-replication";

   prefix ingress-replication;

   import junos-common-ddl-extensions {
     prefix junos;
     revision-date 2025-01-01;
   }

   import junos-common-types {
     prefix jt;
     revision-date 2025-01-01;
   }

   organization "Juniper Networks, Inc.";

   contact "yang-support@juniper.net";

   description "Junos RPC YANG module for ingress-replication command(s)";

   revision 2025-01-01 {
     description "Junos: 25.4R1.12";
   }

   rpc get-ingress-replication-information {
     description "Show Ingress-Replication tunnel information";
     junos:command "show ingress-replication";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf application {
         description "Display application specific ingress-replication tunnels";
         junos:cli-feature "nokeyword";
         type enumeration {
           enum "mvpn" {
             description "MVPN ingress-replication tunnels";
           }
         }
         mandatory true;
       }
       leaf tunnel-name {
         description "Name of Ingress-Replication tunnel";
         junos:cli-feature "nokeyword";
         default "all";
         type string;
       }
     }
     output {
       container ingress-replication-information {
         uses ingress-replication-information-block;
       }
     }
   }
   grouping command-forwarding {
     leaf no-forwarding {
       description "No forwarding";
       type empty;
     }
     choice chassis-selector {
       case case_1 {
         leaf all-chassis {
           description "All chassis";
           type empty;
         }
       }
       case case_2 {
         leaf all-lcc {
           description "All LCC chassis";
           type empty;
         }
       }
       case case_3 {
         leaf scc {
           description "SCC";
           type empty;
         }
       }
       case case_4 {
         leaf sfc {
           description "SFC";
           type union {
             type string {
               pattern "<.*>|$.*";
             }
             type uint32;
           }
         }
       }
       case case_5 {
         leaf lcc {
           description "Specific LCC";
           type union {
             type string {
               pattern "<.*>|$.*";
             }
             type uint32;
           }
         }
       }
       case case_6 {
         leaf node {
           description "Specific node";
           type string;
         }
       }
       case case_7 {
         leaf bsys {
           description "Base system";
           type empty;
         }
       }
       case case_8 {
         leaf gnf {
           description "Specific guest network function";
           type union {
             type string {
               pattern "<.*>|$.*";
             }
             type uint32 {
               range "1 .. 10";
             }
           }
         }
       }
       case case_9 {
         leaf all-gnfs {
           description "All guest network functions";
           type empty;
         }
       }
       case case_10 {
         leaf all-system {
           description "All system (BSYS and GNFs)";
           type empty;
         }
       }
       case case_11 {
         leaf server {
           description "Specific server slot";
           type union {
             type string {
               pattern "<.*>|$.*";
             }
             type uint32 {
               range "0 .. 1";
             }
           }
         }
       }
       case case_12 {
         leaf all-servers {
           description "All servers";
           type empty;
         }
       }
       case case_13 {
         leaf vnf {
           description "Specific virtual-network-function";
           type string;
         }
       }
       case case_14 {
         leaf all-vnfs {
           description "All virtual-network-functions";
           type empty;
         }
       }
     }
     choice re-selector {
       case case_1 {
         leaf re0 {
           description "RE0";
           type empty;
         }
       }
       case case_2 {
         leaf re1 {
           description "RE1";
           type empty;
         }
       }
       case case_3 {
         leaf routing-engine {
           description "Specific routing engine";
           type enumeration {
             enum "local" {
               description "Local routing engine";
             }
             enum "other" {
               description "Other routing engine";
             }
             enum "master" {
               description "Master routing engine";
             }
             enum "backup" {
               description "Backup routing engine";
             }
             enum "both" {
               description "Both routing engines";
             }
           }
         }
       }
     }
     choice lr-selector {
       case case_1 {
         leaf logical-system {
           description "Name of logical system, or 'all'";
           type string;
         }
       }
     }
     choice tenant-selector {
       case case_1 {
         leaf tenant {
           description "Name of tenant, or 'all'";
           type string;
         }
       }
     }
     choice vc-selector {
       case case_1 {
         leaf local {
           description "Local virtual chassis member";
           type empty;
         }
       }
       case case_2 {
         leaf all-members {
           description "All virtual chassis members";
           type empty;
         }
       }
       case case_3 {
         leaf member {
           description "Specific virtual chassis member which is master";
           type union {
             type string {
               pattern "<.*>|$.*";
             }
             type uint32;
           }
         }
       }
     }
   }
   grouping ingress-replication-information-block {
     container ir-tunnel {
       list ir-tunnel-entry {
         leaf ir-tunnel-name {
           type string;
           description "Ingress-Replication tunnel name";
         }
         leaf ir-tunnel-nh {
           type uint32;
         }
         leaf ir-tunnel-nh-type {
           type string;
         }
         leaf ir-tunnel-application {
           type string;
           description "Application that owns the Ingress-Replication tunnel";
         }
         leaf ir-tunnel-transport-class-name {
           type string;
           description "Ingress-Replication transport class name";
         }
         leaf ir-tunnel-regular-expression {
           type string;
           description "Ingress-Replication regular expression";
         }
         container ir-unicast-tunnel {
           list ir-unicast-tunnel-entry {
             leaf ir-unicast-tunnel-dst {
               type string;
               description "Unicast tunnel leaf address";
             }
             leaf ir-unicast-tunnel-type {
               type string;
               description "Ingress-Replication unicast tunnel type";
             }
             leaf ir-unicast-tunnel-mode {
               type string;
               description "Ingress-Replication unicast tunnel mode";
             }
             leaf ir-unicast-tunnel-state {
               type string;
               description "Ingress-Replication unicast tunnel status";
             }
             leaf ir-unicast-tunnel-nh {
               type uint32;
             }
             leaf ir-unicast-is-preferred {
               type string;
               description "Ingress-Replication unicast preferred tunnel information";
             }
           }
         }
       }
     }
     container ir-unicast-tunnel {
     }
   }
 }
