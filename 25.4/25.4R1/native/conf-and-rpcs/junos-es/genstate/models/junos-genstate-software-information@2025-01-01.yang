module junos-genstate-software-information {
   yang-version 1;
   namespace "http://yang.juniper.net/junos/genstate/software-information";
   prefix jgsi;

   import junos-genstate {
     prefix jgs;
     revision-date 2025-01-01;
   }

   import junos-common-types {
     prefix jt;
     revision-date 2025-01-01;
   }

   organization
     "Juniper Networks, Inc.";

   contact
     "Juniper Networks, Inc.

      1133 Innovation Way
      Sunnyvale, CA 94089

      +1 888 314-5822

      E-mail: yang-support@juniper.net";

   description "Junos genstate data model for software-information";

   revision 2025-01-01 {
     description "Junos: 25.4R1.12";
   }

   grouping software-information-top {
     description "Top-level grouping";
     container software-information {
       description "Top-level container";
       leaf host-name {
         type string;
         description "Hostname of router";
       }
       leaf product-model {
         type string;
         description "Hardware model name";
       }
       leaf os-name {
         type string;
         description "Operating System Name";
       }
       leaf junos-version {
         type string;
         description "Junos Version";
       }
       leaf yocto-version {
         type string;
         description "Yocto Version";
       }
       leaf kernel-version {
         type string;
         description "Kernel version";
       }
       leaf product-name {
         type string;
         description "Product name";
       }
       container external-package-information {
         list external-package-item {
           leaf external-package-name {
             type string;
           }
           leaf external-package-version {
             type string;
           }
         }
       }
       list package-information {
         key "name";
         leaf comment {
           type string;
         }
         leaf name {
           type string;
           description "Syslog message tag name";
         }
         leaf package-name {
           type string;
           description "Name of software package";
         }
       }
       list version-information {
         leaf component {
           type string;
         }
         leaf release {
           type string;
           description "Release name";
         }
         leaf builder {
           type string;
         }
         leaf build-date {
           type string;
           description "Build date";
         }
         leaf service-interface {
           type string;
         }
         leaf major {
           type int32;
         }
         leaf minor {
           type int32;
         }
         leaf edit {
           type int32;
         }
         leaf release-category {
           type string;
         }
         leaf build-number {
           type int32;
         }
         leaf spin {
           type int32;
         }
       }
     }
   }
   augment "/jgs:genstate" {
     description "Adds software-information to top-level genstate";
     uses software-information-top;
   }
 }
