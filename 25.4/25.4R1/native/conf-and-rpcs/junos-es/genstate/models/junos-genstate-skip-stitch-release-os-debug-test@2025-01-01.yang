module junos-genstate-skip-stitch-release-os-debug-test {
   yang-version 1;
   namespace "http://yang.juniper.net/junos/genstate/skip-stitch-release-os-debug-test";
   prefix jgssrodt;

   import junos-genstate {
     prefix jgs;
     revision-date 2025-01-01;
   }

   import junos-common-types {
     prefix jt;
     revision-date 2025-01-01;
   }

   organization
     "Juniper Networks, Inc.";

   contact
     "Juniper Networks, Inc.

      1133 Innovation Way
      Sunnyvale, CA 94089

      +1 888 314-5822

      E-mail: yang-support@juniper.net";

   description "Junos genstate data model for skip-stitch-release-os-debug-test";

   revision 2025-01-01 {
     description "Junos: 25.4R1.12";
   }

   grouping skip-stitch-release-os-debug-test-top {
     description "Top-level grouping";
     container skip-stitch-release-os-debug-test {
       description "Top-level container";
       leaf srlg-name {
         type string;
       }
       leaf srlg-value {
         type uint32;
       }
     }
   }
   augment "/jgs:genstate" {
     description "Adds skip-stitch-release-os-debug-test to top-level genstate";
     uses skip-stitch-release-os-debug-test-top;
   }
 }
