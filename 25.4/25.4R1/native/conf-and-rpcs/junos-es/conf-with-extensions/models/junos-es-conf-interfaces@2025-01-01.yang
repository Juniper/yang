/*
 * Copyright (c) 2025 Juniper Networks, Inc.
 * All rights reserved.
 */
 module junos-es-conf-interfaces {
   namespace "http://yang.juniper.net/junos-es/conf/interfaces";

   prefix jc-interfaces;

   import junos-common-ddl-extensions {
     prefix junos;
     revision-date 2025-01-01;
   }

   import junos-common-types {
     prefix jt;
     revision-date 2025-01-01;
   }

   import junos-es-conf-root {
     prefix jc;
     revision-date 2025-01-01;
   }

   organization "Juniper Networks, Inc.";

   contact "yang-support@juniper.net";

   description "Junos interfaces configuration module";

   revision 2025-01-01 {
     description "Junos: 25.4R1.12";
   }

   augment /jc:configuration {
     uses interfaces-group;
   }
   augment /jc:configuration/jc:groups {
     uses interfaces-group;
   }
   grouping interfaces-group {
     container interfaces {
       description "Interface configuration";
       uses apply-advanced;
       list pic-set {
         key name;
         ordered-by user;
         description "NP bundling configuration";
         leaf name {
           description "Pic set name";
           junos:cli-feature "nokeyword";
           type string {
             length "1 .. 127";
           }
         }
         uses apply-advanced;
         list interface {
           key name;
           ordered-by user;
           description "One or more interfaces that use this picset";
           leaf name {
             description "Interface name";
             junos:cli-feature "nokeyword";
             type string {
               length "1 .. 127";
               junos:posix-pattern "^((ge-)|(mge-)|(xe-))";
               junos:pattern-message "Only ge, mge and xe inteface is supported";
             }
           }
           uses apply-advanced;
         }
         list fpc {
           key name;
           ordered-by user;
           leaf name {
             description "FPC slot number";
             junos:cli-feature "nokeyword";
             type union {
               type string {
                 pattern "<.*>|$.*";
               }
               type uint32;
             }
           }
           uses apply-advanced;
           list pic {
             key name;
             ordered-by user;
             description "Physical Interface Card number";
             leaf name {
               description "PIC slot number";
               junos:cli-feature "nokeyword";
               type union {
                 type string {
                   pattern "<.*>|$.*";
                 }
                 type uint32;
               }
             }
             uses apply-advanced;
           }
         }
       }
       list interface-set {
         key name;
         description "Logical interface set configuration";
         leaf name {
           junos:cli-feature "nokeyword";
           type string;
         }
         uses apply-advanced;
         list interface {
           key name;
           description "One or more interfaces that belong to interface set";
           leaf name {
             description "Interface name";
             junos:cli-feature "nokeyword";
             junos:must "(\"interfaces $$\")";
             junos:must-message "Interface should have configuration defined for adding to interface-set";
             type union {
               type jt:interface-device;
               type string {
                 pattern "<.*>|$.*";
               }
             }
           }
           uses apply-advanced;
           list unit {
             key name;
             description "One or more logical interface unit numbers";
             junos:must "(!(\".. vlan-tags-outer\"))";
             junos:must-message "'unit' statement cannot be included along with 'vlan-tags-outer' statement";
             leaf name {
               description "Unit number";
               junos:cli-feature "nokeyword";
               junos:must "(\"interfaces ${interface} unit $$\")";
               junos:must-message "Interface unit should have configuration defined for adding to interface-set";
               type union {
                 type string {
                   pattern "<.*>|$.*";
                 }
                 type uint32 {
                   range "0 .. 1073741823";
                 }
               }
             }
             uses apply-advanced;
           }
           list vlan-tags-outer {
             key name;
             description "One or more outer VLAN tags";
             junos:must "(!(\".. unit\"))";
             junos:must-message "'vlan-tags-outer' statement cannot be included along with 'unit' statement";
             leaf name {
               description "VLAN tag ID";
               junos:cli-feature "nokeyword";
               type union {
                 type string {
                   pattern "<.*>|$.*";
                 }
                 type uint32 {
                   range "0 .. 4094";
                 }
               }
             }
             uses apply-advanced;
           }
         }
       }
       container stacked-interface-set {
         presence "enable stacked-interface-set";
         description "Stacked interface set configuration";
         uses apply-advanced;
         list interface-set {
           key name;
           ordered-by user;
           description "Stacked parent interface set configuration";
           leaf name {
             junos:cli-feature "nokeyword";
             type string;
           }
           uses apply-advanced;
           list interface-set {
             key name;
             ordered-by user;
             description "Stacked child interface set configuration";
             leaf name {
               junos:cli-feature "nokeyword";
               type string;
             }
             uses apply-advanced;
           }
         }
       }
       container traceoptions {
         description "Interface trace options";
         uses apply-advanced;
         leaf no-remote-trace {
           description "Disable remote tracing";
           junos:must "(\"system tracing\")";
           junos:must-message "'no-remote-trace' is valid only when [system tracing] is configured";
           type empty;
         }
         container file {
           junos:cli-feature "oneliner";
           description "Trace file information";
           leaf filename {
             description "Name of file in which to write trace information";
             junos:cli-feature "nokeyword";
             type string {
               length "1 .. 1024";
               junos:posix-pattern "![/ %]";
               junos:pattern-message "Must not contain \'/\', % or a space";
             }
           }
           leaf size {
             description "Maximum trace file size";
             units "bytes";
             type string;
           }
           leaf files {
             description "Maximum number of trace files";
             default "3";
             type union {
               type string {
                 pattern "<.*>|$.*";
               }
               type uint32 {
                 range "2 .. 1000";
               }
             }
           }
           choice world-readable-choice {
             leaf world-readable {
               description "Allow any user to read the log file";
               type empty;
             }
             leaf no-world-readable {
               description "Don't allow any user to read the log file";
               type empty;
             }
           }
           leaf match {
             description "Regular expression for lines to be logged";
             type jt:regular-expression;
           }
         }
         list flag {
           key name;
           junos:cli-feature "oneliner";
           description "Tracing parameters";
           leaf name {
             junos:cli-feature "nokeyword";
             type enumeration {
               enum "all" {
                 description "Enable all configuration logging";
               }
               enum "kernel" {
                 description "Log configuration IPC messages to kernel";
               }
               enum "change-events" {
                 description "Log changes that produce configuration events";
               }
               enum "kernel-detail" {
                 description "Log details of configuration messages to kernel";
               }
               enum "config-states" {
                 description "Log the configuration state machine changes";
               }
               enum "resource-usage" {
                 description "Log the resource usage for different states";
               }
               enum "gres-events" {
                 description "Log the events related to GRES ";
               }
               enum "select-events" {
                 description "Log the events on select state machine ";
               }
               enum "bfd-events" {
                 description "Log BFD related events";
               }
               enum "lib-events" {
                 description "Log DCD library related events";
               }
               enum "reserved" {
                 description "Reserved DCD logs";
               }
               enum "emergency" {
                 description "Log DCD emergency events";
               }
               enum "alert" {
                 description "Log DCD alert events";
               }
               enum "critical" {
                 description "Log DCD critical events";
               }
               enum "error" {
                 description "Log DCD error events";
               }
               enum "warning" {
                 description "Log DCD warning events";
               }
               enum "notice" {
                 description "Log DCD notification events";
               }
               enum "informational" {
                 description "Log DCD informations";
               }
               enum "debugging" {
                 description "Log DCD debug events";
               }
               enum "verbose" {
                 description "Log DCD debug all events";
               }
               enum "japi" {
                 description "Log DCD JAPI events";
               }
             }
           }
           leaf disable {
             description "Disable this trace flag";
             type empty;
           }
         }
       }
       list interface-range {
         key name;
         ordered-by user;
         description "Interface ranges configuration";
         leaf name {
           description "Interface-range name";
           junos:cli-feature "nokeyword";
           type string {
             length "1 .. 128";
             junos:posix-pattern "^[[:alpha:]][[:alnum:]_.-]+$";
             junos:pattern-message "Must start with a letter followed by letters, numbers, dashes or underscore";
           }
         }
         list member {
           key name;
           ordered-by user;
           description "Interfaces belonging to the interface range";
           leaf name {
             description "Member interface name";
             junos:cli-feature "nokeyword";
             type union {
               type jt:interface-range-wild;
               type string {
                 pattern "<.*>|$.*";
               }
             }
           }
           uses apply-advanced;
         }
         list member-range {
           key name;
           ordered-by user;
           junos:cli-feature "oneliner";
           description "Interfaces range in <start-range> to <end-range> format";
           leaf name {
             junos:cli-feature "nokeyword";
             type union {
               type jt:interface-device;
               type string {
                 pattern "<.*>|$.*";
               }
             }
           }
           leaf end-range {
             type union {
               type jt:interface-device;
               type string {
                 pattern "<.*>|$.*";
               }
             }
           }
         }
         uses apply-advanced;
         leaf description {
           description "Text description of interface";
           type string;
         }
         leaf external-model-name {
           description "Name for interface as configured using 3rd-party model";
           type string;
         }
         container management-ethernet-redundancy {
           presence "enable management-ethernet-redundancy";
           description "Management Interface Redundancy";
           uses apply-advanced;
           choice enable_choice {
             case case_1 {
               leaf redundancy-enable {
                 description "Enable Managment Ethernet Redundancy";
                 type empty;
               }
             }
             case case_2 {
               leaf redundancy-disable {
                 description "Disable  Managment Ethernet Redundancy";
                 type empty;
               }
             }
           }
           leaf connectivity-test-interval {
             description "Connectivity test interval";
             default "5";
             units "seconds";
             type union {
               type string {
                 pattern "<.*>|$.*";
               }
               type uint32 {
                 range "1 .. 10";
               }
             }
           }
           leaf connectivity-test-response-interval {
             description "Connectivity test response wait time";
             default "5";
             units "seconds";
             type union {
               type string {
                 pattern "<.*>|$.*";
               }
               type uint32 {
                 range "1 .. 10";
               }
             }
           }
           leaf remote-ipv4-address {
             description "Destination IPV4 address to reach remote ";
             default "nil";
             type jt:ipv4addr;
           }
           leaf remote-ipv6-address {
             description "Destination IPV6 address to reach remote";
             default "nil";
             type jt:ipv6addr;
           }
           leaf number-of-connectivity-retries {
             description "Number of Connectivity retries ";
             default "2";
             type union {
               type string {
                 pattern "<.*>|$.*";
               }
               type uint32 {
                 range "1 .. 8";
               }
             }
           }
         }
         choice enable-disable {
           case case_1 {
             leaf disable {
               description "Disable this interface";
               type empty;
             }
           }
         }
         leaf promiscuous-mode {
           description "Enable promiscuous mode for L3 interface";
           type empty;
         }
         leaf port-mirror-instance {
           description "Port-mirror the packet to specified instance";
           junos:must "(\"forwarding-options port-mirroring instance $$\")";
           junos:must-message "Referenced port-mirroring instance does not exist";
           type string {
             length "1 .. 64";
           }
         }
         container fabric-options {
           description "Fabric interface specific options";
           uses apply-advanced;
           list member-interfaces {
             key name;
             junos:cli-feature "homogeneous";
             description "Member interface for the fabric interface";
             leaf name {
               description "Interface name of member";
               junos:cli-feature "nokeyword";
               junos:must "(!((\"interfaces $$ flexible-vlan-tagging\" || (\"interfaces $$ stacked-vlan-tagging\" || (\"interfaces $$ vlan-vci-tagging\" || \"interfaces $$ vlan-tagging\")))))";
               junos:must-message "VLAN configuration is not allowed on fabric member";
               junos:must "(!(\"interfaces $$ disable\"))";
               junos:must-message "fabric member device disable setting is not allowed";
               junos:must "(!(\"interfaces $$ encapsulation\"))";
               junos:must-message "fabric member device encapsulation is not allowed";
               junos:must "(!(\"interfaces $$ mac\"))";
               junos:must-message "fabric member device mac address setting is not allowed";
               junos:must "(!(\"interfaces $$ mtu\"))";
               junos:must-message "fabric member device mtu setting and vlan-tagging is not allowed";
               junos:must "(!(\"interfaces $$ passive-monitor-mode\"))";
               junos:must-message "Fabric member cannot be configured in passive monitor mode";
               junos:must "(!(\"interfaces $$ gigether-options 802.3ad\"))";
               junos:must-message "Fabric member cannot be part of aggregated ethernet";
               junos:must "(!(\"interfaces $$ gigether-options redundant-parent\"))";
               junos:must-message "Fabric member cannot be part of redundant ethernet";
               junos:must "(!(\"interfaces $$ unit\"))";
               junos:must-message "Logical unit is not allowed on fabric member";
               junos:must "(!(\"system autoinstallation\"))";
               junos:must-message "incompatible with 'system autoinstallation'";
               type union {
                 type jt:interface-device;
                 type string {
                   pattern "<.*>|$.*";
                 }
               }
             }
             uses apply-advanced;
           }
           container remote-chassis {
             presence "enable remote-chassis";
             description "Remote chassis reachability";
             uses apply-advanced;
             leaf destination {
               description "Destination IP address to reach remote chassis";
               type jt:ipv4addr;
             }
           }
         }
         container traceoptions {
           presence "enable traceoptions";
           description "Interface trace options";
           uses apply-advanced;
           list flag {
             key name;
             ordered-by user;
             junos:cli-feature "oneliner";
             description "Tracing parameters";
             leaf name {
               junos:cli-feature "nokeyword";
               type enumeration {
                 enum "ipc" {
                   description "Trace interface IPC messages";
                 }
                 enum "event" {
                   description "Trace interface events";
                 }
                 enum "media" {
                   description "Trace interface media changes";
                 }
                 enum "all" {
                   description "Enable all interface trace flags";
                 }
                 enum "q921" {
                   description "Trace ISDN Q.921 frames";
                 }
                 enum "q931" {
                   description "Trace ISDN Q.931 frames";
                 }
               }
             }
           }
           container file {
             presence "enable file";
             description "Trace file information for ISDN decoded frames";
             uses apply-advanced;
             leaf filename {
               description "Name of file in which to write trace information";
               junos:cli-feature "nokeyword";
               type string {
                 length "1 .. 1024";
                 junos:posix-pattern "![/ %]";
                 junos:pattern-message "Must not contain \'/\', % or a space";
               }
             }
             leaf size {
               description "Maximum trace file size";
               default "128k";
               type string;
             }
             leaf files {
               description "Maximum number of trace files";
               default "10";
               type union {
                 type uint32;
                 type string {
                   pattern "<.*>|$.*";
                 }
               }
             }
             choice world-readable-choice {
               leaf world-readable {
                 description "Allow any user to read the log file";
                 type empty;
               }
               leaf no-world-readable {
                 description "Don't allow any user to read the log file";
                 type empty;
               }
             }
           }
         }
         leaf passive-monitor-mode {
           description "Use interface to tap packets from another router";
           junos:must "(!((\"services nat ipv6-multicast-interfaces $$={all}\" || \"services nat ipv6-multicast-interfaces ${interface}\")))";
           junos:must-message "Can not configure 'services nat ipv6-multicast-interfaces' when passive montioring is enabled for the interface";
           junos:must "(!((\".. encapsulation ethernet-ccc\" || (\".. encapsulation ethernet-tcc\" || (\".. encapsulation ethernet-bridge\" || (\".. encapsulation ethernet-vpls\" || (\".. encapsulation extended-vlan-ccc\" || (\".. encapsulation extended-vlan-tcc\" || (\".. encapsulation extended-vlan-vpls\" || (\".. encapsulation extended-vlan-bridge\" || (\".. encapsulation flexible-ethernet-services\" || (\".. encapsulation vlan-ccc\" || (\".. encapsulation vlan-vci-ccc\" || \".. encapsulation vlan-vpls\")))))))))))))";
           junos:must-message "Not compatible with specified 'encapsulation`";
           type empty;
         }
         choice keepalive_choices {
           case case_1 {
             container keepalives {
               description "Send or demand keepalive messages";
               presence "enable keepalives";
               junos:cli-feature "oneliner";
               uses keepalives_type;
             }
           }
           case case_2 {
             leaf no-keepalives {
               description "Do not send keepalive messages";
               type empty;
             }
           }
         }
         choice traps-choice {
           leaf traps {
             description "Enable SNMP notifications on state changes";
             type empty;
           }
           leaf no-traps {
             description "Don't enable SNMP notifications on state changes";
             type empty;
           }
         }
         choice interface-mib-choice {
           leaf interface-mib {
             description "Enable interface-related MIBs";
             type empty;
           }
           leaf no-interface-mib {
             description "Don't enable interface-related MIBs";
             type empty;
           }
         }
         leaf accounting-profile {
           description "Accounting profile name";
           junos:must "((\"accounting-options interface-profile $$\" || \"accounting-options flat-file-profile $$\"))";
           junos:must-message "referenced accounting profile must be defined";
           type string;
         }
         choice scheduler_type {
           case case_1 {
             choice per-unit-scheduler-choice {
               leaf per-unit-scheduler {
                 description "Enable subunit queuing on Frame Relay or VLAN IQ interface";
                 type empty;
               }
               leaf no-per-unit-scheduler {
                 description "Don't enable subunit queuing on Frame Relay or VLAN IQ interface";
                 type empty;
               }
             }
           }
           case case_2 {
             leaf shared-scheduler {
               description "Enabled shared queuing on an IQ2 interface";
               junos:must "((\".. vlan-tagging\" || (\".. stacked-vlan-tagging\" || (\".. flexible-vlan-tagging\" || \".. vlan-vci-tagging\"))))";
               junos:must-message "vlan tagging needs to be enabled for shared scheduler";
               type empty;
             }
           }
           case case_3 {
             container hierarchical-scheduler {
               presence "enable hierarchical-scheduler";
               junos:cli-feature "oneliner";
               description "Enable hierarchical scheduling";
               leaf maximum-hierarchy-levels {
                 description "Maximum hierarchy levels";
                 type union {
                   type string {
                     pattern "<.*>|$.*";
                   }
                   type uint32;
                 }
               }
               leaf implicit-hierarchy {
                 description "Implicit hierarchy (follows interface hierarchy)";
                 type empty;
               }
             }
           }
         }
         leaf l2tp-maximum-session {
           description "Maximum L2TP session";
           type union {
             type string {
               pattern "<.*>|$.*";
             }
             type uint32 {
               range "0 .. 64000";
             }
           }
         }
         leaf schedulers {
           description "Number of schedulers to allocate for interface";
           type union {
             type uint32;
             type string {
               pattern "<.*>|$.*";
             }
           }
         }
         leaf port-extender-cascade-port {
           description "NGPE Cascade port";
           junos:must "(!(\".. shared-scheduler\"))";
           junos:must-message "NGPE cascade-port cannot have shared-scheduler config";
           junos:must "(!(\".. hierarchical-scheduler\"))";
           junos:must-message "NGPE cascade-port cannot have hierarchical-scheduler config";
           type empty;
         }
         leaf dce {
           description "Respond to Frame Relay status enquiry messages";
           type empty;
         }
         choice vlan_tag_mode {
           case case_1 {
             leaf vlan-tagging {
               description "802.1q VLAN tagging support";
               type empty;
             }
           }
           case case_2 {
             leaf stacked-vlan-tagging {
               description "Stacked 802.1q VLAN tagging support";
               junos:must "(!((\".. passive-monitor-mode\" || \".. 802.3ad\")))";
               junos:must-message "Not compatible with passive-monitor-mode statement";
               type empty;
             }
           }
           case case_3 {
             leaf flexible-vlan-tagging {
               description "Support for no tagging, or single and double 802.1q VLAN tagging";
               junos:must "(!(\"system autoinstallation\"))";
               junos:must-message "incompatible with 'system autoinstallation'";
               junos:must "((\".. encapsulation vlan-vpls\" || (\".. encapsulation extended-vlan-vpls\" || (\".. encapsulation extended-vlan-bridge\" || !(\".. encapsulation\")))))";
               junos:must-message "Only compatible with vpls vlan encapsulations or no encapsulation";
               type empty;
             }
           }
           case case_4 {
           }
         }
         leaf native-vlan-id {
           description "Virtual LAN identifier for untagged frames";
           junos:must "((\".. flexible-vlan-tagging\" || (\".. unit $$={0} family bridge interface-mode trunk\" || any \".. unit <*> family ethernet-switching interface-mode trunk\")))";
           junos:must-message "native-vlan-id can be specified with flexible-vlan-tagging mode or with interface-mode trunk";
           junos:must "((\".. flexible-vlan-tagging\" || (any \".. unit <*> family bridge interface-mode trunk\" || any \".. unit <*> family ethernet-switching interface-mode trunk\")))";
           junos:must-message "native-vlan-id can be specified with flexible-vlan-tagging mode or with interface-mode trunk";
           type union {
             type string {
               pattern "<.*>|$.*";
             }
             type uint32 {
               range "0 .. 4094";
             }
           }
         }
         leaf input-native-vlan-push {
           description "Control native-vlan-id insertion to untagged frames when input-vlan-map push is configured";
           junos:must "(any \"interfaces ${interface}  unit <*> input-vlan-map push \")";
           junos:must-message "input-native-vlan-push can be set only when input-vlan-map push is configured";
           type enumeration {
             enum "disable" {
               description "Disable input-native-vlan-push";
             }
             enum "enable" {
               description "Enable input-native-vlan-push";
             }
           }
         }
         leaf number-of-sub-ports {
           description "Number of channels to create for a port";
           type union {
             type string {
               pattern "<.*>|$.*";
             }
             type uint32 {
               range "1 .. 8";
             }
           }
         }
         leaf speed {
           description "Link speed";
           type enumeration {
             enum "auto" {
               description "Enable auto negotiation of interface speed";
               junos:must "((!(\"interfaces ${interface} gigether-options 802.3ad\") || !(\"interfaces ${interface} ether-options 802.3ad\")))";
               junos:must-message "Auto speed cannot be configured for an aggregated ethernet member link";
               junos:must "((\"interfaces ${interface} gigether-options auto-negotiation\" || \"interfaces ${interface} ether-options auto-negotiation\"))";
               junos:must-message "gigether-options/ether-options auto-negotiation must be enabled";
             }
             enum "auto-10m-100m" {
               description "Enable auto negotiation of limiting interface speed to 10m/100m";
               junos:must "((!(\"interfaces ${interface} gigether-options 802.3ad\") || !(\"interfaces ${interface} ether-options 802.3ad\")))";
               junos:must-message "Auto speed cannot be configured for an aggregated ethernet member link";
               junos:must "((\"interfaces ${interface} gigether-options auto-negotiation\" || \"interfaces ${interface} ether-options auto-negotiation\"))";
               junos:must-message "gigether-options/ether-options auto-negotiation must be enabled";
             }
             enum "10m" {
             }
             enum "100m" {
             }
             enum "1g" {
             }
             enum "2.5g" {
             }
             enum "5g" {
             }
             enum "10g" {
             }
             enum "25g" {
             }
             enum "40g" {
             }
             enum "50g" {
             }
             enum "100g" {
             }
             enum "200g" {
             }
             enum "400g" {
             }
             enum "800g" {
             }
             enum "oc3" {
             }
             enum "oc12" {
             }
             enum "oc48" {
             }
             enum "1.6t" {
             }
           }
         }
         leaf mtu {
           description "Maximum transmit packet size";
           junos:must "(!(\"interfaces ${interface} container-options container-list\"))";
           junos:must-message "mtu is not supported for container child interfaces";
           type union {
             type string {
               pattern "<.*>|$.*";
             }
             type uint32;
           }
         }
         container hold-time {
           junos:cli-feature "oneliner";
           description "Hold time for link up and link down";
           leaf up {
             description "Link up hold time";
             units "milliseconds";
             type union {
               type uint32;
               type string {
                 pattern "<.*>|$.*";
               }
             }
           }
           leaf down {
             description "Link down hold time";
             units "milliseconds";
             type union {
               type uint32;
               type string {
                 pattern "<.*>|$.*";
               }
             }
           }
         }
         container port-extender {
           description "Tunnel binding information for the extended port";
           uses apply-advanced;
           container vxlan {
             presence "enable vxlan";
             description "VXLAN binding information for the extended port";
             uses apply-advanced;
             leaf end-point {
               description "Satellite loopback IP address";
               type jt:ipaddr;
             }
             leaf vni {
               description "VNI of the satellite extended-port";
               type union {
                 type string {
                   pattern "<.*>|$.*";
                 }
                 type uint32 {
                   range "0 .. 16777214";
                 }
               }
             }
           }
         }
         container link-degrade-monitor {
           presence "enable link-degrade-monitor";
           description "Enable link degrade monitoring";
           uses apply-advanced;
           choice enable_choice {
             case case_1 {
               leaf link-degrade-monitor-enable {
                 description "Enable Link Degrade Monitoring";
                 type empty;
               }
             }
             case case_2 {
               leaf no-link-degrade-monitor-enable {
                 description "Disable Link Degrade Monitoring";
                 type empty;
               }
             }
           }
           container actions {
             description "Action upon link degrade event";
             uses apply-advanced;
             choice action_choice {
               case case_1 {
                 leaf media-based {
                   description "Media based";
                   type empty;
                 }
               }
             }
           }
           container recovery {
             description "Link degrade recovery mechanism";
             uses apply-advanced;
             leaf timer {
               description "Auto recovery timer in seconds";
               default "1800";
               junos:must "(!(\".. manual\"))";
               junos:must-message "Recovery mechanism must be auto to configure recovery timer";
               type union {
                 type uint32;
                 type string {
                   pattern "<.*>|$.*";
                 }
               }
             }
             choice receovery_choice {
               case case_1 {
                 leaf auto {
                   description "Automatic recovery";
                   type empty;
                 }
               }
               case case_2 {
                 leaf manual {
                   description "Manual recovery";
                   type empty;
                 }
               }
             }
           }
           container thresholds {
             description "Link degrade threshold parameters";
             uses apply-advanced;
             leaf set {
               description "BER at which link considered degraded(1..16)";
               default "1e-7";
               type string {
                 junos:posix-pattern "^1e-(1[0-6]?|[2-9])$";
                 junos:pattern-message "Ber threshold value in format: 1e-n, n = 1..16";
               }
             }
             leaf clear {
               description "BER at which link considered improved(1..16)";
               default "1e-12";
               type string {
                 junos:posix-pattern "^1e-(1[0-6]?|[2-9])$";
                 junos:pattern-message "Ber threshold value in format: 1e-n, n = 1..16";
               }
             }
             leaf warning-set {
               description "BER at which link degrade warning raised(1..16)";
               default "1e-9";
               type string {
                 junos:posix-pattern "^1e-(1[0-6]?|[2-9])$";
                 junos:pattern-message "Ber threshold value in format: 1e-n, n = 1..16";
               }
             }
             leaf warning-clear {
               description "BER at which link degrade warning cleared(1..16)";
               default "1e-11";
               type string {
                 junos:posix-pattern "^1e-(1[0-6]?|[2-9])$";
                 junos:pattern-message "Ber threshold value in format: 1e-n, n = 1..16";
               }
             }
             leaf interval {
               description "Consecutive link degrade events";
               default "10";
               type union {
                 type string {
                   pattern "<.*>|$.*";
                 }
                 type uint32 {
                   range "1 .. 256";
                 }
               }
             }
           }
         }
         container satop-options {
           junos:must "((!(\".. t1-options framing\") && !(\".. e1-options framing\")))";
           junos:must-message "SAToP & Framing cannot be configured on same interface";
           junos:must "(!(\".. ima-link-options\"))";
           junos:must-message "SAToP & IMA cannot be configured on same interface";
           junos:must "((!(\"interfaces ${interface} container-options\") || (\"interfaces ${interface} container-options container-type\" || \"interfaces ${interface} container-options allow-configuration-override\")))";
           junos:must-message "satop-options cannot be configured without allow-configuration-override";
           junos:cli-feature "oneliner-plus";
           description "Structure-Agnostic TDM over Packet protocol options";
           uses apply-advanced;
           leaf idle-pattern {
             description "An 8-bit hexadecimal pattern to replace TDM data in a lost packet";
             type union {
               type string {
                 pattern "<.*>|$.*";
               }
               type uint32 {
                 range "0 .. 255";
               }
             }
           }
           leaf payload-size {
             description "Number of payload bytes per packet";
             type union {
               type string {
                 pattern "<.*>|$.*";
               }
               type uint32 {
                 range "64 .. 1024";
               }
             }
           }
           container excessive-packet-loss-rate {
             junos:cli-feature "oneliner-plus";
             description "Packet loss options";
             uses apply-advanced;
             leaf threshold {
               description "Percentile designating the threshold of excessive packet loss rate";
               type union {
                 type string {
                   pattern "<.*>|$.*";
                 }
                 type uint8 {
                   range "1 .. 100";
                 }
               }
             }
             leaf sample-period {
               description "Number of milliseconds over which excessive packet loss rate is calculated";
               type union {
                 type string {
                   pattern "<.*>|$.*";
                 }
                 type uint32 {
                   range "1000 .. 65535";
                 }
               }
             }
           }
           choice jitter-buffer-size {
             case case_1 {
               leaf jitter-buffer-packets {
                 description "Number of packets in jitter buffer before packet data is played out in the line";
                 type union {
                   type string {
                     pattern "<.*>|$.*";
                   }
                   type uint32 {
                     range "1 .. 64";
                   }
                 }
               }
             }
             case case_2 {
               leaf jitter-buffer-latency {
                 description "Number of milliseconds delay in jitter buffer before packet data is played out in the line";
                 units "milliseconds";
                 type union {
                   type string {
                     pattern "<.*>|$.*";
                   }
                   type uint32 {
                     range "1 .. 1000";
                   }
                 }
               }
             }
             case case_3 {
               leaf jitter-buffer-auto-adjust {
                 description "Automatically adjust jitter buffer";
                 type empty;
               }
             }
           }
           leaf bit-rate {
             description "In multiples of DS0";
             type union {
               type string {
                 pattern "<.*>|$.*";
               }
               type uint32 {
                 range "1 .. 10240";
               }
             }
           }
         }
         container cesopsn-options {
           junos:must "((!(\"interfaces ${interface} container-options\") || (\"interfaces ${interface} container-options container-type\" || \"interfaces ${interface} container-options allow-configuration-override\")))";
           junos:must-message "cesopsn-options cannot be configured without allow-configuration-override";
           junos:cli-feature "oneliner-plus";
           description "Structure-Aware TDM over Packet protocol options";
           uses apply-advanced;
           leaf idle-pattern {
             description "An 8-bit hexadecimal pattern to replace TDM data in a lost packet";
             type union {
               type string {
                 pattern "<.*>|$.*";
               }
               type uint32 {
                 range "0 .. 255";
               }
             }
           }
           leaf packetization-latency {
             description "Number of microseconds to create packets";
             units "microseconds";
             type union {
               type string {
                 pattern "<.*>|$.*";
               }
               type uint32 {
                 range "1000 .. 8000";
               }
             }
           }
           leaf payload-size {
             description "Number of payload bytes per packet";
             type union {
               type string {
                 pattern "<.*>|$.*";
               }
               type uint32 {
                 range "64 .. 1024";
               }
             }
           }
           container excessive-packet-loss-rate {
             junos:cli-feature "oneliner-plus";
             description "Packet loss options";
             uses apply-advanced;
             leaf threshold {
               description "Percentile designating the threshold of excessive packet loss rate";
               type union {
                 type string {
                   pattern "<.*>|$.*";
                 }
                 type uint8 {
                   range "1 .. 100";
                 }
               }
             }
             leaf sample-period {
               description "Number of milliseconds over which excessive packet loss rate is calculated";
               type union {
                 type string {
                   pattern "<.*>|$.*";
                 }
                 type uint32 {
                   range "1000 .. 65535";
                 }
               }
             }
           }
           choice jitter-buffer-size {
             case case_1 {
               leaf jitter-buffer-packets {
                 description "Number of packets in jitter buffer before packet data is played out in the line";
                 type union {
                   type string {
                     pattern "<.*>|$.*";
                   }
                   type uint32 {
                     range "1 .. 64";
                   }
                 }
               }
             }
             case case_2 {
               leaf jitter-buffer-latency {
                 description "Number of milliseconds delay in jitter buffer before packet data is played out in the line";
                 units "milliseconds";
                 type union {
                   type string {
                     pattern "<.*>|$.*";
                   }
                   type uint32 {
                     range "1 .. 1000";
                   }
                 }
               }
             }
             case case_3 {
               leaf jitter-buffer-auto-adjust {
                 description "Automatically adjust jitter buffer";
                 type empty;
               }
             }
           }
           leaf bit-rate {
             description "In multiples of DS0";
             type union {
               type string {
                 pattern "<.*>|$.*";
               }
               type uint32 {
                 range "1 .. 10240";
               }
             }
           }
         }
         container clocking {
           junos:cli-feature "oneliner";
           description "Interface clock source";
           choice clocking_choices {
             case case_1 {
               leaf internal {
                 description "Clocking provided by local system";
                 type empty;
               }
             }
             case case_2 {
               container external {
                 presence "enable external";
                 description "Clocking provided by DCE (loop timing)";
                 uses apply-advanced;
                 leaf interface {
                   description "Interface that acts as clock source";
                   junos:must "(!(\"interfaces $$ clocking external interface\"))";
                   junos:must-message "Interface should not have clock input interface configured";
                   junos:must "(\"interfaces $$\")";
                   junos:must-message "Referenced clock input interface must be defined";
                   type union {
                     type jt:interface-device;
                     type string {
                       pattern "<.*>|$.*";
                     }
                   }
                 }
               }
             }
           }
           uses apply-advanced;
         }
         leaf link-mode {
           description "Link operational mode";
           type enumeration {
             enum "automatic" {
               description "Automatically negotiate duplex";
             }
             enum "half-duplex" {
               description "Half-duplex operation";
             }
             enum "full-duplex" {
               description "Full-duplex operation";
             }
           }
         }
         leaf media-type {
           description "Interface media type (copper or fiber)";
           type enumeration {
             enum "copper" {
               description "Copper as media";
             }
             enum "fiber" {
               description "Fiber as media";
             }
           }
         }
         leaf encapsulation {
           description "Physical link-layer encapsulation";
           junos:must "(!(\"interfaces ${interface} container-options container-list\"))";
           junos:must-message "encapsulation is not supported for container child interfaces";
           type enumeration {
             enum "ethernet" {
               description "Ethernet physical media";
             }
             enum "fddi" {
               description "FDDI physical media";
             }
             enum "token-ring" {
               description "Token Ring physical media";
             }
             enum "ppp" {
               description "Serial PPP device";
             }
             enum "ppp-ccc" {
               description "Serial PPP device for a cross-connect";
             }
             enum "ppp-tcc" {
               description "Serial PPP device for a translational cross-connect";
             }
             enum "ether-vpls-ppp" {
               description "Ethernet VPLS over PPP (bridging) device";
             }
             enum "frame-relay" {
               description "Frame Relay encapsulation";
             }
             enum "frame-relay-ccc" {
               description "Frame Relay for cross-connect";
             }
             enum "frame-relay-tcc" {
               description "Frame Relay for translational cross-connect";
             }
             enum "extended-frame-relay-ccc" {
               description "Any Frame Relay DLCI for cross-connect";
             }
             enum "extended-frame-relay-tcc" {
               description "Any Frame Relay DLCI for translational cross-connect";
             }
             enum "flexible-frame-relay" {
               description "Multiple Frame Relay encapsulations";
             }
             enum "frame-relay-port-ccc" {
               description "Frame Relay port encapsulation for a cross-connect";
             }
             enum "frame-relay-ether-type" {
               description "Cisco-compatible Frame Relay encapsulation";
             }
             enum "frame-relay-ether-type-tcc" {
               description "Cisco-compatible Frame Relay encapsulation for translational cross-connect";
             }
             enum "extended-frame-relay-ether-type-tcc" {
               description "Cisco-compatible Frame Relay encapsulation any DLCI for translational cross-connect";
             }
             enum "cisco-hdlc" {
               description "Cisco-compatible HDLC framing";
             }
             enum "cisco-hdlc-ccc" {
               description "Cisco-compatible HDLC framing for a cross-connect";
             }
             enum "cisco-hdlc-tcc" {
               description "Cisco-compatible HDLC framing for a translational cross-connect";
             }
             enum "vlan-ccc" {
               description "802.1q tagging for a cross-connect";
             }
             enum "extended-vlan-ccc" {
               description "Nonstandard TPID tagging for a cross-connect";
             }
             enum "ethernet-ccc" {
               description "Ethernet cross-connect";
             }
             enum "flexible-ethernet-services" {
               description "Allows per-unit Ethernet encapsulation configuration";
             }
             enum "smds-dxi" {
               description "SMDS DXI framing";
             }
             enum "atm-pvc" {
               description "ATM permanent virtual circuits";
             }
             enum "atm-ccc-cell-relay" {
               description "ATM cell relay encapsulation for cross-connect";
             }
             enum "ethernet-over-atm" {
               description "Ethernet over ATM encapsulation";
             }
             enum "ethernet-tcc" {
               description "Ethernet translational cross-connect";
             }
             enum "extended-vlan-tcc" {
               description "802.1q tagging for a translational cross-connect";
             }
             enum "multilink-frame-relay-uni-nni" {
               description "Multilink Frame Relay UNI NNI (FRF.16) encapsulation";
             }
             enum "satop" {
               description "Structure-Agnostic TDM over Packet encapsulation";
               junos:must "((!(\".. t1-options framing\") && !(\".. e1-options framing\")))";
               junos:must-message "SAToP & Framing cannot be configured on same interface";
               junos:must "(!(\".. ima-link-options\"))";
               junos:must-message "SAToP & IMA cannot be configured on same interface";
             }
             enum "cesopsn" {
               description "Structure-Agnostic TDM over Packet encapsulation";
             }
             enum "ima" {
               description "Inverse Multiplexing for ATM";
               junos:must "(!(\".. satop-options\"))";
               junos:must-message "SAToP & IMA cannot be configured on same interface";
             }
             enum "ethernet-vpls" {
               description "Ethernet virtual private LAN service";
             }
             enum "ethernet-bridge" {
               description "Ethernet layer-2 bridging";
             }
             enum "vlan-vpls" {
               description "VLAN virtual private LAN service";
             }
             enum "vlan-vci-ccc" {
               description "CCC for VLAN Q-in-Q and ATM VPI/VCI interworking";
               junos:must "(\"interfaces ${interface} vlan-vci-tagging\")";
               junos:must-message "valid only with vlan-vci-tagging mode";
             }
             enum "extended-vlan-vpls" {
               description "Extended VLAN virtual private LAN service";
             }
             enum "extended-vlan-bridge" {
               description "VLAN layer-2 bridging";
             }
             enum "multilink-ppp" {
               description "Multilink PPP";
             }
             enum "generic-services" {
               description "Generic services";
             }
           }
         }
         leaf network-isolation-profile {
           description "Attach a network isolation profile on this interface";
           junos:must "(!((\".. .. .. protocols network-isolation group $$ service-tracking-action lacp-out-of-sync\" && !(\".. aggregated-ether-options lacp\"))))";
           junos:must-message "lacp-out-of-sync is allowed only on LACP interfaces";
           junos:must "(\".. .. .. protocols network-isolation group $$ service-tracking-action\")";
           junos:must-message "service-tracking-action must be configured";
           junos:must "((\".. .. .. protocols network-isolation group $$ detection service-tracking\" || \".. .. .. protocols network-isolation group $$ detection link-tracking\"))";
           junos:must-message "service-tracking or link-tracking must be configured";
           type string;
         }
         container framing {
           description "Frame type";
           uses apply-advanced;
           choice frame {
             case case_1 {
               leaf lan-phy {
                 description "802.3ae 10-Gbps LAN-mode interface";
                 type empty;
               }
             }
             case case_2 {
               leaf wan-phy {
                 description "802.3ae 10-Gbps WAN-mode interface";
                 type empty;
               }
             }
             case case_3 {
               leaf sonet {
                 description "SONET framing";
                 type empty;
               }
             }
             case case_4 {
               leaf sdh {
                 description "SDH framing";
                 type empty;
               }
             }
           }
         }
         container lmi {
           description "Local Management Interface settings";
           uses apply-advanced;
           leaf n391dte {
             description "DTE full status polling interval";
             junos:must "(!((\".. .. dce\" || \".. .. loose-ncp\")))";
             junos:must-message "LMI DTE options not valid for DCE interface";
             type union {
               type string {
                 pattern "<.*>|$.*";
               }
               type uint16 {
                 range "1 .. 255";
               }
             }
           }
           leaf n392dce {
             description "DCE error threshold";
             junos:must "((\".. .. dce\" || \".. .. loose-ncp\"))";
             junos:must-message "LMI DCE options not valid for DTE interface";
             type union {
               type string {
                 pattern "<.*>|$.*";
               }
               type uint16 {
                 range "1 .. 10";
               }
             }
           }
           leaf n392dte {
             description "DTE error threshold";
             junos:must "(!((\".. .. dce\" || \".. .. loose-ncp\")))";
             junos:must-message "LMI DTE options not valid for DCE interface";
             type union {
               type string {
                 pattern "<.*>|$.*";
               }
               type uint16 {
                 range "1 .. 10";
               }
             }
           }
           leaf n393dce {
             description "DCE monitored event count";
             junos:must "((\".. .. dce\" || \".. .. loose-ncp\"))";
             junos:must-message "LMI DCE options not valid for DTE interface.";
             type union {
               type string {
                 pattern "<.*>|$.*";
               }
               type uint16 {
                 range "1 .. 10";
               }
             }
           }
           leaf n393dte {
             description "DTE monitored event count";
             junos:must "(!((\".. .. dce\" || \".. .. loose-ncp\")))";
             junos:must-message "LMI DTE options not valid for DCE interface";
             type union {
               type string {
                 pattern "<.*>|$.*";
               }
               type uint16 {
                 range "1 .. 10";
               }
             }
           }
           leaf t391dte {
             description "DTE polling timer";
             units "seconds";
             junos:must "(!((\".. .. dce\" || \".. .. loose-ncp\")))";
             junos:must-message "LMI DTE options not valid for DCE interface";
             type union {
               type string {
                 pattern "<.*>|$.*";
               }
               type uint16 {
                 range "5 .. 30";
               }
             }
           }
           leaf t392dce {
             description "DCE polling verification timer";
             units "seconds";
             junos:must "((\".. .. dce\" || \".. .. loose-ncp\"))";
             junos:must-message "LMI DCE options not valid for DTE interface.";
             type union {
               type string {
                 pattern "<.*>|$.*";
               }
               type uint16 {
                 range "5 .. 30";
               }
             }
           }
           leaf lmi-type {
             description "Specify the Frame Relay LMI type";
             type enumeration {
               enum "ansi" {
                 description "Use ANSI Annex D LMI";
               }
               enum "itu" {
                 description "Use ITU Q933a Annex A LMI";
               }
               enum "c-lmi" {
                 description "Use Consortium LMI";
               }
             }
           }
         }
         container mlfr-uni-nni-bundle-options {
           description "Multilink Frame Relay UNI NNI (FRF.16) management settings";
           uses apply-advanced;
           container cisco-interoperability {
             description "FRF.16 Cisco interoperability settings";
             uses apply-advanced;
             leaf send-lip-remove-link-for-link-reject {
               description "Send Link Integrity Protocol remove link on receiving add-link rejection";
               type empty;
             }
           }
           leaf mrru {
             description "Maximum received reconstructed unit";
             units "bytes";
             type union {
               type string {
                 pattern "<.*>|$.*";
               }
               type uint16 {
                 range "1500 .. 4500";
               }
             }
           }
           leaf yellow-differential-delay {
             description "Yellow differential delay among bundle links to give warning";
             units "milliseconds";
             type union {
               type string {
                 pattern "<.*>|$.*";
               }
               type uint16 {
                 range "3 .. 2000";
               }
             }
           }
           leaf red-differential-delay {
             description "Red differential delay among bundle links to take action";
             units "milliseconds";
             type union {
               type string {
                 pattern "<.*>|$.*";
               }
               type uint16 {
                 range "5 .. 2000";
               }
             }
           }
           leaf action-red-differential-delay {
             description "Type of actions when differential delay exceeds red limit";
             type enumeration {
               enum "remove-link" {
                 description "Remove bundle link from service when exceeding red limit";
               }
               enum "disable-tx" {
                 description "Disable transfer of bundle link when exceeding red limit";
               }
             }
           }
           leaf fragment-threshold {
             description "Fragmentation threshold";
             units "bytes";
             type union {
               type string {
                 pattern "<.*>|$.*";
               }
               type uint32 {
                 range "64 .. 16320";
               }
             }
           }
           leaf drop-timeout {
             description "Drop timeout";
             units "milliseconds";
             type union {
               type string {
                 pattern "<.*>|$.*";
               }
               type uint16 {
                 range "0 .. 2000";
               }
             }
           }
           leaf link-layer-overhead {
             description "Link layer bit stuffing overhead (0.0 .. 50.0 percent)";
             type jt:unsigned-float;
           }
           leaf lmi-type {
             description "Specify the multilink Frame Relay UNI NNI LMI type";
             type enumeration {
               enum "ansi" {
                 description "Use ANSI Annex D LMI";
               }
               enum "itu" {
                 description "Use ITU Q933a Annex A LMI";
               }
               enum "c-lmi" {
                 description "Use Consortium LMI";
               }
             }
           }
           leaf minimum-links {
             description "Minimum number of links to sustain the bundle";
             type union {
               type string {
                 pattern "<.*>|$.*";
               }
               type uint16 {
                 range "1 .. 8";
               }
             }
           }
           leaf hello-timer {
             description "LIP hello timer";
             type union {
               type string {
                 pattern "<.*>|$.*";
               }
               type uint16 {
                 range "5 .. 180";
               }
             }
           }
           leaf acknowledge-timer {
             description "LIP ack timer";
             type union {
               type string {
                 pattern "<.*>|$.*";
               }
               type uint16 {
                 range "1 .. 10";
               }
             }
           }
           leaf acknowledge-retries {
             description "LIP ack retry times";
             type union {
               type string {
                 pattern "<.*>|$.*";
               }
               type uint16 {
                 range "1 .. 5";
               }
             }
           }
           leaf n391 {
             description "Multilink Frame Relay UNI NNI full status polling counter";
             type union {
               type string {
                 pattern "<.*>|$.*";
               }
               type uint16 {
                 range "1 .. 255";
               }
             }
           }
           leaf n392 {
             description "Multilink Frame Relay UNI NNI LMI error threshold";
             type union {
               type string {
                 pattern "<.*>|$.*";
               }
               type uint16 {
                 range "1 .. 10";
               }
             }
           }
           leaf n393 {
             description "Multilink Frame Relay UNI NNI LMI monitored event count";
             type union {
               type string {
                 pattern "<.*>|$.*";
               }
               type uint16 {
                 range "1 .. 10";
               }
             }
           }
           leaf t391 {
             description "Multilink Frame Relay UNI NNI link integrity verify polling timer";
             type union {
               type string {
                 pattern "<.*>|$.*";
               }
               type uint16 {
                 range "5 .. 30";
               }
             }
           }
           leaf t392 {
             description "Multilink Frame Relay UNI NNI polling verification timer";
             type union {
               type string {
                 pattern "<.*>|$.*";
               }
               type uint16 {
                 range "5 .. 30";
               }
             }
           }
         }
         leaf mac {
           description "Hardware MAC address";
           type jt:mac-unicast;
         }
         container receive-bucket {
           description "Set receive bucket parameters";
           uses dcd_rx_bucket_config;
         }
         container transmit-bucket {
           description "Set transmit bucket parameters";
           uses dcd_tx_bucket_config;
         }
         leaf shared-interface {
           description "Enable shared interface on the interface";
           type empty;
         }
         container sonet-options {
           description "SONET interface-specific options";
           junos:must "((!(\"interfaces ${interface} container-options\") || (\"interfaces ${interface} container-options container-type\" || \"interfaces ${interface} container-options allow-configuration-override\")))";
           junos:must-message "sonet-options cannot be configured without allow-configuration-override";
           uses sonet_options_type;
         }
         container logical-tunnel-options {
           description "Logical Tunnel interface-specific options";
           uses apply-advanced;
           container link-protection {
             presence "enable link-protection";
             junos:must "(any \"interfaces ${interface} redundancy-group member-interface <*> active\")";
             junos:must-message "Active and Backup child links must be configured to use link-protection";
             description "Enable link protection mode";
             uses apply-advanced;
             leaf revertive {
               description "Revert back (Default mode) from active backup link to primary, if primary is UP";
               junos:must "(!(\"interfaces ${interface} logical-tunnel-options link-protection non-revertive\"))";
               junos:must-message "link-protection revertive and non-revertive are mutually exclusive";
               junos:must "(any \"interfaces ${interface} redundancy-group member-interface <*> active\")";
               junos:must-message "link-protection mode can be configured only when link-protection is enabled";
               type empty;
             }
             leaf non-revertive {
               description "Do not revert back from active backup link to primary, if primary is UP";
               junos:must "(!(\"interfaces ${interface} logical-tunnel-options link-protection revertive\"))";
               junos:must-message "link-protection revertive and non-revertive are mutually exclusive";
               junos:must "(any \"interfaces ${interface} redundancy-group member-interface <*> active\")";
               junos:must-message "link-protection mode can be configured only when link-protection is enabled";
               type empty;
             }
           }
           leaf per-unit-mac-disable {
             description "Disable the creation of per unit mac address on LT IFLs for VPLS/CCC encaps";
             type empty;
           }
         }
         container aggregated-sonet-options {
           description "Aggregated SONET interface-specific options";
           uses apply-advanced;
           leaf minimum-links {
             description "Minimum number of aggregated links";
             type union {
               type string {
                 pattern "<.*>|$.*";
               }
               type uint16;
             }
           }
           leaf link-speed {
             description "Aggregated links speed";
             type enumeration {
               enum "oc3" {
                 description "Links are OC-3c or STM-1c";
               }
               enum "oc12" {
                 description "Links are OC-12c or STM-4c";
               }
               enum "oc48" {
                 description "Links are OC-48c or STM-16c";
               }
               enum "oc192" {
                 description "Links are OC-192c or STM-64c";
               }
               enum "oc768" {
                 description "Links are OC-768c or STM-256c";
               }
               enum "mixed" {
                 description "Links are various speeds";
               }
             }
           }
           leaf minimum-bandwidth {
             description "Minimum bandwidth necessary to sustain bundle";
             units "bps";
             type union {
               type string {
                 pattern "<.*>|$.*";
               }
               type uint64 {
                 range "0 .. 159232000000";
               }
             }
           }
         }
         container atm-options {
           junos:must "((!(\"interfaces ${interface} container-options\") || (\"interfaces ${interface} container-options container-type\" || !(\"interfaces ${interface} container-options container-list\"))))";
           junos:must-message "atm-options cannot be configured on container children";
           description "ATM interface-specific options";
           uses apply-advanced;
           leaf pic-type {
             description "Type of ATM PIC (ATM I, ATM II or ATM CE)";
             type enumeration {
               enum "atm-ce" {
                 description "CE PIC";
               }
               enum "atm2" {
                 description "ATM II IQ PIC";
               }
               enum "atm1" {
                 description "ATM I PIC";
                 junos:must "(!(\"interfaces ${interface} container-options\"))";
                 junos:must-message "Only ATM-II pics are supported as container member link";
               }
             }
           }
           leaf cell-bundle-size {
             description "L2 circuit cell bundle size";
             units "cells";
             type union {
               type string {
                 pattern "<.*>|$.*";
               }
               type uint32 {
                 range "1 .. 176";
               }
             }
           }
           leaf cell-bundle-timeout {
             description "L2 circuit cell bundle timeout";
             units "microseconds";
             type union {
               type string {
                 pattern "<.*>|$.*";
               }
               type uint32 {
                 range "1 .. 512";
               }
             }
           }
           leaf plp-to-clp {
             description "Enable ATM2 PLP to CLP copy";
             type empty;
           }
           leaf use-null-cw {
             description "Always insert/strip null control words with cell-relay";
             type empty;
           }
           container promiscuous-mode {
             presence "enable promiscuous-mode";
             description "Set ATM interface to promiscuous mode";
             uses apply-advanced;
             list vpi {
               key name;
               ordered-by user;
               junos:cli-feature "oneliner";
               description "Open this VPI in promiscuous mode";
               leaf name {
                 description "Virtual path index";
                 junos:cli-feature "nokeyword";
                 type union {
                   type string {
                     pattern "<.*>|$.*";
                   }
                   type uint32 {
                     range "0 .. 255";
                   }
                 }
               }
             }
           }
           list vpi {
             key name;
             ordered-by user;
             description "Define a virtual path";
             leaf name {
               description "Virtual path index";
               junos:cli-feature "nokeyword";
               type union {
                 type string {
                   pattern "<.*>|$.*";
                 }
                 type uint32 {
                   range "0 .. 255";
                 }
               }
             }
             uses apply-advanced;
             leaf maximum-vcs {
               description "Maximum number of virtual circuits on this VP";
               junos:must "(!(\"interfaces ${interface} container-options\"))";
               junos:must-message "Only ATM-II pics are supported as container member link";
               type union {
                 type uint32;
                 type string {
                   pattern "<.*>|$.*";
                 }
               }
             }
             container shaping {
               description "Virtual path traffic-shaping options";
               uses dcd_shaping_config;
             }
             container oam-period {
               junos:cli-feature "oneliner";
               description "F4 OAM cell period";
               choice oam_period_choices {
                 case case_1 {
                   leaf oam-period {
                     description "F4 OAM cell period";
                     junos:cli-feature "nokeyword";
                     units "seconds";
                     type union {
                       type string {
                         pattern "<.*>|$.*";
                       }
                       type uint32 {
                         range "1 .. 900";
                       }
                     }
                   }
                 }
                 case case_2 {
                   container disable {
                     presence "enable disable";
                     junos:cli-feature "oneliner";
                     description "Disable F4 OAM loopback";
                   }
                 }
               }
             }
             container oam-liveness {
               description "F4 OAM virtual path liveness parameters";
               uses apply-advanced;
               leaf up-count {
                 description "Number of F4 OAM cells to consider VP up";
                 type union {
                   type string {
                     pattern "<.*>|$.*";
                   }
                   type uint32 {
                     range "1 .. 255";
                   }
                 }
               }
               leaf down-count {
                 description "Number of F4 OAM cells to consider VP down";
                 type union {
                   type string {
                     pattern "<.*>|$.*";
                   }
                   type uint32 {
                     range "1 .. 255";
                   }
                 }
               }
             }
           }
           container ilmi {
             presence "enable ilmi";
             description "Enable Interim Local Management Interface";
             uses apply-advanced;
           }
           list linear-red-profiles {
             key name;
             ordered-by user;
             junos:cli-feature "homogeneous";
             junos:cli-feature "oneliner";
             description "ATM2 CoS virtual circuit drop profiles";
             leaf name {
               description "Linear RED profile name";
               junos:cli-feature "nokeyword";
               type string {
                 junos:posix-pattern "^.{1,64}$";
                 junos:pattern-message "Must be string of 64 characters or less";
               }
             }
             leaf queue-depth {
               description "Maximum queue depth";
               units "cells";
               type string;
             }
             leaf high-plp-threshold {
               description "Fill level percentage when linear RED is applied for high PLP";
               type union {
                 type string {
                   pattern "<.*>|$.*";
                 }
                 type uint32 {
                   range "0 .. 100";
                 }
               }
             }
             leaf low-plp-threshold {
               description "Fill level percentage when linear RED is applied for low PLP";
               type union {
                 type string {
                   pattern "<.*>|$.*";
                 }
                 type uint32 {
                   range "0 .. 100";
                 }
               }
             }
             leaf high-plp-max-threshold {
               description "Fill level percentage with 100 percent packet drop for high PLP";
               type union {
                 type string {
                   pattern "<.*>|$.*";
                 }
                 type uint32 {
                   range "0 .. 100";
                 }
               }
             }
             leaf low-plp-max-threshold {
               description "Fill level percentage with 100 percent packet drop for low PLP";
               type union {
                 type string {
                   pattern "<.*>|$.*";
                 }
                 type uint32 {
                   range "0 .. 100";
                 }
               }
             }
           }
           list scheduler-maps {
             key name;
             ordered-by user;
             junos:cli-feature "homogeneous";
             description "ATM2 CoS parameters assigned to forwarding classes";
             leaf name {
               description "ATM2 CoS scheduler map name";
               junos:cli-feature "nokeyword";
               type string {
                 junos:posix-pattern "^((default)|(.{1,64}))$";
                 junos:pattern-message "Must be a string of 64 characters or less and not \'default\'";
               }
             }
             uses apply-advanced;
             leaf vc-cos-mode {
               description "ATM2 virtual circuit CoS mode";
               type enumeration {
                 enum "strict" {
                   description "Always schedule high priority queue first";
                 }
                 enum "alternate" {
                   description "Every other packet from high priority queue (default)";
                 }
               }
             }
             list forwarding-class {
               key name;
               ordered-by user;
               description "Scheduling parameters associated with forwarding class";
               leaf name {
                 description "Forwarding class name";
                 junos:cli-feature "nokeyword";
                 type string {
                   junos:posix-pattern "^.{1,64}$";
                   junos:pattern-message "Must be string of 64 characters or less";
                 }
               }
               uses apply-advanced;
               leaf priority {
                 description "Queuing priority assigned to forwarding class";
                 type enumeration {
                   enum "low" {
                     description "Low priority queuing";
                   }
                   enum "high" {
                     description "High priority queuing";
                   }
                 }
               }
               container transmit-weight {
                 junos:cli-feature "oneliner";
                 description "Transmit weight";
                 choice weight-method {
                   case case_1 {
                     leaf percent {
                       description "Transmit weight as percentage";
                       type union {
                         type string {
                           pattern "<.*>|$.*";
                         }
                         type uint32 {
                           range "5 .. 100";
                         }
                       }
                     }
                   }
                   case case_2 {
                     leaf cells {
                       description "Transmit weight by cells count";
                       type string;
                     }
                   }
                 }
               }
               choice drop-profile-method {
                 case case_1 {
                   container epd-threshold {
                     description "Early packet discard threshold for ATM2";
                     junos:cli-feature "oneliner";
                     uses epd_threshold_config;
                   }
                 }
                 case case_2 {
                   leaf linear-red-profile {
                     description "Linear RED profile profile name";
                     type string;
                   }
                 }
               }
             }
           }
           container mpls {
             description "MPLS options";
             uses mpls_ifd_options;
           }
           choice payload-scrambler-choice {
             leaf payload-scrambler {
               description "Enable payload scrambling";
               type empty;
             }
             leaf no-payload-scrambler {
               description "Don't enable payload scrambling";
               type empty;
             }
           }
         }
         container multiservice-options {
           description "Multiservice interface-specific options";
           uses apply-advanced;
           choice syslog-choice {
             leaf syslog {
               description "Enable system logging on this interface";
               type empty;
             }
             leaf no-syslog {
               description "Don't enable system logging on this interface";
               type empty;
             }
           }
           choice core-dump-choice {
             leaf core-dump {
               description "Enable core dumping on this interface";
               type empty;
             }
             leaf no-core-dump {
               description "Don't enable core dumping on this interface";
               type empty;
             }
           }
           choice dump-on-flow-control-choice {
             leaf dump-on-flow-control {
               description "Enable dumping for this interface on prolonged flow-control";
               status deprecated;
               type empty;
             }
             leaf no-dump-on-flow-control {
               description "Don't enable dumping for this interface on prolonged flow-control";
               status deprecated;
               type empty;
             }
           }
           choice reset-on-flow-control-choice {
             leaf reset-on-flow-control {
               description "Enable resetting this interface on prolonged flow-control";
               status deprecated;
               type empty;
             }
             leaf no-reset-on-flow-control {
               description "Don't enable resetting this interface on prolonged flow-control";
               status deprecated;
               type empty;
             }
           }
           container flow-control-options {
             description "Flow control configuration";
             uses apply-advanced;
             leaf dump-on-flow-control {
               description "Cause core dump during prolonged flow-control";
               junos:must "(!(\".. up-on-flow-control\"))";
               junos:must-message "Option not valid with up-on-flow-control";
               junos:must "(!(\".. down-on-flow-control\"))";
               junos:must-message "Option not valid with down-on-flow-control";
               junos:must "(!(\".. reset-on-flow-control\"))";
               junos:must-message "Option not valid with reset-on-flow-control";
               type empty;
             }
             leaf reset-on-flow-control {
               description "Reset interface during prolonged flow-control";
               junos:must "(!(\".. up-on-flow-control\"))";
               junos:must-message "Option not valid with up-on-flow-control";
               junos:must "(!(\".. down-on-flow-control\"))";
               junos:must-message "Option not valid with down-on-flow-control";
               junos:must "(!(\".. dump-on-flow-control\"))";
               junos:must-message "Option not valid with dump-on-flow-control";
               type empty;
             }
             leaf down-on-flow-control {
               description "Bring interface down during prolonged flow-control";
               junos:must "(!(\".. up-on-flow-control\"))";
               junos:must-message "Option not valid with up-on-flow-control";
               junos:must "(!(\".. reset-on-flow-control\"))";
               junos:must-message "Option not valid with reset-on-flow-control";
               junos:must "(!(\".. dump-on-flow-control\"))";
               junos:must-message "Option not valid with dump-on-flow-control";
               type empty;
             }
             leaf up-on-flow-control {
               description "Keep interface up during prolonged flow-control";
               junos:must "(!(\".. down-on-flow-control\"))";
               junos:must-message "Option not valid with down-on-flow-control";
               junos:must "(!(\".. reset-on-flow-control\"))";
               junos:must-message "Option not valid with reset-on-flow-control";
               junos:must "(!(\".. dump-on-flow-control\"))";
               junos:must-message "Option not valid with dump-on-flow-control";
               type empty;
             }
           }
         }
         container ggsn-options {
           description "GGSN interface-specific options";
           uses apply-advanced;
           choice syslog-choice {
             leaf syslog {
               description "Enable system logging on this interface";
               type empty;
             }
             leaf no-syslog {
               description "Don't enable system logging on this interface";
               type empty;
             }
           }
           choice core-dump-choice {
             leaf core-dump {
               description "Enable core dumping on this interface";
               type empty;
             }
             leaf no-core-dump {
               description "Don't enable core dumping on this interface";
               type empty;
             }
           }
         }
         container ppp-options {
           description "Point-to-Point Protocol (PPP) interface-specific options";
           junos:must "((\".. encapsulation ppp\" || (\".. encapsulation ether-vpls-ppp\" || !(\".. encapsulation\"))))";
           junos:must-message "invalid encapsulation";
           uses ppp_options_type;
         }
         container lsq-failure-options {
           description "Link services queuing failure options";
           uses apply-advanced;
           list trigger-link-failure {
             key name;
             ordered-by user;
             junos:cli-feature "oneliner-plus";
             description "Link on which to trigger failure";
             leaf name {
               description "Interface name";
               junos:cli-feature "nokeyword";
               type union {
                 type jt:interface-device;
                 type string {
                   pattern "<.*>|$.*";
                 }
               }
             }
             uses apply-advanced;
           }
           choice no-termination-request-choice {
             leaf no-termination-request {
               description "Do not send PPP termination requests";
               type empty;
             }
             leaf no-no-termination-request {
               description "Don't do not send PPP termination requests";
               type empty;
             }
           }
         }
         container services-options {
           description "Services interface-specific options";
           uses apply-advanced;
           container syslog {
             description "Define system log parameters";
             uses log-object;
           }
           container jflow-log {
             description "Define Jflow-log parameters.";
             uses apply-advanced;
             leaf message-rate-limit {
               description "Maximum jflow-log NAT error events allowed per second from this interface";
               units "messages per second";
               type union {
                 type string {
                   pattern "<.*>|$.*";
                 }
                 type uint32 {
                   range "1 .. 2147483647";
                 }
               }
             }
           }
           container deterministic-nat-configuration-log-interval {
             presence "enable deterministic-nat-configuration-log-interval";
             description "Define Deterministic NAT parameters";
             uses apply-advanced;
             leaf interval {
               description "Interval in which deterministic NAT logs are generated";
               units "seconds";
               type union {
                 type string {
                   pattern "<.*>|$.*";
                 }
                 type uint32 {
                   range "1800 .. 86400";
                 }
               }
             }
           }
           leaf open-timeout {
             description "Timeout period for TCP session establishment";
             units "seconds";
             type union {
               type string {
                 pattern "<.*>|$.*";
               }
               type uint32 {
                 range "4 .. 300";
               }
             }
           }
           leaf close-timeout {
             description "Timeout period for TCP session tear-down";
             units "seconds";
             type union {
               type string {
                 pattern "<.*>|$.*";
               }
               type uint32 {
                 range "2 .. 300";
               }
             }
           }
           leaf inactivity-timeout {
             description "Inactivity timeout period for established sessions (4..86400)";
             units "seconds";
             type union {
               type uint32;
               type string {
                 pattern "<.*>|$.*";
               }
             }
           }
           leaf inactivity-tcp-timeout {
             description "Inactivity timeout period for TCP established sessions";
             units "seconds";
             type union {
               type string {
                 pattern "<.*>|$.*";
               }
               type uint32 {
                 range "4 .. 86400";
               }
             }
           }
           leaf inactivity-asymm-tcp-timeout {
             description "Inactivity timeout period for asymmetric TCP established sessions";
             units "seconds";
             type union {
               type string {
                 pattern "<.*>|$.*";
               }
               type uint32 {
                 range "4 .. 86400";
               }
             }
           }
           leaf inactivity-non-tcp-timeout {
             description "Inactivity timeout period for non-TCP established sessions";
             units "seconds";
             type union {
               type string {
                 pattern "<.*>|$.*";
               }
               type uint32 {
                 range "4 .. 86400";
               }
             }
           }
           leaf session-timeout {
             description "Session timeout period for established sessions";
             units "seconds";
             type union {
               type string {
                 pattern "<.*>|$.*";
               }
               type uint32 {
                 range "4 .. 86400";
               }
             }
           }
           leaf disable-global-timeout-override {
             description "Disallow overriding  global inactivity or session timeout";
             type empty;
           }
           leaf tcp-tickles {
             description "Number of TCP keep-alive packets to be sent for bi-directional TCP flows";
             default "4";
             type union {
               type string {
                 pattern "<.*>|$.*";
               }
               type uint8 {
                 range "0 .. 30";
               }
             }
           }
           leaf fragment-limit {
             description "Maximum number of fragments allowed for a packet";
             default "64";
             type union {
               type string {
                 pattern "<.*>|$.*";
               }
               type uint8 {
                 range "1 .. 250";
               }
             }
           }
           leaf reassembly-timeout {
             description "Re-assembly timeout (seconds) for fragments of a packet";
             default "4";
             units "seconds";
             type union {
               type string {
                 pattern "<.*>|$.*";
               }
               type uint8 {
                 range "1 .. 60";
               }
             }
           }
           leaf cgn-pic {
             description "PIC will be used for Carrier Grade NAT configuration only";
             type empty;
           }
           leaf pba-interim-logging-interval {
             description "Interim logging interval in seconds";
             default "0";
             units "seconds";
             type union {
               type string {
                 pattern "<.*>|$.*";
               }
               type uint32 {
                 range "0 .. 86400";
               }
             }
           }
           container session-limit {
             presence "enable session-limit";
             description "Session limit";
             uses apply-advanced;
             leaf maximum {
               description "Maximum number of sessions allowed simultaneously";
               type string;
             }
             leaf rate {
               description "Maximum number of new sessions allowed per second";
               type string;
             }
             leaf cpu-load-threshold {
               description "CPU limit in percentage for auto-tuning of session rate";
               units "percent";
               type union {
                 type string {
                   pattern "<.*>|$.*";
                 }
                 type uint8 {
                   range "1 .. 100";
                 }
               }
             }
           }
           leaf enable-subscriber-analysis {
             description "Enable subscriber analysis on the interface";
             junos:must "(!(\".. disable-subscriber-analysis\"))";
             junos:must-message "can not set with enable-subscriber-analysis";
             type empty;
           }
           leaf disable-subscriber-analysis {
             description "Disable subscriber analysis on the interface";
             junos:must "(!(\".. enable-subscriber-analysis\"))";
             junos:must-message "can not set with disable-subscriber-analysis";
             type empty;
           }
           leaf disable-usp-tracing {
             description "Disable usp tracing on this pic";
             type empty;
           }
           leaf disable-drop-flows {
             description "Disable drop flows on this pic";
             type empty;
           }
           container ignore-errors {
             presence "enable ignore-errors";
             junos:cli-feature "oneliner";
             description "Ignore anomalies or errors";
             leaf tcp {
               description "TCP protocol errors";
               type empty;
             }
             leaf alg {
               description "ALG anomalies or errors";
               type empty;
             }
           }
           container capture {
             description "Packet capture for SFW and NAT on the Services PIC";
             uses apply-advanced;
             leaf capture-size {
               description "The number of packets to store";
               type union {
                 type string {
                   pattern "<.*>|$.*";
                 }
                 type uint32 {
                   range "1 .. 344000";
                 }
               }
             }
             leaf pkt-size {
               description "Number of bytes to be saved from each packet";
               type union {
                 type string {
                   pattern "<.*>|$.*";
                 }
                 type uint16 {
                   range "64 .. 15000";
                 }
               }
             }
             leaf logs-per-packet {
               description "The number of trace messages stored for each packet";
               type union {
                 type string {
                   pattern "<.*>|$.*";
                 }
                 type uint16 {
                   range "0 .. 500";
                 }
               }
             }
             leaf max-log-line-size {
               description "The maximum length of a stored trace message";
               type union {
                 type uint8;
                 type string {
                   pattern "<.*>|$.*";
                 }
               }
             }
             container filter {
               presence "enable filter";
               description "Filtering options for the packet capture";
               uses apply-advanced;
               container source-ip {
                 junos:cli-feature "oneliner";
                 description "Filter based on source-ip (and wildcard)";
                 leaf ip {
                   description "Source IP";
                   junos:cli-feature "nokeyword";
                   type jt:ipaddr;
                 }
                 leaf wildcard {
                   description "Source IP wildcard";
                   type jt:ipaddr;
                 }
               }
               container dest-ip {
                 junos:cli-feature "oneliner";
                 description "Filter based on dest-ip (and wildcard)";
                 leaf ip {
                   description "Dest IP";
                   junos:cli-feature "nokeyword";
                   type jt:ipaddr;
                 }
                 leaf wildcard {
                   description "Dest IP wildcard";
                   type jt:ipaddr;
                 }
               }
               container sw-sip {
                 junos:cli-feature "oneliner";
                 description "Filter based on source softwire ip (and wildcard)";
                 leaf ip {
                   description "Source softwire IP";
                   junos:cli-feature "nokeyword";
                   type jt:ipv6addr;
                 }
                 leaf wildcard {
                   description "Source IP wildcard";
                   type jt:ipv6addr;
                 }
               }
               container sw-dip {
                 junos:cli-feature "oneliner";
                 description "Filter based on destination softwire ip (and wildcard)";
                 leaf ip {
                   description "Destination softwire IP";
                   junos:cli-feature "nokeyword";
                   type jt:ipaddr;
                 }
                 leaf wildcard {
                   description "Destination IP wildcard";
                   type jt:ipaddr;
                 }
               }
               container sport-range {
                 junos:cli-feature "oneliner";
                 description "Filter based on source port";
                 leaf low {
                   description "Source port range start";
                   type union {
                     type uint16;
                     type string {
                       pattern "<.*>|$.*";
                     }
                   }
                 }
                 leaf high {
                   description "Source port range end";
                   type union {
                     type uint16;
                     type string {
                       pattern "<.*>|$.*";
                     }
                   }
                 }
               }
               container dport-range {
                 junos:cli-feature "oneliner";
                 description "Filter based on destination port";
                 leaf low {
                   description "Destination port range start";
                   type union {
                     type uint16;
                     type string {
                       pattern "<.*>|$.*";
                     }
                   }
                 }
                 leaf high {
                   description "Destination port range end";
                   type union {
                     type uint16;
                     type string {
                       pattern "<.*>|$.*";
                     }
                   }
                 }
               }
               leaf proto {
                 description "Filter based on L4 protocol";
                 type enumeration {
                   enum "icmp" {
                   }
                   enum "tcp" {
                   }
                   enum "udp" {
                   }
                 }
               }
             }
           }
           container flow {
             description "Define flow parameters";
             uses apply-advanced;
             container traceoptions {
               description "Trace options for flow services";
             }
           }
           leaf fpc-pic-information {
             description "Include FPC and PIC slot number in the syslogs";
             type empty;
           }
           leaf utc-timestamp {
             description "Use UTC time for security log timestamps";
             type empty;
           }
           leaf syslog-local-system-timestamp {
             description "Use local system time for services syslog timestamp";
             type empty;
           }
         }
         container t3-options {
           junos:must "((!(\"interfaces ${interface} container-options\") || (\"interfaces ${interface} container-options container-type\" || \"interfaces ${interface} container-options allow-configuration-override\")))";
           junos:must-message "t1-options cannot be configured without allow-configuration-override";
           description "T3 interface-specific options";
           uses apply-advanced;
           leaf loopback {
             description "Loopback mode";
             type enumeration {
               enum "local" {
                 description "Local loopback";
               }
               enum "remote" {
                 description "Remote loopback";
               }
               enum "payload" {
                 description "Payload loopback";
               }
             }
           }
           choice long-buildout-choice {
             leaf long-buildout {
               description "Set hardware to drive line longer than 255 feet";
               type empty;
             }
             leaf no-long-buildout {
               description "Don't set hardware to drive line longer than 255 feet";
               type empty;
             }
           }
           choice loop-timing-choice {
             leaf loop-timing {
               description "Set loop timing for T3";
               type empty;
             }
             leaf no-loop-timing {
               description "Don't set loop timing for T3";
               type empty;
             }
           }
           choice unframed-choice {
             leaf unframed {
               description "Enable unframed mode";
               type empty;
             }
             leaf no-unframed {
               description "Don't enable unframed mode";
               type empty;
             }
           }
           container compatibility-mode {
             junos:cli-feature "oneliner";
             description "Set CSU compatibility mode";
             choice vendor {
               case case_1 {
                 container larscom {
                   presence "enable larscom";
                   junos:must "(!(\".. .. unframed\"))";
                   junos:must-message "unframed and larscom cannot coexist";
                   junos:cli-feature "oneliner";
                   description "Compatible with Larscom CSU";
                   leaf subrate {
                     description "Set subrate value";
                     type union {
                       type string {
                         pattern "<.*>|$.*";
                       }
                       type uint32 {
                         range "1 .. 14";
                       }
                     }
                   }
                 }
               }
               case case_2 {
                 container verilink {
                   presence "enable verilink";
                   junos:must "(!(\".. .. unframed\"))";
                   junos:must-message "unframed and verilink cannot coexist";
                   junos:cli-feature "oneliner";
                   description "Compatible with Verilink CSU (not on 2/4-port T3 PIC)";
                   leaf subrate {
                     description "Set subrate value";
                     type union {
                       type string {
                         pattern "<.*>|$.*";
                       }
                       type uint32 {
                         range "1 .. 28";
                       }
                     }
                   }
                 }
               }
               case case_3 {
                 container adtran {
                   presence "enable adtran";
                   junos:must "(!(\".. .. unframed\"))";
                   junos:must-message "unframed and adtran cannot coexist";
                   junos:cli-feature "oneliner";
                   description "Compatible with Adtran CSU (not on 2/4-port T3 PIC)";
                   leaf subrate {
                     description "Set subrate value";
                     type union {
                       type string {
                         pattern "<.*>|$.*";
                       }
                       type uint32 {
                         range "1 .. 588";
                       }
                     }
                   }
                 }
               }
               case case_4 {
                 container kentrox {
                   presence "enable kentrox";
                   junos:cli-feature "oneliner";
                   description "Compatible with Kentrox CSU";
                   leaf subrate {
                     description "Set subrate value (not on 2/4-port T3 PIC)";
                     type union {
                       type string {
                         pattern "<.*>|$.*";
                       }
                       type uint32 {
                         range "1 .. 69";
                       }
                     }
                   }
                 }
               }
               case case_5 {
                 container digital-link {
                   presence "enable digital-link";
                   junos:must "(!(\".. .. unframed\"))";
                   junos:must-message "unframed and digital-link cannot coexist";
                   junos:cli-feature "oneliner";
                   description "Compatible with Digital Link CSU";
                   leaf subrate {
                     description "Set subrate value";
                     type enumeration {
                       enum "301Kb" {
                         description "301 Kbps";
                       }
                       enum "601Kb" {
                         description "601 Kbps";
                       }
                       enum "902Kb" {
                         description "902 Kbps";
                       }
                       enum "1.2Mb" {
                         description "1.2 Mbps";
                       }
                       enum "1.5Mb" {
                         description "1.5 Mbps";
                       }
                       enum "1.8Mb" {
                         description "1.8 Mbps";
                       }
                       enum "2.1Mb" {
                         description "2.1 Mbps";
                       }
                       enum "2.4Mb" {
                         description "2.4 Mbps";
                       }
                       enum "2.7Mb" {
                         description "2.7 Mbps";
                       }
                       enum "3.0Mb" {
                         description "3.0 Mbps";
                       }
                       enum "3.3Mb" {
                         description "3.3 Mbps";
                       }
                       enum "3.6Mb" {
                         description "3.6 Mbps";
                       }
                       enum "3.9Mb" {
                         description "3.9 Mbps";
                       }
                       enum "4.2Mb" {
                         description "4.2 Mbps";
                       }
                       enum "4.5Mb" {
                         description "4.5 Mbps";
                       }
                       enum "4.8Mb" {
                         description "4.8 Mbps";
                       }
                       enum "5.1Mb" {
                         description "5.1 Mbps";
                       }
                       enum "5.4Mb" {
                         description "5.4 Mbps";
                       }
                       enum "5.7Mb" {
                         description "5.7 Mbps";
                       }
                       enum "6.0Mb" {
                         description "6.0 Mbps";
                       }
                       enum "6.3Mb" {
                         description "6.3 Mbps";
                       }
                       enum "6.6Mb" {
                         description "6.6 Mbps";
                       }
                       enum "6.9Mb" {
                         description "6.9 Mbps";
                       }
                       enum "7.2Mb" {
                         description "7.2 Mbps";
                       }
                       enum "7.5Mb" {
                         description "7.5 Mbps";
                       }
                       enum "7.8Mb" {
                         description "7.8 Mbps";
                       }
                       enum "8.1Mb" {
                         description "8.1 Mbps";
                       }
                       enum "8.4Mb" {
                         description "8.4 Mbps";
                       }
                       enum "8.7Mb" {
                         description "8.7 Mbps";
                       }
                       enum "9.0Mb" {
                         description "9.0 Mbps";
                       }
                       enum "9.3Mb" {
                         description "9.3 Mbps";
                       }
                       enum "9.6Mb" {
                         description "9.6 Mbps";
                       }
                       enum "9.9Mb" {
                         description "9.9 Mbps";
                       }
                       enum "10.2Mb" {
                         description "10.2 Mbps";
                       }
                       enum "10.5Mb" {
                         description "10.5 Mbps";
                       }
                       enum "10.8Mb" {
                         description "10.8 Mbps";
                       }
                       enum "11.1Mb" {
                         description "11.1 Mbps";
                       }
                       enum "11.4Mb" {
                         description "11.4 Mbps";
                       }
                       enum "11.7Mb" {
                         description "11.7 Mbps";
                       }
                       enum "12.0Mb" {
                         description "12.0 Mbps";
                       }
                       enum "12.3Mb" {
                         description "12.3 Mbps";
                       }
                       enum "12.6Mb" {
                         description "12.6 Mbps";
                       }
                       enum "12.9Mb" {
                         description "12.9 Mbps";
                       }
                       enum "13.2Mb" {
                         description "13.2 Mbps";
                       }
                       enum "13.5Mb" {
                         description "13.5 Mbps";
                       }
                       enum "13.8Mb" {
                         description "13.8 Mbps";
                       }
                       enum "14.1Mb" {
                         description "14.1 Mbps";
                       }
                       enum "14.4Mb" {
                         description "14.4 Mbps";
                       }
                       enum "14.7Mb" {
                         description "14.7 Mbps";
                       }
                       enum "15.0Mb" {
                         description "15.0 Mbps";
                       }
                       enum "15.3Mb" {
                         description "15.3 Mbps";
                       }
                       enum "15.6Mb" {
                         description "15.6 Mbps";
                       }
                       enum "15.9Mb" {
                         description "15.9 Mbps";
                       }
                       enum "16.2Mb" {
                         description "16.2 Mbps";
                       }
                       enum "16.5Mb" {
                         description "16.5 Mbps";
                       }
                       enum "16.8Mb" {
                         description "16.8 Mbps";
                       }
                       enum "17.1Mb" {
                         description "17.1 Mbps";
                       }
                       enum "17.4Mb" {
                         description "17.4 Mbps";
                       }
                       enum "17.7Mb" {
                         description "17.7 Mbps";
                       }
                       enum "18.0Mb" {
                         description "18.0 Mbps";
                       }
                       enum "18.3Mb" {
                         description "18.3 Mbps";
                       }
                       enum "18.6Mb" {
                         description "18.6 Mbps";
                       }
                       enum "18.9Mb" {
                         description "18.9 Mbps";
                       }
                       enum "19.2Mb" {
                         description "19.2 Mbps";
                       }
                       enum "19.5Mb" {
                         description "19.5 Mbps";
                       }
                       enum "19.8Mb" {
                         description "19.8 Mbps";
                       }
                       enum "20.1Mb" {
                         description "20.1 Mbps";
                       }
                       enum "20.5Mb" {
                         description "20.5 Mbps";
                       }
                       enum "20.8Mb" {
                         description "20.8 Mbps";
                       }
                       enum "21.1Mb" {
                         description "21.1 Mbps";
                       }
                       enum "21.4Mb" {
                         description "21.4 Mbps";
                       }
                       enum "21.7Mb" {
                         description "21.7 Mbps";
                       }
                       enum "22.0Mb" {
                         description "22.0 Mbps";
                       }
                       enum "22.3Mb" {
                         description "22.3 Mbps";
                       }
                       enum "22.6Mb" {
                         description "22.6 Mbps";
                       }
                       enum "22.9Mb" {
                         description "22.9 Mbps";
                       }
                       enum "23.2Mb" {
                         description "23.2 Mbps";
                       }
                       enum "23.5Mb" {
                         description "23.5 Mbps";
                       }
                       enum "23.8Mb" {
                         description "23.8 Mbps";
                       }
                       enum "24.1Mb" {
                         description "24.1 Mbps";
                       }
                       enum "24.4Mb" {
                         description "24.4 Mbps";
                       }
                       enum "24.7Mb" {
                         description "24.7 Mbps";
                       }
                       enum "25.0Mb" {
                         description "25.0 Mbps";
                       }
                       enum "25.3Mb" {
                         description "25.3 Mbps";
                       }
                       enum "25.6Mb" {
                         description "25.6 Mbps";
                       }
                       enum "25.9Mb" {
                         description "25.9 Mbps";
                       }
                       enum "26.2Mb" {
                         description "26.2 Mbps";
                       }
                       enum "26.5Mb" {
                         description "26.5 Mbps";
                       }
                       enum "26.8Mb" {
                         description "26.8 Mbps";
                       }
                       enum "27.1Mb" {
                         description "27.1 Mbps";
                       }
                       enum "27.4Mb" {
                         description "27.4 Mbps";
                       }
                       enum "27.7Mb" {
                         description "27.7 Mbps";
                       }
                       enum "28.0Mb" {
                         description "28.0 Mbps";
                       }
                       enum "28.3Mb" {
                         description "28.3 Mbps";
                       }
                       enum "28.6Mb" {
                         description "28.6 Mbps";
                       }
                       enum "28.9Mb" {
                         description "28.9 Mbps";
                       }
                       enum "29.2Mb" {
                         description "29.2 Mbps";
                       }
                       enum "29.5Mb" {
                         description "29.5 Mbps";
                       }
                       enum "29.8Mb" {
                         description "29.8 Mbps";
                       }
                       enum "30.1Mb" {
                         description "30.1 Mbps";
                       }
                       enum "30.4Mb" {
                         description "30.4 Mbps";
                       }
                       enum "30.7Mb" {
                         description "30.7 Mbps";
                       }
                       enum "31.0Mb" {
                         description "31.0 Mbps";
                       }
                       enum "31.3Mb" {
                         description "31.3 Mbps";
                       }
                       enum "31.6Mb" {
                         description "31.6 Mbps";
                       }
                       enum "31.9Mb" {
                         description "31.9 Mbps";
                       }
                       enum "32.2Mb" {
                         description "32.2 Mbps";
                       }
                       enum "32.5Mb" {
                         description "32.5 Mbps";
                       }
                       enum "32.8Mb" {
                         description "32.8 Mbps";
                       }
                       enum "33.1Mb" {
                         description "33.1 Mbps";
                       }
                       enum "33.4Mb" {
                         description "33.4 Mbps";
                       }
                       enum "33.7Mb" {
                         description "33.7 Mbps";
                       }
                       enum "34.0Mb" {
                         description "34.0 Mbps";
                       }
                       enum "34.3Mb" {
                         description "34.3 Mbps";
                       }
                       enum "34.6Mb" {
                         description "34.6 Mbps";
                       }
                       enum "34.9Mb" {
                         description "34.9 Mbps";
                       }
                       enum "35.2Mb" {
                         description "35.2 Mbps";
                       }
                       enum "35.5Mb" {
                         description "35.5 Mbps";
                       }
                       enum "35.8Mb" {
                         description "35.8 Mbps";
                       }
                       enum "36.1Mb" {
                         description "36.1 Mbps";
                       }
                       enum "36.4Mb" {
                         description "36.4 Mbps";
                       }
                       enum "36.7Mb" {
                         description "36.7 Mbps";
                       }
                       enum "37.0Mb" {
                         description "37.0 Mbps";
                       }
                       enum "37.3Mb" {
                         description "37.3 Mbps";
                       }
                       enum "37.6Mb" {
                         description "37.6 Mbps";
                       }
                       enum "37.9Mb" {
                         description "37.9 Mbps";
                       }
                       enum "38.2Mb" {
                         description "38.2 Mbps";
                       }
                       enum "38.5Mb" {
                         description "38.5 Mbps";
                       }
                       enum "38.8Mb" {
                         description "38.8 Mbps";
                       }
                       enum "39.1Mb" {
                         description "39.1 Mbps";
                       }
                       enum "39.4Mb" {
                         description "39.4 Mbps";
                       }
                       enum "39.7Mb" {
                         description "39.7 Mbps";
                       }
                       enum "40.0Mb" {
                         description "40.0 Mbps";
                       }
                       enum "40.3Mb" {
                         description "40.3 Mbps";
                       }
                       enum "40.6Mb" {
                         description "40.6 Mbps";
                       }
                       enum "40.9Mb" {
                         description "40.9 Mbps";
                       }
                       enum "41.2Mb" {
                         description "41.2 Mbps";
                       }
                       enum "41.5Mb" {
                         description "41.5 Mbps";
                       }
                       enum "41.8Mb" {
                         description "41.8 Mbps";
                       }
                       enum "42.1Mb" {
                         description "42.1 Mbps";
                       }
                       enum "42.4Mb" {
                         description "42.4 Mbps";
                       }
                       enum "42.7Mb" {
                         description "42.7 Mbps";
                       }
                       enum "43.0Mb" {
                         description "43.0 Mbps";
                       }
                       enum "43.3Mb" {
                         description "43.3 Mbps";
                       }
                       enum "43.6Mb" {
                         description "43.6 Mbps";
                       }
                       enum "43.9Mb" {
                         description "43.9 Mbps";
                       }
                       enum "44.2Mb" {
                         description "44.2 Mbps";
                       }
                     }
                   }
                 }
               }
             }
           }
           choice payload-scrambler-choice {
             leaf payload-scrambler {
               description "Enable payload scrambling";
               type empty;
             }
             leaf no-payload-scrambler {
               description "Don't enable payload scrambling";
               type empty;
             }
           }
           choice cbit-parity-choice {
             leaf cbit-parity {
               description "Enable C-bit parity mode";
               junos:must "(!(\".. unframed\"))";
               junos:must-message "cbit-parity and unframed cannot coexist";
               type empty;
             }
             leaf no-cbit-parity {
               description "Don't enable C-bit parity mode";
               junos:must "(!(\".. unframed\"))";
               junos:must-message "cbit-parity and unframed cannot coexist";
               type empty;
             }
           }
           leaf fcs {
             description "Frame checksum";
             type enumeration {
               enum "32" {
                 description "32-bit mode";
               }
               enum "16" {
                 description "16-bit mode";
               }
             }
           }
           leaf idle-cycle-flag {
             description "Value to transmit in idle cycles";
             type enumeration {
               enum "flags" {
                 description "Transmit 0x7E in idle cycles";
               }
               enum "ones" {
                 description "Transmit 0xFF (all ones) in idle cycles";
               }
             }
           }
           leaf start-end-flag {
             description "Set start/end flags on transmission";
             type enumeration {
               enum "shared" {
                 description "Share start/end flags on transmit";
               }
               enum "filler" {
                 description "Send two idle cycles between start/end flags";
               }
             }
           }
           choice feac-loop-respond-choice {
             leaf feac-loop-respond {
               description "Respond to FEAC loop requests";
               type empty;
             }
             leaf no-feac-loop-respond {
               description "Don't respond to FEAC loop requests";
               type empty;
             }
           }
           leaf bert-algorithm {
             description "Set BERT algorithm";
             type enumeration {
               enum "pseudo-2e3" {
                 description "Pattern is 2^3 - 1";
               }
               enum "pseudo-2e4" {
                 description "Pattern is 2^4 - 1";
               }
               enum "pseudo-2e5" {
                 description "Pattern is 2^5 - 1";
               }
               enum "pseudo-2e6" {
                 description "Pattern is 2^6 - 1";
               }
               enum "pseudo-2e7" {
                 description "Pattern is 2^7 - 1";
               }
               enum "pseudo-2e9-o153" {
                 description "Pattern is 2^9 - 1 (per O.153 standard)";
               }
               enum "pseudo-2e10" {
                 description "Pattern is 2^10 - 1";
               }
               enum "pseudo-2e11-o152" {
                 description "Pattern is 2^11 -1 (per O.152 standard)";
               }
               enum "pseudo-2e15-o151" {
                 description "Pattern is 2^15 - 1 (per O.151 standard)";
               }
               enum "pseudo-2e17" {
                 description "Pattern is 2^17 - 1";
               }
               enum "pseudo-2e18" {
                 description "Pattern is 2^18 - 1";
               }
               enum "pseudo-2e20-o153" {
                 description "Pattern is 2^20 - 1 (per O.153 standard)";
               }
               enum "pseudo-2e20-o151" {
                 description "Pattern is 2^20 - 1 (per O.151 standard)";
               }
               enum "pseudo-2e21" {
                 description "Pattern is 2^21 - 1";
               }
               enum "pseudo-2e22" {
                 description "Pattern is 2^22 - 1";
               }
               enum "pseudo-2e23-o151" {
                 description "Pattern is 2^23 (per O.151 standard)";
               }
               enum "pseudo-2e25" {
                 description "Pattern is 2^25 - 1";
               }
               enum "pseudo-2e28" {
                 description "Pattern is 2^28 - 1";
               }
               enum "pseudo-2e29" {
                 description "Pattern is 2^29 - 1";
               }
               enum "pseudo-2e31" {
                 description "Pattern is 2^31 - 1";
               }
               enum "pseudo-2e32" {
                 description "Pattern is 2^32 - 1";
               }
               enum "all-ones-repeating" {
                 description "Repeating one bits";
               }
               enum "all-zeros-repeating" {
                 description "Repeating zero bits";
               }
               enum "alternating-ones-zeros" {
                 description "Alternating ones and zeros";
               }
               enum "alternating-double-ones-zeros" {
                 description "Alternating pairs of ones and zeros";
               }
               enum "repeating-3-in-24" {
                 description "3 bits in 24 are set";
               }
               enum "repeating-1-in-8" {
                 description "1 bit in 8 is set";
               }
               enum "repeating-1-in-4" {
                 description "1 bit in 4 is set";
               }
             }
           }
           leaf bert-error-rate {
             description "Bit error rate (10^-n for n > 0, and zero for n = 0)";
             type union {
               type string {
                 pattern "<.*>|$.*";
               }
               type uint32 {
                 range "0 .. 7";
               }
             }
           }
           leaf bert-period {
             description "Length of BERT test";
             units "seconds";
             type union {
               type string {
                 pattern "<.*>|$.*";
               }
               type uint32 {
                 range "1 .. 240";
               }
             }
           }
           leaf buildout {
             description "Line buildout";
             units "feet";
             type union {
               type string {
                 pattern "<.*>|$.*";
               }
               type uint32 {
                 range "0 .. 450";
               }
             }
           }
           leaf atm-encapsulation {
             description "DS-3 interface encapsulation";
             type enumeration {
               enum "plcp" {
                 description "PLCP encapsulation";
               }
               enum "direct" {
                 description "ATM direct mapping";
               }
             }
           }
         }
         container e3-options {
           junos:must "((!(\"interfaces ${interface} container-options\") || (\"interfaces ${interface} container-options container-type\" || \"interfaces ${interface} container-options allow-configuration-override\")))";
           junos:must-message "t1-options cannot be configured without allow-configuration-override";
           description "E3 interface-specific options";
           uses apply-advanced;
           leaf loopback {
             description "Loopback mode";
             type enumeration {
               enum "local" {
                 description "Local loopback";
               }
               enum "remote" {
                 description "Remote loopback";
               }
             }
           }
           choice unframed-choice {
             leaf unframed {
               description "Enable unframed mode";
               type empty;
             }
             leaf no-unframed {
               description "Don't enable unframed mode";
               type empty;
             }
           }
           container compatibility-mode {
             junos:cli-feature "oneliner";
             description "Set CSU compatibility mode";
             choice vendor {
               case case_1 {
                 leaf larscom {
                   description "Compatible with Larscom CSU (only non IQ E3 interfaces)";
                   type empty;
                 }
               }
               case case_2 {
                 container digital-link {
                   presence "enable digital-link";
                   junos:must "(!(\".. .. unframed\"))";
                   junos:must-message "unframed and digital-link cannot coexist";
                   junos:cli-feature "oneliner";
                   description "Compatible with Digital Link CSU";
                   leaf subrate {
                     description "Set subrate value";
                     type enumeration {
                       enum "358Kb" {
                         description "358 Kbps";
                       }
                       enum "716Kb" {
                         description "716 Kbps";
                       }
                       enum "1.1Mb" {
                         description "1.1 Mbps";
                       }
                       enum "1.4Mb" {
                         description "1.4 Mbps";
                       }
                       enum "1.8Mb" {
                         description "1.8 Mbps";
                       }
                       enum "2.1Mb" {
                         description "2.1 Mbps";
                       }
                       enum "2.5Mb" {
                         description "2.5 Mbps";
                       }
                       enum "2.9Mb" {
                         description "2.9 Mbps";
                       }
                       enum "3.2Mb" {
                         description "3.2 Mbps";
                       }
                       enum "3.6Mb" {
                         description "3.6 Mbps";
                       }
                       enum "3.9Mb" {
                         description "3.9 Mbps";
                       }
                       enum "4.3Mb" {
                         description "4.3 Mbps";
                       }
                       enum "4.7Mb" {
                         description "4.7 Mbps";
                       }
                       enum "5.0Mb" {
                         description "5.0 Mbps";
                       }
                       enum "5.4Mb" {
                         description "5.4 Mbps";
                       }
                       enum "5.7Mb" {
                         description "5.7 Mbps";
                       }
                       enum "6.1Mb" {
                         description "6.1 Mbps";
                       }
                       enum "6.4Mb" {
                         description "6.4 Mbps";
                       }
                       enum "6.8Mb" {
                         description "6.8 Mbps";
                       }
                       enum "7.2Mb" {
                         description "7.2 Mbps";
                       }
                       enum "7.5Mb" {
                         description "7.5 Mbps";
                       }
                       enum "7.9Mb" {
                         description "7.9 Mbps";
                       }
                       enum "8.2Mb" {
                         description "8.2 Mbps";
                       }
                       enum "8.6Mb" {
                         description "8.6 Mbps";
                       }
                       enum "9.0Mb" {
                         description "9.0 Mbps";
                       }
                       enum "9.3Mb" {
                         description "9.3 Mbps";
                       }
                       enum "9.7Mb" {
                         description "9.7 Mbps";
                       }
                       enum "10.0Mb" {
                         description "10.0 Mbps";
                       }
                       enum "10.4Mb" {
                         description "10.4 Mbps";
                       }
                       enum "10.7Mb" {
                         description "10.7 Mbps";
                       }
                       enum "11.1Mb" {
                         description "11.1 Mbps";
                       }
                       enum "11.5Mb" {
                         description "11.5 Mbps";
                       }
                       enum "11.8Mb" {
                         description "11.8 Mbps";
                       }
                       enum "12.2Mb" {
                         description "12.2 Mbps";
                       }
                       enum "12.5Mb" {
                         description "12.5 Mbps";
                       }
                       enum "12.9Mb" {
                         description "12.9 Mbps";
                       }
                       enum "13.2Mb" {
                         description "13.2 Mbps";
                       }
                       enum "13.6Mb" {
                         description "13.6 Mbps";
                       }
                       enum "14.0Mb" {
                         description "14.0 Mbps";
                       }
                       enum "14.3Mb" {
                         description "14.3 Mbps";
                       }
                       enum "14.7Mb" {
                         description "14.7 Mbps";
                       }
                       enum "15.0Mb" {
                         description "15.0 Mbps";
                       }
                       enum "15.4Mb" {
                         description "15.4 Mbps";
                       }
                       enum "15.8Mb" {
                         description "15.8 Mbps";
                       }
                       enum "16.1Mb" {
                         description "16.1 Mbps";
                       }
                       enum "16.5Mb" {
                         description "16.5 Mbps";
                       }
                       enum "16.8Mb" {
                         description "16.8 Mbps";
                       }
                       enum "17.2Mb" {
                         description "17.2 Mbps";
                       }
                       enum "17.5Mb" {
                         description "17.5 Mbps";
                       }
                       enum "17.9Mb" {
                         description "17.9 Mbps";
                       }
                       enum "18.3Mb" {
                         description "18.3 Mbps";
                       }
                       enum "18.6Mb" {
                         description "18.6 Mbps";
                       }
                       enum "19.0Mb" {
                         description "19.0 Mbps";
                       }
                       enum "19.3Mb" {
                         description "19.3 Mbps";
                       }
                       enum "19.7Mb" {
                         description "19.7 Mbps";
                       }
                       enum "20.0Mb" {
                         description "20.0 Mbps";
                       }
                       enum "20.4Mb" {
                         description "20.4 Mbps";
                       }
                       enum "20.8Mb" {
                         description "20.8 Mbps";
                       }
                       enum "21.1Mb" {
                         description "21.1 Mbps";
                       }
                       enum "21.5Mb" {
                         description "21.5 Mbps";
                       }
                       enum "21.8Mb" {
                         description "21.8 Mbps";
                       }
                       enum "22.2Mb" {
                         description "22.2 Mbps";
                       }
                       enum "22.6Mb" {
                         description "22.6 Mbps";
                       }
                       enum "22.9Mb" {
                         description "22.9 Mbps";
                       }
                       enum "23.3Mb" {
                         description "23.3 Mbps";
                       }
                       enum "23.6Mb" {
                         description "23.6 Mbps";
                       }
                       enum "24.0Mb" {
                         description "24.0 Mbps";
                       }
                       enum "24.3Mb" {
                         description "24.3 Mbps";
                       }
                       enum "24.7Mb" {
                         description "24.7 Mbps";
                       }
                       enum "25.1Mb" {
                         description "25.1 Mbps";
                       }
                       enum "25.4Mb" {
                         description "25.4 Mbps";
                       }
                       enum "25.8Mb" {
                         description "25.8 Mbps";
                       }
                       enum "26.1Mb" {
                         description "26.1 Mbps";
                       }
                       enum "26.5Mb" {
                         description "26.5 Mbps";
                       }
                       enum "26.9Mb" {
                         description "26.9 Mbps";
                       }
                       enum "27.2Mb" {
                         description "27.2 Mbps";
                       }
                       enum "27.6Mb" {
                         description "27.6 Mbps";
                       }
                       enum "27.9Mb" {
                         description "27.9 Mbps";
                       }
                       enum "28.3Mb" {
                         description "28.3 Mbps";
                       }
                       enum "28.6Mb" {
                         description "28.6 Mbps";
                       }
                       enum "29.0Mb" {
                         description "29.0 Mbps";
                       }
                       enum "29.4Mb" {
                         description "29.4 Mbps";
                       }
                       enum "29.7Mb" {
                         description "29.7 Mbps";
                       }
                       enum "30.1Mb" {
                         description "30.1 Mbps";
                       }
                       enum "30.4Mb" {
                         description "30.4 Mbps";
                       }
                       enum "30.8Mb" {
                         description "30.8 Mbps";
                       }
                       enum "31.1Mb" {
                         description "31.1 Mbps";
                       }
                       enum "31.5Mb" {
                         description "31.5 Mbps";
                       }
                       enum "31.9Mb" {
                         description "31.9 Mbps";
                       }
                       enum "32.2Mb" {
                         description "32.2 Mbps";
                       }
                       enum "32.6Mb" {
                         description "32.6 Mbps";
                       }
                       enum "32.9Mb" {
                         description "32.9 Mbps";
                       }
                       enum "33.3Mb" {
                         description "33.3 Mbps";
                       }
                       enum "33.7Mb" {
                         description "33.7 Mbps";
                       }
                       enum "34.0Mb" {
                         description "34.0 Mbps";
                       }
                     }
                   }
                 }
               }
               case case_3 {
                 container kentrox {
                   presence "enable kentrox";
                   junos:cli-feature "oneliner";
                   description "Compatible with Kentrox CSU";
                   leaf subrate {
                     description "Set subrate value (only for E3 IQ interfaces)";
                     type union {
                       type string {
                         pattern "<.*>|$.*";
                       }
                       type uint32 {
                         range "1 .. 48";
                       }
                     }
                   }
                 }
               }
             }
           }
           choice payload-scrambler-choice {
             leaf payload-scrambler {
               description "Enable payload scrambling";
               type empty;
             }
             leaf no-payload-scrambler {
               description "Don't enable payload scrambling";
               type empty;
             }
           }
           leaf fcs {
             description "Frame checksum";
             type enumeration {
               enum "32" {
                 description "32-bit mode";
               }
               enum "16" {
                 description "16-bit mode";
               }
             }
           }
           leaf idle-cycle-flag {
             description "Value to transmit in idle cycles";
             type enumeration {
               enum "flags" {
                 description "Transmit 0x7E in idle cycles";
               }
               enum "ones" {
                 description "Transmit 0xFF (all ones) in idle cycles";
               }
             }
           }
           leaf invert-data {
             description "Invert data";
             type empty;
           }
           leaf start-end-flag {
             description "Set start/end flags on transmission";
             type enumeration {
               enum "shared" {
                 description "Share start/end flags on transmit";
               }
               enum "filler" {
                 description "Send two idle cycles between start/end flags";
               }
             }
           }
           leaf bert-algorithm {
             description "Set BERT algorithm";
             type enumeration {
               enum "pseudo-2e3" {
                 description "Pattern is 2^3 - 1";
               }
               enum "pseudo-2e4" {
                 description "Pattern is 2^4 - 1";
               }
               enum "pseudo-2e5" {
                 description "Pattern is 2^5 - 1";
               }
               enum "pseudo-2e6" {
                 description "Pattern is 2^6 - 1";
               }
               enum "pseudo-2e7" {
                 description "Pattern is 2^7 - 1";
               }
               enum "pseudo-2e9-o153" {
                 description "Pattern is 2^9 - 1 (per O.153 standard)";
               }
               enum "pseudo-2e10" {
                 description "Pattern is 2^10 - 1";
               }
               enum "pseudo-2e11-o152" {
                 description "Pattern is 2^11 -1 (per O.152 standard)";
               }
               enum "pseudo-2e15-o151" {
                 description "Pattern is 2^15 - 1 (per O.151 standard)";
               }
               enum "pseudo-2e17" {
                 description "Pattern is 2^17 - 1";
               }
               enum "pseudo-2e18" {
                 description "Pattern is 2^18 - 1";
               }
               enum "pseudo-2e20-o153" {
                 description "Pattern is 2^20 - 1 (per O.153 standard)";
               }
               enum "pseudo-2e20-o151" {
                 description "Pattern is 2^20 - 1 (per O.151 standard)";
               }
               enum "pseudo-2e21" {
                 description "Pattern is 2^21 - 1";
               }
               enum "pseudo-2e22" {
                 description "Pattern is 2^22 - 1";
               }
               enum "pseudo-2e23-o151" {
                 description "Pattern is 2^23 (per O.151 standard)";
               }
               enum "pseudo-2e25" {
                 description "Pattern is 2^25 - 1";
               }
               enum "pseudo-2e28" {
                 description "Pattern is 2^28 - 1";
               }
               enum "pseudo-2e29" {
                 description "Pattern is 2^29 - 1";
               }
               enum "pseudo-2e31" {
                 description "Pattern is 2^31 - 1";
               }
               enum "pseudo-2e32" {
                 description "Pattern is 2^32 - 1";
               }
               enum "all-ones-repeating" {
                 description "Repeating one bits";
               }
               enum "all-zeros-repeating" {
                 description "Repeating zero bits";
               }
               enum "alternating-ones-zeros" {
                 description "Alternating ones and zeros";
               }
               enum "alternating-double-ones-zeros" {
                 description "Alternating pairs of ones and zeros";
               }
               enum "repeating-3-in-24" {
                 description "3 bits in 24 are set";
               }
               enum "repeating-1-in-8" {
                 description "1 bit in 8 is set";
               }
               enum "repeating-1-in-4" {
                 description "1 bit in 4 is set";
               }
             }
           }
           leaf bert-error-rate {
             description "Bit error rate (10^-n for n > 0, and zero for n = 0)";
             type union {
               type string {
                 pattern "<.*>|$.*";
               }
               type uint32 {
                 range "0 .. 7";
               }
             }
           }
           leaf bert-period {
             description "Length of BERT test";
             units "seconds";
             type union {
               type string {
                 pattern "<.*>|$.*";
               }
               type uint32 {
                 range "1 .. 240";
               }
             }
           }
           leaf buildout {
             description "Line buildout";
             units "feet";
             type union {
               type string {
                 pattern "<.*>|$.*";
               }
               type uint32 {
                 range "0 .. 450";
               }
             }
           }
           leaf atm-encapsulation {
             description "E3 interface encapsulation";
             type enumeration {
               enum "plcp" {
                 description "PLCP encapsulation";
               }
               enum "direct" {
                 description "ATM direct mapping";
               }
             }
           }
           leaf framing {
             description "E3 line format";
             type enumeration {
               enum "g.751" {
                 description "G.751 format";
               }
               enum "g.832" {
                 description "G.832 format";
               }
             }
           }
         }
         container e1-options {
           junos:must "((!(\"interfaces ${interface} container-options\") || (\"interfaces ${interface} container-options container-type\" || \"interfaces ${interface} container-options allow-configuration-override\")))";
           junos:must-message "e1-options cannot be configured without allow-configuration-override";
           description "E1 interface-specific options";
           uses apply-advanced;
           leaf timeslots {
             description "Timeslots (1..32); for example, 1-4,6,9-11,32 (no space)";
             type string;
           }
           leaf loopback {
             description "Loopback mode";
             type enumeration {
               enum "local" {
                 description "Local loopback";
               }
               enum "remote" {
                 description "Remote loopback";
               }
             }
           }
           leaf framing {
             description "Framing mode";
             type enumeration {
               enum "g704" {
                 description "G704 mode with CRC4";
               }
               enum "unframed" {
                 description "Unframed mode";
               }
               enum "g704-no-crc4" {
                 description "G704 mode without CRC4";
               }
             }
           }
           leaf fcs {
             description "Frame checksum";
             type enumeration {
               enum "32" {
                 description "32-bit mode";
               }
               enum "16" {
                 description "16-bit mode";
               }
             }
           }
           leaf invert-data {
             description "Invert data";
             type empty;
           }
           leaf idle-cycle-flag {
             description "Value to transmit in idle cycles";
             type enumeration {
               enum "flags" {
                 description "Transmit 0x7E in idle cycles";
               }
               enum "ones" {
                 description "Transmit 0xFF (all ones) in idle cycles";
               }
             }
           }
           leaf start-end-flag {
             description "Set start/end flags on transmission";
             type enumeration {
               enum "shared" {
                 description "Share start/end flags on transmit";
               }
               enum "filler" {
                 description "Send two idle cycles between start/end flags";
               }
             }
           }
           leaf bert-algorithm {
             description "Set BERT algorithm";
             type enumeration {
               enum "pseudo-2e3" {
                 description "Pattern is 2^3 - 1";
               }
               enum "pseudo-2e4" {
                 description "Pattern is 2^4 - 1";
               }
               enum "pseudo-2e5" {
                 description "Pattern is 2^5 - 1";
               }
               enum "pseudo-2e6" {
                 description "Pattern is 2^6 - 1";
               }
               enum "pseudo-2e7" {
                 description "Pattern is 2^7 - 1";
               }
               enum "pseudo-2e9-o153" {
                 description "Pattern is 2^9 - 1 (per O.153 standard)";
               }
               enum "pseudo-2e10" {
                 description "Pattern is 2^10 - 1";
               }
               enum "pseudo-2e11-o152" {
                 description "Pattern is 2^11 -1 (per O.152 standard)";
               }
               enum "pseudo-2e15-o151" {
                 description "Pattern is 2^15 - 1 (per O.151 standard)";
               }
               enum "pseudo-2e17" {
                 description "Pattern is 2^17 - 1";
               }
               enum "pseudo-2e18" {
                 description "Pattern is 2^18 - 1";
               }
               enum "pseudo-2e20-o153" {
                 description "Pattern is 2^20 - 1 (per O.153 standard)";
               }
               enum "pseudo-2e20-o151" {
                 description "Pattern is 2^20 - 1 (per O.151 standard)";
               }
               enum "pseudo-2e21" {
                 description "Pattern is 2^21 - 1";
               }
               enum "pseudo-2e22" {
                 description "Pattern is 2^22 - 1";
               }
               enum "pseudo-2e23-o151" {
                 description "Pattern is 2^23 (per O.151 standard)";
               }
               enum "pseudo-2e25" {
                 description "Pattern is 2^25 - 1";
               }
               enum "pseudo-2e28" {
                 description "Pattern is 2^28 - 1";
               }
               enum "pseudo-2e29" {
                 description "Pattern is 2^29 - 1";
               }
               enum "pseudo-2e31" {
                 description "Pattern is 2^31 - 1";
               }
               enum "pseudo-2e32" {
                 description "Pattern is 2^32 - 1";
               }
               enum "all-ones-repeating" {
                 description "Repeating one bits";
               }
               enum "all-zeros-repeating" {
                 description "Repeating zero bits";
               }
               enum "alternating-ones-zeros" {
                 description "Alternating ones and zeros";
               }
               enum "alternating-double-ones-zeros" {
                 description "Alternating pairs of ones and zeros";
               }
               enum "repeating-3-in-24" {
                 description "3 bits in 24 are set";
               }
               enum "repeating-1-in-8" {
                 description "1 bit in 8 is set";
               }
               enum "repeating-1-in-4" {
                 description "1 bit in 4 is set";
               }
             }
           }
           leaf bert-error-rate {
             description "Bit error rate (10^-n for n > 0, and zero for n = 0)";
             type union {
               type string {
                 pattern "<.*>|$.*";
               }
               type uint32 {
                 range "0 .. 7";
               }
             }
           }
           leaf bert-period {
             description "Length of BERT test";
             units "seconds";
             type union {
               type string {
                 pattern "<.*>|$.*";
               }
               type uint32 {
                 range "1 .. 86400";
               }
             }
           }
         }
         container t1-options {
           junos:must "((!(\"interfaces ${interface} container-options\") || (\"interfaces ${interface} container-options container-type\" || \"interfaces ${interface} container-options allow-configuration-override\")))";
           junos:must-message "t1-options cannot be configured without allow-configuration-override";
           description "T1 interface-specific options";
           uses apply-advanced;
           leaf timeslots {
             description "Timeslots (1..24; for example, 1-3,4,9,22-24 (no space)";
             type string;
           }
           leaf voice-timeslots {
             description "Voice timeslots (1..24),for example, 1-3,4,9,22-24 (no space)";
             type string;
           }
           leaf loopback {
             description "Loopback mode";
             type enumeration {
               enum "local" {
                 description "Local loopback";
               }
               enum "remote" {
                 description "Remote loopback";
               }
               enum "payload" {
                 description "Payload loopback";
               }
             }
           }
           leaf buildout {
             description "Line buildout";
             type enumeration {
               enum "0-132" {
                 description "Line buildout is between 0-132 feet";
               }
               enum "133-265" {
                 description "Line buildout is between 133-265 feet";
               }
               enum "266-398" {
                 description "Line buildout is between 266-398 feet";
               }
               enum "399-531" {
                 description "Line buildout is between 399-531 feet";
               }
               enum "532-655" {
                 description "Line buildout is between 532-655 feet";
               }
               enum "long-0db" {
                 description "Long buildout with 0 dB transmit attenuation";
               }
               enum "long-7.5db" {
                 description "Long buildout with 7.5 dB transmit attenuation";
               }
               enum "long-15db" {
                 description "Long buildout with 15 dB transmit attenuation";
               }
               enum "long-22.5db" {
                 description "Long buildout with 22.5 dB transmit attenuation";
               }
             }
           }
           leaf byte-encoding {
             description "Byte encoding";
             type enumeration {
               enum "nx64" {
                 description "8 bits per byte";
               }
               enum "nx56" {
                 description "7 bits per byte";
               }
             }
           }
           leaf line-encoding {
             description "Line encoding";
             type enumeration {
               enum "ami" {
                 description "Automatic mark inversion";
               }
               enum "b8zs" {
                 description "8-bit zero suppression";
               }
             }
           }
           leaf invert-data {
             description "Invert data";
             type empty;
           }
           leaf framing {
             description "Framing mode";
             type enumeration {
               enum "sf" {
                 description "Super frame";
               }
               enum "esf" {
                 description "Extended super frame";
               }
             }
           }
           leaf fcs {
             description "Frame checksum";
             type enumeration {
               enum "32" {
                 description "32-bit mode";
               }
               enum "16" {
                 description "16-bit mode";
               }
             }
           }
           leaf idle-cycle-flag {
             description "Value to transmit in idle cycles";
             type enumeration {
               enum "flags" {
                 description "Transmit 0x7E in idle cycles";
               }
               enum "ones" {
                 description "Transmit 0xFF (all ones) in idle cycles";
               }
             }
           }
           leaf start-end-flag {
             description "Set start/end flags on transmission";
             type enumeration {
               enum "shared" {
                 description "Share start/end flags on transmit";
               }
               enum "filler" {
                 description "Send two idle cycles between start/end flags";
               }
             }
           }
           leaf bert-algorithm {
             description "Set BERT algorithm";
             type enumeration {
               enum "pseudo-2e3" {
                 description "Pattern is 2^3 - 1";
               }
               enum "pseudo-2e4" {
                 description "Pattern is 2^4 - 1";
               }
               enum "pseudo-2e5" {
                 description "Pattern is 2^5 - 1";
               }
               enum "pseudo-2e6" {
                 description "Pattern is 2^6 - 1";
               }
               enum "pseudo-2e7" {
                 description "Pattern is 2^7 - 1";
               }
               enum "pseudo-2e9-o153" {
                 description "Pattern is 2^9 - 1 (per O.153 standard)";
               }
               enum "pseudo-2e10" {
                 description "Pattern is 2^10 - 1";
               }
               enum "pseudo-2e11-o152" {
                 description "Pattern is 2^11 -1 (per O.152 standard)";
               }
               enum "pseudo-2e15-o151" {
                 description "Pattern is 2^15 - 1 (per O.151 standard)";
               }
               enum "pseudo-2e17" {
                 description "Pattern is 2^17 - 1";
               }
               enum "pseudo-2e18" {
                 description "Pattern is 2^18 - 1";
               }
               enum "pseudo-2e20-o153" {
                 description "Pattern is 2^20 - 1 (per O.153 standard)";
               }
               enum "pseudo-2e20-o151" {
                 description "Pattern is 2^20 - 1 (per O.151 standard)";
               }
               enum "pseudo-2e21" {
                 description "Pattern is 2^21 - 1";
               }
               enum "pseudo-2e22" {
                 description "Pattern is 2^22 - 1";
               }
               enum "pseudo-2e23-o151" {
                 description "Pattern is 2^23 (per O.151 standard)";
               }
               enum "pseudo-2e25" {
                 description "Pattern is 2^25 - 1";
               }
               enum "pseudo-2e28" {
                 description "Pattern is 2^28 - 1";
               }
               enum "pseudo-2e29" {
                 description "Pattern is 2^29 - 1";
               }
               enum "pseudo-2e31" {
                 description "Pattern is 2^31 - 1";
               }
               enum "pseudo-2e32" {
                 description "Pattern is 2^32 - 1";
               }
               enum "all-ones-repeating" {
                 description "Repeating one bits";
               }
               enum "all-zeros-repeating" {
                 description "Repeating zero bits";
               }
               enum "alternating-ones-zeros" {
                 description "Alternating ones and zeros";
               }
               enum "alternating-double-ones-zeros" {
                 description "Alternating pairs of ones and zeros";
               }
               enum "repeating-3-in-24" {
                 description "3 bits in 24 are set";
               }
               enum "repeating-1-in-8" {
                 description "1 bit in 8 is set";
               }
               enum "repeating-1-in-4" {
                 description "1 bit in 4 is set";
               }
             }
           }
           leaf bert-error-rate {
             description "Bit error rate (10^-n for n > 0, and zero for n = 0)";
             type union {
               type string {
                 pattern "<.*>|$.*";
               }
               type uint32 {
                 range "0 .. 7";
               }
             }
           }
           leaf bert-period {
             description "Length of BERT test";
             units "seconds";
             type union {
               type string {
                 pattern "<.*>|$.*";
               }
               type uint32 {
                 range "1 .. 86400";
               }
             }
           }
           leaf remote-loopback-respond {
             description "Respond to loop requests from remote end";
             type empty;
           }
           leaf crc-major-alarm-threshold {
             description "CRC Major alarm threshold value";
             default "5e-5";
             type enumeration {
               enum "1e-3" {
                 description "1 crc error in 10^3 bits";
               }
               enum "5e-4" {
                 description "5 crc errors in 10^4 bits";
               }
               enum "1e-4" {
                 description "1 crc error in 10^4 bits";
               }
               enum "5e-5" {
                 description "5 crc errors in 10^5 bits";
               }
               enum "1e-5" {
                 description "1 crc error in 10^5 bits";
               }
             }
           }
           leaf crc-minor-alarm-threshold {
             description "CRC Minor alarm threshold value";
             default "5e-6";
             type enumeration {
               enum "1e-3" {
                 description "1 crc error in 10^3 bits";
               }
               enum "5e-4" {
                 description "5 crc errors in 10^4 bits";
               }
               enum "1e-4" {
                 description "1 crc error in 10^4 bits";
               }
               enum "5e-5" {
                 description "5 crc errors in 10^5 bits";
               }
               enum "1e-5" {
                 description "1 crc error in 10^5 bits";
               }
               enum "5e-6" {
                 description "5 crc errors in 10^6 bits";
               }
               enum "1e-6" {
                 description "1 crc error in 10^6 bits";
               }
             }
           }
           leaf alarm-compliance {
             description "Enforce standard for alarm reporting";
             type enumeration {
               enum "accunet-t1-5-service" {
                 description "T1.5 interface specification";
               }
             }
           }
         }
         container ds0-options {
           junos:must "((!(\"interfaces ${interface} container-options\") || (\"interfaces ${interface} container-options container-type\" || \"interfaces ${interface} container-options allow-configuration-override\")))";
           junos:must-message "ds0-options cannot be configured without allow-configuration-override";
           description "DS-0 interface-specific options";
           uses apply-advanced;
           leaf loopback {
             description "Loopback mode";
             type enumeration {
               enum "payload" {
                 description "Payload loopback";
               }
             }
           }
           leaf byte-encoding {
             description "Byte encoding";
             type enumeration {
               enum "nx64" {
                 description "8 bits per byte";
               }
               enum "nx56" {
                 description "7 bits per byte";
               }
             }
           }
           leaf invert-data {
             description "Invert data";
             type empty;
           }
           leaf fcs {
             description "Frame checksum";
             type enumeration {
               enum "32" {
                 description "32-bit mode";
               }
               enum "16" {
                 description "16-bit mode";
               }
             }
           }
           leaf idle-cycle-flag {
             description "Value to transmit in idle cycles";
             type enumeration {
               enum "flags" {
                 description "Transmit 0x7E in idle cycles";
               }
               enum "ones" {
                 description "Transmit 0xFF (all ones) in idle cycles";
               }
             }
           }
           leaf start-end-flag {
             description "Set start/end flags on transmission";
             type enumeration {
               enum "shared" {
                 description "Share start/end flags on transmit";
               }
               enum "filler" {
                 description "Send two idle cycles between start/end flags";
               }
             }
           }
           leaf bert-algorithm {
             description "Set BERT algorithm";
             type enumeration {
               enum "pseudo-2e11-o152" {
                 description "Pattern is 2^11 -1 (per O.152 standard)";
               }
               enum "pseudo-2e15-o151" {
                 description "Pattern is 2^15 - 1 (per O.151 standard)";
               }
               enum "pseudo-2e20-o153" {
                 description "Pattern is 2^20 - 1 (per O.153 standard)";
               }
               enum "pseudo-2e20-o151" {
                 description "Pattern is 2^20 - 1 (per O.151 standard)";
               }
               enum "all-ones-repeating" {
                 description "Repeating one bits";
               }
               enum "all-zeros-repeating" {
                 description "Repeating zero bits";
               }
               enum "alternating-ones-zeros" {
                 description "Alternating ones and zeros";
               }
               enum "alternating-double-ones-zeros" {
                 description "Alternating pairs of ones and zeros";
               }
               enum "repeating-3-in-24" {
                 description "3 bits in 24 are set";
               }
               enum "repeating-1-in-8" {
                 description "1 bit in 8 is set";
               }
               enum "repeating-1-in-4" {
                 description "1 bit in 4 is set";
               }
               enum "repeating-1-in-16" {
                 description "1 bit in 16 is set";
               }
             }
           }
           leaf bert-error-rate {
             description "Bit error rate (10^-n for n > 0, and zero for n = 0)";
             type union {
               type string {
                 pattern "<.*>|$.*";
               }
               type uint32 {
                 range "0 .. 7";
               }
             }
           }
           leaf bert-period {
             description "Length of BERT test";
             units "seconds";
             type union {
               type string {
                 pattern "<.*>|$.*";
               }
               type uint32 {
                 range "1 .. 240";
               }
             }
           }
         }
         container serial-options {
           description "Serial interface-specific options";
           uses apply-advanced;
           leaf line-protocol {
             description "Line protocol to be used";
             default "eia530";
             type enumeration {
               enum "eia530" {
                 description "Line protocol EIA530";
               }
               enum "v.35" {
                 description "Line protocol V.35";
               }
               enum "x.21" {
                 description "Line protocol X.21";
               }
             }
           }
           choice control_leads_choice {
             case case_1 {
               container dte-options {
                 description "DTE options/control leads";
                 uses apply-advanced;
                 leaf ignore-all {
                   description "Ignore all control leads";
                   junos:must "(!(\".. indication\"))";
                   junos:must-message "SERIAL: ignore-all configured when indication explicitly configured";
                   junos:must "(!(\".. cts\"))";
                   junos:must-message "SERIAL: ignore-all configured when cts explicitly configured";
                   junos:must "(!(\".. dsr\"))";
                   junos:must-message "SERIAL: ignore-all configured when dsr explicitly configured";
                   junos:must "(!(\".. tm\"))";
                   junos:must-message "SERIAL: ignore-all configured when tm explicitly configured";
                   junos:must "(!(\".. dcd\"))";
                   junos:must-message "SERIAL: ignore-all configured when dcd explicitly configured";
                   type empty;
                 }
                 container dtr {
                   junos:cli-feature "oneliner";
                   description "Data Transmit Ready signal handling";
                   choice dtr_choices {
                     case case_1 {
                       leaf assert {
                         description "Assert DTR signal";
                         type empty;
                       }
                     }
                     case case_2 {
                       leaf de-assert {
                         description "Deassert DTR signal";
                         type empty;
                       }
                     }
                     case case_3 {
                       leaf normal {
                         description "Normal DTR signal";
                         type empty;
                       }
                     }
                     case case_4 {
                       container auto-synchronize {
                         presence "enable auto-synchronize";
                         description "Normal DTR signal, with autoresynchronization";
                         uses apply-advanced;
                         leaf duration {
                           description "Duration of autoresynchronization";
                           units "milliseconds";
                           type union {
                             type string {
                               pattern "<.*>|$.*";
                             }
                             type uint16 {
                               range "1 .. 1000";
                             }
                           }
                         }
                         leaf interval {
                           description "Interval for autoresynchronization";
                           units "seconds";
                           type union {
                             type string {
                               pattern "<.*>|$.*";
                             }
                             type uint16 {
                               range "1 .. 31";
                             }
                           }
                         }
                       }
                     }
                   }
                 }
                 leaf control-signal {
                   description "X.21 control signal handling";
                   junos:must "(!(\".. .. line-protocol eia530\"))";
                   junos:must-message "Control signal  invalid on line-protocol eia530";
                   junos:must "(!(\".. .. line-protocol v.35\"))";
                   junos:must-message "Control signal invalid on line-protocol v.35";
                   type enumeration {
                     enum "assert" {
                       description "Assert control signal";
                     }
                     enum "de-assert" {
                       description "Deassert control signal";
                     }
                     enum "normal" {
                       description "Normal control signal";
                     }
                   }
                 }
                 leaf rts {
                   description "Request To Send signal handling";
                   junos:must "(!(\".. .. line-protocol x.21\"))";
                   junos:must-message "rts invalid on line-protocol x.21";
                   type enumeration {
                     enum "assert" {
                       description "Assert RTS signal";
                     }
                     enum "de-assert" {
                       description "Deassert RTS signal";
                     }
                     enum "normal" {
                       description "Normal RTS signal";
                     }
                   }
                 }
                 leaf dcd {
                   description "Data Carrier Detect signal handling";
                   type enumeration {
                     enum "require" {
                       description "Require DCD signal";
                     }
                     enum "ignore" {
                       description "Ignore DCD signal";
                     }
                     enum "normal" {
                       description "Normal DCD signal";
                     }
                   }
                 }
                 leaf dsr {
                   description "Data Set Ready signal handling";
                   type enumeration {
                     enum "require" {
                       description "Require DSR signal";
                     }
                     enum "ignore" {
                       description "Ignore DSR signal";
                     }
                     enum "normal" {
                       description "Normal DSR signal";
                     }
                   }
                 }
                 leaf cts {
                   description "Clear To Send signal handling";
                   junos:must "(!(\".. .. line-protocol x.21\"))";
                   junos:must-message "cts invalid on line-protocol x.21";
                   type enumeration {
                     enum "require" {
                       description "Require CTS signal";
                     }
                     enum "ignore" {
                       description "Ignore CTS signal";
                     }
                     enum "normal" {
                       description "Normal CTS signal";
                     }
                   }
                 }
                 leaf indication {
                   description "X.21 Indication signal handling";
                   junos:must "(!(\".. .. line-protocol eia530\"))";
                   junos:must-message "Indication   invalid on line-protocol eia530";
                   junos:must "(!(\".. .. line-protocol v.35\"))";
                   junos:must-message "Indication invalid on line-protocol v.35";
                   type enumeration {
                     enum "require" {
                       description "Require Indication signal";
                     }
                     enum "ignore" {
                       description "Ignore Indication signal";
                     }
                     enum "normal" {
                       description "Normal Indication signal";
                     }
                   }
                 }
                 leaf tm {
                   description "Test Mode signal handling";
                   type enumeration {
                     enum "require" {
                       description "Require TM signal";
                     }
                     enum "ignore" {
                       description "Ignore TM signal";
                     }
                     enum "normal" {
                       description "Normal TM signal";
                     }
                   }
                 }
               }
             }
             case case_2 {
               container dce-options {
                 junos:must "(!(\".. clocking-mode dce\"))";
                 junos:must-message "SERIAL DCE clocking cannot be set when dce-options is configured";
                 junos:must "(!(\".. loopback dce-local\"))";
                 junos:must-message "dce-local cannot be set when dce-options is configured";
                 description "DCE options";
                 uses apply-advanced;
                 leaf ignore-all {
                   description "Ignore all control leads";
                   junos:must "(!(\".. cts\"))";
                   junos:must-message "SERIAL: ignore-all configured when cts explicitly configured";
                   junos:must "(!(\".. dsr\"))";
                   junos:must-message "SERIAL: ignore-all configured when dsr explicitly configured";
                   junos:must "(!(\".. dcd\"))";
                   junos:must-message "SERIAL: ignore-all configured when dcd explicitly configured";
                   junos:must "(!(\".. tm\"))";
                   junos:must-message "SERIAL: ignore-all configured when tm explicitly configured";
                   junos:must "(!(\".. dtr\"))";
                   junos:must-message "SERIAL: ignore-all configured when dtr explicitly configured";
                   junos:must "(!(\".. rts\"))";
                   junos:must-message "SERIAL: ignore-all configured when rts explicitly configured";
                   type empty;
                 }
                 leaf dtr {
                   description "Data Transmit Ready signal handling";
                   type enumeration {
                     enum "require" {
                       description "Require Data Carrier Detect (DCD) signal";
                     }
                     enum "ignore" {
                       description "Ignore Data Carrier Detect (DCD) signal";
                     }
                     enum "normal" {
                       description "Normal Data Carrier Detect (DCD) signal";
                     }
                   }
                 }
                 leaf rts {
                   description "Request To Send signal handling";
                   type enumeration {
                     enum "require" {
                       description "Require Data Carrier Detect (DCD) signal";
                     }
                     enum "ignore" {
                       description "Ignore Data Carrier Detect (DCD) signal";
                     }
                     enum "normal" {
                       description "Normal Data Carrier Detect (DCD) signal";
                     }
                   }
                 }
                 leaf dcd {
                   description "Data Carrier Detect signal handling";
                   type enumeration {
                     enum "assert" {
                       description "Assert Request To Send (RTS) signal";
                     }
                     enum "de-assert" {
                       description "Deassert Request To Send (RTS) signal";
                     }
                     enum "normal" {
                       description "Normal Request To Send (RTS) signal";
                     }
                   }
                 }
                 leaf dsr {
                   description "Data Set Ready signal handling";
                   type enumeration {
                     enum "assert" {
                       description "Assert Request To Send (RTS) signal";
                     }
                     enum "de-assert" {
                       description "Deassert Request To Send (RTS) signal";
                     }
                     enum "normal" {
                       description "Normal Request To Send (RTS) signal";
                     }
                   }
                 }
                 leaf cts {
                   description "Clear To Send signal handling";
                   type enumeration {
                     enum "assert" {
                       description "Assert Request To Send (RTS) signal";
                     }
                     enum "de-assert" {
                       description "Deassert Request To Send (RTS) signal";
                     }
                     enum "normal" {
                       description "Normal Request To Send (RTS) signal";
                     }
                   }
                 }
                 leaf tm {
                   description "Test Mode signal handling";
                   type enumeration {
                     enum "require" {
                       description "Require TM signal";
                     }
                     enum "ignore" {
                       description "Ignore TM signal";
                     }
                     enum "normal" {
                       description "Normal TM signal";
                     }
                   }
                 }
                 leaf dce-loopback-override {
                   description "DCE loopback override";
                   type empty;
                 }
               }
             }
           }
           leaf dtr-circuit {
             description "Data Transmit Ready circuit mode";
             junos:must "(!(\".. line-protocol x.21\"))";
             junos:must-message "dtr-circuit invalid with line protocol x.21";
             type enumeration {
               enum "balanced" {
                 description "Balanced signal";
               }
               enum "unbalanced" {
                 description "Unbalanced signal";
               }
             }
           }
           leaf dtr-polarity {
             description "Data Transmit Ready signal polarity";
             junos:must "(!(\".. line-protocol x.21\"))";
             junos:must-message "dtr-polarity invalid with line protocol x.21";
             type enumeration {
               enum "positive" {
                 description "Positive polarity";
               }
               enum "negative" {
                 description "Negative polarity";
               }
             }
           }
           leaf rts-polarity {
             description "Request To Send signal polarity";
             junos:must "(!(\".. line-protocol x.21\"))";
             junos:must-message "rts invalid on line-protocol x.21";
             type enumeration {
               enum "positive" {
                 description "Positive polarity";
               }
               enum "negative" {
                 description "Negative polarity";
               }
             }
           }
           leaf control-polarity {
             description "X.21 Control signal polarity";
             junos:must "(!(\".. line-protocol eia530\"))";
             junos:must-message "Control signal  invalid on line-protocol eia530";
             junos:must "(!(\".. line-protocol v.35\"))";
             junos:must-message "Control signal invalid on line-protocol v.35";
             type enumeration {
               enum "positive" {
                 description "Positive polarity";
               }
               enum "negative" {
                 description "Negative polarity";
               }
             }
           }
           leaf dcd-polarity {
             description "Data Carrier Detect signal polarity";
             junos:must "(!(\".. line-protocol x.21\"))";
             junos:must-message "dcd-polarity invalid with line protocol x.21";
             type enumeration {
               enum "positive" {
                 description "Positive polarity";
               }
               enum "negative" {
                 description "Negative polarity";
               }
             }
           }
           leaf dsr-polarity {
             description "Data Set Ready signal polarity";
             junos:must "(!(\".. line-protocol x.21\"))";
             junos:must-message "dsr-polarity invalid with line protocol x.21";
             type enumeration {
               enum "positive" {
                 description "Positive polarity";
               }
               enum "negative" {
                 description "Negative polarity";
               }
             }
           }
           leaf cts-polarity {
             description "Clear To Send signal polarity";
             junos:must "(!(\".. line-protocol x.21\"))";
             junos:must-message "cts invalid on line-protocol x.21";
             type enumeration {
               enum "positive" {
                 description "Positive polarity";
               }
               enum "negative" {
                 description "Negative polarity";
               }
             }
           }
           leaf indication-polarity {
             description "X.21 Indication signal polarity";
             junos:must "(!(\".. line-protocol eia530\"))";
             junos:must-message "Indication  invalid on line-protocol eia530";
             junos:must "(!(\".. line-protocol v.35\"))";
             junos:must-message "Indication invalid on line-protocol v.35";
             type enumeration {
               enum "positive" {
                 description "Positive polarity";
               }
               enum "negative" {
                 description "Negative polarity";
               }
             }
           }
           leaf tm-polarity {
             description "Test Mode signal polarity";
             junos:must "(!(\".. line-protocol x.21\"))";
             junos:must-message "tm-polarity invalid for line protocol x.21";
             junos:must "(!(\".. line-protocol v.35\"))";
             junos:must-message "tm-polarity invalid for line protocol v.35";
             type enumeration {
               enum "positive" {
                 description "Positive polarity";
               }
               enum "negative" {
                 description "Negative polarity";
               }
             }
           }
           leaf clocking-mode {
             description "Clock mode";
             type enumeration {
               enum "dce" {
                 description "DCE timing (DTE mode only, not valid for X.21)";
               }
               enum "internal" {
                 description "Internal baud timing";
               }
               enum "loop" {
                 description "Loop timing";
               }
             }
           }
           leaf transmit-clock {
             description "Transmit clock phase";
             type enumeration {
               enum "invert" {
                 description "Shift clock phase 180 degrees";
               }
             }
           }
           leaf clock-rate {
             description "Interface clock rate";
             type enumeration {
               enum "2.048mhz" {
                 description "2.048 MHz";
               }
               enum "2.341mhz" {
                 description "2.341 MHz";
               }
               enum "2.731mhz" {
                 description "2.731 MHz";
               }
               enum "3.277mhz" {
                 description "3.277 MHz";
               }
               enum "4.096mhz" {
                 description "4.096 MHz";
               }
               enum "5.461mhz" {
                 description "5.461 MHz";
               }
               enum "8.192mhz" {
                 description "8.192 MHz";
               }
               enum "16.384mhz" {
                 description "16.384 MHz";
               }
               enum "1.2khz" {
                 description "1.2 KHz";
               }
               enum "2.4khz" {
                 description "2.4 KHz";
               }
               enum "9.6khz" {
                 description "9.6 KHz";
               }
               enum "19.2khz" {
                 description "19.2 KHz";
               }
               enum "38.4khz" {
                 description "38.4 KHz";
               }
               enum "56.0khz" {
                 description "56.0 KHz";
               }
               enum "64.0khz" {
                 description "64.0 KHz";
               }
               enum "72.0khz" {
                 description "72.0 KHz";
               }
               enum "125.0khz" {
                 description "125.0 KHz";
               }
               enum "148.0khz" {
                 description "148.0 KHz";
               }
               enum "250.0khz" {
                 description "250.0 KHz";
               }
               enum "500.0khz" {
                 description "500.0 KHz";
               }
               enum "800.0khz" {
                 description "800.0 KHz";
               }
               enum "1.0mhz" {
                 description "1.0 MHz";
               }
               enum "1.3mhz" {
                 description "1.3 MHz";
               }
               enum "2.0mhz" {
                 description "2.0 MHz";
               }
               enum "4.0mhz" {
                 description "4.0 MHz";
               }
               enum "8.0mhz" {
                 description "8.0 MHz";
               }
             }
           }
           leaf loopback {
             description "Loopback mode";
             type enumeration {
               enum "local" {
                 description "Local loopback";
               }
               enum "remote" {
                 description "Remote/LIU loopback";
               }
               enum "dce-local" {
                 description "DCE local loopback (DTE mode only)";
               }
               enum "dce-remote" {
                 description "DCE remote loopback";
               }
             }
           }
           leaf encoding {
             description "Line encoding";
             type enumeration {
               enum "nrz" {
                 description "Non-Return-To-Zero";
               }
               enum "nrzi" {
                 description "Non-Return-To-Zero-Invertible";
               }
             }
           }
           leaf idle-cycle-flag {
             description "Value to transmit in idle cycles";
             type enumeration {
               enum "flags" {
                 description "Transmit 0x7E in idle cycles";
               }
               enum "ones" {
                 description "Transmit 0xFF (all ones) in idle cycles";
               }
             }
           }
         }
         choice gratuitous-arp-reply-choice {
           leaf gratuitous-arp-reply {
             description "Enable gratuitous ARP reply";
             type empty;
           }
           leaf no-gratuitous-arp-reply {
             description "Don't enable gratuitous ARP reply";
             type empty;
           }
         }
         choice no-gratuitous-arp-request-choice {
           leaf no-gratuitous-arp-request {
             description "Ignore gratuitous ARP request";
             type empty;
           }
           leaf no-no-gratuitous-arp-request {
             description "Don't ignore gratuitous ARP request";
             type empty;
           }
         }
         container ether-options {
           description "Ethernet interface-specific options";
           uses apply-advanced;
           choice loopback-choice {
             leaf loopback {
               description "Enable loopback";
               type empty;
             }
             leaf no-loopback {
               description "Don't enable loopback";
               type empty;
             }
           }
           leaf loopback-remote {
             description "Enable remote loopback";
             junos:must "(!(\".. .. optics-options loopback\"))";
             junos:must-message "'optics-options loopback' and loopback-remote are mutually exclusive";
             junos:must "(!(\".. loopback\"))";
             junos:must-message "loopback and loopback-remote are mutually exclusive";
             type empty;
           }
           choice source-filtering-choice {
             leaf source-filtering {
               description "Enable source address filtering";
               type empty;
             }
             leaf no-source-filtering {
               description "Don't enable source address filtering";
               type empty;
             }
           }
           container ethernet-switch-profile {
             description "Ethernet virtual LAN/media access control-level options";
             uses apply-advanced;
             leaf-list tag-protocol-id {
               ordered-by user;
               description "IEEE 802.1q Tag Protocol Identifier values for VLAN-tagged frames";
               type string;
               max-elements 1;
             }
             container ethernet-policer-profile {
               description "Ethernet level CoS-based policer configuration";
               uses apply-advanced;
               container input-priority-map {
                 description "Input policer priority map";
                 uses cos_policer_input_priority_map;
               }
               container output-priority-map {
                 description "Output policer priority map";
                 uses cos_policer_output_priority_map;
               }
               list policer {
                 key name;
                 ordered-by user;
                 description "Policer template definition";
                 uses cos_policer;
               }
             }
             container storm-control {
               junos:cli-feature "oneliner-plus";
               description "Storm control profile name to bind";
               uses apply-advanced;
               leaf profile-name {
                 description "Profile name";
                 junos:cli-feature "nokeyword";
                 junos:must "(\"forwarding-options storm-control-profiles $$\")";
                 junos:must-message "Storm profile name must be defined in the [edit forwarding-options storm-control-profiles] hierarchy";
                 type string;
               }
             }
             container recovery-timeout {
               junos:cli-feature "oneliner";
               description "Recovery timeout for this interface";
               leaf time-in-seconds {
                 junos:cli-feature "nokeyword";
                 units "seconds";
                 type union {
                   type string {
                     pattern "<.*>|$.*";
                   }
                   type uint32 {
                     range "10 .. 3600";
                   }
                 }
               }
             }
             choice mac-learn-enable-choice {
               leaf mac-learn-enable {
                 description "Learn MAC addresses dynamically";
                 type empty;
               }
               leaf no-mac-learn-enable {
                 description "Don't learn MAC addresses dynamically";
                 type empty;
               }
             }
           }
           leaf asynchronous-notification {
             description "Enable sending asynchronous notification to peer on CCC-down";
             type empty;
           }
           list source-address-filter {
             key name;
             junos:cli-feature "homogeneous";
             junos:cli-feature "oneliner";
             description "Source address filters";
             leaf name {
               description "Remote MAC address";
               junos:cli-feature "nokeyword";
               type jt:mac-addr;
             }
           }
           choice auto-negotiation-choice {
             leaf auto-negotiation {
               description "Enable auto-negotiation";
               type empty;
             }
             leaf no-auto-negotiation {
               description "Don't enable auto-negotiation";
               type empty;
             }
           }
           choice flow-control-choice {
             leaf flow-control {
               description "Enable flow control";
               type empty;
             }
             leaf no-flow-control {
               description "Don't enable flow control";
               type empty;
             }
           }
           leaf link-mode {
             description "Link duplex";
             type enumeration {
               enum "automatic" {
                 description "Automatic negotiate duplex ";
               }
               enum "half-duplex" {
                 description "Half-duplex operation";
               }
               enum "full-duplex" {
                 description "Full-duplex operation";
               }
             }
           }
           container mpls {
             description "MPLS options";
             uses mpls_ifd_options;
           }
           leaf ignore-l3-incompletes {
             description "Ignore L3 incomplete errors";
             type empty;
           }
           leaf no-auto-mdix {
             description "Disable auto MDI/MDIX";
             type empty;
           }
           leaf fec {
             description "Forward Error Correction mode";
             type enumeration {
               enum "none" {
                 description "FEC disabled";
               }
               enum "fec91" {
                 description "IEEE 802.3bj Clause 91, Reed-Solomon FEC (RS-FEC)";
               }
               enum "fec74" {
                 description "FEC74 enabled";
               }
               enum "fec108" {
                 description "IEEE 802.3by Clause 108, Reed-Solomon FEC (RS-FEC) on 25g links";
               }
               enum "fec161" {
                 description "IEEE 802.3ck Clause 161 for 100G electrical links";
               }
             }
           }
           container speed {
             description "Specify speed";
             choice automatic {
               case case_1 {
                 container auto-negotiation {
                   presence "enable auto-negotiation";
                   junos:cli-feature "oneliner";
                   description "Enable auto-negotiation";
                   leaf auto-negotiate-10-100 {
                     description "Limits the auto-negotiation to 10m/100m only";
                     type empty;
                   }
                 }
               }
               case case_2 {
                 leaf ethernet-10m {
                   description "10Mbps";
                   type empty;
                 }
               }
               case case_3 {
                 leaf ethernet-100m {
                   description "100Mbps";
                   type empty;
                 }
               }
               case case_4 {
                 leaf ethernet-1g {
                   description "1Gbps";
                   type empty;
                 }
               }
               case case_5 {
                 leaf ethernet-10g {
                   description "10Gbps";
                   type empty;
                 }
               }
             }
           }
           container ieee-802.3ad {
             junos:must "(!(\"system autoinstallation\"))";
             junos:must-message "incompatible with 'system autoinstallation'";
             junos:cli-feature "oneliner-plus";
             description "IEEE 802.3ad";
             uses apply-advanced;
             container lacp {
               description "Link Aggregation Control Protocol configuration";
               uses apply-advanced;
               leaf force-up {
                 description "Keep the port up in absence of received LACPDU";
                 type empty;
               }
               leaf port-priority {
                 description "Priority of the port (0 ... 65535)";
                 type union {
                   type uint16;
                   type string {
                     pattern "<.*>|$.*";
                   }
                 }
               }
             }
             leaf bundle {
               description "Join an aggregated Ethernet interface";
               junos:cli-feature "nokeyword";
               junos:must "(!(\"class-of-service interfaces ${interface} dynamic-threshold-profile\"))";
               junos:must-message "dynamic-threshold-profile config cannot be applied on ae child";
               junos:must "(!(any \"class-of-service interfaces ${interface} unit <*> rewrite-rules\"))";
               junos:must-message "rewrite config can not be applied on ae child";
               junos:must "(!(any \"class-of-service interfaces ${interface} unit <*> classifiers\"))";
               junos:must-message "classifier config can not be applied on ae child";
               junos:must "(!(any \"class-of-service interfaces ${interface} unit <*> output-traffic-control-profile\"))";
               junos:must-message "output-traffic-control-profile config can not be applied on ae child";
               junos:must "(!(\"class-of-service interfaces ${interface} output-traffic-control-profile\"))";
               junos:must-message "output-traffic-control-profile config can not be applied on ae child";
               junos:must "(!(\"class-of-service interfaces ${interface} shaping-rate\"))";
               junos:must-message "shaping-rate config can not be applied on ae child";
               junos:must "(!(\"class-of-service interfaces ${interface} scheduler-map\"))";
               junos:must-message "scheduler-map config can not be applied on ae child";
               junos:must "(!(\".. .. .. gigether-options 802.3ad\"))";
               junos:must-message "Member link cannot be a part of multiple aggregation group";
               junos:must "(!(\".. .. .. vlan-offload\"))";
               junos:must-message "ae child device vlan-offload is not allowed";
               junos:must "(!(\".. .. .. flow-control\"))";
               junos:must-message "Setting flow-control on ae child device is not allowed";
               junos:must "(!(\".. .. .. mtu\"))";
               junos:must-message "Setting mtu on ae child device is not allowed";
               junos:must "(!(\".. .. .. vlan-vci-tagging\"))";
               junos:must-message "ae child device vlan-vci-tagging is not allowed";
               junos:must "(!(\".. .. .. stacked-vlan-tagging\"))";
               junos:must-message "ae child device stacked-vlan-tagging is not allowed";
               junos:must "(!(\".. .. .. flexible-vlan-tagging\"))";
               junos:must-message "ae child device flexible-vlan-tagging is not allowed";
               junos:must "(!(\".. .. .. vlan-tagging\"))";
               junos:must-message "ae child device vlan-tagging is not allowed";
               junos:must "(!(\".. .. .. passive-monitor-mode\"))";
               junos:must-message "802.3ad not valid for passive-monitor-mode";
               type union {
                 type jt:interface-device;
                 type string {
                   pattern "<.*>|$.*";
                 }
               }
             }
             choice type {
               case case_1 {
                 leaf primary {
                   description "Primary interface for link-protection mode";
                   type empty;
                 }
               }
               case case_2 {
                 leaf backup {
                   description "Backup interface for link-protection mode";
                   type empty;
                 }
               }
             }
           }
           leaf ieee-802-3az-eee {
             description "IEEE 802.3az Energy Efficient Ethernet(EEE)";
             type empty;
           }
           leaf mdi-mode {
             description "Cable cross-over mode";
             type enumeration {
               enum "auto" {
                 description "Automatic mdi/mdi-x mode";
               }
               enum "force" {
                 description "Enable auto-MDIX always";
               }
               enum "mdi" {
                 description "MDI(straight through) mode";
               }
               enum "mdix" {
                 description "MDI Cross-over mode";
               }
             }
           }
           container redundant-parent {
             junos:must "(!(\".. .. unit\"))";
             junos:must-message "Logical unit is not allowed on redundant-ethernet member";
             junos:cli-feature "oneliner-plus";
             description " Parent of this interface";
             uses apply-advanced;
             leaf parent {
               description "Join a redundant ethernet interface";
               junos:cli-feature "nokeyword";
               junos:must "(!(any \"interfaces <*> fastether-options redundant-parent $$\"))";
               junos:must-message "All children must be of the same ethernet type";
               junos:must "(!(any \"interfaces <*> gigether-options redundant-parent $$\"))";
               junos:must-message "All children must be of the same ethernet type";
               type union {
                 type jt:interface-device;
                 type string {
                   pattern "<.*>|$.*";
                 }
               }
             }
           }
           leaf autostate-exclude {
             description "Interface will not contribute to IRB state";
             type empty;
           }
         }
         container fibrechannel-options {
           description "Fibre Channel interface-specific options";
           uses apply-advanced;
           choice loopback-choice {
             leaf loopback {
               description "Enable loopback";
               type empty;
             }
             leaf no-loopback {
               description "Don't enable loopback";
               type empty;
             }
           }
           leaf bb-sc-n {
             description "B2B state change number";
             type union {
               type string {
                 pattern "<.*>|$.*";
               }
               type uint16 {
                 range "0 .. 15";
               }
             }
           }
           leaf speed {
             description "Specify speed";
             type enumeration {
               enum "auto-negotiation" {
                 description "Enable auto-negotiation";
               }
               enum "1g" {
                 description "1Gbps";
               }
               enum "2g" {
                 description "2Gbps";
               }
               enum "4g" {
                 description "4Gbps";
               }
               enum "8g" {
                 description "8Gbps";
               }
             }
           }
         }
         container gigether-options {
           description "Gigabit Ethernet interface-specific options";
           uses apply-advanced;
           choice loopback-choice {
             leaf loopback {
               description "Enable loopback";
               type empty;
             }
             leaf no-loopback {
               description "Don't enable loopback";
               type empty;
             }
           }
           leaf loopback-remote {
             description "Enable remote loopback";
             junos:must "(!(\".. .. optics-options loopback\"))";
             junos:must-message "'optics-options loopback' and loopback-remote are mutually exclusive";
             junos:must "(!(\".. loopback\"))";
             junos:must-message "loopback and loopback-remote are mutually exclusive";
             type empty;
           }
           choice flow-control-choice {
             leaf flow-control {
               description "Enable flow control";
               type empty;
             }
             leaf no-flow-control {
               description "Don't enable flow control";
               type empty;
             }
           }
           choice source-filtering-choice {
             leaf source-filtering {
               description "Enable source address filtering";
               type empty;
             }
             leaf no-source-filtering {
               description "Don't enable source address filtering";
               type empty;
             }
           }
           choice auto_negotiation_option {
             case case_1 {
               leaf no-auto-negotiation {
                 description "Disable auto-negotiation";
                 type empty;
               }
             }
             case case_2 {
               container auto-negotiation {
                 presence "enable auto-negotiation";
                 junos:cli-feature "oneliner";
                 description "Enable auto-negotiation";
                 leaf remote-fault {
                   type enumeration {
                     enum "local-interface-offline" {
                       description "Disable local interface";
                     }
                     enum "local-interface-online" {
                       description "Enable local interface";
                     }
                   }
                 }
               }
             }
           }
           leaf mac-mode {
             description "Physical layer protocol of MAC's SERDES interface";
             type enumeration {
               enum "sgmii" {
                 description "Serial Gigabit Media Independent Interface (10/100/1000 Mbps)";
               }
               enum "mac-mode-1000base-x" {
                 description "1000Base-X (1000 Mbps)";
                 junos:must "(\".. auto-negotiation\")";
                 junos:must-message "Auto-negotiation must be enabled for 1000Base-X SERDES interface";
                 junos:must "(\".. .. link-mode full-duplex\")";
                 junos:must-message "Link operational mode must be full-duplex to enable 1000Base-X SERDES interface";
                 junos:must "(\".. .. speed 1g\")";
                 junos:must-message "Link speed must be 1g to enable 1000Base-X SERDES interface";
               }
             }
           }
           leaf asynchronous-notification {
             description "Enable sending asynchronous notification to peer on CCC-down";
             type empty;
           }
           list source-address-filter {
             key name;
             junos:cli-feature "homogeneous";
             junos:cli-feature "oneliner";
             description "Source address filters";
             leaf name {
               description "Remote MAC address";
               junos:cli-feature "nokeyword";
               type jt:mac-addr;
             }
           }
           container redundant-parent {
             junos:must "(!(\".. .. passive-monitor-mode\"))";
             junos:must-message "Redundant-ethernet member cannot be in passive-monitor-mode";
             junos:must "(!((\".. .. flexible-vlan-tagging\" || (\".. .. stacked-vlan-tagging\" || (\".. .. vlan-vci-tagging\" || \".. .. vlan-tagging\")))))";
             junos:must-message "Tagging is not allowed on redundant-ethernet member";
             junos:must "(!(\".. 802.3ad\"))";
             junos:must-message "Redundant-ethernet member cannot be part of 802.3ad";
             junos:must "(!(\".. .. unit\"))";
             junos:must-message "Logical unit is not allowed on redundant-ethernet member";
             junos:cli-feature "oneliner-plus";
             description "Parent of this interface";
             uses apply-advanced;
             leaf parent {
               description "Join a redundant-ethernet interface";
               junos:cli-feature "nokeyword";
               junos:must "(!(any \"interfaces <*> ether-options redundant-parent $$\"))";
               junos:must-message "All the children must be of same ethernet type";
               junos:must "(!(any \"interfaces <*> fastether-options redundant-parent $$\"))";
               junos:must-message "All the children must be of same ethernet type";
               type union {
                 type jt:interface-device;
                 type string {
                   pattern "<.*>|$.*";
                 }
               }
             }
           }
           container ieee-802.3ad {
             junos:must "(!(\"system autoinstallation\"))";
             junos:must-message "incompatible with 'system autoinstallation'";
             junos:cli-feature "oneliner-plus";
             description "IEEE 802.3ad";
             uses apply-advanced;
             container lacp {
               description "Link Aggregation Control Protocol configuration";
               uses apply-advanced;
               leaf port-priority {
                 description "Priority of the port (0 ... 65535)";
                 type union {
                   type uint16;
                   type string {
                     pattern "<.*>|$.*";
                   }
                 }
               }
             }
             leaf bundle {
               description "Join an aggregated Ethernet interface";
               junos:cli-feature "nokeyword";
               junos:must "(!(any \"class-of-service interfaces ${interface} unit <*> rewrite-rules\"))";
               junos:must-message "rewrite config can not be applied on ae child";
               junos:must "(!(any \"class-of-service interfaces ${interface} unit <*> classifiers\"))";
               junos:must-message "classifier config can not be applied on ae child";
               junos:must "(!(any \"class-of-service interfaces ${interface} unit <*> output-traffic-control-profile\"))";
               junos:must-message "output-traffic-control-profile config can not be applied on ae child";
               junos:must "(!(\"class-of-service interfaces ${interface} output-traffic-control-profile\"))";
               junos:must-message "output-traffic-control-profile config can not be applied on ae child";
               junos:must "(!(\"class-of-service interfaces ${interface} shaping-rate\"))";
               junos:must-message "shaping-rate config can not be applied on ae child";
               junos:must "(!(\"class-of-service interfaces ${interface} scheduler-map\"))";
               junos:must-message "scheduler-map config can not be applied on ae child";
               junos:must "(!(\".. .. .. ether-options 802.3ad\"))";
               junos:must-message "Member link cannot be a part of multiple aggregation group";
               junos:must "(!(\".. .. .. vlan-offload\"))";
               junos:must-message "ae child device vlan-offload is not allowed";
               junos:must "(!(\".. .. .. flow-control\"))";
               junos:must-message "Setting flow-control on ae child device is not allowed";
               junos:must "(!(\".. .. .. mtu\"))";
               junos:must-message "Setting mtu on ae child device is not allowed";
               junos:must "(!(\".. .. .. vlan-vci-tagging\"))";
               junos:must-message "ae child device vlan-vci-tagging is not allowed";
               junos:must "(!(\".. .. .. stacked-vlan-tagging\"))";
               junos:must-message "ae child device stacked-vlan-tagging is not allowed";
               junos:must "(!(\".. .. .. flexible-vlan-tagging\"))";
               junos:must-message "ae child device flexible-vlan-tagging is not allowed";
               junos:must "(!(\".. .. .. vlan-tagging\"))";
               junos:must-message "ae child device vlan-tagging is not allowed";
               junos:must "(!(\".. .. .. passive-monitor-mode\"))";
               junos:must-message "802.3ad not valid for passive-monitor-mode";
               type union {
                 type jt:interface-device;
                 type string {
                   pattern "<.*>|$.*";
                 }
               }
             }
             choice type {
               case case_1 {
                 leaf primary {
                   description "Primary interface for link-protection mode";
                   type empty;
                 }
               }
               case case_2 {
                 leaf backup {
                   description "Backup interface for link-protection mode";
                   type empty;
                 }
               }
             }
           }
           container ethernet-switch-profile {
             description "Ethernet virtual LAN/media access control-level options";
             uses apply-advanced;
             leaf-list tag-protocol-id {
               ordered-by user;
               description "IEEE 802.1q Tag Protocol Identifier values for VLAN-tagged frames";
               type string;
             }
             container ethernet-policer-profile {
               description "Ethernet level CoS-based policer configuration";
               uses apply-advanced;
               container ieee802.1-priority-map {
                 presence "enable ieee802.1-priority-map";
                 description "Premium priority values for IEEE 802.1p bits";
                 status deprecated;
                 uses apply-advanced;
                 leaf-list premium {
                   ordered-by user;
                   description "Premium policer priority map";
                   type union {
                     type string {
                       pattern "<.*>|$.*";
                     }
                     type uint32 {
                       range "0 .. 7";
                     }
                   }
                 }
               }
               container input-priority-map {
                 description "Input policer priority map";
                 uses cos_policer_input_priority_map;
               }
               container output-priority-map {
                 description "Output policer priority map";
                 uses cos_policer_output_priority_map;
               }
               list policer {
                 key name;
                 ordered-by user;
                 description "Policer template definition";
                 uses cos_policer;
               }
             }
             container accept-from {
               description "Accept traffic from or to specified remote MAC";
               status deprecated;
               uses apply-advanced;
               list mac-address {
                 key name;
                 description "Remote MAC";
                 uses mac_list;
               }
             }
             choice reject-the-rest-choice {
               leaf reject-the-rest {
                 description "Accept traffic from only the specified MAC addresses";
                 status deprecated;
                 type empty;
               }
               leaf no-reject-the-rest {
                 description "Don't accept traffic from only the specified MAC addresses";
                 status deprecated;
                 type empty;
               }
             }
             leaf mac-learn-enable {
               description "Learn MAC addresses dynamically";
               type empty;
             }
           }
           container mpls {
             description "MPLS options";
             uses mpls_ifd_options;
           }
           leaf ignore-l3-incompletes {
             description "Ignore L3 incomplete errors";
             type empty;
           }
           leaf ieee-802-3az-eee {
             description "IEEE 802.3az Energy Efficient Ethernet(EEE)";
             type empty;
           }
           leaf mru {
             description "Maximum receive packet size";
             type union {
               type string {
                 pattern "<.*>|$.*";
               }
               type uint32;
             }
           }
           leaf fec {
             description "Forward Error Correction mode";
             type enumeration {
               enum "none" {
                 description "FEC disabled";
               }
               enum "fec91" {
                 description "IEEE 802.3bj Clause 91, Reed-Solomon FEC (RS-FEC)";
               }
               enum "fec74" {
                 description "FEC74 enabled";
               }
               enum "fec108" {
                 description "IEEE 802.3by Clause 108, Reed-Solomon FEC (RS-FEC) on 25g links";
               }
               enum "fec161" {
                 description "IEEE 802.3ck Clause 161 for 100G electrical links";
               }
             }
           }
           leaf speed {
             description "Speed mode";
             type enumeration {
               enum "1g" {
                 description "Speed 1g";
                 junos:must "((\".. auto-negotiation\" || \".. no-auto-negotiation\"))";
                 junos:must-message "Enabling gigether-options auto-negotiation is highly recommended to prevent traffic drops due to RF peer link up. But if needed, no-auto-negotiation can be enabled";
               }
               enum "10g" {
                 description "Speed 10g";
               }
             }
           }
         }
         container optics-options {
           description "Optics options";
           uses apply-advanced;
           leaf wavelength {
             description "Wavelength of the optics (nanometers) for 50Ghz/100Ghz spacing";
             type enumeration {
               enum "1568.77" {
                 description "1568.77 nm/191.1003 THz 50/100Ghz spacing";
               }
               enum "1568.36" {
                 description "1568.36 nm/191.150000 THz 3.125/6.25/12.5/50GHz spacing";
               }
               enum "1568.34" {
                 description "1568.34 nm/191.153125 THz 3.125GHz spacing";
               }
               enum "1568.31" {
                 description "1568.31 nm/191.156250 THz 3.125/6.25GHz spacing";
               }
               enum "1568.29" {
                 description "1568.29 nm/191.159375 THz 3.125GHz spacing";
               }
               enum "1568.26" {
                 description "1568.26 nm/191.162500 THz 3.125/6.25/12.5GHz spacing";
               }
               enum "1568.23" {
                 description "1568.23 nm/191.165625 THz 3.125GHz spacing";
               }
               enum "1568.21" {
                 description "1568.21 nm/191.168750 THz 3.125/6.25GHz spacing";
               }
               enum "1568.18" {
                 description "1568.18 nm/191.171875 THz 3.125GHz spacing";
               }
               enum "1568.16" {
                 description "1568.16 nm/191.175000 THz 3.125/6.25/12.5/75GHz spacing";
               }
               enum "1568.13" {
                 description "1568.13 nm/191.178125 THz 3.125GHz spacing";
               }
               enum "1568.11" {
                 description "1568.11 nm/191.181250 THz 3.125/6.25GHz spacing";
               }
               enum "1568.08" {
                 description "1568.08 nm/191.184375 THz 3.125GHz spacing";
               }
               enum "1568.05" {
                 description "1568.05 nm/191.187500 THz 3.125/6.25/12.5GHz spacing";
               }
               enum "1568.03" {
                 description "1568.03 nm/191.190625 THz 3.125GHz spacing";
               }
               enum "1568.00" {
                 description "1568.00 nm/191.193750 THz 3.125/6.25GHz spacing";
               }
               enum "1567.98" {
                 description "1567.98 nm/191.196875 THz 3.125GHz spacing";
               }
               enum "1567.95" {
                 description "1567.95 nm/191.200000 THz 3.125/6.25/12.5/100GHz spacing";
               }
               enum "1567.93" {
                 description "1567.93 nm/191.203125 THz 3.125GHz spacing";
               }
               enum "1567.90" {
                 description "1567.90 nm/191.206250 THz 3.125/6.25GHz spacing";
               }
               enum "1567.88" {
                 description "1567.88 nm/191.209375 THz 3.125GHz spacing";
               }
               enum "1567.85" {
                 description "1567.85 nm/191.212500 THz 3.125/6.25/12.5GHz spacing";
               }
               enum "1567.82" {
                 description "1567.82 nm/191.215625 THz 3.125GHz spacing";
               }
               enum "1567.80" {
                 description "1567.80 nm/191.218750 THz 3.125/6.25GHz spacing";
               }
               enum "1567.77" {
                 description "1567.77 nm/191.221875 THz 3.125GHz spacing";
               }
               enum "1567.75" {
                 description "1567.75 nm/191.225000 THz 3.125/6.25/12.5GHz spacing";
               }
               enum "1567.72" {
                 description "1567.72 nm/191.228125 THz 3.125GHz spacing";
               }
               enum "1567.70" {
                 description "1567.70 nm/191.231250 THz 3.125/6.25GHz spacing";
               }
               enum "1567.67" {
                 description "1567.67 nm/191.234375 THz 3.125GHz spacing";
               }
               enum "1567.64" {
                 description "1567.64 nm/191.237500 THz 3.125/6.25/12.5GHz spacing";
               }
               enum "1567.62" {
                 description "1567.62 nm/191.240625 THz 3.125GHz spacing";
               }
               enum "1567.59" {
                 description "1567.59 nm/191.243750 THz 3.125/6.25GHz spacing";
               }
               enum "1567.57" {
                 description "1567.57 nm/191.246875 THz 3.125GHz spacing";
               }
               enum "1567.54" {
                 description "1567.54 nm/191.250000 THz 3.125/6.25/12.5/50/75GHz spacing";
               }
               enum "1567.52" {
                 description "1567.52 nm/191.253125 THz 3.125GHz spacing";
               }
               enum "1567.49" {
                 description "1567.49 nm/191.256250 THz 3.125/6.25GHz spacing";
               }
               enum "1567.47" {
                 description "1567.47 nm/191.259375 THz 3.125GHz spacing";
               }
               enum "1567.44" {
                 description "1567.44 nm/191.262500 THz 3.125/6.25/12.5GHz spacing";
               }
               enum "1567.41" {
                 description "1567.41 nm/191.265625 THz 3.125GHz spacing";
               }
               enum "1567.39" {
                 description "1567.39 nm/191.268750 THz 3.125/6.25GHz spacing";
               }
               enum "1567.36" {
                 description "1567.36 nm/191.271875 THz 3.125GHz spacing";
               }
               enum "1567.34" {
                 description "1567.34 nm/191.275000 THz 3.125/6.25/12.5GHz spacing";
               }
               enum "1567.31" {
                 description "1567.31 nm/191.278125 THz 3.125GHz spacing";
               }
               enum "1567.29" {
                 description "1567.29 nm/191.281250 THz 3.125/6.25GHz spacing";
               }
               enum "1567.26" {
                 description "1567.26 nm/191.284375 THz 3.125GHz spacing";
               }
               enum "1567.23" {
                 description "1567.23 nm/191.287500 THz 3.125/6.25/12.5GHz spacing";
               }
               enum "1567.21" {
                 description "1567.21 nm/191.290625 THz 3.125GHz spacing";
               }
               enum "1567.18" {
                 description "1567.18 nm/191.293750 THz 3.125/6.25GHz spacing";
               }
               enum "1567.16" {
                 description "1567.16 nm/191.296875 THz 3.125GHz spacing";
               }
               enum "1567.13" {
                 description "1567.13 nm/191.300000 THz 3.125/6.25/12.5/100GHz spacing";
               }
               enum "1567.11" {
                 description "1567.11 nm/191.303125 THz 3.125GHz spacing";
               }
               enum "1567.08" {
                 description "1567.08 nm/191.306250 THz 3.125/6.25GHz spacing";
               }
               enum "1567.06" {
                 description "1567.06 nm/191.309375 THz 3.125GHz spacing";
               }
               enum "1567.03" {
                 description "1567.03 nm/191.312500 THz 3.125/6.25/12.5GHz spacing";
               }
               enum "1567.00" {
                 description "1567.00 nm/191.315625 THz 3.125GHz spacing";
               }
               enum "1566.98" {
                 description "1566.98 nm/191.318750 THz 3.125/6.25GHz spacing";
               }
               enum "1566.95" {
                 description "1566.95 nm/191.321875 THz 3.125GHz spacing";
               }
               enum "1566.93" {
                 description "1566.93 nm/191.325000 THz 3.125/6.25/12.5/75GHz spacing";
               }
               enum "1566.90" {
                 description "1566.90 nm/191.328125 THz 3.125GHz spacing";
               }
               enum "1566.88" {
                 description "1566.88 nm/191.331250 THz 3.125/6.25GHz spacing";
               }
               enum "1566.85" {
                 description "1566.85 nm/191.334375 THz 3.125GHz spacing";
               }
               enum "1566.83" {
                 description "1566.83 nm/191.337500 THz 3.125/6.25/12.5GHz spacing";
               }
               enum "1566.80" {
                 description "1566.80 nm/191.340625 THz 3.125GHz spacing";
               }
               enum "1566.77" {
                 description "1566.77 nm/191.343750 THz 3.125/6.25GHz spacing";
               }
               enum "1566.75" {
                 description "1566.75 nm/191.346875 THz 3.125GHz spacing";
               }
               enum "1566.72" {
                 description "1566.72 nm/191.350000 THz 3.125/6.25/12.5/50GHz spacing";
               }
               enum "1566.70" {
                 description "1566.70 nm/191.353125 THz 3.125GHz spacing";
               }
               enum "1566.67" {
                 description "1566.67 nm/191.356250 THz 3.125/6.25GHz spacing";
               }
               enum "1566.65" {
                 description "1566.65 nm/191.359375 THz 3.125GHz spacing";
               }
               enum "1566.62" {
                 description "1566.62 nm/191.362500 THz 3.125/6.25/12.5GHz spacing";
               }
               enum "1566.60" {
                 description "1566.60 nm/191.365625 THz 3.125GHz spacing";
               }
               enum "1566.57" {
                 description "1566.57 nm/191.368750 THz 3.125/6.25GHz spacing";
               }
               enum "1566.54" {
                 description "1566.54 nm/191.371875 THz 3.125GHz spacing";
               }
               enum "1566.52" {
                 description "1566.52 nm/191.375000 THz 3.125/6.25/12.5GHz spacing";
               }
               enum "1566.49" {
                 description "1566.49 nm/191.378125 THz 3.125GHz spacing";
               }
               enum "1566.47" {
                 description "1566.47 nm/191.381250 THz 3.125/6.25GHz spacing";
               }
               enum "1566.44" {
                 description "1566.44 nm/191.384375 THz 3.125GHz spacing";
               }
               enum "1566.42" {
                 description "1566.42 nm/191.387500 THz 3.125/6.25/12.5GHz spacing";
               }
               enum "1566.39" {
                 description "1566.39 nm/191.390625 THz 3.125GHz spacing";
               }
               enum "1566.36" {
                 description "1566.36 nm/191.393750 THz 3.125/6.25GHz spacing";
               }
               enum "1566.34" {
                 description "1566.34 nm/191.396875 THz 3.125GHz spacing";
               }
               enum "1566.31" {
                 description "1566.31 nm/191.400000 THz 3.125/6.25/12.5/50/75/100GHz spacing";
               }
               enum "1566.29" {
                 description "1566.29 nm/191.403125 THz 3.125GHz spacing";
               }
               enum "1566.26" {
                 description "1566.26 nm/191.406250 THz 3.125/6.25GHz spacing";
               }
               enum "1566.24" {
                 description "1566.24 nm/191.409375 THz 3.125GHz spacing";
               }
               enum "1566.21" {
                 description "1566.21 nm/191.412500 THz 3.125/6.25/12.5GHz spacing";
               }
               enum "1566.19" {
                 description "1566.19 nm/191.415625 THz 3.125GHz spacing";
               }
               enum "1566.16" {
                 description "1566.16 nm/191.418750 THz 3.125/6.25GHz spacing";
               }
               enum "1566.13" {
                 description "1566.13 nm/191.421875 THz 3.125GHz spacing";
               }
               enum "1566.11" {
                 description "1566.11 nm/191.425000 THz 3.125/6.25/12.5GHz spacing";
               }
               enum "1566.08" {
                 description "1566.08 nm/191.428125 THz 3.125GHz spacing";
               }
               enum "1566.06" {
                 description "1566.06 nm/191.431250 THz 3.125/6.25GHz spacing";
               }
               enum "1566.03" {
                 description "1566.03 nm/191.434375 THz 3.125GHz spacing";
               }
               enum "1566.01" {
                 description "1566.01 nm/191.437500 THz 3.125/6.25/12.5GHz spacing";
               }
               enum "1565.98" {
                 description "1565.98 nm/191.440625 THz 3.125GHz spacing";
               }
               enum "1565.96" {
                 description "1565.96 nm/191.443750 THz 3.125/6.25GHz spacing";
               }
               enum "1565.93" {
                 description "1565.93 nm/191.446875 THz 3.125GHz spacing";
               }
               enum "1565.90" {
                 description "1565.90 nm/191.450000 THz 3.125/6.25/12.5/50GHz spacing";
               }
               enum "1565.88" {
                 description "1565.88 nm/191.453125 THz 3.125GHz spacing";
               }
               enum "1565.85" {
                 description "1565.85 nm/191.456250 THz 3.125/6.25GHz spacing";
               }
               enum "1565.83" {
                 description "1565.83 nm/191.459375 THz 3.125GHz spacing";
               }
               enum "1565.80" {
                 description "1565.80 nm/191.462500 THz 3.125/6.25/12.5GHz spacing";
               }
               enum "1565.78" {
                 description "1565.78 nm/191.465625 THz 3.125GHz spacing";
               }
               enum "1565.75" {
                 description "1565.75 nm/191.468750 THz 3.125/6.25GHz spacing";
               }
               enum "1565.73" {
                 description "1565.73 nm/191.471875 THz 3.125GHz spacing";
               }
               enum "1565.70" {
                 description "1565.70 nm/191.475000 THz 3.125/6.25/12.5/75GHz spacing";
               }
               enum "1565.67" {
                 description "1565.67 nm/191.478125 THz 3.125GHz spacing";
               }
               enum "1565.65" {
                 description "1565.65 nm/191.481250 THz 3.125/6.25GHz spacing";
               }
               enum "1565.62" {
                 description "1565.62 nm/191.484375 THz 3.125GHz spacing";
               }
               enum "1565.60" {
                 description "1565.60 nm/191.487500 THz 3.125/6.25/12.5GHz spacing";
               }
               enum "1565.57" {
                 description "1565.57 nm/191.490625 THz 3.125GHz spacing";
               }
               enum "1565.55" {
                 description "1565.55 nm/191.493750 THz 3.125/6.25GHz spacing";
               }
               enum "1565.52" {
                 description "1565.52 nm/191.496875 THz 3.125GHz spacing";
               }
               enum "1565.50" {
                 description "1565.50 nm/191.500000 THz 3.125/6.25/12.5/100GHz spacing";
               }
               enum "1565.47" {
                 description "1565.47 nm/191.503125 THz 3.125GHz spacing";
               }
               enum "1565.44" {
                 description "1565.44 nm/191.506250 THz 3.125/6.25GHz spacing";
               }
               enum "1565.42" {
                 description "1565.42 nm/191.509375 THz 3.125GHz spacing";
               }
               enum "1565.39" {
                 description "1565.39 nm/191.512500 THz 3.125/6.25/12.5GHz spacing";
               }
               enum "1565.37" {
                 description "1565.37 nm/191.515625 THz 3.125GHz spacing";
               }
               enum "1565.34" {
                 description "1565.34 nm/191.518750 THz 3.125/6.25GHz spacing";
               }
               enum "1565.32" {
                 description "1565.32 nm/191.521875 THz 3.125GHz spacing";
               }
               enum "1565.29" {
                 description "1565.29 nm/191.525000 THz 3.125/6.25/12.5GHz spacing";
               }
               enum "1565.27" {
                 description "1565.27 nm/191.528125 THz 3.125GHz spacing";
               }
               enum "1565.24" {
                 description "1565.24 nm/191.531250 THz 3.125/6.25GHz spacing";
               }
               enum "1565.21" {
                 description "1565.21 nm/191.534375 THz 3.125GHz spacing";
               }
               enum "1565.19" {
                 description "1565.19 nm/191.537500 THz 3.125/6.25/12.5GHz spacing";
               }
               enum "1565.16" {
                 description "1565.16 nm/191.540625 THz 3.125GHz spacing";
               }
               enum "1565.14" {
                 description "1565.14 nm/191.543750 THz 3.125/6.25GHz spacing";
               }
               enum "1565.11" {
                 description "1565.11 nm/191.546875 THz 3.125GHz spacing";
               }
               enum "1565.09" {
                 description "1565.09 nm/191.550000 THz 3.125/6.25/12.5/50/75GHz spacing";
               }
               enum "1565.06" {
                 description "1565.06 nm/191.553125 THz 3.125GHz spacing";
               }
               enum "1565.04" {
                 description "1565.04 nm/191.556250 THz 3.125/6.25GHz spacing";
               }
               enum "1565.01" {
                 description "1565.01 nm/191.559375 THz 3.125GHz spacing";
               }
               enum "1564.99" {
                 description "1564.99 nm/191.562500 THz 3.125/6.25/12.5GHz spacing";
               }
               enum "1564.96" {
                 description "1564.96 nm/191.565625 THz 3.125GHz spacing";
               }
               enum "1564.93" {
                 description "1564.93 nm/191.568750 THz 3.125/6.25GHz spacing";
               }
               enum "1564.91" {
                 description "1564.91 nm/191.571875 THz 3.125GHz spacing";
               }
               enum "1564.88" {
                 description "1564.88 nm/191.575000 THz 3.125/6.25/12.5GHz spacing";
               }
               enum "1564.86" {
                 description "1564.86 nm/191.578125 THz 3.125GHz spacing";
               }
               enum "1564.83" {
                 description "1564.83 nm/191.581250 THz 3.125/6.25GHz spacing";
               }
               enum "1564.81" {
                 description "1564.81 nm/191.584375 THz 3.125GHz spacing";
               }
               enum "1564.78" {
                 description "1564.78 nm/191.587500 THz 3.125/6.25/12.5GHz spacing";
               }
               enum "1564.76" {
                 description "1564.76 nm/191.590625 THz 3.125GHz spacing";
               }
               enum "1564.73" {
                 description "1564.73 nm/191.593750 THz 3.125/6.25GHz spacing";
               }
               enum "1564.70" {
                 description "1564.70 nm/191.596875 THz 3.125GHz spacing";
               }
               enum "1564.68" {
                 description "1564.68 nm/191.600000 THz 3.125/6.25/12.5/100GHz spacing";
               }
               enum "1564.65" {
                 description "1564.65 nm/191.603125 THz 3.125GHz spacing";
               }
               enum "1564.63" {
                 description "1564.63 nm/191.606250 THz 3.125/6.25GHz spacing";
               }
               enum "1564.60" {
                 description "1564.60 nm/191.609375 THz 3.125GHz spacing";
               }
               enum "1564.58" {
                 description "1564.58 nm/191.612500 THz 3.125/6.25/12.5GHz spacing";
               }
               enum "1564.55" {
                 description "1564.55 nm/191.615625 THz 3.125GHz spacing";
               }
               enum "1564.53" {
                 description "1564.53 nm/191.618750 THz 3.125/6.25GHz spacing";
               }
               enum "1564.50" {
                 description "1564.50 nm/191.621875 THz 3.125GHz spacing";
               }
               enum "1564.47" {
                 description "1564.47 nm/191.625000 THz 3.125/6.25/12.5/75GHz spacing";
               }
               enum "1564.45" {
                 description "1564.45 nm/191.628125 THz 3.125GHz spacing";
               }
               enum "1564.42" {
                 description "1564.42 nm/191.631250 THz 3.125/6.25GHz spacing";
               }
               enum "1564.40" {
                 description "1564.40 nm/191.634375 THz 3.125GHz spacing";
               }
               enum "1564.37" {
                 description "1564.37 nm/191.637500 THz 3.125/6.25/12.5GHz spacing";
               }
               enum "1564.35" {
                 description "1564.35 nm/191.640625 THz 3.125GHz spacing";
               }
               enum "1564.32" {
                 description "1564.32 nm/191.643750 THz 3.125/6.25GHz spacing";
               }
               enum "1564.30" {
                 description "1564.30 nm/191.646875 THz 3.125GHz spacing";
               }
               enum "1564.27" {
                 description "1564.27 nm/191.650000 THz 3.125/6.25/12.5/50GHz spacing";
               }
               enum "1564.25" {
                 description "1564.25 nm/191.653125 THz 3.125GHz spacing";
               }
               enum "1564.22" {
                 description "1564.22 nm/191.656250 THz 3.125/6.25GHz spacing";
               }
               enum "1564.19" {
                 description "1564.19 nm/191.659375 THz 3.125GHz spacing";
               }
               enum "1564.17" {
                 description "1564.17 nm/191.662500 THz 3.125/6.25/12.5GHz spacing";
               }
               enum "1564.14" {
                 description "1564.14 nm/191.665625 THz 3.125GHz spacing";
               }
               enum "1564.12" {
                 description "1564.12 nm/191.668750 THz 3.125/6.25GHz spacing";
               }
               enum "1564.09" {
                 description "1564.09 nm/191.671875 THz 3.125GHz spacing";
               }
               enum "1564.07" {
                 description "1564.07 nm/191.675000 THz 3.125/6.25/12.5GHz spacing";
               }
               enum "1564.04" {
                 description "1564.04 nm/191.678125 THz 3.125GHz spacing";
               }
               enum "1564.02" {
                 description "1564.02 nm/191.681250 THz 3.125/6.25GHz spacing";
               }
               enum "1563.99" {
                 description "1563.99 nm/191.684375 THz 3.125GHz spacing";
               }
               enum "1563.96" {
                 description "1563.96 nm/191.687500 THz 3.125/6.25/12.5GHz spacing";
               }
               enum "1563.94" {
                 description "1563.94 nm/191.690625 THz 3.125GHz spacing";
               }
               enum "1563.91" {
                 description "1563.91 nm/191.693750 THz 3.125/6.25GHz spacing";
               }
               enum "1563.89" {
                 description "1563.89 nm/191.696875 THz 3.125GHz spacing";
               }
               enum "1563.86" {
                 description "1563.86 nm/191.700000 THz 3.125/6.25/12.5/50/75/100GHz spacing";
               }
               enum "1563.84" {
                 description "1563.84 nm/191.703125 THz 3.125GHz spacing";
               }
               enum "1563.81" {
                 description "1563.81 nm/191.706250 THz 3.125/6.25GHz spacing";
               }
               enum "1563.79" {
                 description "1563.79 nm/191.709375 THz 3.125GHz spacing";
               }
               enum "1563.76" {
                 description "1563.76 nm/191.712500 THz 3.125/6.25/12.5GHz spacing";
               }
               enum "1563.74" {
                 description "1563.74 nm/191.715625 THz 3.125GHz spacing";
               }
               enum "1563.71" {
                 description "1563.71 nm/191.718750 THz 3.125/6.25GHz spacing";
               }
               enum "1563.68" {
                 description "1563.68 nm/191.721875 THz 3.125GHz spacing";
               }
               enum "1563.66" {
                 description "1563.66 nm/191.725000 THz 3.125/6.25/12.5GHz spacing";
               }
               enum "1563.63" {
                 description "1563.63 nm/191.728125 THz 3.125GHz spacing";
               }
               enum "1563.61" {
                 description "1563.61 nm/191.731250 THz 3.125/6.25GHz spacing";
               }
               enum "1563.58" {
                 description "1563.58 nm/191.734375 THz 3.125GHz spacing";
               }
               enum "1563.56" {
                 description "1563.56 nm/191.737500 THz 3.125/6.25/12.5GHz spacing";
               }
               enum "1563.53" {
                 description "1563.53 nm/191.740625 THz 3.125GHz spacing";
               }
               enum "1563.51" {
                 description "1563.51 nm/191.743750 THz 3.125/6.25GHz spacing";
               }
               enum "1563.48" {
                 description "1563.48 nm/191.746875 THz 3.125GHz spacing";
               }
               enum "1563.45" {
                 description "1563.45 nm/191.750000 THz 3.125/6.25/12.5/50GHz spacing";
               }
               enum "1563.43" {
                 description "1563.43 nm/191.753125 THz 3.125GHz spacing";
               }
               enum "1563.40" {
                 description "1563.40 nm/191.756250 THz 3.125/6.25GHz spacing";
               }
               enum "1563.38" {
                 description "1563.38 nm/191.759375 THz 3.125GHz spacing";
               }
               enum "1563.35" {
                 description "1563.35 nm/191.762500 THz 3.125/6.25/12.5GHz spacing";
               }
               enum "1563.33" {
                 description "1563.33 nm/191.765625 THz 3.125GHz spacing";
               }
               enum "1563.30" {
                 description "1563.30 nm/191.768750 THz 3.125/6.25GHz spacing";
               }
               enum "1563.28" {
                 description "1563.28 nm/191.771875 THz 3.125GHz spacing";
               }
               enum "1563.25" {
                 description "1563.25 nm/191.775000 THz 3.125/6.25/12.5/75GHz spacing";
               }
               enum "1563.23" {
                 description "1563.23 nm/191.778125 THz 3.125GHz spacing";
               }
               enum "1563.20" {
                 description "1563.20 nm/191.781250 THz 3.125/6.25GHz spacing";
               }
               enum "1563.17" {
                 description "1563.17 nm/191.784375 THz 3.125GHz spacing";
               }
               enum "1563.15" {
                 description "1563.15 nm/191.787500 THz 3.125/6.25/12.5GHz spacing";
               }
               enum "1563.12" {
                 description "1563.12 nm/191.790625 THz 3.125GHz spacing";
               }
               enum "1563.10" {
                 description "1563.10 nm/191.793750 THz 3.125/6.25GHz spacing";
               }
               enum "1563.07" {
                 description "1563.07 nm/191.796875 THz 3.125GHz spacing";
               }
               enum "1563.05" {
                 description "1563.05 nm/191.800000 THz 3.125/6.25/12.5/100GHz spacing";
               }
               enum "1563.02" {
                 description "1563.02 nm/191.803125 THz 3.125GHz spacing";
               }
               enum "1563.00" {
                 description "1563.00 nm/191.806250 THz 3.125/6.25GHz spacing";
               }
               enum "1562.97" {
                 description "1562.97 nm/191.809375 THz 3.125GHz spacing";
               }
               enum "1562.95" {
                 description "1562.95 nm/191.812500 THz 3.125/6.25/12.5GHz spacing";
               }
               enum "1562.92" {
                 description "1562.92 nm/191.815625 THz 3.125GHz spacing";
               }
               enum "1562.89" {
                 description "1562.89 nm/191.818750 THz 3.125/6.25GHz spacing";
               }
               enum "1562.87" {
                 description "1562.87 nm/191.821875 THz 3.125GHz spacing";
               }
               enum "1562.84" {
                 description "1562.84 nm/191.825000 THz 3.125/6.25/12.5GHz spacing";
               }
               enum "1562.82" {
                 description "1562.82 nm/191.828125 THz 3.125GHz spacing";
               }
               enum "1562.79" {
                 description "1562.79 nm/191.831250 THz 3.125/6.25GHz spacing";
               }
               enum "1562.77" {
                 description "1562.77 nm/191.834375 THz 3.125GHz spacing";
               }
               enum "1562.74" {
                 description "1562.74 nm/191.837500 THz 3.125/6.25/12.5GHz spacing";
               }
               enum "1562.72" {
                 description "1562.72 nm/191.840625 THz 3.125GHz spacing";
               }
               enum "1562.69" {
                 description "1562.69 nm/191.843750 THz 3.125/6.25GHz spacing";
               }
               enum "1562.67" {
                 description "1562.67 nm/191.846875 THz 3.125GHz spacing";
               }
               enum "1562.64" {
                 description "1562.64 nm/191.850000 THz 3.125/6.25/12.5/50/75GHz spacing";
               }
               enum "1562.61" {
                 description "1562.61 nm/191.853125 THz 3.125GHz spacing";
               }
               enum "1562.59" {
                 description "1562.59 nm/191.856250 THz 3.125/6.25GHz spacing";
               }
               enum "1562.56" {
                 description "1562.56 nm/191.859375 THz 3.125GHz spacing";
               }
               enum "1562.54" {
                 description "1562.54 nm/191.862500 THz 3.125/6.25/12.5GHz spacing";
               }
               enum "1562.51" {
                 description "1562.51 nm/191.865625 THz 3.125GHz spacing";
               }
               enum "1562.49" {
                 description "1562.49 nm/191.868750 THz 3.125/6.25GHz spacing";
               }
               enum "1562.46" {
                 description "1562.46 nm/191.871875 THz 3.125GHz spacing";
               }
               enum "1562.44" {
                 description "1562.44 nm/191.875000 THz 3.125/6.25/12.5GHz spacing";
               }
               enum "1562.41" {
                 description "1562.41 nm/191.878125 THz 3.125GHz spacing";
               }
               enum "1562.39" {
                 description "1562.39 nm/191.881250 THz 3.125/6.25GHz spacing";
               }
               enum "1562.36" {
                 description "1562.36 nm/191.884375 THz 3.125GHz spacing";
               }
               enum "1562.33" {
                 description "1562.33 nm/191.887500 THz 3.125/6.25/12.5GHz spacing";
               }
               enum "1562.31" {
                 description "1562.31 nm/191.890625 THz 3.125GHz spacing";
               }
               enum "1562.28" {
                 description "1562.28 nm/191.893750 THz 3.125/6.25GHz spacing";
               }
               enum "1562.26" {
                 description "1562.26 nm/191.896875 THz 3.125GHz spacing";
               }
               enum "1562.23" {
                 description "1562.23 nm/191.900000 THz 3.125/6.25/12.5/100GHz spacing";
               }
               enum "1562.21" {
                 description "1562.21 nm/191.903125 THz 3.125GHz spacing";
               }
               enum "1562.18" {
                 description "1562.18 nm/191.906250 THz 3.125/6.25GHz spacing";
               }
               enum "1562.16" {
                 description "1562.16 nm/191.909375 THz 3.125GHz spacing";
               }
               enum "1562.13" {
                 description "1562.13 nm/191.912500 THz 3.125/6.25/12.5GHz spacing";
               }
               enum "1562.11" {
                 description "1562.11 nm/191.915625 THz 3.125GHz spacing";
               }
               enum "1562.08" {
                 description "1562.08 nm/191.918750 THz 3.125/6.25GHz spacing";
               }
               enum "1562.05" {
                 description "1562.05 nm/191.921875 THz 3.125GHz spacing";
               }
               enum "1562.03" {
                 description "1562.03 nm/191.925000 THz 3.125/6.25/12.5/75GHz spacing";
               }
               enum "1562.00" {
                 description "1562.00 nm/191.928125 THz 3.125GHz spacing";
               }
               enum "1561.98" {
                 description "1561.98 nm/191.931250 THz 3.125/6.25GHz spacing";
               }
               enum "1561.95" {
                 description "1561.95 nm/191.934375 THz 3.125GHz spacing";
               }
               enum "1561.93" {
                 description "1561.93 nm/191.937500 THz 3.125/6.25/12.5GHz spacing";
               }
               enum "1561.90" {
                 description "1561.90 nm/191.940625 THz 3.125GHz spacing";
               }
               enum "1561.88" {
                 description "1561.88 nm/191.943750 THz 3.125/6.25GHz spacing";
               }
               enum "1561.85" {
                 description "1561.85 nm/191.946875 THz 3.125GHz spacing";
               }
               enum "1561.83" {
                 description "1561.83 nm/191.950000 THz 3.125/6.25/12.5/50GHz spacing";
               }
               enum "1561.80" {
                 description "1561.80 nm/191.953125 THz 3.125GHz spacing";
               }
               enum "1561.77" {
                 description "1561.77 nm/191.956250 THz 3.125/6.25GHz spacing";
               }
               enum "1561.75" {
                 description "1561.75 nm/191.959375 THz 3.125GHz spacing";
               }
               enum "1561.72" {
                 description "1561.72 nm/191.962500 THz 3.125/6.25/12.5GHz spacing";
               }
               enum "1561.70" {
                 description "1561.70 nm/191.965625 THz 3.125GHz spacing";
               }
               enum "1561.67" {
                 description "1561.67 nm/191.968750 THz 3.125/6.25GHz spacing";
               }
               enum "1561.65" {
                 description "1561.65 nm/191.971875 THz 3.125GHz spacing";
               }
               enum "1561.62" {
                 description "1561.62 nm/191.975000 THz 3.125/6.25/12.5GHz spacing";
               }
               enum "1561.60" {
                 description "1561.60 nm/191.978125 THz 3.125GHz spacing";
               }
               enum "1561.57" {
                 description "1561.57 nm/191.981250 THz 3.125/6.25GHz spacing";
               }
               enum "1561.55" {
                 description "1561.55 nm/191.984375 THz 3.125GHz spacing";
               }
               enum "1561.52" {
                 description "1561.52 nm/191.987500 THz 3.125/6.25/12.5GHz spacing";
               }
               enum "1561.50" {
                 description "1561.50 nm/191.990625 THz 3.125GHz spacing";
               }
               enum "1561.47" {
                 description "1561.47 nm/191.993750 THz 3.125/6.25GHz spacing";
               }
               enum "1561.44" {
                 description "1561.44 nm/191.996875 THz 3.125GHz spacing";
               }
               enum "1561.42" {
                 description "1561.42 nm/192.000000 THz 3.125/6.25/12.5/50/75/100GHz spacing";
               }
               enum "1561.39" {
                 description "1561.39 nm/192.003125 THz 3.125GHz spacing";
               }
               enum "1561.37" {
                 description "1561.37 nm/192.006250 THz 3.125/6.25GHz spacing";
               }
               enum "1561.34" {
                 description "1561.34 nm/192.009375 THz 3.125GHz spacing";
               }
               enum "1561.32" {
                 description "1561.32 nm/192.012500 THz 3.125/6.25/12.5GHz spacing";
               }
               enum "1561.29" {
                 description "1561.29 nm/192.015625 THz 3.125GHz spacing";
               }
               enum "1561.27" {
                 description "1561.27 nm/192.018750 THz 3.125/6.25GHz spacing";
               }
               enum "1561.24" {
                 description "1561.24 nm/192.021875 THz 3.125GHz spacing";
               }
               enum "1561.22" {
                 description "1561.22 nm/192.025000 THz 3.125/6.25/12.5GHz spacing";
               }
               enum "1561.19" {
                 description "1561.19 nm/192.028125 THz 3.125GHz spacing";
               }
               enum "1561.16" {
                 description "1561.16 nm/192.031250 THz 3.125/6.25GHz spacing";
               }
               enum "1561.14" {
                 description "1561.14 nm/192.034375 THz 3.125GHz spacing";
               }
               enum "1561.11" {
                 description "1561.11 nm/192.037500 THz 3.125/6.25/12.5GHz spacing";
               }
               enum "1561.09" {
                 description "1561.09 nm/192.040625 THz 3.125GHz spacing";
               }
               enum "1561.06" {
                 description "1561.06 nm/192.043750 THz 3.125/6.25GHz spacing";
               }
               enum "1561.04" {
                 description "1561.04 nm/192.046875 THz 3.125GHz spacing";
               }
               enum "1561.01" {
                 description "1561.01 nm/192.050000 THz 3.125/6.25/12.5/50GHz spacing";
               }
               enum "1560.99" {
                 description "1560.99 nm/192.053125 THz 3.125GHz spacing";
               }
               enum "1560.96" {
                 description "1560.96 nm/192.056250 THz 3.125/6.25GHz spacing";
               }
               enum "1560.94" {
                 description "1560.94 nm/192.059375 THz 3.125GHz spacing";
               }
               enum "1560.91" {
                 description "1560.91 nm/192.062500 THz 3.125/6.25/12.5GHz spacing";
               }
               enum "1560.89" {
                 description "1560.89 nm/192.065625 THz 3.125GHz spacing";
               }
               enum "1560.86" {
                 description "1560.86 nm/192.068750 THz 3.125/6.25GHz spacing";
               }
               enum "1560.83" {
                 description "1560.83 nm/192.071875 THz 3.125GHz spacing";
               }
               enum "1560.81" {
                 description "1560.81 nm/192.075000 THz 3.125/6.25/12.5/75GHz spacing";
               }
               enum "1560.78" {
                 description "1560.78 nm/192.078125 THz 3.125GHz spacing";
               }
               enum "1560.76" {
                 description "1560.76 nm/192.081250 THz 3.125/6.25GHz spacing";
               }
               enum "1560.73" {
                 description "1560.73 nm/192.084375 THz 3.125GHz spacing";
               }
               enum "1560.71" {
                 description "1560.71 nm/192.087500 THz 3.125/6.25/12.5GHz spacing";
               }
               enum "1560.68" {
                 description "1560.68 nm/192.090625 THz 3.125GHz spacing";
               }
               enum "1560.66" {
                 description "1560.66 nm/192.093750 THz 3.125/6.25GHz spacing";
               }
               enum "1560.63" {
                 description "1560.63 nm/192.096875 THz 3.125GHz spacing";
               }
               enum "1560.61" {
                 description "1560.61 nm/192.100000 THz 3.125/6.25/12.5/100GHz spacing";
               }
               enum "1560.58" {
                 description "1560.58 nm/192.103125 THz 3.125GHz spacing";
               }
               enum "1560.56" {
                 description "1560.56 nm/192.106250 THz 3.125/6.25GHz spacing";
               }
               enum "1560.53" {
                 description "1560.53 nm/192.109375 THz 3.125GHz spacing";
               }
               enum "1560.50" {
                 description "1560.50 nm/192.112500 THz 3.125/6.25/12.5GHz spacing";
               }
               enum "1560.48" {
                 description "1560.48 nm/192.115625 THz 3.125GHz spacing";
               }
               enum "1560.45" {
                 description "1560.45 nm/192.118750 THz 3.125/6.25GHz spacing";
               }
               enum "1560.43" {
                 description "1560.43 nm/192.121875 THz 3.125GHz spacing";
               }
               enum "1560.40" {
                 description "1560.40 nm/192.125000 THz 3.125/6.25/12.5GHz spacing";
               }
               enum "1560.38" {
                 description "1560.38 nm/192.128125 THz 3.125GHz spacing";
               }
               enum "1560.35" {
                 description "1560.35 nm/192.131250 THz 3.125/6.25GHz spacing";
               }
               enum "1560.33" {
                 description "1560.33 nm/192.134375 THz 3.125GHz spacing";
               }
               enum "1560.30" {
                 description "1560.30 nm/192.137500 THz 3.125/6.25/12.5GHz spacing";
               }
               enum "1560.28" {
                 description "1560.28 nm/192.140625 THz 3.125GHz spacing";
               }
               enum "1560.25" {
                 description "1560.25 nm/192.143750 THz 3.125/6.25GHz spacing";
               }
               enum "1560.23" {
                 description "1560.23 nm/192.146875 THz 3.125GHz spacing";
               }
               enum "1560.20" {
                 description "1560.20 nm/192.150000 THz 3.125/6.25/12.5/50/75GHz spacing";
               }
               enum "1560.17" {
                 description "1560.17 nm/192.153125 THz 3.125GHz spacing";
               }
               enum "1560.15" {
                 description "1560.15 nm/192.156250 THz 3.125/6.25GHz spacing";
               }
               enum "1560.12" {
                 description "1560.12 nm/192.159375 THz 3.125GHz spacing";
               }
               enum "1560.10" {
                 description "1560.10 nm/192.162500 THz 3.125/6.25/12.5GHz spacing";
               }
               enum "1560.07" {
                 description "1560.07 nm/192.165625 THz 3.125GHz spacing";
               }
               enum "1560.05" {
                 description "1560.05 nm/192.168750 THz 3.125/6.25GHz spacing";
               }
               enum "1560.02" {
                 description "1560.02 nm/192.171875 THz 3.125GHz spacing";
               }
               enum "1560.00" {
                 description "1560.00 nm/192.175000 THz 3.125/6.25/12.5GHz spacing";
               }
               enum "1559.97" {
                 description "1559.97 nm/192.178125 THz 3.125GHz spacing";
               }
               enum "1559.95" {
                 description "1559.95 nm/192.181250 THz 3.125/6.25GHz spacing";
               }
               enum "1559.92" {
                 description "1559.92 nm/192.184375 THz 3.125GHz spacing";
               }
               enum "1559.90" {
                 description "1559.90 nm/192.187500 THz 3.125/6.25/12.5GHz spacing";
               }
               enum "1559.87" {
                 description "1559.87 nm/192.190625 THz 3.125GHz spacing";
               }
               enum "1559.84" {
                 description "1559.84 nm/192.193750 THz 3.125/6.25GHz spacing";
               }
               enum "1559.82" {
                 description "1559.82 nm/192.196875 THz 3.125GHz spacing";
               }
               enum "1559.79" {
                 description "1559.79 nm/192.200000 THz 3.125/6.25/12.5/100GHz spacing";
               }
               enum "1559.77" {
                 description "1559.77 nm/192.203125 THz 3.125GHz spacing";
               }
               enum "1559.74" {
                 description "1559.74 nm/192.206250 THz 3.125/6.25GHz spacing";
               }
               enum "1559.72" {
                 description "1559.72 nm/192.209375 THz 3.125GHz spacing";
               }
               enum "1559.69" {
                 description "1559.69 nm/192.212500 THz 3.125/6.25/12.5GHz spacing";
               }
               enum "1559.67" {
                 description "1559.67 nm/192.215625 THz 3.125GHz spacing";
               }
               enum "1559.64" {
                 description "1559.64 nm/192.218750 THz 3.125/6.25GHz spacing";
               }
               enum "1559.62" {
                 description "1559.62 nm/192.221875 THz 3.125GHz spacing";
               }
               enum "1559.59" {
                 description "1559.59 nm/192.225000 THz 3.125/6.25/12.5/75GHz spacing";
               }
               enum "1559.57" {
                 description "1559.57 nm/192.228125 THz 3.125GHz spacing";
               }
               enum "1559.54" {
                 description "1559.54 nm/192.231250 THz 3.125/6.25GHz spacing";
               }
               enum "1559.52" {
                 description "1559.52 nm/192.234375 THz 3.125GHz spacing";
               }
               enum "1559.49" {
                 description "1559.49 nm/192.237500 THz 3.125/6.25/12.5GHz spacing";
               }
               enum "1559.46" {
                 description "1559.46 nm/192.240625 THz 3.125GHz spacing";
               }
               enum "1559.44" {
                 description "1559.44 nm/192.243750 THz 3.125/6.25GHz spacing";
               }
               enum "1559.41" {
                 description "1559.41 nm/192.246875 THz 3.125GHz spacing";
               }
               enum "1559.39" {
                 description "1559.39 nm/192.250000 THz 3.125/6.25/12.5/50GHz spacing";
               }
               enum "1559.36" {
                 description "1559.36 nm/192.253125 THz 3.125GHz spacing";
               }
               enum "1559.34" {
                 description "1559.34 nm/192.256250 THz 3.125/6.25GHz spacing";
               }
               enum "1559.31" {
                 description "1559.31 nm/192.259375 THz 3.125GHz spacing";
               }
               enum "1559.29" {
                 description "1559.29 nm/192.262500 THz 3.125/6.25/12.5GHz spacing";
               }
               enum "1559.26" {
                 description "1559.26 nm/192.265625 THz 3.125GHz spacing";
               }
               enum "1559.24" {
                 description "1559.24 nm/192.268750 THz 3.125/6.25GHz spacing";
               }
               enum "1559.21" {
                 description "1559.21 nm/192.271875 THz 3.125GHz spacing";
               }
               enum "1559.19" {
                 description "1559.19 nm/192.275000 THz 3.125/6.25/12.5GHz spacing";
               }
               enum "1559.16" {
                 description "1559.16 nm/192.278125 THz 3.125GHz spacing";
               }
               enum "1559.14" {
                 description "1559.14 nm/192.281250 THz 3.125/6.25GHz spacing";
               }
               enum "1559.11" {
                 description "1559.11 nm/192.284375 THz 3.125GHz spacing";
               }
               enum "1559.08" {
                 description "1559.08 nm/192.287500 THz 3.125/6.25/12.5GHz spacing";
               }
               enum "1559.06" {
                 description "1559.06 nm/192.290625 THz 3.125GHz spacing";
               }
               enum "1559.03" {
                 description "1559.03 nm/192.293750 THz 3.125/6.25GHz spacing";
               }
               enum "1559.01" {
                 description "1559.01 nm/192.296875 THz 3.125GHz spacing";
               }
               enum "1558.98" {
                 description "1558.98 nm/192.300000 THz 3.125/6.25/12.5/50/75/100GHz spacing";
               }
               enum "1558.96" {
                 description "1558.96 nm/192.303125 THz 3.125GHz spacing";
               }
               enum "1558.93" {
                 description "1558.93 nm/192.306250 THz 3.125/6.25GHz spacing";
               }
               enum "1558.91" {
                 description "1558.91 nm/192.309375 THz 3.125GHz spacing";
               }
               enum "1558.88" {
                 description "1558.88 nm/192.312500 THz 3.125/6.25/12.5GHz spacing";
               }
               enum "1558.86" {
                 description "1558.86 nm/192.315625 THz 3.125GHz spacing";
               }
               enum "1558.83" {
                 description "1558.83 nm/192.318750 THz 3.125/6.25GHz spacing";
               }
               enum "1558.81" {
                 description "1558.81 nm/192.321875 THz 3.125GHz spacing";
               }
               enum "1558.78" {
                 description "1558.78 nm/192.325000 THz 3.125/6.25/12.5GHz spacing";
               }
               enum "1558.76" {
                 description "1558.76 nm/192.328125 THz 3.125GHz spacing";
               }
               enum "1558.73" {
                 description "1558.73 nm/192.331250 THz 3.125/6.25GHz spacing";
               }
               enum "1558.70" {
                 description "1558.70 nm/192.334375 THz 3.125GHz spacing";
               }
               enum "1558.68" {
                 description "1558.68 nm/192.337500 THz 3.125/6.25/12.5GHz spacing";
               }
               enum "1558.65" {
                 description "1558.65 nm/192.340625 THz 3.125GHz spacing";
               }
               enum "1558.63" {
                 description "1558.63 nm/192.343750 THz 3.125/6.25GHz spacing";
               }
               enum "1558.60" {
                 description "1558.60 nm/192.346875 THz 3.125GHz spacing";
               }
               enum "1558.58" {
                 description "1558.58 nm/192.350000 THz 3.125/6.25/12.5/50GHz spacing";
               }
               enum "1558.55" {
                 description "1558.55 nm/192.353125 THz 3.125GHz spacing";
               }
               enum "1558.53" {
                 description "1558.53 nm/192.356250 THz 3.125/6.25GHz spacing";
               }
               enum "1558.50" {
                 description "1558.50 nm/192.359375 THz 3.125GHz spacing";
               }
               enum "1558.48" {
                 description "1558.48 nm/192.362500 THz 3.125/6.25/12.5GHz spacing";
               }
               enum "1558.45" {
                 description "1558.45 nm/192.365625 THz 3.125GHz spacing";
               }
               enum "1558.43" {
                 description "1558.43 nm/192.368750 THz 3.125/6.25GHz spacing";
               }
               enum "1558.40" {
                 description "1558.40 nm/192.371875 THz 3.125GHz spacing";
               }
               enum "1558.38" {
                 description "1558.38 nm/192.375000 THz 3.125/6.25/12.5/75GHz spacing";
               }
               enum "1558.35" {
                 description "1558.35 nm/192.378125 THz 3.125GHz spacing";
               }
               enum "1558.32" {
                 description "1558.32 nm/192.381250 THz 3.125/6.25GHz spacing";
               }
               enum "1558.30" {
                 description "1558.30 nm/192.384375 THz 3.125GHz spacing";
               }
               enum "1558.27" {
                 description "1558.27 nm/192.387500 THz 3.125/6.25/12.5GHz spacing";
               }
               enum "1558.25" {
                 description "1558.25 nm/192.390625 THz 3.125GHz spacing";
               }
               enum "1558.22" {
                 description "1558.22 nm/192.393750 THz 3.125/6.25GHz spacing";
               }
               enum "1558.20" {
                 description "1558.20 nm/192.396875 THz 3.125GHz spacing";
               }
               enum "1558.17" {
                 description "1558.17 nm/192.400000 THz 3.125/6.25/12.5/100GHz spacing";
               }
               enum "1558.15" {
                 description "1558.15 nm/192.403125 THz 3.125GHz spacing";
               }
               enum "1558.12" {
                 description "1558.12 nm/192.406250 THz 3.125/6.25GHz spacing";
               }
               enum "1558.10" {
                 description "1558.10 nm/192.409375 THz 3.125GHz spacing";
               }
               enum "1558.07" {
                 description "1558.07 nm/192.412500 THz 3.125/6.25/12.5GHz spacing";
               }
               enum "1558.05" {
                 description "1558.05 nm/192.415625 THz 3.125GHz spacing";
               }
               enum "1558.02" {
                 description "1558.02 nm/192.418750 THz 3.125/6.25GHz spacing";
               }
               enum "1558.00" {
                 description "1558.00 nm/192.421875 THz 3.125GHz spacing";
               }
               enum "1557.97" {
                 description "1557.97 nm/192.425000 THz 3.125/6.25/12.5GHz spacing";
               }
               enum "1557.95" {
                 description "1557.95 nm/192.428125 THz 3.125GHz spacing";
               }
               enum "1557.92" {
                 description "1557.92 nm/192.431250 THz 3.125/6.25GHz spacing";
               }
               enum "1557.89" {
                 description "1557.89 nm/192.434375 THz 3.125GHz spacing";
               }
               enum "1557.87" {
                 description "1557.87 nm/192.437500 THz 3.125/6.25/12.5GHz spacing";
               }
               enum "1557.84" {
                 description "1557.84 nm/192.440625 THz 3.125GHz spacing";
               }
               enum "1557.82" {
                 description "1557.82 nm/192.443750 THz 3.125/6.25GHz spacing";
               }
               enum "1557.79" {
                 description "1557.79 nm/192.446875 THz 3.125GHz spacing";
               }
               enum "1557.77" {
                 description "1557.77 nm/192.450000 THz 3.125/6.25/12.5/50/75GHz spacing";
               }
               enum "1557.74" {
                 description "1557.74 nm/192.453125 THz 3.125GHz spacing";
               }
               enum "1557.72" {
                 description "1557.72 nm/192.456250 THz 3.125/6.25GHz spacing";
               }
               enum "1557.69" {
                 description "1557.69 nm/192.459375 THz 3.125GHz spacing";
               }
               enum "1557.67" {
                 description "1557.67 nm/192.462500 THz 3.125/6.25/12.5GHz spacing";
               }
               enum "1557.64" {
                 description "1557.64 nm/192.465625 THz 3.125GHz spacing";
               }
               enum "1557.62" {
                 description "1557.62 nm/192.468750 THz 3.125/6.25GHz spacing";
               }
               enum "1557.59" {
                 description "1557.59 nm/192.471875 THz 3.125GHz spacing";
               }
               enum "1557.57" {
                 description "1557.57 nm/192.475000 THz 3.125/6.25/12.5GHz spacing";
               }
               enum "1557.54" {
                 description "1557.54 nm/192.478125 THz 3.125GHz spacing";
               }
               enum "1557.52" {
                 description "1557.52 nm/192.481250 THz 3.125/6.25GHz spacing";
               }
               enum "1557.49" {
                 description "1557.49 nm/192.484375 THz 3.125GHz spacing";
               }
               enum "1557.46" {
                 description "1557.46 nm/192.487500 THz 3.125/6.25/12.5GHz spacing";
               }
               enum "1557.44" {
                 description "1557.44 nm/192.490625 THz 3.125GHz spacing";
               }
               enum "1557.41" {
                 description "1557.41 nm/192.493750 THz 3.125/6.25GHz spacing";
               }
               enum "1557.39" {
                 description "1557.39 nm/192.496875 THz 3.125GHz spacing";
               }
               enum "1557.36" {
                 description "1557.36 nm/192.500000 THz 3.125/6.25/12.5/100GHz spacing";
               }
               enum "1557.34" {
                 description "1557.34 nm/192.503125 THz 3.125GHz spacing";
               }
               enum "1557.31" {
                 description "1557.31 nm/192.506250 THz 3.125/6.25GHz spacing";
               }
               enum "1557.29" {
                 description "1557.29 nm/192.509375 THz 3.125GHz spacing";
               }
               enum "1557.26" {
                 description "1557.26 nm/192.512500 THz 3.125/6.25/12.5GHz spacing";
               }
               enum "1557.24" {
                 description "1557.24 nm/192.515625 THz 3.125GHz spacing";
               }
               enum "1557.21" {
                 description "1557.21 nm/192.518750 THz 3.125/6.25GHz spacing";
               }
               enum "1557.19" {
                 description "1557.19 nm/192.521875 THz 3.125GHz spacing";
               }
               enum "1557.16" {
                 description "1557.16 nm/192.525000 THz 3.125/6.25/12.5/75GHz spacing";
               }
               enum "1557.14" {
                 description "1557.14 nm/192.528125 THz 3.125GHz spacing";
               }
               enum "1557.11" {
                 description "1557.11 nm/192.531250 THz 3.125/6.25GHz spacing";
               }
               enum "1557.09" {
                 description "1557.09 nm/192.534375 THz 3.125GHz spacing";
               }
               enum "1557.06" {
                 description "1557.06 nm/192.537500 THz 3.125/6.25/12.5GHz spacing";
               }
               enum "1557.03" {
                 description "1557.03 nm/192.540625 THz 3.125GHz spacing";
               }
               enum "1557.01" {
                 description "1557.01 nm/192.543750 THz 3.125/6.25GHz spacing";
               }
               enum "1556.98" {
                 description "1556.98 nm/192.546875 THz 3.125GHz spacing";
               }
               enum "1556.96" {
                 description "1556.96 nm/192.550000 THz 3.125/6.25/12.5/50GHz spacing";
               }
               enum "1556.93" {
                 description "1556.93 nm/192.553125 THz 3.125GHz spacing";
               }
               enum "1556.91" {
                 description "1556.91 nm/192.556250 THz 3.125/6.25GHz spacing";
               }
               enum "1556.88" {
                 description "1556.88 nm/192.559375 THz 3.125GHz spacing";
               }
               enum "1556.86" {
                 description "1556.86 nm/192.562500 THz 3.125/6.25/12.5GHz spacing";
               }
               enum "1556.83" {
                 description "1556.83 nm/192.565625 THz 3.125GHz spacing";
               }
               enum "1556.81" {
                 description "1556.81 nm/192.568750 THz 3.125/6.25GHz spacing";
               }
               enum "1556.78" {
                 description "1556.78 nm/192.571875 THz 3.125GHz spacing";
               }
               enum "1556.76" {
                 description "1556.76 nm/192.575000 THz 3.125/6.25/12.5GHz spacing";
               }
               enum "1556.73" {
                 description "1556.73 nm/192.578125 THz 3.125GHz spacing";
               }
               enum "1556.71" {
                 description "1556.71 nm/192.581250 THz 3.125/6.25GHz spacing";
               }
               enum "1556.68" {
                 description "1556.68 nm/192.584375 THz 3.125GHz spacing";
               }
               enum "1556.66" {
                 description "1556.66 nm/192.587500 THz 3.125/6.25/12.5GHz spacing";
               }
               enum "1556.63" {
                 description "1556.63 nm/192.590625 THz 3.125GHz spacing";
               }
               enum "1556.61" {
                 description "1556.61 nm/192.593750 THz 3.125/6.25GHz spacing";
               }
               enum "1556.58" {
                 description "1556.58 nm/192.596875 THz 3.125GHz spacing";
               }
               enum "1556.55" {
                 description "1556.55 nm/192.600000 THz 3.125/6.25/12.5/50/75/100GHz spacing";
               }
               enum "1556.53" {
                 description "1556.53 nm/192.603125 THz 3.125GHz spacing";
               }
               enum "1556.50" {
                 description "1556.50 nm/192.606250 THz 3.125/6.25GHz spacing";
               }
               enum "1556.48" {
                 description "1556.48 nm/192.609375 THz 3.125GHz spacing";
               }
               enum "1556.45" {
                 description "1556.45 nm/192.612500 THz 3.125/6.25/12.5GHz spacing";
               }
               enum "1556.43" {
                 description "1556.43 nm/192.615625 THz 3.125GHz spacing";
               }
               enum "1556.40" {
                 description "1556.40 nm/192.618750 THz 3.125/6.25GHz spacing";
               }
               enum "1556.38" {
                 description "1556.38 nm/192.621875 THz 3.125GHz spacing";
               }
               enum "1556.35" {
                 description "1556.35 nm/192.625000 THz 3.125/6.25/12.5GHz spacing";
               }
               enum "1556.33" {
                 description "1556.33 nm/192.628125 THz 3.125GHz spacing";
               }
               enum "1556.30" {
                 description "1556.30 nm/192.631250 THz 3.125/6.25GHz spacing";
               }
               enum "1556.28" {
                 description "1556.28 nm/192.634375 THz 3.125GHz spacing";
               }
               enum "1556.25" {
                 description "1556.25 nm/192.637500 THz 3.125/6.25/12.5GHz spacing";
               }
               enum "1556.23" {
                 description "1556.23 nm/192.640625 THz 3.125GHz spacing";
               }
               enum "1556.20" {
                 description "1556.20 nm/192.643750 THz 3.125/6.25GHz spacing";
               }
               enum "1556.18" {
                 description "1556.18 nm/192.646875 THz 3.125GHz spacing";
               }
               enum "1556.15" {
                 description "1556.15 nm/192.650000 THz 3.125/6.25/12.5/50GHz spacing";
               }
               enum "1556.13" {
                 description "1556.13 nm/192.653125 THz 3.125GHz spacing";
               }
               enum "1556.10" {
                 description "1556.10 nm/192.656250 THz 3.125/6.25GHz spacing";
               }
               enum "1556.08" {
                 description "1556.08 nm/192.659375 THz 3.125GHz spacing";
               }
               enum "1556.05" {
                 description "1556.05 nm/192.662500 THz 3.125/6.25/12.5GHz spacing";
               }
               enum "1556.02" {
                 description "1556.02 nm/192.665625 THz 3.125GHz spacing";
               }
               enum "1556.00" {
                 description "1556.00 nm/192.668750 THz 3.125/6.25GHz spacing";
               }
               enum "1555.97" {
                 description "1555.97 nm/192.671875 THz 3.125GHz spacing";
               }
               enum "1555.95" {
                 description "1555.95 nm/192.675000 THz 3.125/6.25/12.5/75GHz spacing";
               }
               enum "1555.92" {
                 description "1555.92 nm/192.678125 THz 3.125GHz spacing";
               }
               enum "1555.90" {
                 description "1555.90 nm/192.681250 THz 3.125/6.25GHz spacing";
               }
               enum "1555.87" {
                 description "1555.87 nm/192.684375 THz 3.125GHz spacing";
               }
               enum "1555.85" {
                 description "1555.85 nm/192.687500 THz 3.125/6.25/12.5GHz spacing";
               }
               enum "1555.82" {
                 description "1555.82 nm/192.690625 THz 3.125GHz spacing";
               }
               enum "1555.80" {
                 description "1555.80 nm/192.693750 THz 3.125/6.25GHz spacing";
               }
               enum "1555.77" {
                 description "1555.77 nm/192.696875 THz 3.125GHz spacing";
               }
               enum "1555.75" {
                 description "1555.75 nm/192.700000 THz 3.125/6.25/12.5/100GHz spacing";
               }
               enum "1555.72" {
                 description "1555.72 nm/192.703125 THz 3.125GHz spacing";
               }
               enum "1555.70" {
                 description "1555.70 nm/192.706250 THz 3.125/6.25GHz spacing";
               }
               enum "1555.67" {
                 description "1555.67 nm/192.709375 THz 3.125GHz spacing";
               }
               enum "1555.65" {
                 description "1555.65 nm/192.712500 THz 3.125/6.25/12.5GHz spacing";
               }
               enum "1555.62" {
                 description "1555.62 nm/192.715625 THz 3.125GHz spacing";
               }
               enum "1555.60" {
                 description "1555.60 nm/192.718750 THz 3.125/6.25GHz spacing";
               }
               enum "1555.57" {
                 description "1555.57 nm/192.721875 THz 3.125GHz spacing";
               }
               enum "1555.55" {
                 description "1555.55 nm/192.725000 THz 3.125/6.25/12.5GHz spacing";
               }
               enum "1555.52" {
                 description "1555.52 nm/192.728125 THz 3.125GHz spacing";
               }
               enum "1555.49" {
                 description "1555.49 nm/192.731250 THz 3.125/6.25GHz spacing";
               }
               enum "1555.47" {
                 description "1555.47 nm/192.734375 THz 3.125GHz spacing";
               }
               enum "1555.44" {
                 description "1555.44 nm/192.737500 THz 3.125/6.25/12.5GHz spacing";
               }
               enum "1555.42" {
                 description "1555.42 nm/192.740625 THz 3.125GHz spacing";
               }
               enum "1555.39" {
                 description "1555.39 nm/192.743750 THz 3.125/6.25GHz spacing";
               }
               enum "1555.37" {
                 description "1555.37 nm/192.746875 THz 3.125GHz spacing";
               }
               enum "1555.34" {
                 description "1555.34 nm/192.750000 THz 3.125/6.25/12.5/50/75GHz spacing";
               }
               enum "1555.32" {
                 description "1555.32 nm/192.753125 THz 3.125GHz spacing";
               }
               enum "1555.29" {
                 description "1555.29 nm/192.756250 THz 3.125/6.25GHz spacing";
               }
               enum "1555.27" {
                 description "1555.27 nm/192.759375 THz 3.125GHz spacing";
               }
               enum "1555.24" {
                 description "1555.24 nm/192.762500 THz 3.125/6.25/12.5GHz spacing";
               }
               enum "1555.22" {
                 description "1555.22 nm/192.765625 THz 3.125GHz spacing";
               }
               enum "1555.19" {
                 description "1555.19 nm/192.768750 THz 3.125/6.25GHz spacing";
               }
               enum "1555.17" {
                 description "1555.17 nm/192.771875 THz 3.125GHz spacing";
               }
               enum "1555.14" {
                 description "1555.14 nm/192.775000 THz 3.125/6.25/12.5GHz spacing";
               }
               enum "1555.12" {
                 description "1555.12 nm/192.778125 THz 3.125GHz spacing";
               }
               enum "1555.09" {
                 description "1555.09 nm/192.781250 THz 3.125/6.25GHz spacing";
               }
               enum "1555.07" {
                 description "1555.07 nm/192.784375 THz 3.125GHz spacing";
               }
               enum "1555.04" {
                 description "1555.04 nm/192.787500 THz 3.125/6.25/12.5GHz spacing";
               }
               enum "1555.02" {
                 description "1555.02 nm/192.790625 THz 3.125GHz spacing";
               }
               enum "1554.99" {
                 description "1554.99 nm/192.793750 THz 3.125/6.25GHz spacing";
               }
               enum "1554.97" {
                 description "1554.97 nm/192.796875 THz 3.125GHz spacing";
               }
               enum "1554.94" {
                 description "1554.94 nm/192.800000 THz 3.125/6.25/12.5/100GHz spacing";
               }
               enum "1554.91" {
                 description "1554.91 nm/192.803125 THz 3.125GHz spacing";
               }
               enum "1554.89" {
                 description "1554.89 nm/192.806250 THz 3.125/6.25GHz spacing";
               }
               enum "1554.86" {
                 description "1554.86 nm/192.809375 THz 3.125GHz spacing";
               }
               enum "1554.84" {
                 description "1554.84 nm/192.812500 THz 3.125/6.25/12.5GHz spacing";
               }
               enum "1554.81" {
                 description "1554.81 nm/192.815625 THz 3.125GHz spacing";
               }
               enum "1554.79" {
                 description "1554.79 nm/192.818750 THz 3.125/6.25GHz spacing";
               }
               enum "1554.76" {
                 description "1554.76 nm/192.821875 THz 3.125GHz spacing";
               }
               enum "1554.74" {
                 description "1554.74 nm/192.825000 THz 3.125/6.25/12.5/75GHz spacing";
               }
               enum "1554.71" {
                 description "1554.71 nm/192.828125 THz 3.125GHz spacing";
               }
               enum "1554.69" {
                 description "1554.69 nm/192.831250 THz 3.125/6.25GHz spacing";
               }
               enum "1554.66" {
                 description "1554.66 nm/192.834375 THz 3.125GHz spacing";
               }
               enum "1554.64" {
                 description "1554.64 nm/192.837500 THz 3.125/6.25/12.5GHz spacing";
               }
               enum "1554.61" {
                 description "1554.61 nm/192.840625 THz 3.125GHz spacing";
               }
               enum "1554.59" {
                 description "1554.59 nm/192.843750 THz 3.125/6.25GHz spacing";
               }
               enum "1554.56" {
                 description "1554.56 nm/192.846875 THz 3.125GHz spacing";
               }
               enum "1554.54" {
                 description "1554.54 nm/192.850000 THz 3.125/6.25/12.5/50GHz spacing";
               }
               enum "1554.51" {
                 description "1554.51 nm/192.853125 THz 3.125GHz spacing";
               }
               enum "1554.49" {
                 description "1554.49 nm/192.856250 THz 3.125/6.25GHz spacing";
               }
               enum "1554.46" {
                 description "1554.46 nm/192.859375 THz 3.125GHz spacing";
               }
               enum "1554.44" {
                 description "1554.44 nm/192.862500 THz 3.125/6.25/12.5GHz spacing";
               }
               enum "1554.41" {
                 description "1554.41 nm/192.865625 THz 3.125GHz spacing";
               }
               enum "1554.39" {
                 description "1554.39 nm/192.868750 THz 3.125/6.25GHz spacing";
               }
               enum "1554.36" {
                 description "1554.36 nm/192.871875 THz 3.125GHz spacing";
               }
               enum "1554.34" {
                 description "1554.34 nm/192.875000 THz 3.125/6.25/12.5GHz spacing";
               }
               enum "1554.31" {
                 description "1554.31 nm/192.878125 THz 3.125GHz spacing";
               }
               enum "1554.29" {
                 description "1554.29 nm/192.881250 THz 3.125/6.25GHz spacing";
               }
               enum "1554.26" {
                 description "1554.26 nm/192.884375 THz 3.125GHz spacing";
               }
               enum "1554.23" {
                 description "1554.23 nm/192.887500 THz 3.125/6.25/12.5GHz spacing";
               }
               enum "1554.21" {
                 description "1554.21 nm/192.890625 THz 3.125GHz spacing";
               }
               enum "1554.18" {
                 description "1554.18 nm/192.893750 THz 3.125/6.25GHz spacing";
               }
               enum "1554.16" {
                 description "1554.16 nm/192.896875 THz 3.125GHz spacing";
               }
               enum "1554.13" {
                 description "1554.13 nm/192.900000 THz 3.125/6.25/12.5/50/75/100GHz spacing";
               }
               enum "1554.11" {
                 description "1554.11 nm/192.903125 THz 3.125GHz spacing";
               }
               enum "1554.08" {
                 description "1554.08 nm/192.906250 THz 3.125/6.25GHz spacing";
               }
               enum "1554.06" {
                 description "1554.06 nm/192.909375 THz 3.125GHz spacing";
               }
               enum "1554.03" {
                 description "1554.03 nm/192.912500 THz 3.125/6.25/12.5GHz spacing";
               }
               enum "1554.01" {
                 description "1554.01 nm/192.915625 THz 3.125GHz spacing";
               }
               enum "1553.98" {
                 description "1553.98 nm/192.918750 THz 3.125/6.25GHz spacing";
               }
               enum "1553.96" {
                 description "1553.96 nm/192.921875 THz 3.125GHz spacing";
               }
               enum "1553.93" {
                 description "1553.93 nm/192.925000 THz 3.125/6.25/12.5GHz spacing";
               }
               enum "1553.91" {
                 description "1553.91 nm/192.928125 THz 3.125GHz spacing";
               }
               enum "1553.88" {
                 description "1553.88 nm/192.931250 THz 3.125/6.25GHz spacing";
               }
               enum "1553.86" {
                 description "1553.86 nm/192.934375 THz 3.125GHz spacing";
               }
               enum "1553.83" {
                 description "1553.83 nm/192.937500 THz 3.125/6.25/12.5GHz spacing";
               }
               enum "1553.81" {
                 description "1553.81 nm/192.940625 THz 3.125GHz spacing";
               }
               enum "1553.78" {
                 description "1553.78 nm/192.943750 THz 3.125/6.25GHz spacing";
               }
               enum "1553.76" {
                 description "1553.76 nm/192.946875 THz 3.125GHz spacing";
               }
               enum "1553.73" {
                 description "1553.73 nm/192.950000 THz 3.125/6.25/12.5/50GHz spacing";
               }
               enum "1553.71" {
                 description "1553.71 nm/192.953125 THz 3.125GHz spacing";
               }
               enum "1553.68" {
                 description "1553.68 nm/192.956250 THz 3.125/6.25GHz spacing";
               }
               enum "1553.66" {
                 description "1553.66 nm/192.959375 THz 3.125GHz spacing";
               }
               enum "1553.63" {
                 description "1553.63 nm/192.962500 THz 3.125/6.25/12.5GHz spacing";
               }
               enum "1553.61" {
                 description "1553.61 nm/192.965625 THz 3.125GHz spacing";
               }
               enum "1553.58" {
                 description "1553.58 nm/192.968750 THz 3.125/6.25GHz spacing";
               }
               enum "1553.56" {
                 description "1553.56 nm/192.971875 THz 3.125GHz spacing";
               }
               enum "1553.53" {
                 description "1553.53 nm/192.975000 THz 3.125/6.25/12.5/75GHz spacing";
               }
               enum "1553.50" {
                 description "1553.50 nm/192.978125 THz 3.125GHz spacing";
               }
               enum "1553.48" {
                 description "1553.48 nm/192.981250 THz 3.125/6.25GHz spacing";
               }
               enum "1553.45" {
                 description "1553.45 nm/192.984375 THz 3.125GHz spacing";
               }
               enum "1553.43" {
                 description "1553.43 nm/192.987500 THz 3.125/6.25/12.5GHz spacing";
               }
               enum "1553.40" {
                 description "1553.40 nm/192.990625 THz 3.125GHz spacing";
               }
               enum "1553.38" {
                 description "1553.38 nm/192.993750 THz 3.125/6.25GHz spacing";
               }
               enum "1553.35" {
                 description "1553.35 nm/192.996875 THz 3.125GHz spacing";
               }
               enum "1553.33" {
                 description "1553.33 nm/193.000000 THz 3.125/6.25/12.5/100GHz spacing";
               }
               enum "1553.30" {
                 description "1553.30 nm/193.003125 THz 3.125GHz spacing";
               }
               enum "1553.28" {
                 description "1553.28 nm/193.006250 THz 3.125/6.25GHz spacing";
               }
               enum "1553.25" {
                 description "1553.25 nm/193.009375 THz 3.125GHz spacing";
               }
               enum "1553.23" {
                 description "1553.23 nm/193.012500 THz 3.125/6.25/12.5GHz spacing";
               }
               enum "1553.20" {
                 description "1553.20 nm/193.015625 THz 3.125GHz spacing";
               }
               enum "1553.18" {
                 description "1553.18 nm/193.018750 THz 3.125/6.25GHz spacing";
               }
               enum "1553.15" {
                 description "1553.15 nm/193.021875 THz 3.125GHz spacing";
               }
               enum "1553.13" {
                 description "1553.13 nm/193.025000 THz 3.125/6.25/12.5GHz spacing";
               }
               enum "1553.10" {
                 description "1553.10 nm/193.028125 THz 3.125GHz spacing";
               }
               enum "1553.08" {
                 description "1553.08 nm/193.031250 THz 3.125/6.25GHz spacing";
               }
               enum "1553.05" {
                 description "1553.05 nm/193.034375 THz 3.125GHz spacing";
               }
               enum "1553.03" {
                 description "1553.03 nm/193.037500 THz 3.125/6.25/12.5GHz spacing";
               }
               enum "1553.00" {
                 description "1553.00 nm/193.040625 THz 3.125GHz spacing";
               }
               enum "1552.98" {
                 description "1552.98 nm/193.043750 THz 3.125/6.25GHz spacing";
               }
               enum "1552.95" {
                 description "1552.95 nm/193.046875 THz 3.125GHz spacing";
               }
               enum "1552.93" {
                 description "1552.93 nm/193.050000 THz 3.125/6.25/12.5/50/75GHz spacing";
               }
               enum "1552.90" {
                 description "1552.90 nm/193.053125 THz 3.125GHz spacing";
               }
               enum "1552.88" {
                 description "1552.88 nm/193.056250 THz 3.125/6.25GHz spacing";
               }
               enum "1552.85" {
                 description "1552.85 nm/193.059375 THz 3.125GHz spacing";
               }
               enum "1552.83" {
                 description "1552.83 nm/193.062500 THz 3.125/6.25/12.5GHz spacing";
               }
               enum "1552.80" {
                 description "1552.80 nm/193.065625 THz 3.125GHz spacing";
               }
               enum "1552.78" {
                 description "1552.78 nm/193.068750 THz 3.125/6.25GHz spacing";
               }
               enum "1552.75" {
                 description "1552.75 nm/193.071875 THz 3.125GHz spacing";
               }
               enum "1552.73" {
                 description "1552.73 nm/193.075000 THz 3.125/6.25/12.5GHz spacing";
               }
               enum "1552.70" {
                 description "1552.70 nm/193.078125 THz 3.125GHz spacing";
               }
               enum "1552.68" {
                 description "1552.68 nm/193.081250 THz 3.125/6.25GHz spacing";
               }
               enum "1552.65" {
                 description "1552.65 nm/193.084375 THz 3.125GHz spacing";
               }
               enum "1552.62" {
                 description "1552.62 nm/193.087500 THz 3.125/6.25/12.5GHz spacing";
               }
               enum "1552.60" {
                 description "1552.60 nm/193.090625 THz 3.125GHz spacing";
               }
               enum "1552.57" {
                 description "1552.57 nm/193.093750 THz 3.125/6.25GHz spacing";
               }
               enum "1552.55" {
                 description "1552.55 nm/193.096875 THz 3.125GHz spacing";
               }
               enum "1552.52" {
                 description "1552.52 nm/193.100000 THz 3.125/6.25/12.5/100GHz spacing";
               }
               enum "1552.50" {
                 description "1552.50 nm/193.103125 THz 3.125GHz spacing";
               }
               enum "1552.47" {
                 description "1552.47 nm/193.106250 THz 3.125/6.25GHz spacing";
               }
               enum "1552.45" {
                 description "1552.45 nm/193.109375 THz 3.125GHz spacing";
               }
               enum "1552.42" {
                 description "1552.42 nm/193.112500 THz 3.125/6.25/12.5GHz spacing";
               }
               enum "1552.40" {
                 description "1552.40 nm/193.115625 THz 3.125GHz spacing";
               }
               enum "1552.37" {
                 description "1552.37 nm/193.118750 THz 3.125/6.25GHz spacing";
               }
               enum "1552.35" {
                 description "1552.35 nm/193.121875 THz 3.125GHz spacing";
               }
               enum "1552.32" {
                 description "1552.32 nm/193.125000 THz 3.125/6.25/12.5/75GHz spacing";
               }
               enum "1552.30" {
                 description "1552.30 nm/193.128125 THz 3.125GHz spacing";
               }
               enum "1552.27" {
                 description "1552.27 nm/193.131250 THz 3.125/6.25GHz spacing";
               }
               enum "1552.25" {
                 description "1552.25 nm/193.134375 THz 3.125GHz spacing";
               }
               enum "1552.22" {
                 description "1552.22 nm/193.137500 THz 3.125/6.25/12.5GHz spacing";
               }
               enum "1552.20" {
                 description "1552.20 nm/193.140625 THz 3.125GHz spacing";
               }
               enum "1552.17" {
                 description "1552.17 nm/193.143750 THz 3.125/6.25GHz spacing";
               }
               enum "1552.15" {
                 description "1552.15 nm/193.146875 THz 3.125GHz spacing";
               }
               enum "1552.12" {
                 description "1552.12 nm/193.150000 THz 3.125/6.25/12.5/50GHz spacing";
               }
               enum "1552.10" {
                 description "1552.10 nm/193.153125 THz 3.125GHz spacing";
               }
               enum "1552.07" {
                 description "1552.07 nm/193.156250 THz 3.125/6.25GHz spacing";
               }
               enum "1552.05" {
                 description "1552.05 nm/193.159375 THz 3.125GHz spacing";
               }
               enum "1552.02" {
                 description "1552.02 nm/193.162500 THz 3.125/6.25/12.5GHz spacing";
               }
               enum "1552.00" {
                 description "1552.00 nm/193.165625 THz 3.125GHz spacing";
               }
               enum "1551.97" {
                 description "1551.97 nm/193.168750 THz 3.125/6.25GHz spacing";
               }
               enum "1551.95" {
                 description "1551.95 nm/193.171875 THz 3.125GHz spacing";
               }
               enum "1551.92" {
                 description "1551.92 nm/193.175000 THz 3.125/6.25/12.5GHz spacing";
               }
               enum "1551.90" {
                 description "1551.90 nm/193.178125 THz 3.125GHz spacing";
               }
               enum "1551.87" {
                 description "1551.87 nm/193.181250 THz 3.125/6.25GHz spacing";
               }
               enum "1551.85" {
                 description "1551.85 nm/193.184375 THz 3.125GHz spacing";
               }
               enum "1551.82" {
                 description "1551.82 nm/193.187500 THz 3.125/6.25/12.5GHz spacing";
               }
               enum "1551.80" {
                 description "1551.80 nm/193.190625 THz 3.125GHz spacing";
               }
               enum "1551.77" {
                 description "1551.77 nm/193.193750 THz 3.125/6.25GHz spacing";
               }
               enum "1551.75" {
                 description "1551.75 nm/193.196875 THz 3.125GHz spacing";
               }
               enum "1551.72" {
                 description "1551.72 nm/193.200000 THz 3.125/6.25/12.5/50/75/100GHz spacing";
               }
               enum "1551.70" {
                 description "1551.70 nm/193.203125 THz 3.125GHz spacing";
               }
               enum "1551.67" {
                 description "1551.67 nm/193.206250 THz 3.125/6.25GHz spacing";
               }
               enum "1551.65" {
                 description "1551.65 nm/193.209375 THz 3.125GHz spacing";
               }
               enum "1551.62" {
                 description "1551.62 nm/193.212500 THz 3.125/6.25/12.5GHz spacing";
               }
               enum "1551.60" {
                 description "1551.60 nm/193.215625 THz 3.125GHz spacing";
               }
               enum "1551.57" {
                 description "1551.57 nm/193.218750 THz 3.125/6.25GHz spacing";
               }
               enum "1551.55" {
                 description "1551.55 nm/193.221875 THz 3.125GHz spacing";
               }
               enum "1551.52" {
                 description "1551.52 nm/193.225000 THz 3.125/6.25/12.5GHz spacing";
               }
               enum "1551.49" {
                 description "1551.49 nm/193.228125 THz 3.125GHz spacing";
               }
               enum "1551.47" {
                 description "1551.47 nm/193.231250 THz 3.125/6.25GHz spacing";
               }
               enum "1551.44" {
                 description "1551.44 nm/193.234375 THz 3.125GHz spacing";
               }
               enum "1551.42" {
                 description "1551.42 nm/193.237500 THz 3.125/6.25/12.5GHz spacing";
               }
               enum "1551.39" {
                 description "1551.39 nm/193.240625 THz 3.125GHz spacing";
               }
               enum "1551.37" {
                 description "1551.37 nm/193.243750 THz 3.125/6.25GHz spacing";
               }
               enum "1551.34" {
                 description "1551.34 nm/193.246875 THz 3.125GHz spacing";
               }
               enum "1551.32" {
                 description "1551.32 nm/193.250000 THz 3.125/6.25/12.5/50GHz spacing";
               }
               enum "1551.29" {
                 description "1551.29 nm/193.253125 THz 3.125GHz spacing";
               }
               enum "1551.27" {
                 description "1551.27 nm/193.256250 THz 3.125/6.25GHz spacing";
               }
               enum "1551.24" {
                 description "1551.24 nm/193.259375 THz 3.125GHz spacing";
               }
               enum "1551.22" {
                 description "1551.22 nm/193.262500 THz 3.125/6.25/12.5GHz spacing";
               }
               enum "1551.19" {
                 description "1551.19 nm/193.265625 THz 3.125GHz spacing";
               }
               enum "1551.17" {
                 description "1551.17 nm/193.268750 THz 3.125/6.25GHz spacing";
               }
               enum "1551.14" {
                 description "1551.14 nm/193.271875 THz 3.125GHz spacing";
               }
               enum "1551.12" {
                 description "1551.12 nm/193.275000 THz 3.125/6.25/12.5/75GHz spacing";
               }
               enum "1551.09" {
                 description "1551.09 nm/193.278125 THz 3.125GHz spacing";
               }
               enum "1551.07" {
                 description "1551.07 nm/193.281250 THz 3.125/6.25GHz spacing";
               }
               enum "1551.04" {
                 description "1551.04 nm/193.284375 THz 3.125GHz spacing";
               }
               enum "1551.02" {
                 description "1551.02 nm/193.287500 THz 3.125/6.25/12.5GHz spacing";
               }
               enum "1550.99" {
                 description "1550.99 nm/193.290625 THz 3.125GHz spacing";
               }
               enum "1550.97" {
                 description "1550.97 nm/193.293750 THz 3.125/6.25GHz spacing";
               }
               enum "1550.94" {
                 description "1550.94 nm/193.296875 THz 3.125GHz spacing";
               }
               enum "1550.92" {
                 description "1550.92 nm/193.300000 THz 3.125/6.25/12.5/100GHz spacing";
               }
               enum "1550.89" {
                 description "1550.89 nm/193.303125 THz 3.125GHz spacing";
               }
               enum "1550.87" {
                 description "1550.87 nm/193.306250 THz 3.125/6.25GHz spacing";
               }
               enum "1550.84" {
                 description "1550.84 nm/193.309375 THz 3.125GHz spacing";
               }
               enum "1550.82" {
                 description "1550.82 nm/193.312500 THz 3.125/6.25/12.5GHz spacing";
               }
               enum "1550.79" {
                 description "1550.79 nm/193.315625 THz 3.125GHz spacing";
               }
               enum "1550.77" {
                 description "1550.77 nm/193.318750 THz 3.125/6.25GHz spacing";
               }
               enum "1550.74" {
                 description "1550.74 nm/193.321875 THz 3.125GHz spacing";
               }
               enum "1550.72" {
                 description "1550.72 nm/193.325000 THz 3.125/6.25/12.5GHz spacing";
               }
               enum "1550.69" {
                 description "1550.69 nm/193.328125 THz 3.125GHz spacing";
               }
               enum "1550.67" {
                 description "1550.67 nm/193.331250 THz 3.125/6.25GHz spacing";
               }
               enum "1550.64" {
                 description "1550.64 nm/193.334375 THz 3.125GHz spacing";
               }
               enum "1550.62" {
                 description "1550.62 nm/193.337500 THz 3.125/6.25/12.5GHz spacing";
               }
               enum "1550.59" {
                 description "1550.59 nm/193.340625 THz 3.125GHz spacing";
               }
               enum "1550.57" {
                 description "1550.57 nm/193.343750 THz 3.125/6.25GHz spacing";
               }
               enum "1550.54" {
                 description "1550.54 nm/193.346875 THz 3.125GHz spacing";
               }
               enum "1550.52" {
                 description "1550.52 nm/193.350000 THz 3.125/6.25/12.5/50/75GHz spacing";
               }
               enum "1550.49" {
                 description "1550.49 nm/193.353125 THz 3.125GHz spacing";
               }
               enum "1550.47" {
                 description "1550.47 nm/193.356250 THz 3.125/6.25GHz spacing";
               }
               enum "1550.44" {
                 description "1550.44 nm/193.359375 THz 3.125GHz spacing";
               }
               enum "1550.42" {
                 description "1550.42 nm/193.362500 THz 3.125/6.25/12.5GHz spacing";
               }
               enum "1550.39" {
                 description "1550.39 nm/193.365625 THz 3.125GHz spacing";
               }
               enum "1550.37" {
                 description "1550.37 nm/193.368750 THz 3.125/6.25GHz spacing";
               }
               enum "1550.34" {
                 description "1550.34 nm/193.371875 THz 3.125GHz spacing";
               }
               enum "1550.32" {
                 description "1550.32 nm/193.375000 THz 3.125/6.25/12.5GHz spacing";
               }
               enum "1550.29" {
                 description "1550.29 nm/193.378125 THz 3.125GHz spacing";
               }
               enum "1550.27" {
                 description "1550.27 nm/193.381250 THz 3.125/6.25GHz spacing";
               }
               enum "1550.24" {
                 description "1550.24 nm/193.384375 THz 3.125GHz spacing";
               }
               enum "1550.22" {
                 description "1550.22 nm/193.387500 THz 3.125/6.25/12.5GHz spacing";
               }
               enum "1550.19" {
                 description "1550.19 nm/193.390625 THz 3.125GHz spacing";
               }
               enum "1550.17" {
                 description "1550.17 nm/193.393750 THz 3.125/6.25GHz spacing";
               }
               enum "1550.14" {
                 description "1550.14 nm/193.396875 THz 3.125GHz spacing";
               }
               enum "1550.12" {
                 description "1550.12 nm/193.400000 THz 3.125/6.25/12.5/100GHz spacing";
               }
               enum "1550.09" {
                 description "1550.09 nm/193.403125 THz 3.125GHz spacing";
               }
               enum "1550.07" {
                 description "1550.07 nm/193.406250 THz 3.125/6.25GHz spacing";
               }
               enum "1550.04" {
                 description "1550.04 nm/193.409375 THz 3.125GHz spacing";
               }
               enum "1550.02" {
                 description "1550.02 nm/193.412500 THz 3.125/6.25/12.5GHz spacing";
               }
               enum "1549.99" {
                 description "1549.99 nm/193.415625 THz 3.125GHz spacing";
               }
               enum "1549.97" {
                 description "1549.97 nm/193.418750 THz 3.125/6.25GHz spacing";
               }
               enum "1549.94" {
                 description "1549.94 nm/193.421875 THz 3.125GHz spacing";
               }
               enum "1549.92" {
                 description "1549.92 nm/193.425000 THz 3.125/6.25/12.5/75GHz spacing";
               }
               enum "1549.89" {
                 description "1549.89 nm/193.428125 THz 3.125GHz spacing";
               }
               enum "1549.87" {
                 description "1549.87 nm/193.431250 THz 3.125/6.25GHz spacing";
               }
               enum "1549.84" {
                 description "1549.84 nm/193.434375 THz 3.125GHz spacing";
               }
               enum "1549.82" {
                 description "1549.82 nm/193.437500 THz 3.125/6.25/12.5GHz spacing";
               }
               enum "1549.79" {
                 description "1549.79 nm/193.440625 THz 3.125GHz spacing";
               }
               enum "1549.77" {
                 description "1549.77 nm/193.443750 THz 3.125/6.25GHz spacing";
               }
               enum "1549.74" {
                 description "1549.74 nm/193.446875 THz 3.125GHz spacing";
               }
               enum "1549.72" {
                 description "1549.72 nm/193.450000 THz 3.125/6.25/12.5/50GHz spacing";
               }
               enum "1549.69" {
                 description "1549.69 nm/193.453125 THz 3.125GHz spacing";
               }
               enum "1549.67" {
                 description "1549.67 nm/193.456250 THz 3.125/6.25GHz spacing";
               }
               enum "1549.64" {
                 description "1549.64 nm/193.459375 THz 3.125GHz spacing";
               }
               enum "1549.62" {
                 description "1549.62 nm/193.462500 THz 3.125/6.25/12.5GHz spacing";
               }
               enum "1549.59" {
                 description "1549.59 nm/193.465625 THz 3.125GHz spacing";
               }
               enum "1549.57" {
                 description "1549.57 nm/193.468750 THz 3.125/6.25GHz spacing";
               }
               enum "1549.54" {
                 description "1549.54 nm/193.471875 THz 3.125GHz spacing";
               }
               enum "1549.52" {
                 description "1549.52 nm/193.475000 THz 3.125/6.25/12.5GHz spacing";
               }
               enum "1549.49" {
                 description "1549.49 nm/193.478125 THz 3.125GHz spacing";
               }
               enum "1549.47" {
                 description "1549.47 nm/193.481250 THz 3.125/6.25GHz spacing";
               }
               enum "1549.44" {
                 description "1549.44 nm/193.484375 THz 3.125GHz spacing";
               }
               enum "1549.42" {
                 description "1549.42 nm/193.487500 THz 3.125/6.25/12.5GHz spacing";
               }
               enum "1549.39" {
                 description "1549.39 nm/193.490625 THz 3.125GHz spacing";
               }
               enum "1549.37" {
                 description "1549.37 nm/193.493750 THz 3.125/6.25GHz spacing";
               }
               enum "1549.34" {
                 description "1549.34 nm/193.496875 THz 3.125GHz spacing";
               }
               enum "1549.32" {
                 description "1549.32 nm/193.500000 THz 3.125/6.25/12.5/50/75/100GHz spacing";
               }
               enum "1549.29" {
                 description "1549.29 nm/193.503125 THz 3.125GHz spacing";
               }
               enum "1549.26" {
                 description "1549.26 nm/193.506250 THz 3.125/6.25GHz spacing";
               }
               enum "1549.24" {
                 description "1549.24 nm/193.509375 THz 3.125GHz spacing";
               }
               enum "1549.21" {
                 description "1549.21 nm/193.512500 THz 3.125/6.25/12.5GHz spacing";
               }
               enum "1549.19" {
                 description "1549.19 nm/193.515625 THz 3.125GHz spacing";
               }
               enum "1549.16" {
                 description "1549.16 nm/193.518750 THz 3.125/6.25GHz spacing";
               }
               enum "1549.14" {
                 description "1549.14 nm/193.521875 THz 3.125GHz spacing";
               }
               enum "1549.11" {
                 description "1549.11 nm/193.525000 THz 3.125/6.25/12.5GHz spacing";
               }
               enum "1549.09" {
                 description "1549.09 nm/193.528125 THz 3.125GHz spacing";
               }
               enum "1549.06" {
                 description "1549.06 nm/193.531250 THz 3.125/6.25GHz spacing";
               }
               enum "1549.04" {
                 description "1549.04 nm/193.534375 THz 3.125GHz spacing";
               }
               enum "1549.01" {
                 description "1549.01 nm/193.537500 THz 3.125/6.25/12.5GHz spacing";
               }
               enum "1548.99" {
                 description "1548.99 nm/193.540625 THz 3.125GHz spacing";
               }
               enum "1548.96" {
                 description "1548.96 nm/193.543750 THz 3.125/6.25GHz spacing";
               }
               enum "1548.94" {
                 description "1548.94 nm/193.546875 THz 3.125GHz spacing";
               }
               enum "1548.91" {
                 description "1548.91 nm/193.550000 THz 3.125/6.25/12.5/50GHz spacing";
               }
               enum "1548.89" {
                 description "1548.89 nm/193.553125 THz 3.125GHz spacing";
               }
               enum "1548.86" {
                 description "1548.86 nm/193.556250 THz 3.125/6.25GHz spacing";
               }
               enum "1548.84" {
                 description "1548.84 nm/193.559375 THz 3.125GHz spacing";
               }
               enum "1548.81" {
                 description "1548.81 nm/193.562500 THz 3.125/6.25/12.5GHz spacing";
               }
               enum "1548.79" {
                 description "1548.79 nm/193.565625 THz 3.125GHz spacing";
               }
               enum "1548.76" {
                 description "1548.76 nm/193.568750 THz 3.125/6.25GHz spacing";
               }
               enum "1548.74" {
                 description "1548.74 nm/193.571875 THz 3.125GHz spacing";
               }
               enum "1548.71" {
                 description "1548.71 nm/193.575000 THz 3.125/6.25/12.5/75GHz spacing";
               }
               enum "1548.69" {
                 description "1548.69 nm/193.578125 THz 3.125GHz spacing";
               }
               enum "1548.66" {
                 description "1548.66 nm/193.581250 THz 3.125/6.25GHz spacing";
               }
               enum "1548.64" {
                 description "1548.64 nm/193.584375 THz 3.125GHz spacing";
               }
               enum "1548.61" {
                 description "1548.61 nm/193.587500 THz 3.125/6.25/12.5GHz spacing";
               }
               enum "1548.59" {
                 description "1548.59 nm/193.590625 THz 3.125GHz spacing";
               }
               enum "1548.56" {
                 description "1548.56 nm/193.593750 THz 3.125/6.25GHz spacing";
               }
               enum "1548.54" {
                 description "1548.54 nm/193.596875 THz 3.125GHz spacing";
               }
               enum "1548.51" {
                 description "1548.51 nm/193.600000 THz 3.125/6.25/12.5/100GHz spacing";
               }
               enum "1548.49" {
                 description "1548.49 nm/193.603125 THz 3.125GHz spacing";
               }
               enum "1548.46" {
                 description "1548.46 nm/193.606250 THz 3.125/6.25GHz spacing";
               }
               enum "1548.44" {
                 description "1548.44 nm/193.609375 THz 3.125GHz spacing";
               }
               enum "1548.41" {
                 description "1548.41 nm/193.612500 THz 3.125/6.25/12.5GHz spacing";
               }
               enum "1548.39" {
                 description "1548.39 nm/193.615625 THz 3.125GHz spacing";
               }
               enum "1548.36" {
                 description "1548.36 nm/193.618750 THz 3.125/6.25GHz spacing";
               }
               enum "1548.34" {
                 description "1548.34 nm/193.621875 THz 3.125GHz spacing";
               }
               enum "1548.31" {
                 description "1548.31 nm/193.625000 THz 3.125/6.25/12.5GHz spacing";
               }
               enum "1548.29" {
                 description "1548.29 nm/193.628125 THz 3.125GHz spacing";
               }
               enum "1548.26" {
                 description "1548.26 nm/193.631250 THz 3.125/6.25GHz spacing";
               }
               enum "1548.24" {
                 description "1548.24 nm/193.634375 THz 3.125GHz spacing";
               }
               enum "1548.21" {
                 description "1548.21 nm/193.637500 THz 3.125/6.25/12.5GHz spacing";
               }
               enum "1548.19" {
                 description "1548.19 nm/193.640625 THz 3.125GHz spacing";
               }
               enum "1548.16" {
                 description "1548.16 nm/193.643750 THz 3.125/6.25GHz spacing";
               }
               enum "1548.14" {
                 description "1548.14 nm/193.646875 THz 3.125GHz spacing";
               }
               enum "1548.11" {
                 description "1548.11 nm/193.650000 THz 3.125/6.25/12.5/50/75GHz spacing";
               }
               enum "1548.09" {
                 description "1548.09 nm/193.653125 THz 3.125GHz spacing";
               }
               enum "1548.06" {
                 description "1548.06 nm/193.656250 THz 3.125/6.25GHz spacing";
               }
               enum "1548.04" {
                 description "1548.04 nm/193.659375 THz 3.125GHz spacing";
               }
               enum "1548.02" {
                 description "1548.02 nm/193.662500 THz 3.125/6.25/12.5GHz spacing";
               }
               enum "1547.99" {
                 description "1547.99 nm/193.665625 THz 3.125GHz spacing";
               }
               enum "1547.97" {
                 description "1547.97 nm/193.668750 THz 3.125/6.25GHz spacing";
               }
               enum "1547.94" {
                 description "1547.94 nm/193.671875 THz 3.125GHz spacing";
               }
               enum "1547.92" {
                 description "1547.92 nm/193.675000 THz 3.125/6.25/12.5GHz spacing";
               }
               enum "1547.89" {
                 description "1547.89 nm/193.678125 THz 3.125GHz spacing";
               }
               enum "1547.87" {
                 description "1547.87 nm/193.681250 THz 3.125/6.25GHz spacing";
               }
               enum "1547.84" {
                 description "1547.84 nm/193.684375 THz 3.125GHz spacing";
               }
               enum "1547.82" {
                 description "1547.82 nm/193.687500 THz 3.125/6.25/12.5GHz spacing";
               }
               enum "1547.79" {
                 description "1547.79 nm/193.690625 THz 3.125GHz spacing";
               }
               enum "1547.77" {
                 description "1547.77 nm/193.693750 THz 3.125/6.25GHz spacing";
               }
               enum "1547.74" {
                 description "1547.74 nm/193.696875 THz 3.125GHz spacing";
               }
               enum "1547.72" {
                 description "1547.72 nm/193.700000 THz 3.125/6.25/12.5/100GHz spacing";
               }
               enum "1547.69" {
                 description "1547.69 nm/193.703125 THz 3.125GHz spacing";
               }
               enum "1547.67" {
                 description "1547.67 nm/193.706250 THz 3.125/6.25GHz spacing";
               }
               enum "1547.64" {
                 description "1547.64 nm/193.709375 THz 3.125GHz spacing";
               }
               enum "1547.62" {
                 description "1547.62 nm/193.712500 THz 3.125/6.25/12.5GHz spacing";
               }
               enum "1547.59" {
                 description "1547.59 nm/193.715625 THz 3.125GHz spacing";
               }
               enum "1547.57" {
                 description "1547.57 nm/193.718750 THz 3.125/6.25GHz spacing";
               }
               enum "1547.54" {
                 description "1547.54 nm/193.721875 THz 3.125GHz spacing";
               }
               enum "1547.52" {
                 description "1547.52 nm/193.725000 THz 3.125/6.25/12.5/75GHz spacing";
               }
               enum "1547.49" {
                 description "1547.49 nm/193.728125 THz 3.125GHz spacing";
               }
               enum "1547.47" {
                 description "1547.47 nm/193.731250 THz 3.125/6.25GHz spacing";
               }
               enum "1547.44" {
                 description "1547.44 nm/193.734375 THz 3.125GHz spacing";
               }
               enum "1547.42" {
                 description "1547.42 nm/193.737500 THz 3.125/6.25/12.5GHz spacing";
               }
               enum "1547.39" {
                 description "1547.39 nm/193.740625 THz 3.125GHz spacing";
               }
               enum "1547.37" {
                 description "1547.37 nm/193.743750 THz 3.125/6.25GHz spacing";
               }
               enum "1547.34" {
                 description "1547.34 nm/193.746875 THz 3.125GHz spacing";
               }
               enum "1547.32" {
                 description "1547.32 nm/193.750000 THz 3.125/6.25/12.5/50GHz spacing";
               }
               enum "1547.29" {
                 description "1547.29 nm/193.753125 THz 3.125GHz spacing";
               }
               enum "1547.27" {
                 description "1547.27 nm/193.756250 THz 3.125/6.25GHz spacing";
               }
               enum "1547.24" {
                 description "1547.24 nm/193.759375 THz 3.125GHz spacing";
               }
               enum "1547.22" {
                 description "1547.22 nm/193.762500 THz 3.125/6.25/12.5GHz spacing";
               }
               enum "1547.19" {
                 description "1547.19 nm/193.765625 THz 3.125GHz spacing";
               }
               enum "1547.17" {
                 description "1547.17 nm/193.768750 THz 3.125/6.25GHz spacing";
               }
               enum "1547.14" {
                 description "1547.14 nm/193.771875 THz 3.125GHz spacing";
               }
               enum "1547.12" {
                 description "1547.12 nm/193.775000 THz 3.125/6.25/12.5GHz spacing";
               }
               enum "1547.09" {
                 description "1547.09 nm/193.778125 THz 3.125GHz spacing";
               }
               enum "1547.07" {
                 description "1547.07 nm/193.781250 THz 3.125/6.25GHz spacing";
               }
               enum "1547.04" {
                 description "1547.04 nm/193.784375 THz 3.125GHz spacing";
               }
               enum "1547.02" {
                 description "1547.02 nm/193.787500 THz 3.125/6.25/12.5GHz spacing";
               }
               enum "1546.99" {
                 description "1546.99 nm/193.790625 THz 3.125GHz spacing";
               }
               enum "1546.97" {
                 description "1546.97 nm/193.793750 THz 3.125/6.25GHz spacing";
               }
               enum "1546.94" {
                 description "1546.94 nm/193.796875 THz 3.125GHz spacing";
               }
               enum "1546.92" {
                 description "1546.92 nm/193.800000 THz 3.125/6.25/12.5/50/75/100GHz spacing";
               }
               enum "1546.89" {
                 description "1546.89 nm/193.803125 THz 3.125GHz spacing";
               }
               enum "1546.87" {
                 description "1546.87 nm/193.806250 THz 3.125/6.25GHz spacing";
               }
               enum "1546.84" {
                 description "1546.84 nm/193.809375 THz 3.125GHz spacing";
               }
               enum "1546.82" {
                 description "1546.82 nm/193.812500 THz 3.125/6.25/12.5GHz spacing";
               }
               enum "1546.79" {
                 description "1546.79 nm/193.815625 THz 3.125GHz spacing";
               }
               enum "1546.77" {
                 description "1546.77 nm/193.818750 THz 3.125/6.25GHz spacing";
               }
               enum "1546.74" {
                 description "1546.74 nm/193.821875 THz 3.125GHz spacing";
               }
               enum "1546.72" {
                 description "1546.72 nm/193.825000 THz 3.125/6.25/12.5GHz spacing";
               }
               enum "1546.69" {
                 description "1546.69 nm/193.828125 THz 3.125GHz spacing";
               }
               enum "1546.67" {
                 description "1546.67 nm/193.831250 THz 3.125/6.25GHz spacing";
               }
               enum "1546.64" {
                 description "1546.64 nm/193.834375 THz 3.125GHz spacing";
               }
               enum "1546.62" {
                 description "1546.62 nm/193.837500 THz 3.125/6.25/12.5GHz spacing";
               }
               enum "1546.59" {
                 description "1546.59 nm/193.840625 THz 3.125GHz spacing";
               }
               enum "1546.57" {
                 description "1546.57 nm/193.843750 THz 3.125/6.25GHz spacing";
               }
               enum "1546.54" {
                 description "1546.54 nm/193.846875 THz 3.125GHz spacing";
               }
               enum "1546.52" {
                 description "1546.52 nm/193.850000 THz 3.125/6.25/12.5/50GHz spacing";
               }
               enum "1546.49" {
                 description "1546.49 nm/193.853125 THz 3.125GHz spacing";
               }
               enum "1546.47" {
                 description "1546.47 nm/193.856250 THz 3.125/6.25GHz spacing";
               }
               enum "1546.44" {
                 description "1546.44 nm/193.859375 THz 3.125GHz spacing";
               }
               enum "1546.42" {
                 description "1546.42 nm/193.862500 THz 3.125/6.25/12.5GHz spacing";
               }
               enum "1546.39" {
                 description "1546.39 nm/193.865625 THz 3.125GHz spacing";
               }
               enum "1546.37" {
                 description "1546.37 nm/193.868750 THz 3.125/6.25GHz spacing";
               }
               enum "1546.34" {
                 description "1546.34 nm/193.871875 THz 3.125GHz spacing";
               }
               enum "1546.32" {
                 description "1546.32 nm/193.875000 THz 3.125/6.25/12.5/75GHz spacing";
               }
               enum "1546.29" {
                 description "1546.29 nm/193.878125 THz 3.125GHz spacing";
               }
               enum "1546.27" {
                 description "1546.27 nm/193.881250 THz 3.125/6.25GHz spacing";
               }
               enum "1546.24" {
                 description "1546.24 nm/193.884375 THz 3.125GHz spacing";
               }
               enum "1546.22" {
                 description "1546.22 nm/193.887500 THz 3.125/6.25/12.5GHz spacing";
               }
               enum "1546.19" {
                 description "1546.19 nm/193.890625 THz 3.125GHz spacing";
               }
               enum "1546.17" {
                 description "1546.17 nm/193.893750 THz 3.125/6.25GHz spacing";
               }
               enum "1546.14" {
                 description "1546.14 nm/193.896875 THz 3.125GHz spacing";
               }
               enum "1546.12" {
                 description "1546.12 nm/193.900000 THz 3.125/6.25/12.5/100GHz spacing";
               }
               enum "1546.09" {
                 description "1546.09 nm/193.903125 THz 3.125GHz spacing";
               }
               enum "1546.07" {
                 description "1546.07 nm/193.906250 THz 3.125/6.25GHz spacing";
               }
               enum "1546.04" {
                 description "1546.04 nm/193.909375 THz 3.125GHz spacing";
               }
               enum "1546.02" {
                 description "1546.02 nm/193.912500 THz 3.125/6.25/12.5GHz spacing";
               }
               enum "1545.99" {
                 description "1545.99 nm/193.915625 THz 3.125GHz spacing";
               }
               enum "1545.97" {
                 description "1545.97 nm/193.918750 THz 3.125/6.25GHz spacing";
               }
               enum "1545.94" {
                 description "1545.94 nm/193.921875 THz 3.125GHz spacing";
               }
               enum "1545.92" {
                 description "1545.92 nm/193.925000 THz 3.125/6.25/12.5GHz spacing";
               }
               enum "1545.89" {
                 description "1545.89 nm/193.928125 THz 3.125GHz spacing";
               }
               enum "1545.87" {
                 description "1545.87 nm/193.931250 THz 3.125/6.25GHz spacing";
               }
               enum "1545.84" {
                 description "1545.84 nm/193.934375 THz 3.125GHz spacing";
               }
               enum "1545.82" {
                 description "1545.82 nm/193.937500 THz 3.125/6.25/12.5GHz spacing";
               }
               enum "1545.80" {
                 description "1545.80 nm/193.940625 THz 3.125GHz spacing";
               }
               enum "1545.77" {
                 description "1545.77 nm/193.943750 THz 3.125/6.25GHz spacing";
               }
               enum "1545.75" {
                 description "1545.75 nm/193.946875 THz 3.125GHz spacing";
               }
               enum "1545.72" {
                 description "1545.72 nm/193.950000 THz 3.125/6.25/12.5/50/75GHz spacing";
               }
               enum "1545.70" {
                 description "1545.70 nm/193.953125 THz 3.125GHz spacing";
               }
               enum "1545.67" {
                 description "1545.67 nm/193.956250 THz 3.125/6.25GHz spacing";
               }
               enum "1545.65" {
                 description "1545.65 nm/193.959375 THz 3.125GHz spacing";
               }
               enum "1545.62" {
                 description "1545.62 nm/193.962500 THz 3.125/6.25/12.5GHz spacing";
               }
               enum "1545.60" {
                 description "1545.60 nm/193.965625 THz 3.125GHz spacing";
               }
               enum "1545.57" {
                 description "1545.57 nm/193.968750 THz 3.125/6.25GHz spacing";
               }
               enum "1545.55" {
                 description "1545.55 nm/193.971875 THz 3.125GHz spacing";
               }
               enum "1545.52" {
                 description "1545.52 nm/193.975000 THz 3.125/6.25/12.5GHz spacing";
               }
               enum "1545.50" {
                 description "1545.50 nm/193.978125 THz 3.125GHz spacing";
               }
               enum "1545.47" {
                 description "1545.47 nm/193.981250 THz 3.125/6.25GHz spacing";
               }
               enum "1545.45" {
                 description "1545.45 nm/193.984375 THz 3.125GHz spacing";
               }
               enum "1545.42" {
                 description "1545.42 nm/193.987500 THz 3.125/6.25/12.5GHz spacing";
               }
               enum "1545.40" {
                 description "1545.40 nm/193.990625 THz 3.125GHz spacing";
               }
               enum "1545.37" {
                 description "1545.37 nm/193.993750 THz 3.125/6.25GHz spacing";
               }
               enum "1545.35" {
                 description "1545.35 nm/193.996875 THz 3.125GHz spacing";
               }
               enum "1545.32" {
                 description "1545.32 nm/194.000000 THz 3.125/6.25/12.5/100GHz spacing";
               }
               enum "1545.30" {
                 description "1545.30 nm/194.003125 THz 3.125GHz spacing";
               }
               enum "1545.27" {
                 description "1545.27 nm/194.006250 THz 3.125/6.25GHz spacing";
               }
               enum "1545.25" {
                 description "1545.25 nm/194.009375 THz 3.125GHz spacing";
               }
               enum "1545.22" {
                 description "1545.22 nm/194.012500 THz 3.125/6.25/12.5GHz spacing";
               }
               enum "1545.20" {
                 description "1545.20 nm/194.015625 THz 3.125GHz spacing";
               }
               enum "1545.17" {
                 description "1545.17 nm/194.018750 THz 3.125/6.25GHz spacing";
               }
               enum "1545.15" {
                 description "1545.15 nm/194.021875 THz 3.125GHz spacing";
               }
               enum "1545.12" {
                 description "1545.12 nm/194.025000 THz 3.125/6.25/12.5/75GHz spacing";
               }
               enum "1545.10" {
                 description "1545.10 nm/194.028125 THz 3.125GHz spacing";
               }
               enum "1545.07" {
                 description "1545.07 nm/194.031250 THz 3.125/6.25GHz spacing";
               }
               enum "1545.05" {
                 description "1545.05 nm/194.034375 THz 3.125GHz spacing";
               }
               enum "1545.02" {
                 description "1545.02 nm/194.037500 THz 3.125/6.25/12.5GHz spacing";
               }
               enum "1545.00" {
                 description "1545.00 nm/194.040625 THz 3.125GHz spacing";
               }
               enum "1544.97" {
                 description "1544.97 nm/194.043750 THz 3.125/6.25GHz spacing";
               }
               enum "1544.95" {
                 description "1544.95 nm/194.046875 THz 3.125GHz spacing";
               }
               enum "1544.92" {
                 description "1544.92 nm/194.050000 THz 3.125/6.25/12.5/50GHz spacing";
               }
               enum "1544.90" {
                 description "1544.90 nm/194.053125 THz 3.125GHz spacing";
               }
               enum "1544.87" {
                 description "1544.87 nm/194.056250 THz 3.125/6.25GHz spacing";
               }
               enum "1544.85" {
                 description "1544.85 nm/194.059375 THz 3.125GHz spacing";
               }
               enum "1544.82" {
                 description "1544.82 nm/194.062500 THz 3.125/6.25/12.5GHz spacing";
               }
               enum "1544.80" {
                 description "1544.80 nm/194.065625 THz 3.125GHz spacing";
               }
               enum "1544.77" {
                 description "1544.77 nm/194.068750 THz 3.125/6.25GHz spacing";
               }
               enum "1544.75" {
                 description "1544.75 nm/194.071875 THz 3.125GHz spacing";
               }
               enum "1544.72" {
                 description "1544.72 nm/194.075000 THz 3.125/6.25/12.5GHz spacing";
               }
               enum "1544.70" {
                 description "1544.70 nm/194.078125 THz 3.125GHz spacing";
               }
               enum "1544.68" {
                 description "1544.68 nm/194.081250 THz 3.125/6.25GHz spacing";
               }
               enum "1544.65" {
                 description "1544.65 nm/194.084375 THz 3.125GHz spacing";
               }
               enum "1544.63" {
                 description "1544.63 nm/194.087500 THz 3.125/6.25/12.5GHz spacing";
               }
               enum "1544.60" {
                 description "1544.60 nm/194.090625 THz 3.125GHz spacing";
               }
               enum "1544.58" {
                 description "1544.58 nm/194.093750 THz 3.125/6.25GHz spacing";
               }
               enum "1544.55" {
                 description "1544.55 nm/194.096875 THz 3.125GHz spacing";
               }
               enum "1544.53" {
                 description "1544.53 nm/194.100000 THz 3.125/6.25/12.5/50/75/100GHz spacing";
               }
               enum "1544.50" {
                 description "1544.50 nm/194.103125 THz 3.125GHz spacing";
               }
               enum "1544.48" {
                 description "1544.48 nm/194.106250 THz 3.125/6.25GHz spacing";
               }
               enum "1544.45" {
                 description "1544.45 nm/194.109375 THz 3.125GHz spacing";
               }
               enum "1544.43" {
                 description "1544.43 nm/194.112500 THz 3.125/6.25/12.5GHz spacing";
               }
               enum "1544.40" {
                 description "1544.40 nm/194.115625 THz 3.125GHz spacing";
               }
               enum "1544.38" {
                 description "1544.38 nm/194.118750 THz 3.125/6.25GHz spacing";
               }
               enum "1544.35" {
                 description "1544.35 nm/194.121875 THz 3.125GHz spacing";
               }
               enum "1544.33" {
                 description "1544.33 nm/194.125000 THz 3.125/6.25/12.5GHz spacing";
               }
               enum "1544.30" {
                 description "1544.30 nm/194.128125 THz 3.125GHz spacing";
               }
               enum "1544.28" {
                 description "1544.28 nm/194.131250 THz 3.125/6.25GHz spacing";
               }
               enum "1544.25" {
                 description "1544.25 nm/194.134375 THz 3.125GHz spacing";
               }
               enum "1544.23" {
                 description "1544.23 nm/194.137500 THz 3.125/6.25/12.5GHz spacing";
               }
               enum "1544.20" {
                 description "1544.20 nm/194.140625 THz 3.125GHz spacing";
               }
               enum "1544.18" {
                 description "1544.18 nm/194.143750 THz 3.125/6.25GHz spacing";
               }
               enum "1544.15" {
                 description "1544.15 nm/194.146875 THz 3.125GHz spacing";
               }
               enum "1544.13" {
                 description "1544.13 nm/194.150000 THz 3.125/6.25/12.5/50GHz spacing";
               }
               enum "1544.10" {
                 description "1544.10 nm/194.153125 THz 3.125GHz spacing";
               }
               enum "1544.08" {
                 description "1544.08 nm/194.156250 THz 3.125/6.25GHz spacing";
               }
               enum "1544.05" {
                 description "1544.05 nm/194.159375 THz 3.125GHz spacing";
               }
               enum "1544.03" {
                 description "1544.03 nm/194.162500 THz 3.125/6.25/12.5GHz spacing";
               }
               enum "1544.00" {
                 description "1544.00 nm/194.165625 THz 3.125GHz spacing";
               }
               enum "1543.98" {
                 description "1543.98 nm/194.168750 THz 3.125/6.25GHz spacing";
               }
               enum "1543.95" {
                 description "1543.95 nm/194.171875 THz 3.125GHz spacing";
               }
               enum "1543.93" {
                 description "1543.93 nm/194.175000 THz 3.125/6.25/12.5/75GHz spacing";
               }
               enum "1543.90" {
                 description "1543.90 nm/194.178125 THz 3.125GHz spacing";
               }
               enum "1543.88" {
                 description "1543.88 nm/194.181250 THz 3.125/6.25GHz spacing";
               }
               enum "1543.85" {
                 description "1543.85 nm/194.184375 THz 3.125GHz spacing";
               }
               enum "1543.83" {
                 description "1543.83 nm/194.187500 THz 3.125/6.25/12.5GHz spacing";
               }
               enum "1543.81" {
                 description "1543.81 nm/194.190625 THz 3.125GHz spacing";
               }
               enum "1543.78" {
                 description "1543.78 nm/194.193750 THz 3.125/6.25GHz spacing";
               }
               enum "1543.76" {
                 description "1543.76 nm/194.196875 THz 3.125GHz spacing";
               }
               enum "1543.73" {
                 description "1543.73 nm/194.200000 THz 3.125/6.25/12.5/100GHz spacing";
               }
               enum "1543.71" {
                 description "1543.71 nm/194.203125 THz 3.125GHz spacing";
               }
               enum "1543.68" {
                 description "1543.68 nm/194.206250 THz 3.125/6.25GHz spacing";
               }
               enum "1543.66" {
                 description "1543.66 nm/194.209375 THz 3.125GHz spacing";
               }
               enum "1543.63" {
                 description "1543.63 nm/194.212500 THz 3.125/6.25/12.5GHz spacing";
               }
               enum "1543.61" {
                 description "1543.61 nm/194.215625 THz 3.125GHz spacing";
               }
               enum "1543.58" {
                 description "1543.58 nm/194.218750 THz 3.125/6.25GHz spacing";
               }
               enum "1543.56" {
                 description "1543.56 nm/194.221875 THz 3.125GHz spacing";
               }
               enum "1543.53" {
                 description "1543.53 nm/194.225000 THz 3.125/6.25/12.5GHz spacing";
               }
               enum "1543.51" {
                 description "1543.51 nm/194.228125 THz 3.125GHz spacing";
               }
               enum "1543.48" {
                 description "1543.48 nm/194.231250 THz 3.125/6.25GHz spacing";
               }
               enum "1543.46" {
                 description "1543.46 nm/194.234375 THz 3.125GHz spacing";
               }
               enum "1543.43" {
                 description "1543.43 nm/194.237500 THz 3.125/6.25/12.5GHz spacing";
               }
               enum "1543.41" {
                 description "1543.41 nm/194.240625 THz 3.125GHz spacing";
               }
               enum "1543.38" {
                 description "1543.38 nm/194.243750 THz 3.125/6.25GHz spacing";
               }
               enum "1543.36" {
                 description "1543.36 nm/194.246875 THz 3.125GHz spacing";
               }
               enum "1543.33" {
                 description "1543.33 nm/194.250000 THz 3.125/6.25/12.5/50/75GHz spacing";
               }
               enum "1543.31" {
                 description "1543.31 nm/194.253125 THz 3.125GHz spacing";
               }
               enum "1543.28" {
                 description "1543.28 nm/194.256250 THz 3.125/6.25GHz spacing";
               }
               enum "1543.26" {
                 description "1543.26 nm/194.259375 THz 3.125GHz spacing";
               }
               enum "1543.23" {
                 description "1543.23 nm/194.262500 THz 3.125/6.25/12.5GHz spacing";
               }
               enum "1543.21" {
                 description "1543.21 nm/194.265625 THz 3.125GHz spacing";
               }
               enum "1543.18" {
                 description "1543.18 nm/194.268750 THz 3.125/6.25GHz spacing";
               }
               enum "1543.16" {
                 description "1543.16 nm/194.271875 THz 3.125GHz spacing";
               }
               enum "1543.13" {
                 description "1543.13 nm/194.275000 THz 3.125/6.25/12.5GHz spacing";
               }
               enum "1543.11" {
                 description "1543.11 nm/194.278125 THz 3.125GHz spacing";
               }
               enum "1543.08" {
                 description "1543.08 nm/194.281250 THz 3.125/6.25GHz spacing";
               }
               enum "1543.06" {
                 description "1543.06 nm/194.284375 THz 3.125GHz spacing";
               }
               enum "1543.04" {
                 description "1543.04 nm/194.287500 THz 3.125/6.25/12.5GHz spacing";
               }
               enum "1543.01" {
                 description "1543.01 nm/194.290625 THz 3.125GHz spacing";
               }
               enum "1542.99" {
                 description "1542.99 nm/194.293750 THz 3.125/6.25GHz spacing";
               }
               enum "1542.96" {
                 description "1542.96 nm/194.296875 THz 3.125GHz spacing";
               }
               enum "1542.94" {
                 description "1542.94 nm/194.300000 THz 3.125/6.25/12.5/100GHz spacing";
               }
               enum "1542.91" {
                 description "1542.91 nm/194.303125 THz 3.125GHz spacing";
               }
               enum "1542.89" {
                 description "1542.89 nm/194.306250 THz 3.125/6.25GHz spacing";
               }
               enum "1542.86" {
                 description "1542.86 nm/194.309375 THz 3.125GHz spacing";
               }
               enum "1542.84" {
                 description "1542.84 nm/194.312500 THz 3.125/6.25/12.5GHz spacing";
               }
               enum "1542.81" {
                 description "1542.81 nm/194.315625 THz 3.125GHz spacing";
               }
               enum "1542.79" {
                 description "1542.79 nm/194.318750 THz 3.125/6.25GHz spacing";
               }
               enum "1542.76" {
                 description "1542.76 nm/194.321875 THz 3.125GHz spacing";
               }
               enum "1542.74" {
                 description "1542.74 nm/194.325000 THz 3.125/6.25/12.5/75GHz spacing";
               }
               enum "1542.71" {
                 description "1542.71 nm/194.328125 THz 3.125GHz spacing";
               }
               enum "1542.69" {
                 description "1542.69 nm/194.331250 THz 3.125/6.25GHz spacing";
               }
               enum "1542.66" {
                 description "1542.66 nm/194.334375 THz 3.125GHz spacing";
               }
               enum "1542.64" {
                 description "1542.64 nm/194.337500 THz 3.125/6.25/12.5GHz spacing";
               }
               enum "1542.61" {
                 description "1542.61 nm/194.340625 THz 3.125GHz spacing";
               }
               enum "1542.59" {
                 description "1542.59 nm/194.343750 THz 3.125/6.25GHz spacing";
               }
               enum "1542.56" {
                 description "1542.56 nm/194.346875 THz 3.125GHz spacing";
               }
               enum "1542.54" {
                 description "1542.54 nm/194.350000 THz 3.125/6.25/12.5/50GHz spacing";
               }
               enum "1542.51" {
                 description "1542.51 nm/194.353125 THz 3.125GHz spacing";
               }
               enum "1542.49" {
                 description "1542.49 nm/194.356250 THz 3.125/6.25GHz spacing";
               }
               enum "1542.46" {
                 description "1542.46 nm/194.359375 THz 3.125GHz spacing";
               }
               enum "1542.44" {
                 description "1542.44 nm/194.362500 THz 3.125/6.25/12.5GHz spacing";
               }
               enum "1542.42" {
                 description "1542.42 nm/194.365625 THz 3.125GHz spacing";
               }
               enum "1542.39" {
                 description "1542.39 nm/194.368750 THz 3.125/6.25GHz spacing";
               }
               enum "1542.37" {
                 description "1542.37 nm/194.371875 THz 3.125GHz spacing";
               }
               enum "1542.34" {
                 description "1542.34 nm/194.375000 THz 3.125/6.25/12.5GHz spacing";
               }
               enum "1542.32" {
                 description "1542.32 nm/194.378125 THz 3.125GHz spacing";
               }
               enum "1542.29" {
                 description "1542.29 nm/194.381250 THz 3.125/6.25GHz spacing";
               }
               enum "1542.27" {
                 description "1542.27 nm/194.384375 THz 3.125GHz spacing";
               }
               enum "1542.24" {
                 description "1542.24 nm/194.387500 THz 3.125/6.25/12.5GHz spacing";
               }
               enum "1542.22" {
                 description "1542.22 nm/194.390625 THz 3.125GHz spacing";
               }
               enum "1542.19" {
                 description "1542.19 nm/194.393750 THz 3.125/6.25GHz spacing";
               }
               enum "1542.17" {
                 description "1542.17 nm/194.396875 THz 3.125GHz spacing";
               }
               enum "1542.14" {
                 description "1542.14 nm/194.400000 THz 3.125/6.25/12.5/50/75/100GHz spacing";
               }
               enum "1542.12" {
                 description "1542.12 nm/194.403125 THz 3.125GHz spacing";
               }
               enum "1542.09" {
                 description "1542.09 nm/194.406250 THz 3.125/6.25GHz spacing";
               }
               enum "1542.07" {
                 description "1542.07 nm/194.409375 THz 3.125GHz spacing";
               }
               enum "1542.04" {
                 description "1542.04 nm/194.412500 THz 3.125/6.25/12.5GHz spacing";
               }
               enum "1542.02" {
                 description "1542.02 nm/194.415625 THz 3.125GHz spacing";
               }
               enum "1541.99" {
                 description "1541.99 nm/194.418750 THz 3.125/6.25GHz spacing";
               }
               enum "1541.97" {
                 description "1541.97 nm/194.421875 THz 3.125GHz spacing";
               }
               enum "1541.94" {
                 description "1541.94 nm/194.425000 THz 3.125/6.25/12.5GHz spacing";
               }
               enum "1541.92" {
                 description "1541.92 nm/194.428125 THz 3.125GHz spacing";
               }
               enum "1541.89" {
                 description "1541.89 nm/194.431250 THz 3.125/6.25GHz spacing";
               }
               enum "1541.87" {
                 description "1541.87 nm/194.434375 THz 3.125GHz spacing";
               }
               enum "1541.84" {
                 description "1541.84 nm/194.437500 THz 3.125/6.25/12.5GHz spacing";
               }
               enum "1541.82" {
                 description "1541.82 nm/194.440625 THz 3.125GHz spacing";
               }
               enum "1541.80" {
                 description "1541.80 nm/194.443750 THz 3.125/6.25GHz spacing";
               }
               enum "1541.77" {
                 description "1541.77 nm/194.446875 THz 3.125GHz spacing";
               }
               enum "1541.75" {
                 description "1541.75 nm/194.450000 THz 3.125/6.25/12.5/50GHz spacing";
               }
               enum "1541.72" {
                 description "1541.72 nm/194.453125 THz 3.125GHz spacing";
               }
               enum "1541.70" {
                 description "1541.70 nm/194.456250 THz 3.125/6.25GHz spacing";
               }
               enum "1541.67" {
                 description "1541.67 nm/194.459375 THz 3.125GHz spacing";
               }
               enum "1541.65" {
                 description "1541.65 nm/194.462500 THz 3.125/6.25/12.5GHz spacing";
               }
               enum "1541.62" {
                 description "1541.62 nm/194.465625 THz 3.125GHz spacing";
               }
               enum "1541.60" {
                 description "1541.60 nm/194.468750 THz 3.125/6.25GHz spacing";
               }
               enum "1541.57" {
                 description "1541.57 nm/194.471875 THz 3.125GHz spacing";
               }
               enum "1541.55" {
                 description "1541.55 nm/194.475000 THz 3.125/6.25/12.5/75GHz spacing";
               }
               enum "1541.52" {
                 description "1541.52 nm/194.478125 THz 3.125GHz spacing";
               }
               enum "1541.50" {
                 description "1541.50 nm/194.481250 THz 3.125/6.25GHz spacing";
               }
               enum "1541.47" {
                 description "1541.47 nm/194.484375 THz 3.125GHz spacing";
               }
               enum "1541.45" {
                 description "1541.45 nm/194.487500 THz 3.125/6.25/12.5GHz spacing";
               }
               enum "1541.42" {
                 description "1541.42 nm/194.490625 THz 3.125GHz spacing";
               }
               enum "1541.40" {
                 description "1541.40 nm/194.493750 THz 3.125/6.25GHz spacing";
               }
               enum "1541.37" {
                 description "1541.37 nm/194.496875 THz 3.125GHz spacing";
               }
               enum "1541.35" {
                 description "1541.35 nm/194.500000 THz 3.125/6.25/12.5/100GHz spacing";
               }
               enum "1541.32" {
                 description "1541.32 nm/194.503125 THz 3.125GHz spacing";
               }
               enum "1541.30" {
                 description "1541.30 nm/194.506250 THz 3.125/6.25GHz spacing";
               }
               enum "1541.28" {
                 description "1541.28 nm/194.509375 THz 3.125GHz spacing";
               }
               enum "1541.25" {
                 description "1541.25 nm/194.512500 THz 3.125/6.25/12.5GHz spacing";
               }
               enum "1541.23" {
                 description "1541.23 nm/194.515625 THz 3.125GHz spacing";
               }
               enum "1541.20" {
                 description "1541.20 nm/194.518750 THz 3.125/6.25GHz spacing";
               }
               enum "1541.18" {
                 description "1541.18 nm/194.521875 THz 3.125GHz spacing";
               }
               enum "1541.15" {
                 description "1541.15 nm/194.525000 THz 3.125/6.25/12.5GHz spacing";
               }
               enum "1541.13" {
                 description "1541.13 nm/194.528125 THz 3.125GHz spacing";
               }
               enum "1541.10" {
                 description "1541.10 nm/194.531250 THz 3.125/6.25GHz spacing";
               }
               enum "1541.08" {
                 description "1541.08 nm/194.534375 THz 3.125GHz spacing";
               }
               enum "1541.05" {
                 description "1541.05 nm/194.537500 THz 3.125/6.25/12.5GHz spacing";
               }
               enum "1541.03" {
                 description "1541.03 nm/194.540625 THz 3.125GHz spacing";
               }
               enum "1541.00" {
                 description "1541.00 nm/194.543750 THz 3.125/6.25GHz spacing";
               }
               enum "1540.98" {
                 description "1540.98 nm/194.546875 THz 3.125GHz spacing";
               }
               enum "1540.95" {
                 description "1540.95 nm/194.550000 THz 3.125/6.25/12.5/50/75GHz spacing";
               }
               enum "1540.93" {
                 description "1540.93 nm/194.553125 THz 3.125GHz spacing";
               }
               enum "1540.90" {
                 description "1540.90 nm/194.556250 THz 3.125/6.25GHz spacing";
               }
               enum "1540.88" {
                 description "1540.88 nm/194.559375 THz 3.125GHz spacing";
               }
               enum "1540.85" {
                 description "1540.85 nm/194.562500 THz 3.125/6.25/12.5GHz spacing";
               }
               enum "1540.83" {
                 description "1540.83 nm/194.565625 THz 3.125GHz spacing";
               }
               enum "1540.80" {
                 description "1540.80 nm/194.568750 THz 3.125/6.25GHz spacing";
               }
               enum "1540.78" {
                 description "1540.78 nm/194.571875 THz 3.125GHz spacing";
               }
               enum "1540.76" {
                 description "1540.76 nm/194.575000 THz 3.125/6.25/12.5GHz spacing";
               }
               enum "1540.73" {
                 description "1540.73 nm/194.578125 THz 3.125GHz spacing";
               }
               enum "1540.71" {
                 description "1540.71 nm/194.581250 THz 3.125/6.25GHz spacing";
               }
               enum "1540.68" {
                 description "1540.68 nm/194.584375 THz 3.125GHz spacing";
               }
               enum "1540.66" {
                 description "1540.66 nm/194.587500 THz 3.125/6.25/12.5GHz spacing";
               }
               enum "1540.63" {
                 description "1540.63 nm/194.590625 THz 3.125GHz spacing";
               }
               enum "1540.61" {
                 description "1540.61 nm/194.593750 THz 3.125/6.25GHz spacing";
               }
               enum "1540.58" {
                 description "1540.58 nm/194.596875 THz 3.125GHz spacing";
               }
               enum "1540.56" {
                 description "1540.56 nm/194.600000 THz 3.125/6.25/12.5/100GHz spacing";
               }
               enum "1540.53" {
                 description "1540.53 nm/194.603125 THz 3.125GHz spacing";
               }
               enum "1540.51" {
                 description "1540.51 nm/194.606250 THz 3.125/6.25GHz spacing";
               }
               enum "1540.48" {
                 description "1540.48 nm/194.609375 THz 3.125GHz spacing";
               }
               enum "1540.46" {
                 description "1540.46 nm/194.612500 THz 3.125/6.25/12.5GHz spacing";
               }
               enum "1540.43" {
                 description "1540.43 nm/194.615625 THz 3.125GHz spacing";
               }
               enum "1540.41" {
                 description "1540.41 nm/194.618750 THz 3.125/6.25GHz spacing";
               }
               enum "1540.38" {
                 description "1540.38 nm/194.621875 THz 3.125GHz spacing";
               }
               enum "1540.36" {
                 description "1540.36 nm/194.625000 THz 3.125/6.25/12.5/75GHz spacing";
               }
               enum "1540.33" {
                 description "1540.33 nm/194.628125 THz 3.125GHz spacing";
               }
               enum "1540.31" {
                 description "1540.31 nm/194.631250 THz 3.125/6.25GHz spacing";
               }
               enum "1540.29" {
                 description "1540.29 nm/194.634375 THz 3.125GHz spacing";
               }
               enum "1540.26" {
                 description "1540.26 nm/194.637500 THz 3.125/6.25/12.5GHz spacing";
               }
               enum "1540.24" {
                 description "1540.24 nm/194.640625 THz 3.125GHz spacing";
               }
               enum "1540.21" {
                 description "1540.21 nm/194.643750 THz 3.125/6.25GHz spacing";
               }
               enum "1540.19" {
                 description "1540.19 nm/194.646875 THz 3.125GHz spacing";
               }
               enum "1540.16" {
                 description "1540.16 nm/194.650000 THz 3.125/6.25/12.5/50GHz spacing";
               }
               enum "1540.14" {
                 description "1540.14 nm/194.653125 THz 3.125GHz spacing";
               }
               enum "1540.11" {
                 description "1540.11 nm/194.656250 THz 3.125/6.25GHz spacing";
               }
               enum "1540.09" {
                 description "1540.09 nm/194.659375 THz 3.125GHz spacing";
               }
               enum "1540.06" {
                 description "1540.06 nm/194.662500 THz 3.125/6.25/12.5GHz spacing";
               }
               enum "1540.04" {
                 description "1540.04 nm/194.665625 THz 3.125GHz spacing";
               }
               enum "1540.01" {
                 description "1540.01 nm/194.668750 THz 3.125/6.25GHz spacing";
               }
               enum "1539.99" {
                 description "1539.99 nm/194.671875 THz 3.125GHz spacing";
               }
               enum "1539.96" {
                 description "1539.96 nm/194.675000 THz 3.125/6.25/12.5GHz spacing";
               }
               enum "1539.94" {
                 description "1539.94 nm/194.678125 THz 3.125GHz spacing";
               }
               enum "1539.91" {
                 description "1539.91 nm/194.681250 THz 3.125/6.25GHz spacing";
               }
               enum "1539.89" {
                 description "1539.89 nm/194.684375 THz 3.125GHz spacing";
               }
               enum "1539.86" {
                 description "1539.86 nm/194.687500 THz 3.125/6.25/12.5GHz spacing";
               }
               enum "1539.84" {
                 description "1539.84 nm/194.690625 THz 3.125GHz spacing";
               }
               enum "1539.82" {
                 description "1539.82 nm/194.693750 THz 3.125/6.25GHz spacing";
               }
               enum "1539.79" {
                 description "1539.79 nm/194.696875 THz 3.125GHz spacing";
               }
               enum "1539.77" {
                 description "1539.77 nm/194.700000 THz 3.125/6.25/12.5/50/75/100GHz spacing";
               }
               enum "1539.74" {
                 description "1539.74 nm/194.703125 THz 3.125GHz spacing";
               }
               enum "1539.72" {
                 description "1539.72 nm/194.706250 THz 3.125/6.25GHz spacing";
               }
               enum "1539.69" {
                 description "1539.69 nm/194.709375 THz 3.125GHz spacing";
               }
               enum "1539.67" {
                 description "1539.67 nm/194.712500 THz 3.125/6.25/12.5GHz spacing";
               }
               enum "1539.64" {
                 description "1539.64 nm/194.715625 THz 3.125GHz spacing";
               }
               enum "1539.62" {
                 description "1539.62 nm/194.718750 THz 3.125/6.25GHz spacing";
               }
               enum "1539.59" {
                 description "1539.59 nm/194.721875 THz 3.125GHz spacing";
               }
               enum "1539.57" {
                 description "1539.57 nm/194.725000 THz 3.125/6.25/12.5GHz spacing";
               }
               enum "1539.54" {
                 description "1539.54 nm/194.728125 THz 3.125GHz spacing";
               }
               enum "1539.52" {
                 description "1539.52 nm/194.731250 THz 3.125/6.25GHz spacing";
               }
               enum "1539.49" {
                 description "1539.49 nm/194.734375 THz 3.125GHz spacing";
               }
               enum "1539.47" {
                 description "1539.47 nm/194.737500 THz 3.125/6.25/12.5GHz spacing";
               }
               enum "1539.44" {
                 description "1539.44 nm/194.740625 THz 3.125GHz spacing";
               }
               enum "1539.42" {
                 description "1539.42 nm/194.743750 THz 3.125/6.25GHz spacing";
               }
               enum "1539.40" {
                 description "1539.40 nm/194.746875 THz 3.125GHz spacing";
               }
               enum "1539.37" {
                 description "1539.37 nm/194.750000 THz 3.125/6.25/12.5/50GHz spacing";
               }
               enum "1539.35" {
                 description "1539.35 nm/194.753125 THz 3.125GHz spacing";
               }
               enum "1539.32" {
                 description "1539.32 nm/194.756250 THz 3.125/6.25GHz spacing";
               }
               enum "1539.30" {
                 description "1539.30 nm/194.759375 THz 3.125GHz spacing";
               }
               enum "1539.27" {
                 description "1539.27 nm/194.762500 THz 3.125/6.25/12.5GHz spacing";
               }
               enum "1539.25" {
                 description "1539.25 nm/194.765625 THz 3.125GHz spacing";
               }
               enum "1539.22" {
                 description "1539.22 nm/194.768750 THz 3.125/6.25GHz spacing";
               }
               enum "1539.20" {
                 description "1539.20 nm/194.771875 THz 3.125GHz spacing";
               }
               enum "1539.17" {
                 description "1539.17 nm/194.775000 THz 3.125/6.25/12.5/75GHz spacing";
               }
               enum "1539.15" {
                 description "1539.15 nm/194.778125 THz 3.125GHz spacing";
               }
               enum "1539.12" {
                 description "1539.12 nm/194.781250 THz 3.125/6.25GHz spacing";
               }
               enum "1539.10" {
                 description "1539.10 nm/194.784375 THz 3.125GHz spacing";
               }
               enum "1539.07" {
                 description "1539.07 nm/194.787500 THz 3.125/6.25/12.5GHz spacing";
               }
               enum "1539.05" {
                 description "1539.05 nm/194.790625 THz 3.125GHz spacing";
               }
               enum "1539.03" {
                 description "1539.03 nm/194.793750 THz 3.125/6.25GHz spacing";
               }
               enum "1539.00" {
                 description "1539.00 nm/194.796875 THz 3.125GHz spacing";
               }
               enum "1538.98" {
                 description "1538.98 nm/194.800000 THz 3.125/6.25/12.5/100GHz spacing";
               }
               enum "1538.95" {
                 description "1538.95 nm/194.803125 THz 3.125GHz spacing";
               }
               enum "1538.93" {
                 description "1538.93 nm/194.806250 THz 3.125/6.25GHz spacing";
               }
               enum "1538.90" {
                 description "1538.90 nm/194.809375 THz 3.125GHz spacing";
               }
               enum "1538.88" {
                 description "1538.88 nm/194.812500 THz 3.125/6.25/12.5GHz spacing";
               }
               enum "1538.85" {
                 description "1538.85 nm/194.815625 THz 3.125GHz spacing";
               }
               enum "1538.83" {
                 description "1538.83 nm/194.818750 THz 3.125/6.25GHz spacing";
               }
               enum "1538.80" {
                 description "1538.80 nm/194.821875 THz 3.125GHz spacing";
               }
               enum "1538.78" {
                 description "1538.78 nm/194.825000 THz 3.125/6.25/12.5GHz spacing";
               }
               enum "1538.75" {
                 description "1538.75 nm/194.828125 THz 3.125GHz spacing";
               }
               enum "1538.73" {
                 description "1538.73 nm/194.831250 THz 3.125/6.25GHz spacing";
               }
               enum "1538.70" {
                 description "1538.70 nm/194.834375 THz 3.125GHz spacing";
               }
               enum "1538.68" {
                 description "1538.68 nm/194.837500 THz 3.125/6.25/12.5GHz spacing";
               }
               enum "1538.65" {
                 description "1538.65 nm/194.840625 THz 3.125GHz spacing";
               }
               enum "1538.63" {
                 description "1538.63 nm/194.843750 THz 3.125/6.25GHz spacing";
               }
               enum "1538.61" {
                 description "1538.61 nm/194.846875 THz 3.125GHz spacing";
               }
               enum "1538.58" {
                 description "1538.58 nm/194.850000 THz 3.125/6.25/12.5/50/75GHz spacing";
               }
               enum "1538.56" {
                 description "1538.56 nm/194.853125 THz 3.125GHz spacing";
               }
               enum "1538.53" {
                 description "1538.53 nm/194.856250 THz 3.125/6.25GHz spacing";
               }
               enum "1538.51" {
                 description "1538.51 nm/194.859375 THz 3.125GHz spacing";
               }
               enum "1538.48" {
                 description "1538.48 nm/194.862500 THz 3.125/6.25/12.5GHz spacing";
               }
               enum "1538.46" {
                 description "1538.46 nm/194.865625 THz 3.125GHz spacing";
               }
               enum "1538.43" {
                 description "1538.43 nm/194.868750 THz 3.125/6.25GHz spacing";
               }
               enum "1538.41" {
                 description "1538.41 nm/194.871875 THz 3.125GHz spacing";
               }
               enum "1538.38" {
                 description "1538.38 nm/194.875000 THz 3.125/6.25/12.5GHz spacing";
               }
               enum "1538.36" {
                 description "1538.36 nm/194.878125 THz 3.125GHz spacing";
               }
               enum "1538.33" {
                 description "1538.33 nm/194.881250 THz 3.125/6.25GHz spacing";
               }
               enum "1538.31" {
                 description "1538.31 nm/194.884375 THz 3.125GHz spacing";
               }
               enum "1538.28" {
                 description "1538.28 nm/194.887500 THz 3.125/6.25/12.5GHz spacing";
               }
               enum "1538.26" {
                 description "1538.26 nm/194.890625 THz 3.125GHz spacing";
               }
               enum "1538.24" {
                 description "1538.24 nm/194.893750 THz 3.125/6.25GHz spacing";
               }
               enum "1538.21" {
                 description "1538.21 nm/194.896875 THz 3.125GHz spacing";
               }
               enum "1538.19" {
                 description "1538.19 nm/194.900000 THz 3.125/6.25/12.5/100GHz spacing";
               }
               enum "1538.16" {
                 description "1538.16 nm/194.903125 THz 3.125GHz spacing";
               }
               enum "1538.14" {
                 description "1538.14 nm/194.906250 THz 3.125/6.25GHz spacing";
               }
               enum "1538.11" {
                 description "1538.11 nm/194.909375 THz 3.125GHz spacing";
               }
               enum "1538.09" {
                 description "1538.09 nm/194.912500 THz 3.125/6.25/12.5GHz spacing";
               }
               enum "1538.06" {
                 description "1538.06 nm/194.915625 THz 3.125GHz spacing";
               }
               enum "1538.04" {
                 description "1538.04 nm/194.918750 THz 3.125/6.25GHz spacing";
               }
               enum "1538.01" {
                 description "1538.01 nm/194.921875 THz 3.125GHz spacing";
               }
               enum "1537.99" {
                 description "1537.99 nm/194.925000 THz 3.125/6.25/12.5/75GHz spacing";
               }
               enum "1537.96" {
                 description "1537.96 nm/194.928125 THz 3.125GHz spacing";
               }
               enum "1537.94" {
                 description "1537.94 nm/194.931250 THz 3.125/6.25GHz spacing";
               }
               enum "1537.91" {
                 description "1537.91 nm/194.934375 THz 3.125GHz spacing";
               }
               enum "1537.89" {
                 description "1537.89 nm/194.937500 THz 3.125/6.25/12.5GHz spacing";
               }
               enum "1537.87" {
                 description "1537.87 nm/194.940625 THz 3.125GHz spacing";
               }
               enum "1537.84" {
                 description "1537.84 nm/194.943750 THz 3.125/6.25GHz spacing";
               }
               enum "1537.82" {
                 description "1537.82 nm/194.946875 THz 3.125GHz spacing";
               }
               enum "1537.79" {
                 description "1537.79 nm/194.950000 THz 3.125/6.25/12.5/50GHz spacing";
               }
               enum "1537.77" {
                 description "1537.77 nm/194.953125 THz 3.125GHz spacing";
               }
               enum "1537.74" {
                 description "1537.74 nm/194.956250 THz 3.125/6.25GHz spacing";
               }
               enum "1537.72" {
                 description "1537.72 nm/194.959375 THz 3.125GHz spacing";
               }
               enum "1537.69" {
                 description "1537.69 nm/194.962500 THz 3.125/6.25/12.5GHz spacing";
               }
               enum "1537.67" {
                 description "1537.67 nm/194.965625 THz 3.125GHz spacing";
               }
               enum "1537.64" {
                 description "1537.64 nm/194.968750 THz 3.125/6.25GHz spacing";
               }
               enum "1537.62" {
                 description "1537.62 nm/194.971875 THz 3.125GHz spacing";
               }
               enum "1537.59" {
                 description "1537.59 nm/194.975000 THz 3.125/6.25/12.5GHz spacing";
               }
               enum "1537.57" {
                 description "1537.57 nm/194.978125 THz 3.125GHz spacing";
               }
               enum "1537.55" {
                 description "1537.55 nm/194.981250 THz 3.125/6.25GHz spacing";
               }
               enum "1537.52" {
                 description "1537.52 nm/194.984375 THz 3.125GHz spacing";
               }
               enum "1537.50" {
                 description "1537.50 nm/194.987500 THz 3.125/6.25/12.5GHz spacing";
               }
               enum "1537.47" {
                 description "1537.47 nm/194.990625 THz 3.125GHz spacing";
               }
               enum "1537.45" {
                 description "1537.45 nm/194.993750 THz 3.125/6.25GHz spacing";
               }
               enum "1537.42" {
                 description "1537.42 nm/194.996875 THz 3.125GHz spacing";
               }
               enum "1537.40" {
                 description "1537.40 nm/195.000000 THz 3.125/6.25/12.5/50/75/100GHz spacing";
               }
               enum "1537.37" {
                 description "1537.37 nm/195.003125 THz 3.125GHz spacing";
               }
               enum "1537.35" {
                 description "1537.35 nm/195.006250 THz 3.125/6.25GHz spacing";
               }
               enum "1537.32" {
                 description "1537.32 nm/195.009375 THz 3.125GHz spacing";
               }
               enum "1537.30" {
                 description "1537.30 nm/195.012500 THz 3.125/6.25/12.5GHz spacing";
               }
               enum "1537.27" {
                 description "1537.27 nm/195.015625 THz 3.125GHz spacing";
               }
               enum "1537.25" {
                 description "1537.25 nm/195.018750 THz 3.125/6.25GHz spacing";
               }
               enum "1537.22" {
                 description "1537.22 nm/195.021875 THz 3.125GHz spacing";
               }
               enum "1537.20" {
                 description "1537.20 nm/195.025000 THz 3.125/6.25/12.5GHz spacing";
               }
               enum "1537.18" {
                 description "1537.18 nm/195.028125 THz 3.125GHz spacing";
               }
               enum "1537.15" {
                 description "1537.15 nm/195.031250 THz 3.125/6.25GHz spacing";
               }
               enum "1537.13" {
                 description "1537.13 nm/195.034375 THz 3.125GHz spacing";
               }
               enum "1537.10" {
                 description "1537.10 nm/195.037500 THz 3.125/6.25/12.5GHz spacing";
               }
               enum "1537.08" {
                 description "1537.08 nm/195.040625 THz 3.125GHz spacing";
               }
               enum "1537.05" {
                 description "1537.05 nm/195.043750 THz 3.125/6.25GHz spacing";
               }
               enum "1537.03" {
                 description "1537.03 nm/195.046875 THz 3.125GHz spacing";
               }
               enum "1537.00" {
                 description "1537.00 nm/195.050000 THz 3.125/6.25/12.5/50GHz spacing";
               }
               enum "1536.98" {
                 description "1536.98 nm/195.053125 THz 3.125GHz spacing";
               }
               enum "1536.95" {
                 description "1536.95 nm/195.056250 THz 3.125/6.25GHz spacing";
               }
               enum "1536.93" {
                 description "1536.93 nm/195.059375 THz 3.125GHz spacing";
               }
               enum "1536.90" {
                 description "1536.90 nm/195.062500 THz 3.125/6.25/12.5GHz spacing";
               }
               enum "1536.88" {
                 description "1536.88 nm/195.065625 THz 3.125GHz spacing";
               }
               enum "1536.86" {
                 description "1536.86 nm/195.068750 THz 3.125/6.25GHz spacing";
               }
               enum "1536.83" {
                 description "1536.83 nm/195.071875 THz 3.125GHz spacing";
               }
               enum "1536.81" {
                 description "1536.81 nm/195.075000 THz 3.125/6.25/12.5/75GHz spacing";
               }
               enum "1536.78" {
                 description "1536.78 nm/195.078125 THz 3.125GHz spacing";
               }
               enum "1536.76" {
                 description "1536.76 nm/195.081250 THz 3.125/6.25GHz spacing";
               }
               enum "1536.73" {
                 description "1536.73 nm/195.084375 THz 3.125GHz spacing";
               }
               enum "1536.71" {
                 description "1536.71 nm/195.087500 THz 3.125/6.25/12.5GHz spacing";
               }
               enum "1536.68" {
                 description "1536.68 nm/195.090625 THz 3.125GHz spacing";
               }
               enum "1536.66" {
                 description "1536.66 nm/195.093750 THz 3.125/6.25GHz spacing";
               }
               enum "1536.63" {
                 description "1536.63 nm/195.096875 THz 3.125GHz spacing";
               }
               enum "1536.61" {
                 description "1536.61 nm/195.100000 THz 3.125/6.25/12.5/100GHz spacing";
               }
               enum "1536.58" {
                 description "1536.58 nm/195.103125 THz 3.125GHz spacing";
               }
               enum "1536.56" {
                 description "1536.56 nm/195.106250 THz 3.125/6.25GHz spacing";
               }
               enum "1536.54" {
                 description "1536.54 nm/195.109375 THz 3.125GHz spacing";
               }
               enum "1536.51" {
                 description "1536.51 nm/195.112500 THz 3.125/6.25/12.5GHz spacing";
               }
               enum "1536.49" {
                 description "1536.49 nm/195.115625 THz 3.125GHz spacing";
               }
               enum "1536.46" {
                 description "1536.46 nm/195.118750 THz 3.125/6.25GHz spacing";
               }
               enum "1536.44" {
                 description "1536.44 nm/195.121875 THz 3.125GHz spacing";
               }
               enum "1536.41" {
                 description "1536.41 nm/195.125000 THz 3.125/6.25/12.5GHz spacing";
               }
               enum "1536.39" {
                 description "1536.39 nm/195.128125 THz 3.125GHz spacing";
               }
               enum "1536.36" {
                 description "1536.36 nm/195.131250 THz 3.125/6.25GHz spacing";
               }
               enum "1536.34" {
                 description "1536.34 nm/195.134375 THz 3.125GHz spacing";
               }
               enum "1536.31" {
                 description "1536.31 nm/195.137500 THz 3.125/6.25/12.5GHz spacing";
               }
               enum "1536.29" {
                 description "1536.29 nm/195.140625 THz 3.125GHz spacing";
               }
               enum "1536.26" {
                 description "1536.26 nm/195.143750 THz 3.125/6.25GHz spacing";
               }
               enum "1536.24" {
                 description "1536.24 nm/195.146875 THz 3.125GHz spacing";
               }
               enum "1536.22" {
                 description "1536.22 nm/195.150000 THz 3.125/6.25/12.5/50/75GHz spacing";
               }
               enum "1536.19" {
                 description "1536.19 nm/195.153125 THz 3.125GHz spacing";
               }
               enum "1536.17" {
                 description "1536.17 nm/195.156250 THz 3.125/6.25GHz spacing";
               }
               enum "1536.14" {
                 description "1536.14 nm/195.159375 THz 3.125GHz spacing";
               }
               enum "1536.12" {
                 description "1536.12 nm/195.162500 THz 3.125/6.25/12.5GHz spacing";
               }
               enum "1536.09" {
                 description "1536.09 nm/195.165625 THz 3.125GHz spacing";
               }
               enum "1536.07" {
                 description "1536.07 nm/195.168750 THz 3.125/6.25GHz spacing";
               }
               enum "1536.04" {
                 description "1536.04 nm/195.171875 THz 3.125GHz spacing";
               }
               enum "1536.02" {
                 description "1536.02 nm/195.175000 THz 3.125/6.25/12.5GHz spacing";
               }
               enum "1535.99" {
                 description "1535.99 nm/195.178125 THz 3.125GHz spacing";
               }
               enum "1535.97" {
                 description "1535.97 nm/195.181250 THz 3.125/6.25GHz spacing";
               }
               enum "1535.94" {
                 description "1535.94 nm/195.184375 THz 3.125GHz spacing";
               }
               enum "1535.92" {
                 description "1535.92 nm/195.187500 THz 3.125/6.25/12.5GHz spacing";
               }
               enum "1535.90" {
                 description "1535.90 nm/195.190625 THz 3.125GHz spacing";
               }
               enum "1535.87" {
                 description "1535.87 nm/195.193750 THz 3.125/6.25GHz spacing";
               }
               enum "1535.85" {
                 description "1535.85 nm/195.196875 THz 3.125GHz spacing";
               }
               enum "1535.82" {
                 description "1535.82 nm/195.200000 THz 3.125/6.25/12.5/100GHz spacing";
               }
               enum "1535.80" {
                 description "1535.80 nm/195.203125 THz 3.125GHz spacing";
               }
               enum "1535.77" {
                 description "1535.77 nm/195.206250 THz 3.125/6.25GHz spacing";
               }
               enum "1535.75" {
                 description "1535.75 nm/195.209375 THz 3.125GHz spacing";
               }
               enum "1535.72" {
                 description "1535.72 nm/195.212500 THz 3.125/6.25/12.5GHz spacing";
               }
               enum "1535.70" {
                 description "1535.70 nm/195.215625 THz 3.125GHz spacing";
               }
               enum "1535.67" {
                 description "1535.67 nm/195.218750 THz 3.125/6.25GHz spacing";
               }
               enum "1535.65" {
                 description "1535.65 nm/195.221875 THz 3.125GHz spacing";
               }
               enum "1535.63" {
                 description "1535.63 nm/195.225000 THz 3.125/6.25/12.5/75GHz spacing";
               }
               enum "1535.60" {
                 description "1535.60 nm/195.228125 THz 3.125GHz spacing";
               }
               enum "1535.58" {
                 description "1535.58 nm/195.231250 THz 3.125/6.25GHz spacing";
               }
               enum "1535.55" {
                 description "1535.55 nm/195.234375 THz 3.125GHz spacing";
               }
               enum "1535.53" {
                 description "1535.53 nm/195.237500 THz 3.125/6.25/12.5GHz spacing";
               }
               enum "1535.50" {
                 description "1535.50 nm/195.240625 THz 3.125GHz spacing";
               }
               enum "1535.48" {
                 description "1535.48 nm/195.243750 THz 3.125/6.25GHz spacing";
               }
               enum "1535.45" {
                 description "1535.45 nm/195.246875 THz 3.125GHz spacing";
               }
               enum "1535.43" {
                 description "1535.43 nm/195.250000 THz 3.125/6.25/12.5/50GHz spacing";
               }
               enum "1535.40" {
                 description "1535.40 nm/195.253125 THz 3.125GHz spacing";
               }
               enum "1535.38" {
                 description "1535.38 nm/195.256250 THz 3.125/6.25GHz spacing";
               }
               enum "1535.36" {
                 description "1535.36 nm/195.259375 THz 3.125GHz spacing";
               }
               enum "1535.33" {
                 description "1535.33 nm/195.262500 THz 3.125/6.25/12.5GHz spacing";
               }
               enum "1535.31" {
                 description "1535.31 nm/195.265625 THz 3.125GHz spacing";
               }
               enum "1535.28" {
                 description "1535.28 nm/195.268750 THz 3.125/6.25GHz spacing";
               }
               enum "1535.26" {
                 description "1535.26 nm/195.271875 THz 3.125GHz spacing";
               }
               enum "1535.23" {
                 description "1535.23 nm/195.275000 THz 3.125/6.25/12.5GHz spacing";
               }
               enum "1535.21" {
                 description "1535.21 nm/195.278125 THz 3.125GHz spacing";
               }
               enum "1535.18" {
                 description "1535.18 nm/195.281250 THz 3.125/6.25GHz spacing";
               }
               enum "1535.16" {
                 description "1535.16 nm/195.284375 THz 3.125GHz spacing";
               }
               enum "1535.13" {
                 description "1535.13 nm/195.287500 THz 3.125/6.25/12.5GHz spacing";
               }
               enum "1535.11" {
                 description "1535.11 nm/195.290625 THz 3.125GHz spacing";
               }
               enum "1535.08" {
                 description "1535.08 nm/195.293750 THz 3.125/6.25GHz spacing";
               }
               enum "1535.06" {
                 description "1535.06 nm/195.296875 THz 3.125GHz spacing";
               }
               enum "1535.04" {
                 description "1535.04 nm/195.300000 THz 3.125/6.25/12.5/50/75/100GHz spacing";
               }
               enum "1535.01" {
                 description "1535.01 nm/195.303125 THz 3.125GHz spacing";
               }
               enum "1534.99" {
                 description "1534.99 nm/195.306250 THz 3.125/6.25GHz spacing";
               }
               enum "1534.96" {
                 description "1534.96 nm/195.309375 THz 3.125GHz spacing";
               }
               enum "1534.94" {
                 description "1534.94 nm/195.312500 THz 3.125/6.25/12.5GHz spacing";
               }
               enum "1534.91" {
                 description "1534.91 nm/195.315625 THz 3.125GHz spacing";
               }
               enum "1534.89" {
                 description "1534.89 nm/195.318750 THz 3.125/6.25GHz spacing";
               }
               enum "1534.86" {
                 description "1534.86 nm/195.321875 THz 3.125GHz spacing";
               }
               enum "1534.84" {
                 description "1534.84 nm/195.325000 THz 3.125/6.25/12.5GHz spacing";
               }
               enum "1534.81" {
                 description "1534.81 nm/195.328125 THz 3.125GHz spacing";
               }
               enum "1534.79" {
                 description "1534.79 nm/195.331250 THz 3.125/6.25GHz spacing";
               }
               enum "1534.77" {
                 description "1534.77 nm/195.334375 THz 3.125GHz spacing";
               }
               enum "1534.74" {
                 description "1534.74 nm/195.337500 THz 3.125/6.25/12.5GHz spacing";
               }
               enum "1534.72" {
                 description "1534.72 nm/195.340625 THz 3.125GHz spacing";
               }
               enum "1534.69" {
                 description "1534.69 nm/195.343750 THz 3.125/6.25GHz spacing";
               }
               enum "1534.67" {
                 description "1534.67 nm/195.346875 THz 3.125GHz spacing";
               }
               enum "1534.64" {
                 description "1534.64 nm/195.350000 THz 3.125/6.25/12.5/50GHz spacing";
               }
               enum "1534.62" {
                 description "1534.62 nm/195.353125 THz 3.125GHz spacing";
               }
               enum "1534.59" {
                 description "1534.59 nm/195.356250 THz 3.125/6.25GHz spacing";
               }
               enum "1534.57" {
                 description "1534.57 nm/195.359375 THz 3.125GHz spacing";
               }
               enum "1534.54" {
                 description "1534.54 nm/195.362500 THz 3.125/6.25/12.5GHz spacing";
               }
               enum "1534.52" {
                 description "1534.52 nm/195.365625 THz 3.125GHz spacing";
               }
               enum "1534.50" {
                 description "1534.50 nm/195.368750 THz 3.125/6.25GHz spacing";
               }
               enum "1534.47" {
                 description "1534.47 nm/195.371875 THz 3.125GHz spacing";
               }
               enum "1534.45" {
                 description "1534.45 nm/195.375000 THz 3.125/6.25/12.5/75GHz spacing";
               }
               enum "1534.42" {
                 description "1534.42 nm/195.378125 THz 3.125GHz spacing";
               }
               enum "1534.40" {
                 description "1534.40 nm/195.381250 THz 3.125/6.25GHz spacing";
               }
               enum "1534.37" {
                 description "1534.37 nm/195.384375 THz 3.125GHz spacing";
               }
               enum "1534.35" {
                 description "1534.35 nm/195.387500 THz 3.125/6.25/12.5GHz spacing";
               }
               enum "1534.32" {
                 description "1534.32 nm/195.390625 THz 3.125GHz spacing";
               }
               enum "1534.30" {
                 description "1534.30 nm/195.393750 THz 3.125/6.25GHz spacing";
               }
               enum "1534.27" {
                 description "1534.27 nm/195.396875 THz 3.125GHz spacing";
               }
               enum "1534.25" {
                 description "1534.25 nm/195.400000 THz 3.125/6.25/12.5/100GHz spacing";
               }
               enum "1534.23" {
                 description "1534.23 nm/195.403125 THz 3.125GHz spacing";
               }
               enum "1534.20" {
                 description "1534.20 nm/195.406250 THz 3.125/6.25GHz spacing";
               }
               enum "1534.18" {
                 description "1534.18 nm/195.409375 THz 3.125GHz spacing";
               }
               enum "1534.15" {
                 description "1534.15 nm/195.412500 THz 3.125/6.25/12.5GHz spacing";
               }
               enum "1534.13" {
                 description "1534.13 nm/195.415625 THz 3.125GHz spacing";
               }
               enum "1534.10" {
                 description "1534.10 nm/195.418750 THz 3.125/6.25GHz spacing";
               }
               enum "1534.08" {
                 description "1534.08 nm/195.421875 THz 3.125GHz spacing";
               }
               enum "1534.05" {
                 description "1534.05 nm/195.425000 THz 3.125/6.25/12.5GHz spacing";
               }
               enum "1534.03" {
                 description "1534.03 nm/195.428125 THz 3.125GHz spacing";
               }
               enum "1534.00" {
                 description "1534.00 nm/195.431250 THz 3.125/6.25GHz spacing";
               }
               enum "1533.98" {
                 description "1533.98 nm/195.434375 THz 3.125GHz spacing";
               }
               enum "1533.96" {
                 description "1533.96 nm/195.437500 THz 3.125/6.25/12.5GHz spacing";
               }
               enum "1533.93" {
                 description "1533.93 nm/195.440625 THz 3.125GHz spacing";
               }
               enum "1533.91" {
                 description "1533.91 nm/195.443750 THz 3.125/6.25GHz spacing";
               }
               enum "1533.88" {
                 description "1533.88 nm/195.446875 THz 3.125GHz spacing";
               }
               enum "1533.86" {
                 description "1533.86 nm/195.450000 THz 3.125/6.25/12.5/50/75GHz spacing";
               }
               enum "1533.83" {
                 description "1533.83 nm/195.453125 THz 3.125GHz spacing";
               }
               enum "1533.81" {
                 description "1533.81 nm/195.456250 THz 3.125/6.25GHz spacing";
               }
               enum "1533.78" {
                 description "1533.78 nm/195.459375 THz 3.125GHz spacing";
               }
               enum "1533.76" {
                 description "1533.76 nm/195.462500 THz 3.125/6.25/12.5GHz spacing";
               }
               enum "1533.73" {
                 description "1533.73 nm/195.465625 THz 3.125GHz spacing";
               }
               enum "1533.71" {
                 description "1533.71 nm/195.468750 THz 3.125/6.25GHz spacing";
               }
               enum "1533.69" {
                 description "1533.69 nm/195.471875 THz 3.125GHz spacing";
               }
               enum "1533.66" {
                 description "1533.66 nm/195.475000 THz 3.125/6.25/12.5GHz spacing";
               }
               enum "1533.64" {
                 description "1533.64 nm/195.478125 THz 3.125GHz spacing";
               }
               enum "1533.61" {
                 description "1533.61 nm/195.481250 THz 3.125/6.25GHz spacing";
               }
               enum "1533.59" {
                 description "1533.59 nm/195.484375 THz 3.125GHz spacing";
               }
               enum "1533.56" {
                 description "1533.56 nm/195.487500 THz 3.125/6.25/12.5GHz spacing";
               }
               enum "1533.54" {
                 description "1533.54 nm/195.490625 THz 3.125GHz spacing";
               }
               enum "1533.51" {
                 description "1533.51 nm/195.493750 THz 3.125/6.25GHz spacing";
               }
               enum "1533.49" {
                 description "1533.49 nm/195.496875 THz 3.125GHz spacing";
               }
               enum "1533.47" {
                 description "1533.47 nm/195.500000 THz 3.125/6.25/12.5/100GHz spacing";
               }
               enum "1533.44" {
                 description "1533.44 nm/195.503125 THz 3.125GHz spacing";
               }
               enum "1533.42" {
                 description "1533.42 nm/195.506250 THz 3.125/6.25GHz spacing";
               }
               enum "1533.39" {
                 description "1533.39 nm/195.509375 THz 3.125GHz spacing";
               }
               enum "1533.37" {
                 description "1533.37 nm/195.512500 THz 3.125/6.25/12.5GHz spacing";
               }
               enum "1533.34" {
                 description "1533.34 nm/195.515625 THz 3.125GHz spacing";
               }
               enum "1533.32" {
                 description "1533.32 nm/195.518750 THz 3.125/6.25GHz spacing";
               }
               enum "1533.29" {
                 description "1533.29 nm/195.521875 THz 3.125GHz spacing";
               }
               enum "1533.27" {
                 description "1533.27 nm/195.525000 THz 3.125/6.25/12.5/75GHz spacing";
               }
               enum "1533.24" {
                 description "1533.24 nm/195.528125 THz 3.125GHz spacing";
               }
               enum "1533.22" {
                 description "1533.22 nm/195.531250 THz 3.125/6.25GHz spacing";
               }
               enum "1533.20" {
                 description "1533.20 nm/195.534375 THz 3.125GHz spacing";
               }
               enum "1533.17" {
                 description "1533.17 nm/195.537500 THz 3.125/6.25/12.5GHz spacing";
               }
               enum "1533.15" {
                 description "1533.15 nm/195.540625 THz 3.125GHz spacing";
               }
               enum "1533.12" {
                 description "1533.12 nm/195.543750 THz 3.125/6.25GHz spacing";
               }
               enum "1533.10" {
                 description "1533.10 nm/195.546875 THz 3.125GHz spacing";
               }
               enum "1533.07" {
                 description "1533.07 nm/195.550000 THz 3.125/6.25/12.5/50GHz spacing";
               }
               enum "1533.05" {
                 description "1533.05 nm/195.553125 THz 3.125GHz spacing";
               }
               enum "1533.02" {
                 description "1533.02 nm/195.556250 THz 3.125/6.25GHz spacing";
               }
               enum "1533.00" {
                 description "1533.00 nm/195.559375 THz 3.125GHz spacing";
               }
               enum "1532.98" {
                 description "1532.98 nm/195.562500 THz 3.125/6.25/12.5GHz spacing";
               }
               enum "1532.95" {
                 description "1532.95 nm/195.565625 THz 3.125GHz spacing";
               }
               enum "1532.93" {
                 description "1532.93 nm/195.568750 THz 3.125/6.25GHz spacing";
               }
               enum "1532.90" {
                 description "1532.90 nm/195.571875 THz 3.125GHz spacing";
               }
               enum "1532.88" {
                 description "1532.88 nm/195.575000 THz 3.125/6.25/12.5GHz spacing";
               }
               enum "1532.85" {
                 description "1532.85 nm/195.578125 THz 3.125GHz spacing";
               }
               enum "1532.83" {
                 description "1532.83 nm/195.581250 THz 3.125/6.25GHz spacing";
               }
               enum "1532.80" {
                 description "1532.80 nm/195.584375 THz 3.125GHz spacing";
               }
               enum "1532.78" {
                 description "1532.78 nm/195.587500 THz 3.125/6.25/12.5GHz spacing";
               }
               enum "1532.75" {
                 description "1532.75 nm/195.590625 THz 3.125GHz spacing";
               }
               enum "1532.73" {
                 description "1532.73 nm/195.593750 THz 3.125/6.25GHz spacing";
               }
               enum "1532.71" {
                 description "1532.71 nm/195.596875 THz 3.125GHz spacing";
               }
               enum "1532.68" {
                 description "1532.68 nm/195.600000 THz 3.125/6.25/12.5/50/75/100GHz spacing";
               }
               enum "1532.66" {
                 description "1532.66 nm/195.603125 THz 3.125GHz spacing";
               }
               enum "1532.63" {
                 description "1532.63 nm/195.606250 THz 3.125/6.25GHz spacing";
               }
               enum "1532.61" {
                 description "1532.61 nm/195.609375 THz 3.125GHz spacing";
               }
               enum "1532.58" {
                 description "1532.58 nm/195.612500 THz 3.125/6.25/12.5GHz spacing";
               }
               enum "1532.56" {
                 description "1532.56 nm/195.615625 THz 3.125GHz spacing";
               }
               enum "1532.53" {
                 description "1532.53 nm/195.618750 THz 3.125/6.25GHz spacing";
               }
               enum "1532.51" {
                 description "1532.51 nm/195.621875 THz 3.125GHz spacing";
               }
               enum "1532.49" {
                 description "1532.49 nm/195.625000 THz 3.125/6.25/12.5GHz spacing";
               }
               enum "1532.46" {
                 description "1532.46 nm/195.628125 THz 3.125GHz spacing";
               }
               enum "1532.44" {
                 description "1532.44 nm/195.631250 THz 3.125/6.25GHz spacing";
               }
               enum "1532.41" {
                 description "1532.41 nm/195.634375 THz 3.125GHz spacing";
               }
               enum "1532.39" {
                 description "1532.39 nm/195.637500 THz 3.125/6.25/12.5GHz spacing";
               }
               enum "1532.36" {
                 description "1532.36 nm/195.640625 THz 3.125GHz spacing";
               }
               enum "1532.34" {
                 description "1532.34 nm/195.643750 THz 3.125/6.25GHz spacing";
               }
               enum "1532.31" {
                 description "1532.31 nm/195.646875 THz 3.125GHz spacing";
               }
               enum "1532.29" {
                 description "1532.29 nm/195.650000 THz 3.125/6.25/12.5/50GHz spacing";
               }
               enum "1532.27" {
                 description "1532.27 nm/195.653125 THz 3.125GHz spacing";
               }
               enum "1532.24" {
                 description "1532.24 nm/195.656250 THz 3.125/6.25GHz spacing";
               }
               enum "1532.22" {
                 description "1532.22 nm/195.659375 THz 3.125GHz spacing";
               }
               enum "1532.19" {
                 description "1532.19 nm/195.662500 THz 3.125/6.25/12.5GHz spacing";
               }
               enum "1532.17" {
                 description "1532.17 nm/195.665625 THz 3.125GHz spacing";
               }
               enum "1532.14" {
                 description "1532.14 nm/195.668750 THz 3.125/6.25GHz spacing";
               }
               enum "1532.12" {
                 description "1532.12 nm/195.671875 THz 3.125GHz spacing";
               }
               enum "1532.09" {
                 description "1532.09 nm/195.675000 THz 3.125/6.25/12.5/75GHz spacing";
               }
               enum "1532.07" {
                 description "1532.07 nm/195.678125 THz 3.125GHz spacing";
               }
               enum "1532.04" {
                 description "1532.04 nm/195.681250 THz 3.125/6.25GHz spacing";
               }
               enum "1532.02" {
                 description "1532.02 nm/195.684375 THz 3.125GHz spacing";
               }
               enum "1532.00" {
                 description "1532.00 nm/195.687500 THz 3.125/6.25/12.5GHz spacing";
               }
               enum "1531.97" {
                 description "1531.97 nm/195.690625 THz 3.125GHz spacing";
               }
               enum "1531.95" {
                 description "1531.95 nm/195.693750 THz 3.125/6.25GHz spacing";
               }
               enum "1531.92" {
                 description "1531.92 nm/195.696875 THz 3.125GHz spacing";
               }
               enum "1531.90" {
                 description "1531.90 nm/195.700000 THz 3.125/6.25/12.5/100GHz spacing";
               }
               enum "1531.87" {
                 description "1531.87 nm/195.703125 THz 3.125GHz spacing";
               }
               enum "1531.85" {
                 description "1531.85 nm/195.706250 THz 3.125/6.25GHz spacing";
               }
               enum "1531.82" {
                 description "1531.82 nm/195.709375 THz 3.125GHz spacing";
               }
               enum "1531.80" {
                 description "1531.80 nm/195.712500 THz 3.125/6.25/12.5GHz spacing";
               }
               enum "1531.78" {
                 description "1531.78 nm/195.715625 THz 3.125GHz spacing";
               }
               enum "1531.75" {
                 description "1531.75 nm/195.718750 THz 3.125/6.25GHz spacing";
               }
               enum "1531.73" {
                 description "1531.73 nm/195.721875 THz 3.125GHz spacing";
               }
               enum "1531.70" {
                 description "1531.70 nm/195.725000 THz 3.125/6.25/12.5GHz spacing";
               }
               enum "1531.68" {
                 description "1531.68 nm/195.728125 THz 3.125GHz spacing";
               }
               enum "1531.65" {
                 description "1531.65 nm/195.731250 THz 3.125/6.25GHz spacing";
               }
               enum "1531.63" {
                 description "1531.63 nm/195.734375 THz 3.125GHz spacing";
               }
               enum "1531.60" {
                 description "1531.60 nm/195.737500 THz 3.125/6.25/12.5GHz spacing";
               }
               enum "1531.58" {
                 description "1531.58 nm/195.740625 THz 3.125GHz spacing";
               }
               enum "1531.56" {
                 description "1531.56 nm/195.743750 THz 3.125/6.25GHz spacing";
               }
               enum "1531.53" {
                 description "1531.53 nm/195.746875 THz 3.125GHz spacing";
               }
               enum "1531.51" {
                 description "1531.51 nm/195.750000 THz 3.125/6.25/12.5/50/75GHz spacing";
               }
               enum "1531.48" {
                 description "1531.48 nm/195.753125 THz 3.125GHz spacing";
               }
               enum "1531.46" {
                 description "1531.46 nm/195.756250 THz 3.125/6.25GHz spacing";
               }
               enum "1531.43" {
                 description "1531.43 nm/195.759375 THz 3.125GHz spacing";
               }
               enum "1531.41" {
                 description "1531.41 nm/195.762500 THz 3.125/6.25/12.5GHz spacing";
               }
               enum "1531.38" {
                 description "1531.38 nm/195.765625 THz 3.125GHz spacing";
               }
               enum "1531.36" {
                 description "1531.36 nm/195.768750 THz 3.125/6.25GHz spacing";
               }
               enum "1531.34" {
                 description "1531.34 nm/195.771875 THz 3.125GHz spacing";
               }
               enum "1531.31" {
                 description "1531.31 nm/195.775000 THz 3.125/6.25/12.5GHz spacing";
               }
               enum "1531.29" {
                 description "1531.29 nm/195.778125 THz 3.125GHz spacing";
               }
               enum "1531.26" {
                 description "1531.26 nm/195.781250 THz 3.125/6.25GHz spacing";
               }
               enum "1531.24" {
                 description "1531.24 nm/195.784375 THz 3.125GHz spacing";
               }
               enum "1531.21" {
                 description "1531.21 nm/195.787500 THz 3.125/6.25/12.5GHz spacing";
               }
               enum "1531.19" {
                 description "1531.19 nm/195.790625 THz 3.125GHz spacing";
               }
               enum "1531.16" {
                 description "1531.16 nm/195.793750 THz 3.125/6.25GHz spacing";
               }
               enum "1531.14" {
                 description "1531.14 nm/195.796875 THz 3.125GHz spacing";
               }
               enum "1531.12" {
                 description "1531.12 nm/195.800000 THz 3.125/6.25/12.5/100GHz spacing";
               }
               enum "1531.09" {
                 description "1531.09 nm/195.803125 THz 3.125GHz spacing";
               }
               enum "1531.07" {
                 description "1531.07 nm/195.806250 THz 3.125/6.25GHz spacing";
               }
               enum "1531.04" {
                 description "1531.04 nm/195.809375 THz 3.125GHz spacing";
               }
               enum "1531.02" {
                 description "1531.02 nm/195.812500 THz 3.125/6.25/12.5GHz spacing";
               }
               enum "1530.99" {
                 description "1530.99 nm/195.815625 THz 3.125GHz spacing";
               }
               enum "1530.97" {
                 description "1530.97 nm/195.818750 THz 3.125/6.25GHz spacing";
               }
               enum "1530.94" {
                 description "1530.94 nm/195.821875 THz 3.125GHz spacing";
               }
               enum "1530.92" {
                 description "1530.92 nm/195.825000 THz 3.125/6.25/12.5/75GHz spacing";
               }
               enum "1530.90" {
                 description "1530.90 nm/195.828125 THz 3.125GHz spacing";
               }
               enum "1530.87" {
                 description "1530.87 nm/195.831250 THz 3.125/6.25GHz spacing";
               }
               enum "1530.85" {
                 description "1530.85 nm/195.834375 THz 3.125GHz spacing";
               }
               enum "1530.82" {
                 description "1530.82 nm/195.837500 THz 3.125/6.25/12.5GHz spacing";
               }
               enum "1530.80" {
                 description "1530.80 nm/195.840625 THz 3.125GHz spacing";
               }
               enum "1530.77" {
                 description "1530.77 nm/195.843750 THz 3.125/6.25GHz spacing";
               }
               enum "1530.75" {
                 description "1530.75 nm/195.846875 THz 3.125GHz spacing";
               }
               enum "1530.72" {
                 description "1530.72 nm/195.850000 THz 3.125/6.25/12.5/50GHz spacing";
               }
               enum "1530.70" {
                 description "1530.70 nm/195.853125 THz 3.125GHz spacing";
               }
               enum "1530.68" {
                 description "1530.68 nm/195.856250 THz 3.125/6.25GHz spacing";
               }
               enum "1530.65" {
                 description "1530.65 nm/195.859375 THz 3.125GHz spacing";
               }
               enum "1530.63" {
                 description "1530.63 nm/195.862500 THz 3.125/6.25/12.5GHz spacing";
               }
               enum "1530.60" {
                 description "1530.60 nm/195.865625 THz 3.125GHz spacing";
               }
               enum "1530.58" {
                 description "1530.58 nm/195.868750 THz 3.125/6.25GHz spacing";
               }
               enum "1530.55" {
                 description "1530.55 nm/195.871875 THz 3.125GHz spacing";
               }
               enum "1530.53" {
                 description "1530.53 nm/195.875000 THz 3.125/6.25/12.5GHz spacing";
               }
               enum "1530.51" {
                 description "1530.51 nm/195.878125 THz 3.125GHz spacing";
               }
               enum "1530.48" {
                 description "1530.48 nm/195.881250 THz 3.125/6.25GHz spacing";
               }
               enum "1530.46" {
                 description "1530.46 nm/195.884375 THz 3.125GHz spacing";
               }
               enum "1530.43" {
                 description "1530.43 nm/195.887500 THz 3.125/6.25/12.5GHz spacing";
               }
               enum "1530.41" {
                 description "1530.41 nm/195.890625 THz 3.125GHz spacing";
               }
               enum "1530.38" {
                 description "1530.38 nm/195.893750 THz 3.125/6.25GHz spacing";
               }
               enum "1530.36" {
                 description "1530.36 nm/195.896875 THz 3.125GHz spacing";
               }
               enum "1530.33" {
                 description "1530.33 nm/195.900000 THz 3.125/6.25/12.5/50/75/100GHz spacing";
               }
               enum "1530.31" {
                 description "1530.31 nm/195.903125 THz 3.125GHz spacing";
               }
               enum "1530.29" {
                 description "1530.29 nm/195.906250 THz 3.125/6.25GHz spacing";
               }
               enum "1530.26" {
                 description "1530.26 nm/195.909375 THz 3.125GHz spacing";
               }
               enum "1530.24" {
                 description "1530.24 nm/195.912500 THz 3.125/6.25/12.5GHz spacing";
               }
               enum "1530.21" {
                 description "1530.21 nm/195.915625 THz 3.125GHz spacing";
               }
               enum "1530.19" {
                 description "1530.19 nm/195.918750 THz 3.125/6.25GHz spacing";
               }
               enum "1530.16" {
                 description "1530.16 nm/195.921875 THz 3.125GHz spacing";
               }
               enum "1530.14" {
                 description "1530.14 nm/195.925000 THz 3.125/6.25/12.5GHz spacing";
               }
               enum "1530.11" {
                 description "1530.11 nm/195.928125 THz 3.125GHz spacing";
               }
               enum "1530.09" {
                 description "1530.09 nm/195.931250 THz 3.125/6.25GHz spacing";
               }
               enum "1530.07" {
                 description "1530.07 nm/195.934375 THz 3.125GHz spacing";
               }
               enum "1530.04" {
                 description "1530.04 nm/195.937500 THz 3.125/6.25/12.5GHz spacing";
               }
               enum "1530.02" {
                 description "1530.02 nm/195.940625 THz 3.125GHz spacing";
               }
               enum "1529.99" {
                 description "1529.99 nm/195.943750 THz 3.125/6.25GHz spacing";
               }
               enum "1529.97" {
                 description "1529.97 nm/195.946875 THz 3.125GHz spacing";
               }
               enum "1529.94" {
                 description "1529.94 nm/195.950000 THz 3.125/6.25/12.5/50GHz spacing";
               }
               enum "1529.92" {
                 description "1529.92 nm/195.953125 THz 3.125GHz spacing";
               }
               enum "1529.89" {
                 description "1529.89 nm/195.956250 THz 3.125/6.25GHz spacing";
               }
               enum "1529.87" {
                 description "1529.87 nm/195.959375 THz 3.125GHz spacing";
               }
               enum "1529.85" {
                 description "1529.85 nm/195.962500 THz 3.125/6.25/12.5GHz spacing";
               }
               enum "1529.82" {
                 description "1529.82 nm/195.965625 THz 3.125GHz spacing";
               }
               enum "1529.80" {
                 description "1529.80 nm/195.968750 THz 3.125/6.25GHz spacing";
               }
               enum "1529.77" {
                 description "1529.77 nm/195.971875 THz 3.125GHz spacing";
               }
               enum "1529.75" {
                 description "1529.75 nm/195.975000 THz 3.125/6.25/12.5/75GHz spacing";
               }
               enum "1529.72" {
                 description "1529.72 nm/195.978125 THz 3.125GHz spacing";
               }
               enum "1529.70" {
                 description "1529.70 nm/195.981250 THz 3.125/6.25GHz spacing";
               }
               enum "1529.68" {
                 description "1529.68 nm/195.984375 THz 3.125GHz spacing";
               }
               enum "1529.65" {
                 description "1529.65 nm/195.987500 THz 3.125/6.25/12.5GHz spacing";
               }
               enum "1529.63" {
                 description "1529.63 nm/195.990625 THz 3.125GHz spacing";
               }
               enum "1529.60" {
                 description "1529.60 nm/195.993750 THz 3.125/6.25GHz spacing";
               }
               enum "1529.58" {
                 description "1529.58 nm/195.996875 THz 3.125GHz spacing";
               }
               enum "1529.55" {
                 description "1529.55 nm/196.000000 THz 3.125/6.25/12.5/100GHz spacing";
               }
               enum "1529.53" {
                 description "1529.53 nm/196.003125 THz 3.125GHz spacing";
               }
               enum "1529.50" {
                 description "1529.50 nm/196.006250 THz 3.125/6.25GHz spacing";
               }
               enum "1529.48" {
                 description "1529.48 nm/196.009375 THz 3.125GHz spacing";
               }
               enum "1529.46" {
                 description "1529.46 nm/196.012500 THz 3.125/6.25/12.5GHz spacing";
               }
               enum "1529.43" {
                 description "1529.43 nm/196.015625 THz 3.125GHz spacing";
               }
               enum "1529.41" {
                 description "1529.41 nm/196.018750 THz 3.125/6.25GHz spacing";
               }
               enum "1529.38" {
                 description "1529.38 nm/196.021875 THz 3.125GHz spacing";
               }
               enum "1529.36" {
                 description "1529.36 nm/196.025000 THz 3.125/6.25/12.5GHz spacing";
               }
               enum "1529.33" {
                 description "1529.33 nm/196.028125 THz 3.125GHz spacing";
               }
               enum "1529.31" {
                 description "1529.31 nm/196.031250 THz 3.125/6.25GHz spacing";
               }
               enum "1529.29" {
                 description "1529.29 nm/196.034375 THz 3.125GHz spacing";
               }
               enum "1529.26" {
                 description "1529.26 nm/196.037500 THz 3.125/6.25/12.5GHz spacing";
               }
               enum "1529.24" {
                 description "1529.24 nm/196.040625 THz 3.125GHz spacing";
               }
               enum "1529.21" {
                 description "1529.21 nm/196.043750 THz 3.125/6.25GHz spacing";
               }
               enum "1529.19" {
                 description "1529.19 nm/196.046875 THz 3.125GHz spacing";
               }
               enum "1529.16" {
                 description "1529.16 nm/196.050000 THz 3.125/6.25/12.5/50/75GHz spacing";
               }
               enum "1529.14" {
                 description "1529.14 nm/196.053125 THz 3.125GHz spacing";
               }
               enum "1529.11" {
                 description "1529.11 nm/196.056250 THz 3.125/6.25GHz spacing";
               }
               enum "1529.09" {
                 description "1529.09 nm/196.059375 THz 3.125GHz spacing";
               }
               enum "1529.07" {
                 description "1529.07 nm/196.062500 THz 3.125/6.25/12.5GHz spacing";
               }
               enum "1529.04" {
                 description "1529.04 nm/196.065625 THz 3.125GHz spacing";
               }
               enum "1529.02" {
                 description "1529.02 nm/196.068750 THz 3.125/6.25GHz spacing";
               }
               enum "1528.99" {
                 description "1528.99 nm/196.071875 THz 3.125GHz spacing";
               }
               enum "1528.97" {
                 description "1528.97 nm/196.075000 THz 3.125/6.25/12.5GHz spacing";
               }
               enum "1528.94" {
                 description "1528.94 nm/196.078125 THz 3.125GHz spacing";
               }
               enum "1528.92" {
                 description "1528.92 nm/196.081250 THz 3.125/6.25GHz spacing";
               }
               enum "1528.90" {
                 description "1528.90 nm/196.084375 THz 3.125GHz spacing";
               }
               enum "1528.87" {
                 description "1528.87 nm/196.087500 THz 3.125/6.25/12.5GHz spacing";
               }
               enum "1528.85" {
                 description "1528.85 nm/196.090625 THz 3.125GHz spacing";
               }
               enum "1528.82" {
                 description "1528.82 nm/196.093750 THz 3.125/6.25GHz spacing";
               }
               enum "1528.80" {
                 description "1528.80 nm/196.096875 THz 3.125GHz spacing";
               }
               enum "1528.77" {
                 description "1528.77 nm/196.100000 THz 3.125/6.25/12.5/50/75/100GHz spacing";
               }
               enum "1528.75" {
                 description "1528.75 nm/196.103125 THz 3.125GHz spacing";
               }
               enum "1528.72" {
                 description "1528.72 nm/196.106250 THz 3.125/6.25GHz spacing";
               }
               enum "1528.70" {
                 description "1528.70 nm/196.109375 THz 3.125GHz spacing";
               }
               enum "1528.68" {
                 description "1528.68 nm/196.112500 THz 3.125/6.25/12.5GHz spacing";
               }
               enum "1528.65" {
                 description "1528.65 nm/196.115625 THz 3.125GHz spacing";
               }
               enum "1528.63" {
                 description "1528.63 nm/196.118750 THz 3.125/6.25GHz spacing";
               }
               enum "1528.60" {
                 description "1528.60 nm/196.121875 THz 3.125GHz spacing";
               }
               enum "1528.58" {
                 description "1528.58 nm/196.125000 THz 3.125/6.25/12.5/75GHz spacing";
               }
               enum "1528.55" {
                 description "1528.55 nm/196.128125 THz 3.125GHz spacing";
               }
               enum "1528.53" {
                 description "1528.53 nm/196.131250 THz 3.125/6.25GHz spacing";
               }
               enum "1528.51" {
                 description "1528.51 nm/196.134375 THz 3.125GHz spacing";
               }
               enum "1528.48" {
                 description "1528.48 nm/196.137500 THz 3.125/6.25/12.5GHz spacing";
               }
               enum "1528.46" {
                 description "1528.46 nm/196.140625 THz 3.125GHz spacing";
               }
               enum "1528.43" {
                 description "1528.43 nm/196.143750 THz 3.125/6.25GHz spacing";
               }
               enum "1528.41" {
                 description "1528.41 nm/196.146875 THz 3.125GHz spacing";
               }
               enum "1528.38" {
                 description "1528.38 nm/196.15040 THz 50Ghz spacing";
               }
             }
           }
           leaf tx-power {
             description "Transmit laser output power";
             units "dBm";
             type string {
               junos:posix-pattern "^[+-]?[0-9]+(\\.[0-9]+)?$";
               junos:pattern-message "numerical value must be specified with optional leading sign and optional decimal point";
             }
           }
           container loopback {
             presence "enable loopback";
             description "Put the optics in loopback mode";
             uses apply-advanced;
           }
           leaf los-warning-threshold {
             description "LOS warning threshold";
             units "dBm";
             type string;
           }
           leaf los-alarm-threshold {
             description "LOS alarm threshold";
             units "dBm";
             type string;
           }
           leaf modulation-format {
             description "Type of Modulation Format";
             type enumeration {
               enum "16qam" {
                 description "16-QAM Modulation Format";
               }
               enum "8qam" {
                 description "8-QAM MOdulation Format";
               }
               enum "qpsk" {
                 description "QPSK Modulation Format";
               }
             }
           }
           choice laser-enable-choice {
             leaf laser-enable {
               description "Enable Laser";
               type empty;
             }
             leaf no-laser-enable {
               description "Don't enable Laser";
               type empty;
             }
           }
           choice is-ma-choice {
             leaf is-ma {
               description "Link is enabled with alarms masked";
               type empty;
             }
             leaf no-is-ma {
               description "Don't link is enabled with alarms masked";
               type empty;
             }
           }
           leaf encoding {
             description "Line encoding";
             type enumeration {
               enum "differential" {
                 description "Differential phase line encoding";
               }
               enum "non-differential" {
                 description "Non-differential phase line encoding";
               }
             }
           }
           leaf fec {
             description "Forward Error Correction mode";
             type enumeration {
               enum "sdfec" {
                 description "Sky-Compatible Soft Decision Forward Error Correction";
               }
               enum "sdfec25" {
                 description "Denali-Compatible Soft Decision Forward Error Correction with 25 percent overhead";
               }
               enum "hgfec" {
                 description "High Gain Forward Error Correction";
               }
               enum "sdfec15" {
                 description "Soft Decision Forward Error Correction with 15 percent overhead";
               }
             }
           }
           leaf high-polarization {
             description "High polarization tracking mode";
             type empty;
           }
           container signal-degrade {
             description "Signal degrade thresholds";
             uses apply-advanced;
             leaf interval {
               description "Time interval";
               default "10";
               units "milliseconds";
               type union {
                 type string {
                   pattern "<.*>|$.*";
                 }
                 type uint32 {
                   range "1 .. 1000";
                 }
               }
             }
             leaf ber-threshold-clear {
               description "Ber threshold for signal degrade clear (format: xe-n, example: 4.5e-3)";
               type string {
                 junos:posix-pattern "^[0-9]+(.[0-9]+)?e-[0-9]$";
                 junos:pattern-message "Ber threshold value in format: xe-n, x is an integer or decimal number, n = 0..9";
               }
             }
             leaf ber-threshold-signal-degrade {
               description "Ber threshold for signal-degrade (format: xe-n, example: 4.5e-3)";
               type string {
                 junos:posix-pattern "^[0-9]+(.[0-9]+)?e-[0-9]$";
                 junos:pattern-message "Ber threshold value in format: xe-n, x is an integer or decimal number, n = 0..9";
               }
             }
             leaf q-threshold-signal-degrade-clear {
               description "Q threshold for signal-degrade clear (e.g. 14.26)";
               units "dB";
               type string;
             }
             leaf q-threshold-signal-degrade {
               description "Q threshold for signal-degrade (e.g. 9.26)";
               units "dB";
               type string;
             }
           }
           list alarm {
             key name;
             ordered-by user;
             description "Set optic alarms";
             leaf name {
               junos:cli-feature "nokeyword";
               type enumeration {
                 enum "low-light-alarm" {
                   description "Enable low light alarm";
                 }
               }
             }
             uses apply-advanced;
             choice actiontype {
               case case_1 {
                 leaf syslog {
                   type empty;
                 }
               }
               case case_2 {
                 leaf link-down {
                   type empty;
                 }
               }
             }
           }
           container tca {
             description "Set tca for optic alarms";
             uses apply-advanced;
             container tx-power-high-tca {
               description "Tx power high TCA";
               uses apply-advanced;
               choice enable-tca-choice {
                 leaf enable-tca {
                   description "Enable tca";
                   type empty;
                 }
                 leaf no-enable-tca {
                   description "Don't enable tca";
                   type empty;
                 }
               }
               leaf threshold {
                 description "Threshold for 15 minute tx power high TCA in dBm";
                 type string {
                   junos:posix-pattern "^[+-]?[0-9]+(\\.[0-9]+)?$";
                   junos:pattern-message "numerical value must be specified with optional leading sign and optional decimal point";
                 }
               }
               leaf threshold-24hrs {
                 description "Threshold for 24 hour tx power high TCA in dBm";
                 type string {
                   junos:posix-pattern "^[+-]?[0-9]+(\\.[0-9]+)?$";
                   junos:pattern-message "numerical value must be specified with optional leading sign and optional decimal point";
                 }
               }
             }
             container tx-power-low-tca {
               description "Tx power low TCA";
               uses apply-advanced;
               choice enable-tca-choice {
                 leaf enable-tca {
                   description "Enable tca";
                   type empty;
                 }
                 leaf no-enable-tca {
                   description "Don't enable tca";
                   type empty;
                 }
               }
               leaf threshold {
                 description "Threshold for 15 minute tx power low TCA in dBm";
                 type string {
                   junos:posix-pattern "^[+-]?[0-9]+(\\.[0-9]+)?$";
                   junos:pattern-message "numerical value must be specified with optional leading sign and optional decimal point";
                 }
               }
               leaf threshold-24hrs {
                 description "Threshold for 24 hour tx power low TCA in dBm";
                 type string {
                   junos:posix-pattern "^[+-]?[0-9]+(\\.[0-9]+)?$";
                   junos:pattern-message "numerical value must be specified with optional leading sign and optional decimal point";
                 }
               }
             }
             container rx-power-high-tca {
               description "Rx power high TCA";
               uses apply-advanced;
               choice enable-tca-choice {
                 leaf enable-tca {
                   description "Enable tca";
                   type empty;
                 }
                 leaf no-enable-tca {
                   description "Don't enable tca";
                   type empty;
                 }
               }
               leaf threshold {
                 description "Threshold for 15 minute rx power high TCA in dBm";
                 type string {
                   junos:posix-pattern "^[+-]?[0-9]+(\\.[0-9]+)?$";
                   junos:pattern-message "numerical value must be specified with optional leading sign and optional decimal point";
                 }
               }
               leaf threshold-24hrs {
                 description "Threshold for 24 hour rx power high TCA in dBm";
                 type string {
                   junos:posix-pattern "^[+-]?[0-9]+(\\.[0-9]+)?$";
                   junos:pattern-message "numerical value must be specified with optional leading sign and optional decimal point";
                 }
               }
             }
             container rx-power-low-tca {
               description "Rx power low TCA";
               uses apply-advanced;
               choice enable-tca-choice {
                 leaf enable-tca {
                   description "Enable tca";
                   type empty;
                 }
                 leaf no-enable-tca {
                   description "Don't enable tca";
                   type empty;
                 }
               }
               leaf threshold {
                 description "Threshold for 15 minute rx power low TCA in dBm";
                 type string {
                   junos:posix-pattern "^[+-]?[0-9]+(\\.[0-9]+)?$";
                   junos:pattern-message "numerical value must be specified with optional leading sign and optional decimal point";
                 }
               }
               leaf threshold-24hrs {
                 description "Threshold for 24 hour rx power low TCA in dBm";
                 type string {
                   junos:posix-pattern "^[+-]?[0-9]+(\\.[0-9]+)?$";
                   junos:pattern-message "numerical value must be specified with optional leading sign and optional decimal point";
                 }
               }
             }
             container rx-signal-power-high-tca {
               description "Rx signal power high TCA";
               uses apply-advanced;
               choice enable-tca-choice {
                 leaf enable-tca {
                   description "Enable tca";
                   type empty;
                 }
                 leaf no-enable-tca {
                   description "Don't enable tca";
                   type empty;
                 }
               }
               leaf threshold {
                 description "Threshold for 15 minute rx signal power high TCA in dBm";
                 type string {
                   junos:posix-pattern "^[+-]?[0-9]+(\\.[0-9]+)?$";
                   junos:pattern-message "numerical value must be specified with optional leading sign and optional decimal point";
                 }
               }
               leaf threshold-24hrs {
                 description "Threshold for 24 hour rx signal power high TCA in dBm";
                 type string {
                   junos:posix-pattern "^[+-]?[0-9]+(\\.[0-9]+)?$";
                   junos:pattern-message "numerical value must be specified with optional leading sign and optional decimal point";
                 }
               }
             }
             container rx-signal-power-low-tca {
               description "Rx signal power low TCA";
               uses apply-advanced;
               choice enable-tca-choice {
                 leaf enable-tca {
                   description "Enable tca";
                   type empty;
                 }
                 leaf no-enable-tca {
                   description "Don't enable tca";
                   type empty;
                 }
               }
               leaf threshold {
                 description "Threshold for 15 minute rx signal power low TCA in dBm";
                 type string {
                   junos:posix-pattern "^[+-]?[0-9]+(\\.[0-9]+)?$";
                   junos:pattern-message "numerical value must be specified with optional leading sign and optional decimal point";
                 }
               }
               leaf threshold-24hrs {
                 description "Threshold for 24 hour rx signal power low TCA in dBm";
                 type string {
                   junos:posix-pattern "^[+-]?[0-9]+(\\.[0-9]+)?$";
                   junos:pattern-message "numerical value must be specified with optional leading sign and optional decimal point";
                 }
               }
             }
             container temperature-high-tca {
               description "Temperature high TCA";
               uses apply-advanced;
               choice enable-tca-choice {
                 leaf enable-tca {
                   description "Enable tca";
                   type empty;
                 }
                 leaf no-enable-tca {
                   description "Don't enable tca";
                   type empty;
                 }
               }
               leaf threshold {
                 description "Threshold for 15 minute high temperature TCA in celsius";
                 type string {
                   junos:posix-pattern "^[+-]?[0-9]+(\\.[0-9]+)?$";
                   junos:pattern-message "numerical value must be specified with optional leading sign and optional decimal point";
                 }
               }
               leaf threshold-24hrs {
                 description "Threshold for 24 hour high temperature TCA in celsius";
                 type string {
                   junos:posix-pattern "^[+-]?[0-9]+(\\.[0-9]+)?$";
                   junos:pattern-message "numerical value must be specified with optional leading sign and optional decimal point";
                 }
               }
             }
             container temperature-low-tca {
               description "Temperature low TCA";
               uses apply-advanced;
               choice enable-tca-choice {
                 leaf enable-tca {
                   description "Enable tca";
                   type empty;
                 }
                 leaf no-enable-tca {
                   description "Don't enable tca";
                   type empty;
                 }
               }
               leaf threshold {
                 description "Threshold for 15 minute low temperature TCA in celsius";
                 type string {
                   junos:posix-pattern "^[+-]?[0-9]+(\\.[0-9]+)?$";
                   junos:pattern-message "numerical value must be specified with optional leading sign and optional decimal point";
                 }
               }
               leaf threshold-24hrs {
                 description "Threshold for 24 hour low temperature TCA in celsius";
                 type string {
                   junos:posix-pattern "^[+-]?[0-9]+(\\.[0-9]+)?$";
                   junos:pattern-message "numerical value must be specified with optional leading sign and optional decimal point";
                 }
               }
             }
             container carrier-frequency-offset-high-tca {
               description "Carrier frequency offset high TCA";
               uses apply-advanced;
               choice enable-tca-choice {
                 leaf enable-tca {
                   description "Enable tca";
                   type empty;
                 }
                 leaf no-enable-tca {
                   description "Don't enable tca";
                   type empty;
                 }
               }
               leaf threshold {
                 description "Threshold for 15 minute frequency offset high TCA in MHz";
                 type string {
                   junos:posix-pattern "^[+-]?[0-9]+(\\.[0-9]+)?$";
                   junos:pattern-message "numerical value must be specified with optional leading sign and optional decimal point";
                 }
               }
               leaf threshold-24hrs {
                 description "Threshold for 24 hour frequency offset high TCA in MHz";
                 type string {
                   junos:posix-pattern "^[+-]?[0-9]+(\\.[0-9]+)?$";
                   junos:pattern-message "numerical value must be specified with optional leading sign and optional decimal point";
                 }
               }
             }
             container carrier-frequency-offset-low-tca {
               description "Carrier frequency offset low TCA";
               uses apply-advanced;
               choice enable-tca-choice {
                 leaf enable-tca {
                   description "Enable tca";
                   type empty;
                 }
                 leaf no-enable-tca {
                   description "Don't enable tca";
                   type empty;
                 }
               }
               leaf threshold {
                 description "Threshold for 15 minute frequency offset low TCA in MHz";
                 type string {
                   junos:posix-pattern "^[+-]?[0-9]+(\\.[0-9]+)?$";
                   junos:pattern-message "numerical value must be specified with optional leading sign and optional decimal point";
                 }
               }
               leaf threshold-24hrs {
                 description "Threshold for 24 hour frequency offset low TCA in MHz";
                 type string {
                   junos:posix-pattern "^[+-]?[0-9]+(\\.[0-9]+)?$";
                   junos:pattern-message "numerical value must be specified with optional leading sign and optional decimal point";
                 }
               }
             }
             container fec-ber {
               junos:cli-feature "oneliner";
               description "Optics Errored Seconds Threshold crossing defect trigger";
               choice enable-tca-choice {
                 leaf enable-tca {
                   description "Enable the Optics errored seconds threshold crossing alert";
                   type empty;
                 }
                 leaf no-enable-tca {
                   description "Don't enable the Optics errored seconds threshold crossing alert";
                   type empty;
                 }
               }
               leaf threshold {
                 description "TCA threshold for BER value in format: xe-n, x is an integer or decimal number, n = 0..9";
                 default "10e-3";
                 type string {
                   junos:posix-pattern "^[0-9]+(\\.[0-9]+)?e-[0-9]$";
                   junos:pattern-message "FEC BER threshold value in format: xe-n, x is an integer or decimal number, n = 0..9";
                 }
               }
               leaf threshold-24hrs {
                 description "TCA threshold for BER value in format: xe-n, x is an integer or decimal number, n = 0..9";
                 default "10e-3";
                 type string {
                   junos:posix-pattern "^[0-9]+(\\.[0-9]+)?e-[0-9]$";
                   junos:pattern-message "FEC BER threshold value in format: xe-n, x is an integer or decimal number, n = 0..9";
                 }
               }
             }
             container tec-current-high-tca {
               description "TEC Current high TCA";
               uses apply-advanced;
               choice enable-tca-choice {
                 leaf enable-tca {
                   description "Enable tca";
                   type empty;
                 }
                 leaf no-enable-tca {
                   description "Don't enable tca";
                   type empty;
                 }
               }
               leaf threshold {
                 description "Threshold for 15 minute TEC Current high TCA in mA";
                 type string {
                   junos:posix-pattern "^[+-]?[0-9]+(\\.[0-9]+)?$";
                   junos:pattern-message "numerical value must be specified with optional leading sign and optional decimal point";
                 }
               }
               leaf threshold-24hrs {
                 description "Threshold for 24 hour TEC Current high TCA in mA";
                 type string {
                   junos:posix-pattern "^[+-]?[0-9]+(\\.[0-9]+)?$";
                   junos:pattern-message "numerical value must be specified with optional leading sign and optional decimal point";
                 }
               }
             }
             container tec-current-low-tca {
               description "TEC Current low TCA";
               uses apply-advanced;
               choice enable-tca-choice {
                 leaf enable-tca {
                   description "Enable tca";
                   type empty;
                 }
                 leaf no-enable-tca {
                   description "Don't enable tca";
                   type empty;
                 }
               }
               leaf threshold {
                 description "Threshold for 15 minute TEC Current low TCA in mA";
                 type string {
                   junos:posix-pattern "^[+-]?[0-9]+(\\.[0-9]+)?$";
                   junos:pattern-message "numerical value must be specified with optional leading sign and optional decimal point";
                 }
               }
               leaf threshold-24hrs {
                 description "Threshold for 24 hour TEC Current low TCA in mA";
                 type string {
                   junos:posix-pattern "^[+-]?[0-9]+(\\.[0-9]+)?$";
                   junos:pattern-message "numerical value must be specified with optional leading sign and optional decimal point";
                 }
               }
             }
             container residual-isi-high-tca {
               description "Residual ISI high TCA";
               uses apply-advanced;
               choice enable-tca-choice {
                 leaf enable-tca {
                   description "Enable tca";
                   type empty;
                 }
                 leaf no-enable-tca {
                   description "Don't enable tca";
                   type empty;
                 }
               }
               leaf threshold {
                 description "Threshold for 15 minute Residual ISI high TCA in ps/nm";
                 type string {
                   junos:posix-pattern "^[+-]?[0-9]+(\\.[0-9]+)?$";
                   junos:pattern-message "numerical value must be specified with optional leading sign and optional decimal point";
                 }
               }
               leaf threshold-24hrs {
                 description "Threshold for 24 hour Residual ISI high TCA in ps/nm";
                 type string {
                   junos:posix-pattern "^[+-]?[0-9]+(\\.[0-9]+)?$";
                   junos:pattern-message "numerical value must be specified with optional leading sign and optional decimal point";
                 }
               }
             }
             container residual-isi-low-tca {
               description "Residual ISI low TCA";
               uses apply-advanced;
               choice enable-tca-choice {
                 leaf enable-tca {
                   description "Enable tca";
                   type empty;
                 }
                 leaf no-enable-tca {
                   description "Don't enable tca";
                   type empty;
                 }
               }
               leaf threshold {
                 description "Threshold for 15 minute Residual ISI low TCA in ps/nm";
                 type string {
                   junos:posix-pattern "^[+-]?[0-9]+(\\.[0-9]+)?$";
                   junos:pattern-message "numerical value must be specified with optional leading sign and optional decimal point";
                 }
               }
               leaf threshold-24hrs {
                 description "Threshold for 24 hour Residual ISI low TCA in ps/nm";
                 type string {
                   junos:posix-pattern "^[+-]?[0-9]+(\\.[0-9]+)?$";
                   junos:pattern-message "numerical value must be specified with optional leading sign and optional decimal point";
                 }
               }
             }
             container pam-histogram-high-tca {
               description "PAM Histogram high TCA";
               uses apply-advanced;
               choice enable-tca-choice {
                 leaf enable-tca {
                   description "Enable tca";
                   type empty;
                 }
                 leaf no-enable-tca {
                   description "Don't enable tca";
                   type empty;
                 }
               }
               leaf threshold {
                 description "Threshold for 15 minute PAM Histogram high TCA";
                 type string {
                   junos:posix-pattern "^[0-9]+$";
                   junos:pattern-message "must be an unsigned integer";
                 }
               }
               leaf threshold-24hrs {
                 description "Threshold for 24 hour PAM Histogram high TCA";
                 type string {
                   junos:posix-pattern "^[0-9]+$";
                   junos:pattern-message "must be an unsigned integer";
                 }
               }
             }
             container snr-low-tca {
               description "SNR low TCA";
               uses apply-advanced;
               choice enable-tca-choice {
                 leaf enable-tca {
                   description "Enable tca";
                   type empty;
                 }
                 leaf no-enable-tca {
                   description "Don't enable tca";
                   type empty;
                 }
               }
               leaf threshold {
                 description "Threshold for 15 minute SNR low TCA in dBm ";
                 type string {
                   junos:posix-pattern "^[+-]?[0-9]+(\\.[0-9]+)?$";
                   junos:pattern-message "numerical value must be specified with optional leading sign and optional decimal point";
                 }
               }
               leaf threshold-24hrs {
                 description "Threshold for 24 hour SNR low TCA in dBm";
                 type string {
                   junos:posix-pattern "^[+-]?[0-9]+(\\.[0-9]+)?$";
                   junos:pattern-message "numerical value must be specified with optional leading sign and optional decimal point";
                 }
               }
             }
             container fec-corrected-errors-high-tca {
               description "FEC Corrected Error High Threshold crossing defect trigger";
               uses apply-advanced;
               choice enable-tca-choice {
                 leaf enable-tca {
                   description "Enable the FEC Corrected Errors threshold crossing alert";
                   type empty;
                 }
                 leaf no-enable-tca {
                   description "Don't enable the FEC Corrected Errors threshold crossing alert";
                   type empty;
                 }
               }
               leaf threshold {
                 description "FEC Corrected-Errs value in format: xe-n, x is an integer or decimal number, n = 0..9";
                 default "10e-3";
                 type string {
                   junos:posix-pattern "^[0-9]+(\\.[0-9]+)?e-[0-9]$";
                   junos:pattern-message "FEC Corrected-Errs threshold value in format: xe-n, x is an integer or decimal number, n = 0..9";
                 }
               }
               leaf threshold-24hrs {
                 description "FEC Corrected-Errs value in format: xe-n, x is an integer or decimal number, n = 0..9";
                 default "10e-3";
                 type string {
                   junos:posix-pattern "^[0-9]+(\\.[0-9]+)?e-[0-9]$";
                   junos:pattern-message "FEC Corrected-Errs threshold value in format: xe-n, x is an integer or decimal number, n = 0..9";
                 }
               }
             }
             container fec-ucorrected-words-high-tca {
               description "FEC UCorrected Words High Threshold crossing defect trigger";
               uses apply-advanced;
               choice enable-tca-choice {
                 leaf enable-tca {
                   description "Enable the FEC UCorrected Words threshold crossing alert";
                   type empty;
                 }
                 leaf no-enable-tca {
                   description "Don't enable the FEC UCorrected Words threshold crossing alert";
                   type empty;
                 }
               }
               leaf threshold {
                 description "FEC UCorrected-Words value in format: xe-n, x is an integer or decimal number, n = 0..9";
                 default "10e-3";
                 type string {
                   junos:posix-pattern "^[0-9]+(\\.[0-9]+)?e-[0-9]$";
                   junos:pattern-message "FEC UCorrected-Words threshold value in format: xe-n, x is an integer or decimal number, n = 0..9";
                 }
               }
               leaf threshold-24hrs {
                 description "FEC UCorrected-Words value in format: xe-n, x is an integer or decimal number, n = 0..9";
                 default "10e-3";
                 type string {
                   junos:posix-pattern "^[0-9]+(\\.[0-9]+)?e-[0-9]$";
                   junos:pattern-message "FEC UCorrected-Words threshold value in format: xe-n, x is an integer or decimal number, n = 0..9";
                 }
               }
             }
             container laser-frequency-error-high-tca {
               description "Laser frequency error high TCA";
               uses apply-advanced;
               choice enable-tca-choice {
                 leaf enable-tca {
                   description "Enable tca";
                   type empty;
                 }
                 leaf no-enable-tca {
                   description "Don't enable tca";
                   type empty;
                 }
               }
               leaf threshold {
                 description "Threshold for 15 minute frequency error high TCA in MHz";
                 type string {
                   junos:posix-pattern "^[+-]?[0-9]+(\\.[0-9]+)?$";
                   junos:pattern-message "numerical value must be specified with optional leading sign and optional decimal point";
                 }
               }
               leaf threshold-24hrs {
                 description "Threshold for 24 hour frequency error high TCA in MHz";
                 type string {
                   junos:posix-pattern "^[+-]?[0-9]+(\\.[0-9]+)?$";
                   junos:pattern-message "numerical value must be specified with optional leading sign and optional decimal point";
                 }
               }
             }
             container laser-frequency-error-low-tca {
               description "Laser frequency error low TCA";
               uses apply-advanced;
               choice enable-tca-choice {
                 leaf enable-tca {
                   description "Enable tca";
                   type empty;
                 }
                 leaf no-enable-tca {
                   description "Don't enable tca";
                   type empty;
                 }
               }
               leaf threshold {
                 description "Threshold for 15 minute frequency error low TCA in MHz";
                 type string {
                   junos:posix-pattern "^[+-]?[0-9]+(\\.[0-9]+)?$";
                   junos:pattern-message "numerical value must be specified with optional leading sign and optional decimal point";
                 }
               }
               leaf threshold-24hrs {
                 description "Threshold for 24 hour frequency error low TCA in MHz";
                 type string {
                   junos:posix-pattern "^[+-]?[0-9]+(\\.[0-9]+)?$";
                   junos:pattern-message "numerical value must be specified with optional leading sign and optional decimal point";
                 }
               }
             }
           }
           list warning {
             key name;
             ordered-by user;
             description "Set optic warnings";
             leaf name {
               junos:cli-feature "nokeyword";
               type enumeration {
                 enum "low-light-warning" {
                   description "Enable low light warning";
                 }
               }
             }
             uses apply-advanced;
             choice actiontype {
               case case_1 {
                 leaf syslog {
                   description "Set action as syslog";
                   type empty;
                 }
               }
               case case_2 {
                 leaf link-down {
                   description "Set action as link-down";
                   type empty;
                 }
               }
             }
           }
           choice lane-info {
             case case_1 {
             }
             case case_2 {
             }
           }
         }
         container otn-options {
           description "Optical Transmission Network interface-specific options";
           uses otn_options_type;
         }
         container och-options {
           description "Optical channel configuration options";
           uses och-attributes;
         }
         container otu-options {
           description "Optical transmission unit configuration options";
           uses otu-attributes;
         }
         container odu-options {
           description "Optical data unit configuration options";
           uses odu-attributes;
         }
         container ett-options {
           description "Transport ethernet client configuration options";
           uses ett-attributes;
         }
         container fastether-options {
           description "Fast Ethernet interface-specific options";
           uses apply-advanced;
           choice loopback-choice {
             leaf loopback {
               description "Enable loopback";
               type empty;
             }
             leaf no-loopback {
               description "Don't enable loopback";
               type empty;
             }
           }
           choice flow-control-choice {
             leaf flow-control {
               description "Enable flow control";
               type empty;
             }
             leaf no-flow-control {
               description "Don't enable flow control";
               type empty;
             }
           }
           choice source-filtering-choice {
             leaf source-filtering {
               description "Enable source address filtering";
               type empty;
             }
             leaf no-source-filtering {
               description "Don't enable source address filtering";
               type empty;
             }
           }
           choice auto-negotiation-choice {
             leaf auto-negotiation {
               description "Enable auto-negotiation";
               type empty;
             }
             leaf no-auto-negotiation {
               description "Don't enable auto-negotiation";
               type empty;
             }
           }
           leaf ingress-rate-limit {
             description "Ingress rate at port";
             units "megabits per second";
             type union {
               type string {
                 pattern "<.*>|$.*";
               }
               type uint32 {
                 range "1 .. 100";
               }
             }
           }
           list source-address-filter {
             key name;
             ordered-by user;
             junos:cli-feature "homogeneous";
             junos:cli-feature "oneliner";
             description "Source address filters";
             junos:must "(!(any \".. .. unit <*> family ethernet-switching\"))";
             junos:must-message "source mac filters not allowed on ethernet switched port";
             leaf name {
               description "Remote MAC address";
               junos:cli-feature "nokeyword";
               type jt:mac-addr;
             }
           }
           container redundant-parent {
             junos:cli-feature "oneliner-plus";
             description " Parent of this interface";
             uses apply-advanced;
             leaf parent {
               description "Join a redundant ethernet interface";
               junos:cli-feature "nokeyword";
               junos:must "(!(any \"interfaces <*> ether-options redundant-parent $$\"))";
               junos:must-message "All children must be of the same ethernet type";
               junos:must "(!(any \"interfaces <*> gigether-options redundant-parent $$\"))";
               junos:must-message "All the children must be of same ethernet type";
               type union {
                 type jt:interface-device;
                 type string {
                   pattern "<.*>|$.*";
                 }
               }
             }
           }
           container ieee-802.3ad {
             junos:must "(!(\"system autoinstallation\"))";
             junos:must-message "incompatible with 'system autoinstallation'";
             junos:cli-feature "oneliner-plus";
             description "IEEE 802.3ad";
             uses apply-advanced;
             container lacp {
               description "Link Aggregation Control Protocol configuration";
               uses apply-advanced;
               leaf port-priority {
                 description "Priority of the port (0 ... 65535)";
                 type union {
                   type uint16;
                   type string {
                     pattern "<.*>|$.*";
                   }
                 }
               }
             }
             leaf bundle {
               description "Join an aggregated Ethernet interface";
               junos:cli-feature "nokeyword";
               junos:must "(!(any \"class-of-service interfaces ${interface} unit <*> rewrite-rules\"))";
               junos:must-message "rewrite config can not be applied on ae child";
               junos:must "(!(any \"class-of-service interfaces ${interface} unit <*> classifiers\"))";
               junos:must-message "classifier config can not be applied on ae child";
               junos:must "(!(any \"class-of-service interfaces ${interface} unit <*> output-traffic-control-profile\"))";
               junos:must-message "output-traffic-control-profile config can not be applied on ae child";
               junos:must "(!(\"class-of-service interfaces ${interface} output-traffic-control-profile\"))";
               junos:must-message "output-traffic-control-profile config can not be applied on ae child";
               junos:must "(!(\"class-of-service interfaces ${interface} shaping-rate\"))";
               junos:must-message "shaping-rate config can not be applied on ae child";
               junos:must "(!(\"class-of-service interfaces ${interface} scheduler-map\"))";
               junos:must-message "scheduler-map config can not be applied on ae child";
               junos:must "(!(\".. .. .. vlan-offload\"))";
               junos:must-message "ae child device vlan-offload is not allowed";
               junos:must "(!(\".. .. .. flow-control\"))";
               junos:must-message "Setting flow-control on ae child device is not allowed";
               junos:must "(!(\".. .. .. mtu\"))";
               junos:must-message "Setting mtu on ae child device is not allowed";
               junos:must "(!(\".. .. .. vlan-vci-tagging\"))";
               junos:must-message "ae child device vlan-vci-tagging is not allowed";
               junos:must "(!(\".. .. .. stacked-vlan-tagging\"))";
               junos:must-message "ae child device stacked-vlan-tagging is not allowed";
               junos:must "(!(\".. .. .. flexible-vlan-tagging\"))";
               junos:must-message "ae child device flexible-vlan-tagging is not allowed";
               junos:must "(!(\".. .. .. vlan-tagging\"))";
               junos:must-message "ae child device vlan-tagging is not allowed";
               type union {
                 type jt:interface-device;
                 type string {
                   pattern "<.*>|$.*";
                 }
               }
             }
             choice type {
               case case_1 {
                 leaf primary {
                   description "Primary interface for link-protection mode";
                   type empty;
                 }
               }
               case case_2 {
                 leaf backup {
                   description "Backup interface for link-protection mode";
                   type empty;
                 }
               }
             }
           }
           container mpls {
             description "MPLS options";
             uses mpls_ifd_options;
           }
           leaf ignore-l3-incompletes {
             description "Ignore L3 incomplete errors";
             type empty;
           }
         }
         container redundant-ether-options {
           description "Ethernet redundancy options";
           uses apply-advanced;
           leaf redundancy-group {
             description "Redundancy group of this interface";
             junos:must "(\"chassis cluster redundancy-group $$\")";
             junos:must-message "A redundancy group should be defined";
             type union {
               type string {
                 pattern "<.*>|$.*";
               }
               type uint16 {
                 range "1 .. 128";
               }
             }
           }
           choice loopback-choice {
             leaf loopback {
               description "Enable loopback";
               type empty;
             }
             leaf no-loopback {
               description "Don't enable loopback";
               type empty;
             }
           }
           choice flow-control-choice {
             leaf flow-control {
               description "Enable flow control";
               type empty;
             }
             leaf no-flow-control {
               description "Don't enable flow control";
               type empty;
             }
           }
           choice source-filtering-choice {
             leaf source-filtering {
               description "Enable source address filtering";
               type empty;
             }
             leaf no-source-filtering {
               description "Don't enable source address filtering";
               type empty;
             }
           }
           list source-address-filter {
             key name;
             ordered-by user;
             junos:cli-feature "homogeneous";
             junos:cli-feature "oneliner";
             description "Source address filters";
             leaf name {
               description "Remote MAC address";
               junos:cli-feature "nokeyword";
               type jt:mac-addr;
             }
           }
           leaf mru {
             description "Maximum receive packet size";
             type union {
               type string {
                 pattern "<.*>|$.*";
               }
               type uint32;
             }
           }
           leaf link-speed {
             description "Link speed of individual interface that joins the RETH";
             type enumeration {
               enum "10m" {
                 description "Links are 10M";
               }
               enum "100m" {
                 description "Links are 100M";
               }
               enum "1g" {
                 description "Links are 1G";
               }
               enum "10g" {
                 description "Links are 10G";
               }
               enum "25g" {
                 description "Links are 25G";
               }
               enum "40g" {
                 description "Links are 40G";
               }
               enum "50g" {
                 description "Links are 50G";
               }
               enum "100g" {
                 description "Links are 100G";
               }
               enum "400g" {
                 description "Links are 400G";
               }
             }
           }
           leaf minimum-links {
             description "Minimum number of active links";
             default "1";
             type union {
               type string {
                 pattern "<.*>|$.*";
               }
               type uint16 {
                 range "1 .. 8";
               }
             }
           }
           container lacp {
             description "Link Aggregation Control Protocol configuration";
             uses apply-advanced;
             choice mode {
               case case_1 {
                 leaf active {
                   description "Initiate transmission of LACP packets";
                   type empty;
                 }
               }
               case case_2 {
                 leaf passive {
                   description "Respond to LACP packets";
                   type empty;
                 }
               }
             }
             leaf periodic {
               description "Timer interval for periodic transmission of LACP packets";
               type enumeration {
                 enum "fast" {
                   description "Receive packets every second";
                 }
                 enum "slow" {
                   description "Receive packets every 30 seconds";
                 }
               }
             }
           }
         }
         container aggregated-ether-options {
           description "Aggregated Ethernet interface-specific options";
           uses apply-advanced;
           choice loopback-choice {
             leaf loopback {
               description "Enable loopback";
               type empty;
             }
             leaf no-loopback {
               description "Don't enable loopback";
               type empty;
             }
           }
           choice flow-control-choice {
             leaf flow-control {
               description "Enable flow control";
               type empty;
             }
             leaf no-flow-control {
               description "Don't enable flow control";
               type empty;
             }
           }
           choice source-filtering-choice {
             leaf source-filtering {
               description "Enable source address filtering";
               type empty;
             }
             leaf no-source-filtering {
               description "Don't enable source address filtering";
               type empty;
             }
           }
           leaf autostate-exclude {
             description "Interface will not contribute to IRB state";
             type empty;
           }
           container link-protection {
             presence "enable link-protection";
             description "Enable link protection mode";
             uses apply-advanced;
             leaf revertive {
               description "Revert back from active backup link to primary, if primary is UP";
               junos:must "(!(\"interfaces ${interface} aggregated-ether-options link-protection non-revertive\"))";
               junos:must-message "link-protection revertive and non-revertive are mutually exclusive";
               junos:must "(!(\"chassis aggregated-devices ethernet lacp\"))";
               junos:must-message "link-protection revertive and LACP are mutually exclusive";
               junos:must "(!(\"interfaces ${interface} aggregated-ether-options lacp\"))";
               junos:must-message "link-protection revertive and LACP are mutually exclusive";
               type empty;
             }
             leaf non-revertive {
               description "Do not revert back (default mode) from active backup link to primary, if primary is UP";
               junos:must "(!(\"interfaces ${interface} aggregated-ether-options link-protection revertive\"))";
               junos:must-message "link-protection revertive and non-revertive are mutually exclusive";
               junos:must "(!(\"chassis aggregated-devices ethernet lacp\"))";
               junos:must-message "link-protection revertive and LACP are mutually exclusive";
               junos:must "(!(\"interfaces ${interface} aggregated-ether-options lacp\"))";
               junos:must-message "link-protection revertive and LACP are mutually exclusive";
               type empty;
             }
             leaf backup-state {
               description "Link protection backup link state";
               default "accept-data";
               type enumeration {
                 enum "accept-data" {
                   description "Accept data on receive channel of backup link";
                 }
                 enum "discard-data" {
                   description "Discard data on receive channel of backup link";
                 }
                 enum "down" {
                   description "Backup link is marked down";
                   junos:must "(!(\"chassis aggregated-devices ethernet lacp\"))";
                   junos:must-message "backup-state down and LACP are mutually exclusive";
                   junos:must "(!(\"interfaces ${interface} aggregated-ether-options lacp\"))";
                   junos:must-message "backup-state down and LACP are mutually exclusive";
                 }
               }
             }
             container rtg-config {
               presence "enable rtg-config";
               description "RTG enable on AE";
               uses apply-advanced;
               leaf preempt-cutover-timer {
                 description "RTG preempt-cutover-timer in seconds";
                 default "1";
                 type union {
                   type string {
                     pattern "<.*>|$.*";
                   }
                   type uint32 {
                     range "0 .. 255";
                   }
                 }
               }
             }
           }
           choice fcoe-lag-choice {
             leaf fcoe-lag {
               description "Enable FIP/FCoE LAG";
               type empty;
             }
             leaf no-fcoe-lag {
               description "Don't enable FIP/FCoE LAG";
               type empty;
             }
           }
           list source-address-filter {
             key name;
             ordered-by user;
             junos:cli-feature "homogeneous";
             junos:cli-feature "oneliner";
             description "Source address filters";
             leaf name {
               description "Remote MAC address";
               junos:cli-feature "nokeyword";
               type jt:mac-addr;
             }
           }
           container load-balance {
             uses aggregate-load-balance;
           }
           container bfd-liveness-detection {
             junos:must "(!(\".. lacp fast-failover\"))";
             junos:must-message "BFD not supported with lacp with fast-failover mode";
             junos:must "(!(\".. lacp link-protection\"))";
             junos:must-message "BFD not supported with lacp link protection";
             junos:must "(!(\".. link-protection\"))";
             junos:must-message "BFD not supported with link protection";
             description "Bidirectional Forwarding Detection (BFD) options";
             uses apply-advanced;
             leaf version {
               description "BFD protocol version number";
               default "automatic";
               type enumeration {
                 enum "0" {
                   description "BFD version 0 (deprecated)";
                 }
                 enum "1" {
                   description "BFD version 1";
                 }
                 enum "automatic" {
                   description "Choose BFD version automatically";
                 }
               }
             }
             leaf minimum-interval {
               description "Minimum transmit and receive interval";
               units "milliseconds";
               type union {
                 type string {
                   pattern "<.*>|$.*";
                 }
                 type uint32 {
                   range "1 .. 255000";
                 }
               }
             }
             leaf minimum-transmit-interval {
               description "Minimum transmit interval";
               status deprecated;
               units "milliseconds";
               type union {
                 type string {
                   pattern "<.*>|$.*";
                 }
                 type uint32 {
                   range "1 .. 255000";
                 }
               }
             }
             leaf minimum-receive-interval {
               description "Minimum receive interval";
               units "milliseconds";
               type union {
                 type string {
                   pattern "<.*>|$.*";
                 }
                 type uint32 {
                   range "1 .. 255000";
                 }
               }
             }
             leaf multiplier {
               description "Detection time multiplier";
               default "3";
               type union {
                 type string {
                   pattern "<.*>|$.*";
                 }
                 type uint32 {
                   range "1 .. 255";
                 }
               }
             }
             leaf inline-disable {
               description "Disable inline mode for this BFD session";
               type empty;
             }
             leaf pdu-size {
               description "BFD transport protocol payload size";
               default "24";
               type union {
                 type string {
                   pattern "<.*>|$.*";
                 }
                 type uint32 {
                   range "24 .. 16000";
                 }
               }
             }
             choice adaptation-choice {
               case case_1 {
                 leaf no-adaptation {
                   description "Disable adaptation";
                   type empty;
                 }
               }
             }
             container transmit-interval {
               description "Transmit-interval options";
               uses apply-advanced;
               leaf minimum-interval {
                 description "Minimum transmit interval";
                 units "milliseconds";
                 type union {
                   type string {
                     pattern "<.*>|$.*";
                   }
                   type uint32 {
                     range "1 .. 255000";
                   }
                 }
               }
               leaf threshold {
                 description "High transmit interval triggering a trap";
                 units "milliseconds";
                 type union {
                   type uint32;
                   type string {
                     pattern "<.*>|$.*";
                   }
                 }
               }
             }
             container detection-time {
               description "Detection-time options";
               uses apply-advanced;
               leaf threshold {
                 description "High detection-time triggering a trap";
                 units "milliseconds";
                 type union {
                   type uint32;
                   type string {
                     pattern "<.*>|$.*";
                   }
                 }
               }
             }
             container authentication {
               description "Authentication options";
               uses apply-advanced;
               leaf key-chain {
                 description "Key chain name";
                 junos:must "(\".. algorithm\")";
                 junos:must-message "May not be configured without algorithm";
                 junos:must "(\"security authentication-key-chains key-chain $$\")";
                 junos:must-message "Referenced key-chain must be defined";
                 type string;
               }
               leaf algorithm {
                 description "Algorithm name";
                 junos:must "(\".. key-chain\")";
                 junos:must-message "May not be configured without key-chain";
                 type enumeration {
                   enum "simple-password" {
                     description "Simple password";
                   }
                   enum "keyed-md5" {
                     description "Keyed message Digest 5";
                   }
                   enum "meticulous-keyed-md5" {
                     description "Meticulous keyed message Digest 5";
                   }
                   enum "keyed-sha-1" {
                     description "Keyed secure hash algorithm (SHA1) ";
                   }
                   enum "meticulous-keyed-sha-1" {
                     description "Meticulous keyed secure hash algorithm (SHA1) ";
                   }
                 }
               }
               leaf loose-check {
                 description "Verify authentication only if authentication is negotiated";
                 type empty;
               }
             }
             container damping {
               description "BFD flap damping parameters";
               uses apply-advanced;
               leaf suppress {
                 description "Suppress threshold for figure-of-merit value";
                 default "5000";
                 type union {
                   type string {
                     pattern "<.*>|$.*";
                   }
                   type uint32 {
                     range "1000 .. 200000";
                   }
                 }
               }
               leaf reuse {
                 description "Reuse threshold for figure-of-merit value";
                 default "1000";
                 type union {
                   type string {
                     pattern "<.*>|$.*";
                   }
                   type uint32 {
                     range "1000 .. 200000";
                   }
                 }
               }
               leaf max-suppress-time {
                 description "Maximum hold-down time";
                 default "600";
                 units "seconds";
                 type union {
                   type string {
                     pattern "<.*>|$.*";
                   }
                   type uint32 {
                     range "1 .. 20000";
                   }
                 }
               }
               leaf half-life-interval {
                 description "Decay half life interval";
                 default "30";
                 units "seconds";
                 type union {
                   type string {
                     pattern "<.*>|$.*";
                   }
                   type uint32 {
                     range "1 .. 600";
                   }
                 }
               }
               leaf increment {
                 description "Increments applied to figure-of-merit value for every flap";
                 default "1000";
                 type union {
                   type string {
                     pattern "<.*>|$.*";
                   }
                   type uint32 {
                     range "1000 .. 20000";
                   }
                 }
               }
             }
             leaf neighbor {
               description "BFD neighbor address";
               type jt:ipaddr;
             }
             leaf local-address {
               description "BFD local address";
               type jt:ipaddr;
             }
             leaf holddown-interval {
               description "Time to hold the session-UP notification to the client";
               units "milliseconds";
               type union {
                 type string {
                   pattern "<.*>|$.*";
                 }
                 type uint32 {
                   range "0 .. 255000";
                 }
               }
             }
           }
           leaf minimum-links {
             description "Minimum number of aggregated links";
             junos:must "(!(\"interfaces ${interface} aggregated-ether-options link-speed mixed\"))";
             junos:must-message "Minimum-links option is not compatible with link-speed mixed";
             type union {
               type string {
                 pattern "<.*>|$.*";
               }
               type uint16;
             }
           }
           container minimum-bandwidth {
             presence "enable minimum-bandwidth";
             junos:must "(!(\"interfaces ${interface}  aggregated-ether-options optimize-aggregate-frr\"))";
             junos:must-message "Minimum-bandwidth and optimize-aggregate-frr are mutually exclusive";
             junos:must "(!(\"interfaces ${interface}  aggregated-ether-options minimum-links\"))";
             junos:must-message "Minimum-bandwidth and minimum-links are mutually exclusive";
             description "Minimum bandwidth configured for aggregated bundle";
             uses apply-advanced;
             leaf bw-value {
               description "Bandwidth value";
               default "1";
               type union {
                 type uint64;
                 type string {
                   pattern "<.*>|$.*";
                 }
               }
             }
             leaf bw-unit {
               description "Bandwidth unit";
               type enumeration {
                 enum "bps" {
                   description "Links are in bits per sec";
                 }
                 enum "kbps" {
                   description "Links are in kilo bits per sec";
                 }
                 enum "mbps" {
                   description "Links are in mega bits per sec";
                 }
                 enum "gbps" {
                   description "Links are in giga bits per sec ";
                 }
               }
             }
           }
           choice redundancy_choice {
             case case_1 {
             }
             case case_2 {
             }
           }
           container rebalance-periodic {
             uses apply-advanced;
           }
           leaf link-speed {
             description "Link speed of individual interface that joins the AE";
             type enumeration {
               enum "10m" {
                 description "Links are 10M";
               }
               enum "100m" {
                 description "Links are 100M";
               }
               enum "1g" {
                 description "Links are 1G";
               }
               enum "2.5g" {
                 description "Links are 2.5G";
               }
               enum "5g" {
                 description "Links are 5G";
               }
               enum "8g" {
                 description "Links are 8G";
               }
               enum "10g" {
                 description "Links are 10G";
               }
               enum "25g" {
                 description "Links are 25G";
               }
               enum "40g" {
                 description "Links are 40G";
               }
               enum "50g" {
                 description "Links are 50G";
               }
               enum "80g" {
                 description "Links are 80G";
               }
               enum "100g" {
                 description "Links are 100G";
               }
               enum "200g" {
                 description "Links are 200G";
               }
               enum "400g" {
                 description "Links are 400G";
               }
               enum "800g" {
                 description "Links are 800G";
               }
               enum "oc192" {
                 description "Links are OC-192";
               }
               enum "mixed" {
                 description "Links are various speeds";
                 junos:must "(!(\"interfaces ${interface} per-unit-scheduler\"))";
                 junos:must-message "per-unit-scheduler is incompatible with link-speed mixed";
                 junos:must "(!(\".. resilient-hash\"))";
                 junos:must-message "Mixed-rate AE is not supported along with Resilient Hashing  mode";
                 junos:must "(!(\".. load-balance adaptive\"))";
                 junos:must-message "Mixed-rate AE is not supported along with Adaptive Load balance mode";
               }
             }
           }
           container lacp {
             description "Link Aggregation Control Protocol configuration";
             uses apply-advanced;
             choice mode {
               case case_1 {
                 leaf active {
                   description "Initiate transmission of LACP packets";
                   type empty;
                 }
               }
               case case_2 {
                 leaf passive {
                   description "Respond to LACP packets";
                   type empty;
                 }
               }
             }
             leaf periodic {
               description "Timer interval for periodic transmission of LACP packets";
               type enumeration {
                 enum "fast" {
                   description "Receive packets every second";
                 }
                 enum "slow" {
                   description "Receive packets every 30 seconds";
                 }
               }
             }
             leaf multiplier {
               description "LACP timeout detection multiplier";
               type union {
                 type string {
                   pattern "<.*>|$.*";
                 }
                 type uint32 {
                   range "3 .. 30";
                 }
               }
             }
             container link-protection {
               presence "enable link-protection";
               junos:must "(!(\".. .. link-protection\"))";
               junos:must-message "LACP and non LACP based link-protection not allowed together";
               uses apply-advanced;
               leaf disable {
                 description "To turn off LACP link-protection";
                 type empty;
               }
               choice mode {
                 case case_1 {
                   leaf revertive {
                     description "Switch links when better priority link comes up";
                     type empty;
                   }
                 }
                 case case_2 {
                   leaf non-revertive {
                     description "Do not switch links when better priority link comes up";
                     type empty;
                   }
                 }
               }
               container rtg-config {
                 presence "enable rtg-config";
                 description "RTG Feature enable on AE";
                 uses apply-advanced;
                 leaf preempt-cutover-timer {
                   description "RTG preempt-cutover-timer in seconds";
                   default "1";
                   type union {
                     type string {
                       pattern "<.*>|$.*";
                     }
                     type uint32 {
                       range "0 .. 255";
                     }
                   }
                 }
               }
             }
             leaf sync-reset {
               description "On minimum-link failure notify out of sync to peer";
               type enumeration {
                 enum "disable" {
                   description "To disable minimum-link failure handling at LACP level";
                 }
                 enum "enable" {
                   description "To enable minimum-link failure handling at LACP level";
                 }
               }
             }
             leaf system-priority {
               description "Priority of the system (0 ... 65535)";
               type string;
             }
             leaf system-id {
               description "Node's System ID, encoded as a MAC address";
               type jt:mac-addr;
             }
             leaf admin-key {
               description "Node's administrative key";
               type union {
                 type uint16;
                 type string {
                   pattern "<.*>|$.*";
                 }
               }
             }
           }
           container ethernet-switch-profile {
             description "Ethernet virtual LAN/media access control-level options";
             uses apply-advanced;
             leaf-list tag-protocol-id {
               ordered-by user;
               description "IEEE 802.1q Tag Protocol Identifier values for VLAN-tagged frames";
               type string;
               max-elements 1;
             }
             leaf mac-learn-enable {
               description "Learn MAC addresses dynamically";
               type empty;
             }
           }
         }
         container es-options {
           description "ES PIC interface-specific options";
           uses apply-advanced;
           leaf backup-interface {
             description "Name of backup interface";
             type union {
               type jt:interface-device;
               type string {
                 pattern "<.*>|$.*";
               }
             }
           }
         }
         container dsl-options {
           junos:must "(!(\".. shdsl-options\"))";
           junos:must-message "SHDSL or VDSL options cannot co-exist with DSL options on the same ATM interface";
           description "DSL interface-specific options";
           uses apply-advanced;
           leaf operating-mode {
             description "DSL operating mode";
             type enumeration {
               enum "auto" {
                 description "Autonegotiate mode";
               }
               enum "ansi-dmt" {
                 description "ANSI T1.413 Issue II mode";
               }
               enum "itu-dmt" {
                 description "ITU G.992.1 mode";
               }
               enum "etsi" {
                 description "ETSI TS 101 388 V1.3.1 mode";
               }
               enum "itu-annexb-ur2" {
                 description "ITU G.992.1 UR-2 mode";
               }
               enum "itu-annexb-non-ur2" {
                 description "ITU G.992.1 Non UR-2 mode";
               }
               enum "itu-dmt-bis" {
                 description "ITU G.992.3 mode";
               }
               enum "adsl2plus" {
                 description "ITU G.992.5 mode";
               }
               enum "annexm-itu-dmt-bis" {
                 description "AnnexM ITU G.992.3 mode";
               }
               enum "annexm-adsl2plus" {
                 description "AnnexM ITU G.992.5 mode";
               }
             }
           }
         }
         container vdsl-options {
           description "VDSL interface-specific options";
           uses apply-advanced;
           leaf vdsl-profile {
             description "VDSL profile";
             type enumeration {
               enum "auto" {
                 description "Auto";
               }
               enum "8a" {
                 description "Profile 8a";
               }
               enum "8b" {
                 description "Profile 8b";
               }
               enum "8c" {
                 description "Profile 8c";
               }
               enum "8d" {
                 description "Profile 8d";
               }
               enum "12a" {
                 description "Profile 12a";
               }
               enum "12b" {
                 description "Profile 12b";
               }
               enum "17a" {
                 description "Profile 17a";
               }
             }
           }
           leaf sra {
             description "DSL SRA";
             default "disable";
             type enumeration {
               enum "enable" {
                 description "Enable SRA";
               }
               enum "disable" {
                 description "Disable SRA";
               }
             }
           }
           leaf v43 {
             description "DSL V43 tones";
             default "enable";
             type enumeration {
               enum "enable" {
                 description "Enable V43";
               }
               enum "disable" {
                 description "Disable V43";
               }
             }
           }
           leaf sos {
             description "Enable SOS";
             type empty;
           }
         }
         container dsl-sfp-options {
           description "DSL SFP options";
           uses apply-advanced;
           container adsl-options {
             description "ADSL options";
             uses apply-advanced;
             leaf vpi {
               description "Virtual path identifier";
               junos:must "(\".. vci\")";
               junos:must-message "vci must be specified";
               type union {
                 type string {
                   pattern "<.*>|$.*";
                 }
                 type uint32 {
                   range "0 .. 255";
                 }
               }
             }
             leaf vci {
               description "Virtual circuit identifier";
               junos:must "(\".. vpi\")";
               junos:must-message "vpi must be specified";
               type union {
                 type string {
                   pattern "<.*>|$.*";
                 }
                 type uint32 {
                   range "32 .. 65535";
                 }
               }
             }
             leaf encap {
               description "Encapsulation";
               junos:must "((\".. vci\" && \".. vpi\"))";
               junos:must-message "vci and vpi must be specified";
               type enumeration {
                 enum "bypass" {
                   description "Bypass";
                 }
                 enum "llcsnap-bridged-802dot1q" {
                   description "LLCSNAP bridged 802.1q";
                 }
                 enum "llcsnap-routed-ip" {
                   description "LLCSNAP routed ip";
                 }
                 enum "vc-mux-bridged" {
                   description "VC MUX bridged";
                 }
                 enum "vc-mux-routed-ip" {
                   description "VC MUX routed ip";
                 }
                 enum "generic" {
                   description "Generic";
                 }
               }
             }
             leaf annex {
               description "Annex type";
               junos:must "((\".. vci\" && \".. vpi\"))";
               junos:must-message "vci and vpi must be specified";
               type enumeration {
                 enum "auto" {
                   description "Annex type auto";
                 }
                 enum "annexj-off" {
                   description "Annex type annexj turn off";
                 }
               }
             }
           }
           container vdsl-options {
             description "VDSL options";
             uses apply-advanced;
             leaf profile {
               description "VDSL profile";
               type enumeration {
                 enum "auto" {
                   description "Automatic";
                 }
                 enum "8a" {
                   description "Profile 8a";
                 }
                 enum "8b" {
                   description "Profile 8b";
                 }
                 enum "8c" {
                   description "Profile 8c";
                 }
                 enum "8d" {
                   description "Profile 8d";
                 }
                 enum "12a" {
                   description "Profile 12a";
                 }
                 enum "12b" {
                   description "Profile 12b";
                 }
                 enum "17a" {
                   description "Profile 17a";
                 }
                 enum "30a" {
                   description "Profile 30a";
                 }
               }
             }
             leaf carrier {
               description "Carrier setting";
               type enumeration {
                 enum "auto" {
                   description "Automatic";
                 }
                 enum "a43" {
                   description "Carrier A43";
                 }
                 enum "b43" {
                   description "Carrier B43";
                 }
               }
             }
           }
           container gfast-options {
             description "G.fast options";
             uses apply-advanced;
             leaf carrier {
               description "Carrier setting";
               type enumeration {
                 enum "a43" {
                   description "Carrier A43";
                 }
                 enum "a43c" {
                   description "Carrier A43C";
                 }
                 enum "b43" {
                   description "Carrier B43";
                 }
                 enum "b43c" {
                   description "Carrier B43C";
                 }
               }
             }
           }
         }
         container shdsl-options {
           junos:must "(!(\"interfaces ${interface} vdsl-options\"))";
           junos:must-message "VDSL options cannot co-exist with SHDSL options on the same interface";
           junos:must "(!(\"interfaces ${interface} dsl-options\"))";
           junos:must-message "DSL options cannot co-exist with SHDSL options on the same interface";
           description "SHDSL interface-specific options";
           uses apply-advanced;
           leaf annex {
             description "Type of SHDSL annex";
             default "annex-b";
             type enumeration {
               enum "annex-a" {
                 description "Annex-a PIC";
               }
               enum "annex-b" {
                 description "Annex-b PIC";
               }
               enum "annex-f" {
                 description "Annex-f PIC";
               }
               enum "annex-g" {
                 description "Annex-g PIC";
               }
               enum "annex-auto" {
                 description "Annex-auto PIC";
               }
             }
           }
           leaf line-rate {
             description "SHDSL line rate";
             type string;
           }
           leaf loopback {
             description "Loopback mode";
             type enumeration {
               enum "local" {
                 description "Local loopback";
               }
               enum "remote" {
                 description "Remote loopback";
               }
             }
           }
           container snr-margin {
             presence "enable snr-margin";
             description "Signal to noise ratio margin";
             uses apply-advanced;
             leaf current {
               description "Current signal to noise ratio margin";
               units "dB";
               type string;
             }
             leaf snext {
               description "SNEXT signal to noise ratio margin";
               units "dB";
               type string;
             }
           }
         }
         container data-input {
           description "Configuration for drop-insert data input";
           uses apply-advanced;
           choice input-choice {
             case case_1 {
               leaf system {
                 description "Data sourced from system";
                 type empty;
               }
             }
             case case_2 {
               leaf interface {
                 description "Interface that acts as data source";
                 junos:must "(!(\"interfaces $$ data-input\"))";
                 junos:must-message "Interface should not have data-input configured";
                 type union {
                   type jt:interface-device;
                   type string {
                     pattern "<.*>|$.*";
                   }
                 }
               }
             }
           }
         }
         container switch-options {
           description "Front end ports configuration";
           uses apply-advanced;
           list switch-port {
             key name;
             leaf name {
               description "Front end port number";
               junos:cli-feature "nokeyword";
               type union {
                 type string {
                   pattern "<.*>|$.*";
                 }
                 type uint32 {
                   range "0 .. 15";
                 }
               }
             }
             uses apply-advanced;
             choice auto-negotiation-choice {
               leaf auto-negotiation {
                 description "Enable auto-negotiation";
                 type empty;
               }
               leaf no-auto-negotiation {
                 description "Don't enable auto-negotiation";
                 type empty;
               }
             }
             leaf link-mode {
               description "Link operational mode";
               junos:must "(\".. speed\")";
               junos:must-message "speed must be configured with link-mode";
               type enumeration {
                 enum "half-duplex" {
                   description "Half-duplex operation";
                 }
                 enum "full-duplex" {
                   description "Full-duplex operation";
                 }
               }
             }
             leaf speed {
               description "Link speed";
               junos:must "(\".. link-mode\")";
               junos:must-message "link-mode must be configured with speed";
               type enumeration {
                 enum "10m" {
                 }
                 enum "100m" {
                 }
                 enum "1g" {
                 }
               }
             }
             leaf vlan-id {
               description "VLAN ID for this port";
               junos:must "(\".. .. .. vlan-tagging\")";
               junos:must-message "vlan-tagging needs to be enabled to support vlan-id";
               type union {
                 type string {
                   pattern "<.*>|$.*";
                 }
                 type uint32 {
                   range "0 .. 4094";
                 }
               }
             }
             leaf cascade-port {
               description "Port externally connected to another cascade port";
               junos:must "(!(\".. vlan-id\"))";
               junos:must-message "Cascade port cannot have VLAN id";
               junos:must "(\".. .. .. vlan-tagging\")";
               junos:must-message "vlan-tagging needs to be enabled to support cascade-port";
               type empty;
             }
           }
         }
         container container-options {
           description "Container interface specific options";
           uses apply-advanced;
           container container-type {
             presence "enable container-type";
             description "Protocol type of the container interface";
             uses apply-advanced;
             choice container-type-choice {
               case case_1 {
                 container aps {
                   description "APS options on the container";
                   presence "enable aps";
                   junos:must "((\".. .. member-interface-type sonet\" || (\".. .. member-interface-type atm\" || (\".. .. member-interface-type channelized-sonet\" || \".. .. member-interface-type channelized-sdh\"))))";
                   junos:must-message "APS can be enabled on Sonet, Channelized-Sonet, Channelized-SDH  or ATM interfaces only";
                   uses aps_type;
                 }
               }
             }
           }
           container member-interface-type {
             description "Link type of members of container";
             uses apply-advanced;
             choice member_interface_type_choice {
               case case_1 {
                 container sonet {
                   uses apply-advanced;
                   leaf member-interface-speed {
                     description "Link speed of members of container";
                     type enumeration {
                       enum "oc3" {
                         description "Links are OC-3";
                       }
                       enum "oc12" {
                         description "Links are OC-12";
                       }
                       enum "oc48" {
                         description "Links are OC-48";
                       }
                       enum "oc192" {
                         description "Links are OC-192";
                       }
                       enum "oc768" {
                         description "Links are OC-768";
                       }
                       enum "mixed" {
                         description "Links are of different speeds";
                       }
                     }
                   }
                 }
               }
               case case_2 {
                 container atm {
                   uses apply-advanced;
                   leaf member-interface-speed {
                     description "Link speed of members of container";
                     type enumeration {
                       enum "oc3" {
                         description "Links are OC-3";
                       }
                       enum "oc12" {
                         description "Links are OC-12";
                       }
                       enum "oc48" {
                         description "Links are OC-48";
                       }
                     }
                   }
                 }
               }
               case case_3 {
                 container channelized-sonet {
                   uses apply-advanced;
                   leaf member-interface-speed {
                     description "Link speed of members of container";
                     type enumeration {
                       enum "coc3" {
                         description "Links are COC-3";
                       }
                       enum "coc12" {
                         description "Links are COC-12";
                       }
                       enum "coc48" {
                         description "Links are COC-48";
                       }
                       enum "coc192" {
                         description "Links are COC-192";
                       }
                       enum "coc768" {
                         description "Links are COC-768";
                       }
                     }
                   }
                 }
               }
               case case_4 {
                 container channelized-sdh {
                   uses apply-advanced;
                   leaf member-interface-speed {
                     description "Link speed of members of container";
                     type enumeration {
                       enum "cstm1" {
                         description "Links are cstm-1";
                       }
                       enum "cstm4" {
                         description "Links are cstm-4";
                       }
                       enum "cstm16" {
                         description "Links are cstm-16";
                       }
                       enum "coc64" {
                         description "Links are cstm-64";
                       }
                       enum "cstm256" {
                         description "Links are cstm256";
                       }
                     }
                   }
                 }
               }
             }
           }
           container redundancy {
             description "Container interface redundancy options";
             uses apply-advanced;
             container hold-time {
               junos:cli-feature "oneliner";
               description "Hold time for link up and link down";
               leaf up {
                 description "Link up hold time";
                 units "milliseconds";
                 type union {
                   type string {
                     pattern "<.*>|$.*";
                   }
                   type uint32 {
                     range "0 .. 65534";
                   }
                 }
               }
               leaf down {
                 description "Link down hold time";
                 units "milliseconds";
                 type union {
                   type string {
                     pattern "<.*>|$.*";
                   }
                   type uint32 {
                     range "0 .. 65534";
                   }
                 }
               }
             }
           }
           leaf-list container-list {
             ordered-by user;
             description "List of container interfaces this member link is associated to";
             type union {
               type jt:interface-device;
               type string {
                 pattern "<.*>|$.*";
               }
             }
           }
           choice redundancy-type {
             case case_1 {
               choice aps-redundancy {
                 case case_1 {
                   leaf primary {
                     description "This member link is primary interface of the container";
                     type empty;
                   }
                 }
                 case case_2 {
                   leaf standby {
                     description "This member link is standby interface of the container";
                     type empty;
                   }
                 }
               }
             }
           }
           leaf fast-aps {
             description "Fast APS switch";
             type empty;
           }
           leaf allow-configuration-override {
             description "Allow physical configuration of member link to override container configuration";
             type empty;
           }
         }
         list unit {
           key name;
           description "Logical interface";
           leaf name {
             junos:cli-feature "nokeyword";
             type string;
           }
           uses apply-advanced;
           leaf interface-tag {
             description "Interface tag name";
             type string {
               length "1 .. 64";
               junos:posix-pattern "^[A-Za-z0-9][_0-9A-Za-z-]*$";
               junos:pattern-message "Must be a non-reserved string of 64 characters or less";
             }
           }
           container policer-overhead {
             description "Policer overhead adjustment for this unit";
             uses apply-advanced;
             leaf policer-overhead-value {
               description "Policer overhead bytes to be accounted in ingress and egress";
               junos:cli-feature "nokeyword";
               units "bytes";
               junos:must "((!(\".. ingress\") && !(\".. egress\")))";
               junos:must-message "Do not use the options ingress or egress when adjust values are specified";
               type union {
                 type string {
                   pattern "<.*>|$.*";
                 }
                 type int32;
               }
             }
             leaf ingress {
               description "Ingress value in bytes";
               units "bytes";
               type union {
                 type string {
                   pattern "<.*>|$.*";
                 }
                 type int32 {
                   range "-64 .. 64";
                 }
               }
             }
             leaf egress {
               description "Egress value in bytes";
               units "bytes";
               type union {
                 type string {
                   pattern "<.*>|$.*";
                 }
                 type int32 {
                   range "-64 .. 64";
                 }
               }
             }
           }
           leaf alias {
             description "Interface alias";
             junos:must "(!(\"interfaces interface-range $$\"))";
             junos:must-message "Interface alias cannot be an existing interface range name";
             type string;
           }
           leaf proxy-macip-advertisement {
             description "Proxy advertisement of type 2 MAC+IP route for EVPN";
             type empty;
           }
           leaf virtual-gateway-accept-data {
             description "Accept packets destined for virtual gateway address";
             type empty;
           }
           container peer-psd {
             presence "enable peer-psd";
             junos:cli-feature "oneliner";
             description "Peer psd";
             leaf psd-name {
               description "Peer psd name";
               junos:cli-feature "nokeyword";
               junos:must "(\".. .. peer-interface\")";
               junos:must-message "peer-interface must be configured on this interface";
               type string;
             }
           }
           container peer-interface {
             presence "enable peer-interface";
             junos:cli-feature "oneliner-plus";
             description "Peer interface";
             uses apply-advanced;
             leaf interface-name {
               description "Peer interface name";
               junos:cli-feature "nokeyword";
               junos:must "((\".. .. peer-psd\" || \"interfaces $$-IFL peer-interface\"))";
               junos:must-message "Peer interface or peer psd must be configured";
               type union {
                 type jt:interface-unit;
                 type string {
                   pattern "<.*>|$.*";
                 }
               }
             }
           }
           container interface-shared-with {
             presence "enable interface-shared-with";
             junos:must "(\"chassis system-domains\")";
             junos:must-message "Chassis system-domains must be configured";
             junos:cli-feature "oneliner-plus";
             description "Specify which PSD owns this logical interface";
             uses apply-advanced;
             leaf psd-name {
               description "Name of protected system domain (psd[1-31], ex. psd2)";
               junos:cli-feature "nokeyword";
               type string {
                 junos:posix-pattern "^psd([1-9]|[1-2][0-9]|[3][0-1])$";
                 junos:pattern-message "Protected system domain name is a string consisting of \'psd\' follows by the PSD ID (1-31), ex. psd2";
               }
             }
           }
           choice enable-disable {
             case case_1 {
               leaf disable {
                 description "Disable this logical interface";
                 type empty;
               }
             }
           }
           leaf passive-monitor-mode {
             description "Use interface to tap packets from another router";
             type empty;
           }
           leaf clear-dont-fragment-bit {
             description "Clear DF bit in packet (AS PIC and J-series only as well as MIF)";
             type empty;
           }
           leaf description {
             description "Text description of interface";
             type string;
           }
           leaf encapsulation {
             description "Logical link-layer encapsulation";
             type enumeration {
               enum "atm-nlpid" {
                 description "ATM NLPID encapsulation";
               }
               enum "atm-cisco-nlpid" {
                 description "Cisco-compatible ATM NLPID encapsulation";
               }
               enum "atm-snap" {
                 description "ATM LLC/SNAP encapsulation";
               }
               enum "atm-vc-mux" {
                 description "ATM VC multiplexing";
               }
               enum "atm-ccc-vc-mux" {
                 description "ATM VC for CCC";
               }
               enum "atm-tcc-vc-mux" {
                 description "ATM VC for translational cross-connect";
               }
               enum "atm-tcc-snap" {
                 description "ATM LLC/SNAP for translational cross-connect";
               }
               enum "atm-ccc-cell-relay" {
                 description "ATM cell relay for CCC";
               }
               enum "vlan-vci-ccc" {
                 description "CCC for VLAN Q-in-Q and ATM VPI/VCI interworking";
               }
               enum "ether-over-atm-llc" {
                 description "Ethernet over ATM (LLC/SNAP) encapsulation";
               }
               enum "ether-vpls-over-atm-llc" {
                 description "Ethernet VPLS over ATM (bridging) encapsulation";
               }
               enum "ppp-over-ether-over-atm-llc" {
                 description "PPPoE over ATM (LLC/SNAP) encapsulation";
                 junos:must "(!(\".. family\"))";
                 junos:must-message "Can't configure protocol family with encapsulation ppp-over-ether-over-atm-llc";
                 junos:must "(\".. .. encapsulation ethernet-over-atm\")";
                 junos:must-message "Physical link-layer encapsulation must be ethernet-over-atm";
               }
               enum "ppp-over-ether" {
                 description "PPPoE encapsulation";
                 junos:must "(!(\"forwarding-options hyper-mode\"))";
                 junos:must-message "To configure encapsulation ppp-over-ether, 'forwarding-options hyper-mode' should not be configured";
                 junos:must "(!(\".. family\"))";
                 junos:must-message "Can't configure protocol family with encapsulation ppp-over-ether";
               }
               enum "atm-ppp-vc-mux" {
                 description "ATM PPP over raw AAL5";
               }
               enum "atm-ppp-llc" {
                 description "ATM PPP over AAL5/LLC";
               }
               enum "atm-mlppp-llc" {
                 description "ATM MLPPP over AAL5/LLC";
               }
               enum "frame-relay-ppp" {
                 description "PPP over Frame Relay";
                 junos:must "(!(\".. family inet6\"))";
                 junos:must-message "family inet6 is not supported on encapsulation frame-relay-ppp";
                 junos:must "(!(\".. family inet\"))";
                 junos:must-message "family inet is not supported on encapsulation frame-relay-ppp";
                 junos:must "(\".. .. encapsulation frame-relay\")";
                 junos:must-message "Physical link-layer encapsulation must be frame-relay";
               }
               enum "frame-relay-ccc" {
                 description "Frame Relay DLCI for CCC";
               }
               enum "frame-relay" {
                 description "Frame Relay DLCI";
               }
               enum "frame-relay-tcc" {
                 description "Frame Relay DLCI for translational cross-connect";
               }
               enum "frame-relay-ether-type" {
                 description "Cisco-compatible Frame Relay Encapsulation DLCI";
                 junos:must "((\".. .. encapsulation flexible-frame-relay\" || (\".. .. encapsulation frame-relay-ether-type\" || \".. .. encapsulation frame-relay-ether-type-tcc\")))";
                 junos:must-message "Interface encapsulation must be cisco-compatible or flexible frame relay";
               }
               enum "frame-relay-ether-type-tcc" {
                 description "Cisco-compatible Frame Relay Encapsulation DLCI for TCC";
               }
               enum "ether-vpls-fr" {
                 description "Ethernet VPLS over Frame Relay (bridging) encapsulation";
               }
               enum "vlan-ccc" {
                 description "802.1q tagging for a cross-connect";
               }
               enum "ethernet-ccc" {
                 description "Ethernet for a cross-connect";
               }
               enum "vlan-vpls" {
                 description "VLAN virtual private LAN service";
               }
               enum "vlan-bridge" {
                 description "VLAN layer-2 bridging";
               }
               enum "ethernet-tcc" {
                 description "Ethernet translational cross-connect";
               }
               enum "dix" {
                 description "Ethernet DIXv2 (RFC 894)";
               }
               enum "ethernet" {
                 description "Ethernet II (RFC 894)";
               }
               enum "ethernet-vpls" {
                 description "Ethernet II virtual private LAN service";
               }
               enum "ethernet-bridge" {
                 description "Ethernet II bridging";
               }
               enum "vlan" {
                 description "802.1q-tagged Ethernet";
               }
               enum "vlan-tcc" {
                 description "802.1q tagging for a translational cross-connect";
               }
               enum "multilink-ppp" {
                 description "Multilink PPP";
               }
               enum "multilink-frame-relay-end-to-end" {
                 description "Multilink Frame Relay end-to-end (FRF.15)";
               }
               enum "ppp-ccc" {
                 description "Serial PPP device for a cross-connect";
               }
             }
           }
           leaf mtu {
             description "Maximum transmission unit packet size";
             type union {
               type string {
                 pattern "<.*>|$.*";
               }
               type uint32;
             }
           }
           choice pointedness {
             case case_1 {
               leaf point-to-point {
                 description "Point-to-point connection";
                 type empty;
               }
             }
             case case_2 {
               leaf multipoint {
                 description "Multipoint connection";
                 type empty;
               }
             }
           }
           leaf bandwidth {
             description "Logical unit bandwidth (informational only)";
             type string;
           }
           container radio-router {
             description "Parameters for dynamic link cost management";
             presence "enable radio-router";
             junos:cli-feature "oneliner-plus";
             uses dynamic_ifbw_parms_type;
           }
           choice traps-choice {
             leaf traps {
               description "Enable SNMP notifications on state changes";
               type empty;
             }
             leaf no-traps {
               description "Don't enable SNMP notifications on state changes";
               type empty;
             }
           }
           choice routing-services-choice {
             leaf routing-services {
               description "Enable routing services";
               status deprecated;
               type empty;
             }
             leaf no-routing-services {
               description "Don't enable routing services";
               status deprecated;
               type empty;
             }
           }
           container routing-service {
             description "Routing Services on this interface";
             uses apply-advanced;
             choice enable-disable {
               case case_1 {
                 leaf enable {
                   description "Enable Routing Service";
                   type empty;
                 }
               }
               case case_2 {
                 leaf disable {
                   description "Disable Routing Service";
                   type empty;
                 }
               }
             }
           }
           container arp-resp {
             presence "enable arp-resp";
             junos:cli-feature "oneliner";
             description "Knob to control ARP response on the interface, default is restricted";
             choice arp-response-options {
               case case_1 {
                 leaf unrestricted {
                   description "Enable unrestricted ARP respone on the interface";
                   type empty;
                 }
               }
               case case_2 {
                 leaf restricted {
                   description "Enable restricted proxy ARP response on the interface";
                   type empty;
                 }
               }
             }
           }
           container proxy-arp {
             presence "enable proxy-arp";
             junos:must "(!(\"switch-options no-arp-trap \"))";
             junos:must-message "Cannot enable proxy ARP with no-arp-trap";
             junos:cli-feature "oneliner";
             description "Enable proxy ARP on the interface, default is unrestricted";
             choice proxyarp-options {
               case case_1 {
                 leaf unrestricted {
                   description "Enable unrestricted proxy ARP on the interface";
                   type empty;
                 }
               }
               case case_2 {
                 leaf restricted {
                   description "Enable restricted proxy ARP on the interface";
                   type empty;
                 }
               }
             }
           }
           choice vlan_choice {
             case case_1 {
               leaf vlan-id {
                 description "Virtual LAN identifier value for 802.1q VLAN tags";
                 junos:must "(!(\"interfaces ${interface} stacked-vlan-tagging\"))";
                 junos:must-message "vlan-id is not supported on stacked-vlan-tagging mode";
                 junos:must "((unique \"interfaces ${interface} unit <*> vlan-id $$\" || !(\"interfaces ${interface} flexible-vlan-tagging\")))";
                 junos:must-message "duplicate vlan-id";
                 type string;
               }
             }
             case case_2 {
               leaf vlan-id-range {
                 description "Virtual LAN identifier range of form vid1-vid2";
                 junos:must "((\"interfaces ${interface} vlan-tagging\" || \"interfaces ${interface} flexible-vlan-tagging\"))";
                 junos:must-message "valid only with vlan-tagging or flexible-vlan-tagging mode";
                 type jt:vlan-range;
               }
             }
             case case_3 {
               leaf-list inner-vlan-id-swap-ranges {
                 description "Inner vlan-id swap range(s) of form vid1-vid2 for dynamic L2 VLANs";
                 type jt:vlan-range;
               }
             }
             case case_4 {
               leaf-list vlan-id-list {
                 description "List of VLAN identifiers";
                 junos:must "((\" .. encapsulation vlan-ccc\" || (\"interfaces ${interface} encapsulation extended-vlan-ccc\" || (\" .. encapsulation vlan-vpls\" || (\"interfaces ${interface} encapsulation extended-vlan-vpls\" || (\" .. encapsulation vlan-bridge\" || \"interfaces ${interface} encapsulation extended-vlan-bridge\"))))))";
                 junos:must-message "valid only with ccc/vpls/bridge encapsulation";
                 junos:must "((\"interfaces ${interface} vlan-tagging\" || \"interfaces ${interface} flexible-vlan-tagging\"))";
                 junos:must-message "valid only with vlan-tagging or flexible-vlan-tagging mode";
                 junos:must "(\".. input-vlan-map push\")";
                 junos:must-message "interface with vlan-id-list is supported only with input-vlan-map push";
                 type jt:vlan-range;
               }
             }
             case case_5 {
               leaf-list vlan-tag {
                 ordered-by user;
                 description "IEEE 802.1q tag list for VLAN tagged frames";
                 status deprecated;
                 type string;
               }
             }
             case case_6 {
               container vlan-tags {
                 presence "enable vlan-tags";
                 junos:must "((!(\"interfaces ${interface} vlan-tagging\") || !((\". inner\" || (\". inner-range\" || \". inner-list\")))))";
                 junos:must-message "inner/inner-range/inner-list is valid only on stacked-vlan-tagging and flexible-vlan-tagging mode";
                 junos:must "((!(\"interfaces ${interface} stacked-vlan-tagging\") || (\". inner\" || (\". inner-range\" || \". inner-list\"))))";
                 junos:must-message "inner/inner-range/inner-list must be defined for stacked-vlan-tagging mode";
                 junos:must "((\".. demux-options\" || (\"interfaces ${interface} vlan-tagging\" || (\"interfaces ${interface} stacked-vlan-tagging\" || \"interfaces ${interface} flexible-vlan-tagging\"))))";
                 junos:must-message "valid only with vlan-tagging, stacked-vlan-tagging or flexible-vlan-tagging mode";
                 junos:cli-feature "oneliner";
                 description "IEEE 802.1q tags";
                 leaf outer {
                   description "[tpid.]vlan-id, tpid format is 0xNNNN and is optional";
                   type string;
                 }
                 choice inner_choice {
                   case case_1 {
                     leaf inner {
                       description "[tpid.]vlan-id, tpid format is 0xNNNN and is optional";
                       type string;
                     }
                   }
                   case case_2 {
                     leaf inner-range {
                       description "[tpid.]vid1-vid2, tpid format is 0xNNNN and is optional";
                       type string {
                         junos:posix-pattern "^((0[Xx][0-9A-Fa-f]{4}.){0,1}([1-9][0-9]{0,2}|[1-3][0-9]{3}|40[0-8][0-9]|409[0-4])-([1-9][0-9]{0,2}|[1-3][0-9]{3}|40[0-8][0-9]|409[0-4]))$";
                         junos:pattern-message "vid in vlan-tag ([0xNNNN.]vid1-vid2) must be 1 to 4094";
                       }
                     }
                   }
                   case case_3 {
                     leaf-list inner-list {
                       description "List of VLAN identifiers";
                       junos:must "((\" .. .. encapsulation vlan-ccc\" || (\"interfaces ${interface} encapsulation extended-vlan-ccc\" || (\" .. .. encapsulation vlan-vpls\" || (\"interfaces ${interface} encapsulation extended-vlan-vpls\" || (\" .. .. encapsulation vlan-bridge\" || \"interfaces ${interface} encapsulation extended-vlan-bridge\"))))))";
                       junos:must-message "valid only with ccc/vpls/bridge encapsulation";
                       type jt:vlan-range;
                     }
                   }
                 }
               }
             }
           }
           leaf deep-vlan-qualified-learning {
             description "Enable qualified MAC-address learning on the specified vlan tag";
             junos:must "((\".. vlan-tags outer\" && \".. vlan-tags inner\"))";
             junos:must-message "deep-vlan-qualified-learning can be specified only with one outer and one inner vlan tags";
             type union {
               type string {
                 pattern "<.*>|$.*";
               }
               type uint32 {
                 range 3;
               }
             }
           }
           leaf native-inner-vlan-id {
             description "Native virtual LAN identifier for singly tagged frames";
             junos:must "((\".. vlan-tags\" || \".. family bridge inner-vlan-id-list\"))";
             junos:must-message "native-inner-vlan-id can be specified only on a dual vlan tagged unit";
             junos:must "(\"interfaces ${interface} flexible-vlan-tagging\")";
             junos:must-message "native-inner-vlan-id can be specified only with flexible-vlan-tagging mode";
             type union {
               type string {
                 pattern "<.*>|$.*";
               }
               type uint32 {
                 range "0 .. 4094";
               }
             }
           }
           container accept-source-mac {
             junos:must "(!(\".. family ethernet-switching\"))";
             junos:must-message "source mac filters not allowed on ethernet switched port";
             description "Remote media access control address to/from which to accept traffic";
             uses apply-advanced;
             list mac-address {
               key name;
               description "Remote MAC address";
               uses mac_list;
             }
           }
           container input-vlan-map {
             description "VLAN map operation on input";
             junos:cli-feature "oneliner-plus";
             uses vlan_map;
           }
           container output-vlan-map {
             description "VLAN map operation on output";
             junos:cli-feature "oneliner-plus";
             uses vlan_map;
           }
           leaf swap-by-poppush {
             description "Pop original vlan tag and then push a new vlan tag";
             type empty;
           }
           leaf receive-lsp {
             description "Name of incoming label-switched path";
             type string;
           }
           leaf transmit-lsp {
             description "Name of outgoing label-switched path";
             type string;
           }
           leaf dlci {
             description "Frame Relay data-link control identifier";
             type union {
               type string {
                 pattern "<.*>|$.*";
               }
               type uint32 {
                 range "1 .. 1022";
               }
             }
           }
           leaf multicast-dlci {
             description "Frame Relay data-link control identifier for multicast packets";
             type union {
               type string {
                 pattern "<.*>|$.*";
               }
               type uint32 {
                 range "1 .. 1022";
               }
             }
           }
           choice vci_type {
             case case_1 {
               leaf vci {
                 description "ATM point-to-point virtual circuit identifier ([vpi.]vci)";
                 junos:must "(!(\".. encapsulation vlan-vci-ccc\"))";
                 junos:must-message "'vci-range' must be used with encapsulation vlan-vci-ccc";
                 type jt:atm-vci;
               }
             }
             case case_2 {
               leaf allow-any-vci {
                 description "Allow all VCIs to open in atm-ccc-cell-relay mode";
                 type empty;
               }
             }
             case case_3 {
               leaf vpi {
                 description "ATM point-to-point virtual path identifier (vpi)";
                 type union {
                   type string {
                     pattern "<.*>|$.*";
                   }
                   type uint32 {
                     range "0 .. 255";
                   }
                 }
               }
             }
             case case_4 {
               leaf trunk-id {
                 description "ATM trunk identifier";
                 type union {
                   type string {
                     pattern "<.*>|$.*";
                   }
                   type uint32 {
                     range "0 .. 31";
                   }
                 }
               }
             }
           }
           choice psn_vci_type {
             case case_1 {
             }
             case case_2 {
             }
           }
           container atm-l2circuit-mode {
             junos:cli-feature "oneliner";
             description "Select ATM Layer 2 circuit transport mode";
             choice mode_choice {
               case case_1 {
                 leaf cell {
                   description "ATM Layer 2 circuit cell mode";
                   type empty;
                 }
               }
               case case_2 {
                 leaf aal5 {
                   description "ATM Layer 2 circuit AAL5 mode";
                   type empty;
                 }
               }
             }
           }
           container vci-range {
             junos:must "(!(\".. vci\"))";
             junos:must-message "'vci-range' and 'vci' statements cannot co-exist";
             junos:cli-feature "oneliner";
             description "ATM VCI range start <start-vci> end <end-vci>";
             leaf start {
               description "ATM VCI range's start value";
               type union {
                 type string {
                   pattern "<.*>|$.*";
                 }
                 type uint16 {
                   range "32 .. 4094";
                 }
               }
             }
             leaf end {
               description "ATM VCI range's end value";
               type union {
                 type string {
                   pattern "<.*>|$.*";
                 }
                 type uint16 {
                   range "32 .. 4094";
                 }
               }
             }
           }
           leaf trunk-bandwidth {
             description "ATM trunk bandwidth";
             units "bits per second";
             type string;
           }
           leaf multicast-vci {
             description "ATM virtual circuit identifier for multicast packets";
             type jt:atm-vci;
           }
           container shaping {
             description "Virtual circuit traffic-shaping options";
             uses dcd_shaping_config;
           }
           container oam-period {
             junos:cli-feature "oneliner";
             description "OAM cell period";
             choice oam_period_choices {
               case case_1 {
                 leaf oam-period {
                   description "OAM cell period";
                   junos:cli-feature "nokeyword";
                   units "seconds";
                   type union {
                     type string {
                       pattern "<.*>|$.*";
                     }
                     type uint32 {
                       range "1 .. 900";
                     }
                   }
                 }
               }
               case case_2 {
                 container disable {
                   presence "enable disable";
                   junos:cli-feature "oneliner";
                   description "Disable F5 OAM loopback";
                 }
               }
             }
           }
           container oam-liveness {
             description "OAM virtual circuit liveness parameters";
             uses apply-advanced;
             leaf up-count {
               description "Number of OAM cells to consider VC up";
               type union {
                 type string {
                   pattern "<.*>|$.*";
                 }
                 type uint32 {
                   range "1 .. 255";
                 }
               }
             }
             leaf down-count {
               description "Number of OAM cells to consider VC down";
               type union {
                 type string {
                   pattern "<.*>|$.*";
                 }
                 type uint32 {
                   range "1 .. 255";
                 }
               }
             }
           }
           container ppp-options {
             description "Point-to-Point Protocol interface-specific options";
             uses ppp_options_type;
           }
           container pppoe-options {
             description "PPP over Ethernet interface-specific options";
             uses pppoe_options_type;
           }
           choice keepalive_choices {
             case case_1 {
               container keepalives {
                 description "Send or demand keepalive messages";
                 presence "enable keepalives";
                 junos:cli-feature "oneliner";
                 uses keepalives_type;
               }
             }
             case case_2 {
               leaf no-keepalives {
                 description "Do not send or demand keepalive messages";
                 type empty;
               }
             }
           }
           leaf inverse-arp {
             description "Enable inverse ARP";
             type empty;
           }
           leaf transmit-weight {
             description "ATM2 transmit weight for VC under VP tunnel";
             type union {
               type string {
                 pattern "<.*>|$.*";
               }
               type uint16 {
                 range "1 .. 32767";
               }
             }
           }
           container epd-threshold {
             description "Early packet discard threshold for ATM2";
             junos:cli-feature "oneliner";
             uses epd_threshold_config;
           }
           leaf cell-bundle-size {
             description "L2 circuit cell bundle size";
             units "cells";
             type union {
               type string {
                 pattern "<.*>|$.*";
               }
               type uint32 {
                 range "1 .. 176";
               }
             }
           }
           leaf cell-bundle-timeout {
             description "L2 circuit cell bundle timeout";
             units "microseconds";
             type union {
               type string {
                 pattern "<.*>|$.*";
               }
               type uint32 {
                 range "1 .. 512";
               }
             }
           }
           leaf plp-to-clp {
             description "Enable ATM2 PLP to CLP copy";
             type empty;
           }
           leaf atm-scheduler-map {
             description "Assign ATM2 CoS scheduling map";
             type union {
               type string {
                 pattern "default";
               }
               type string;
             }
           }
           leaf mrru {
             description "Maximum received reconstructed unit";
             units "bytes";
             type union {
               type string {
                 pattern "<.*>|$.*";
               }
               type uint16 {
                 range "1500 .. 4500";
               }
             }
           }
           leaf short-sequence {
             description "Short sequence number header format (MLPPP only)";
             type empty;
           }
           leaf fragment-threshold {
             description "Fragmentation threshold";
             units "bytes";
             type union {
               type string {
                 pattern "<.*>|$.*";
               }
               type uint32 {
                 range "64 .. 4500";
               }
             }
           }
           leaf drop-timeout {
             description "Drop timeout";
             units "milliseconds";
             type union {
               type string {
                 pattern "<.*>|$.*";
               }
               type uint16 {
                 range "0 .. 2000";
               }
             }
           }
           leaf disable-mlppp-inner-ppp-pfc {
             description "Disable compression for inner PPP header in MLPPP payload";
             type empty;
           }
           leaf minimum-links {
             description "Minimum number of links to sustain the bundle";
             type union {
               type string {
                 pattern "<.*>|$.*";
               }
               type uint16;
             }
           }
           leaf multilink-max-classes {
             description "Number of multilink classes";
             type union {
               type string {
                 pattern "<.*>|$.*";
               }
               type uint16;
             }
           }
           container compression {
             presence "enable compression";
             junos:must "(!(\".. encapsulation multilink-frame-relay-end-to-end\"))";
             junos:must-message "CRTP is not supported for multilink-frame-relay-end-to-end encapsulation";
             description "Various packet header compressions";
             uses apply-advanced;
             container rtp {
               presence "enable rtp";
               description "Compress and decompress RTP";
               uses apply-advanced;
               leaf f-max-period {
                 description "Maximum number of compressed packets between transmission of full headers";
                 type union {
                   type string {
                     pattern "<.*>|$.*";
                   }
                   type uint32 {
                     range "1 .. 65535";
                   }
                 }
               }
               leaf-list queues {
                 ordered-by user;
                 description "Queue holding RTP packets. Default is queue 1";
                 type enumeration {
                   enum "q0" {
                     description "RTP packets assigned to queue 0";
                   }
                   enum "q1" {
                     description "RTP packets assigned to queue 1";
                   }
                   enum "q2" {
                     description "RTP packets assigned to queue 2";
                   }
                   enum "q3" {
                     description "RTP packets assigned to queue 3";
                   }
                 }
               }
               container port {
                 presence "enable port";
                 junos:cli-feature "oneliner";
                 description "UDP destination ports reserved for RTP packets";
                 leaf minimum {
                   type union {
                     type string {
                       pattern "<.*>|$.*";
                     }
                     type uint32 {
                       range "0 .. 65535";
                     }
                   }
                 }
                 leaf maximum {
                   type union {
                     type string {
                       pattern "<.*>|$.*";
                     }
                     type uint32 {
                       range "0 .. 65535";
                     }
                   }
                 }
               }
               container maximum-contexts {
                 junos:cli-feature "oneliner";
                 description "Maximum number of simultaneous RTP contexts";
                 leaf number {
                   description "Maximum number of simultaneous RTP contexts";
                   junos:cli-feature "nokeyword";
                   type union {
                     type string {
                       pattern "<.*>|$.*";
                     }
                     type uint32 {
                       range "16 .. 2048";
                     }
                   }
                 }
               }
             }
           }
           leaf interleave-fragments {
             description "Interleave long packets with high priority ones";
             type empty;
           }
           leaf link-layer-overhead {
             description "Link layer bit stuffing overhead (0.0 .. 50.0 percent)";
             type jt:unsigned-float;
           }
           leaf accounting-profile {
             description "Accounting profile name";
             junos:must "((\"accounting-options interface-profile $$\" || \"accounting-options flat-file-profile $$\"))";
             junos:must-message "referenced accounting profile must be defined";
             type string;
           }
           leaf peer-unit {
             description "Peer unit number";
             type union {
               type string {
                 pattern "<.*>|$.*";
               }
               type uint32 {
                 range "0 .. 40960";
               }
             }
           }
           container tunnel {
             description "Tunnel parameters";
             uses apply-advanced;
             container encapsulation {
               presence "enable encapsulation";
               junos:cli-feature "homogeneous";
               description "Encapsulation over tunnel";
               container vxlan-gpe {
                 presence "enable vxlan-gpe";
                 junos:must "((!(\".. udp\") && !(\".. ipip\")))";
                 junos:must-message "Only one encapsulation can  be set per IFL";
                 uses apply-advanced;
                 container source {
                   uses apply-advanced;
                   leaf address {
                     description "Interface address prefix";
                     junos:must "(!(\".. interface\"))";
                     junos:must-message "To configure address interface must be not set";
                     type jt:ipv4addr;
                   }
                   leaf mac-address {
                     description "Interface source mac address";
                     junos:must "((\".. interface\" || \".. address\"))";
                     junos:must-message "Either address or interface must be set";
                     type jt:mac-addr;
                   }
                   leaf interface {
                     description "Name of the interface";
                     type union {
                       type jt:interface-name;
                       type string {
                         pattern "<.*>|$.*";
                       }
                     }
                   }
                 }
                 container destination {
                   uses apply-advanced;
                   leaf address {
                     description "Interface address prefix";
                     type jt:ipv4addr;
                   }
                   leaf mac-address {
                     description "Interface destination mac address";
                     junos:must "(\".. address\")";
                     junos:must-message "destination address must be set";
                     type jt:mac-addr;
                   }
                 }
                 leaf tunnel-endpoint {
                   description "Tunnel end point type";
                   type enumeration {
                     enum "vxlan" {
                       description "To configure vxlan tunnel-end-point";
                     }
                   }
                 }
                 container source-udp-port-range {
                   junos:cli-feature "oneliner";
                   description "Value range for source-udp-port";
                   leaf min {
                     description "Minimum range value";
                     type union {
                       type string {
                         pattern "<.*>|$.*";
                       }
                       type uint32 {
                         range "1 .. 65535";
                       }
                     }
                   }
                   leaf max {
                     description "Maximum range value";
                     type union {
                       type string {
                         pattern "<.*>|$.*";
                       }
                       type uint32 {
                         range "1 .. 65535";
                       }
                     }
                   }
                 }
                 leaf destination-udp-port {
                   description "Value to write to the destination-udp-port field";
                   type union {
                     type string {
                       pattern "<.*>|$.*";
                     }
                     type uint32 {
                       range "1 .. 65535";
                     }
                   }
                 }
                 leaf vni {
                   description "Value to write to the vni field";
                   type union {
                     type string {
                       pattern "<.*>|$.*";
                     }
                     type uint32 {
                       range "0 .. 16777214";
                     }
                   }
                 }
               }
             }
             leaf encap-type {
               description "Tunnel encapsulation type";
               type enumeration {
                 enum "ipv4" {
                   description "Tunnel IPv4 encapsulation";
                 }
                 enum "ipv6" {
                   description "Tunnel IPv6 encapsulation";
                 }
               }
             }
             choice source_type {
               case case_1 {
                 leaf source {
                   description "Tunnel source address";
                   type jt:ipaddr;
                 }
               }
               case case_2 {
                 leaf source-hostname {
                   description "Tunnel source hostname";
                   junos:must "(\".. encap-type\")";
                   junos:must-message "encap-type must be specified for the tunnel with source-hostname";
                   type string;
                 }
               }
               case case_3 {
                 leaf source-interface {
                   description "Tunnel source interface";
                   junos:must "(\".. encap-type\")";
                   junos:must-message "encap-type must be specified for the tunnel with source-interface";
                   type union {
                     type jt:interface-name;
                     type string {
                       pattern "<.*>|$.*";
                     }
                   }
                 }
               }
             }
             choice destination_type {
               case case_1 {
                 leaf destination {
                   description "Tunnel destination address";
                   type jt:ipaddr;
                 }
               }
               case case_2 {
                 leaf destination-hostname {
                   description "Tunnel destination hostname";
                   junos:must "(\".. encap-type\")";
                   junos:must-message "encap-type must be specified for the tunnel with destination-hostname";
                   type string;
                 }
               }
             }
             leaf backup-destination {
               description "Backup tunnel destination";
               junos:must "(!(\".. destination $$\"))";
               junos:must-message "Backup and primary tunnel destinations must be different";
               type jt:ipaddr;
             }
             choice fragmentation {
               case case_1 {
                 leaf allow-fragmentation {
                   description "Do not set DF bit on packets";
                   type empty;
                 }
               }
               case case_2 {
                 leaf do-not-fragment {
                   description "Set DF bit on packets";
                   type empty;
                 }
               }
             }
             leaf ttl {
               description "Time to live";
               type union {
                 type string {
                   pattern "<.*>|$.*";
                 }
                 type uint32 {
                   range "1 .. 255";
                 }
               }
             }
             leaf traffic-class {
               description "TOS/Traffic class field of IP-header";
               type union {
                 type string {
                   pattern "<.*>|$.*";
                 }
                 type uint32 {
                   range "0 .. 255";
                 }
               }
             }
             leaf flow-label {
               description "Flow label field of IP6-header";
               type union {
                 type string {
                   pattern "<.*>|$.*";
                 }
                 type uint32 {
                   range "0 .. 1048575";
                 }
               }
             }
             choice path-mtu-discovery-choice {
               leaf path-mtu-discovery {
                 description "Enable path MTU discovery for tunnels";
                 type empty;
               }
               leaf no-path-mtu-discovery {
                 description "Don't enable path MTU discovery for tunnels";
                 type empty;
               }
             }
             container routing-instance {
               description "Routing instance to which tunnel ends belong";
               uses apply-advanced;
               leaf destination {
                 description "Routing instance of tunnel destination";
                 junos:must "((\"routing-instances $$\" || any \"tenants <*> routing-instances $$\"))";
                 junos:must-message "referenced routing-instance must be defined";
                 type string {
                   junos:posix-pattern "!^((__.*__)|(all)|(.*[ ].*)|(\"\")|(.{129,}))$";
                   junos:pattern-message "Must be a non-reserved string of 128 characters or less with no spaces.";
                 }
               }
             }
           }
           leaf compression-device {
             description "Logical interface used for compression";
             type union {
               type jt:interface-unit;
               type string {
                 pattern "<.*>|$.*";
               }
             }
           }
           container layer2-policer {
             junos:must "(\".. family\")";
             junos:must-message "Family must be defined for a unit with layer2-policer";
             description "Layer2 policing for logical interface";
             uses apply-advanced;
             choice layer2-input-policer-choice {
               case case_1 {
                 leaf input-policer {
                   description "Two-color policer for received packets";
                   type string;
                 }
               }
               case case_2 {
               }
               case case_3 {
                 leaf input-three-color {
                   description "Color-blind three-color policer for received packets";
                   type string;
                 }
               }
             }
             choice layer2-output-policer-choice {
               case case_1 {
                 leaf output-policer {
                   description "Two-color policer for transmitted packets";
                   type string;
                 }
               }
               case case_2 {
                 leaf output-three-color {
                   description "Three-color policer for transmitted packets";
                   type string;
                 }
               }
             }
           }
           choice virtual-gateway {
             case case_1 {
               leaf no-auto-virtual-gateway-esi {
                 description "Disable auto ESI generation for virtual gateway address";
                 junos:must "((any \".. family inet address <*> virtual-gateway-address\" || any \".. family inet6 address <*> virtual-gateway-address\"))";
                 junos:must-message "Only when virtual gateway address is configured";
                 type empty;
               }
             }
             case case_2 {
               container virtual-gateway-esi {
                 description "ESI configuration of virtual gateway";
                 uses apply-advanced;
                 leaf identifier {
                   description "ESI value for the interface";
                   junos:cli-feature "nokeyword";
                   junos:must "(unique \"interfaces <*> unit <*> virtual-gateway-esi $$\")";
                   junos:must-message "virtual-gateway-esi value must be unique under all IFDs and IFLs";
                   junos:must "(unique \"interfaces <*> esi $$\")";
                   junos:must-message "ESI value must be unique under all IFDs and IFLs";
                   type jt:esi;
                 }
                 choice mode {
                   case case_1 {
                     leaf single-active {
                       description "Single-active mode";
                       type empty;
                     }
                   }
                   case case_2 {
                     leaf all-active {
                       description "All-active mode";
                       type empty;
                     }
                   }
                 }
               }
             }
           }
           container service {
             description "Service operations";
             uses apply-advanced;
             list pcef {
               key name;
               ordered-by user;
               description "PCEF configuration";
               leaf name {
                 description "PCEF Profile name";
                 junos:cli-feature "nokeyword";
                 junos:must "((\".. family inet service\" || \".. family inet6 service\"))";
                 junos:must-message "Must be configured along with a family inet/inet6 service.";
                 type string;
               }
               uses apply-advanced;
               leaf activate-all {
                 description "Activate all rules and rulebases in the pcef profile";
                 junos:must "(!(\"activate\"))";
                 junos:must-message "Can't be configured with activate-rule or activate- rulebase.";
                 type empty;
               }
               list activate {
                 key name;
                 ordered-by user;
                 description "Name of pcef profile rule or rulebase to activate";
                 leaf name {
                   description "Name of pcef profile rule or rulebase to activate";
                   junos:cli-feature "nokeyword";
                   type string;
                 }
                 uses apply-advanced;
               }
             }
           }
           choice generate-eui64-choice {
             leaf generate-eui64 {
               description "To generate Link Local EUI-64 addresses";
               junos:must "(\".. family inet6 unnumbered-address\")";
               junos:must-message "generate-eui64 attribute must be set when unnumbered-address is configured under family inet6";
               type empty;
             }
             leaf no-generate-eui64 {
               description "Don't to generate Link Local EUI-64 addresses";
               junos:must "(\".. family inet6 unnumbered-address\")";
               junos:must-message "generate-eui64 attribute must be set when unnumbered-address is configured under family inet6";
               type empty;
             }
           }
           container family {
             junos:must "(!(\".. encapsulation ppp-over-ether\"))";
             junos:must-message "Can't configure protocol family with encapsulation ppp-over-ether";
             junos:cli-feature "homogeneous";
             description "Protocol family";
             container inet {
               presence "enable inet";
               junos:must "(!(\".. .. .. encapsulation vlan-vpls\"))";
               junos:must-message "Can't configure protocol family inet with encapsulation vpls";
               description "IPv4 parameters";
               uses apply-advanced;
               container class-based-filtering {
                 description "Enable class based filter on interface";
                 uses apply-advanced;
               }
               container dhcp {
                 description "Dynamic Host Configuration Protocol client configuration";
                 presence "enable dhcp";
                 junos:must "(!(any \"forwarding-options dhcp-relay group <*> interface ${interface}.${unit}\"))";
                 junos:must-message "Incompatible with the interface configured under 'forwarding-options dhcp-relay group'";
                 junos:must "(!(\"system services dhcp\"))";
                 junos:must-message "Incompatible with the dhcp server configured under 'system services dhcp'";
                 junos:must "(!(\"system autoinstallation interfaces\"))";
                 junos:must-message "Incompatible with 'system autoinstallation interfaces'";
                 junos:must "(!(\".. address\"))";
                 junos:must-message "Incompatible with interface assigned with address";
                 uses dhcp-client-type;
               }
               container targeted-broadcast {
                 presence "enable targeted-broadcast";
                 junos:must "(!((\"interfaces $$={irb} unit ${unit} family $$={inet} targeted-broadcast\" && \"protocols l2-learning global-mode transparent-bridge\")))";
                 junos:must-message "targeted-broadcast do not be supported on irb interface in transparent mode";
                 description "Directed broadcast";
                 uses apply-advanced;
                 choice targeted-bcast-choice {
                   case case_1 {
                     leaf forward-and-send-to-re {
                       description "Allow packets to be forwarded and sent to re";
                       type empty;
                     }
                   }
                   case case_2 {
                     leaf forward-only {
                       description "Allow packets only to be forwarded";
                       type empty;
                     }
                   }
                 }
               }
               leaf destination-class-usage {
                 description "Enable destination class usage on this interface";
                 status deprecated;
                 type empty;
               }
               leaf transit-options-packets {
                 description "Transit IP options packets (don't send to Routing Engine)";
                 status deprecated;
                 type empty;
               }
               leaf transit-ttl-exceeded {
                 description "Transit IP TTL-exceeded packets (don't send to Routing Engine)";
                 status deprecated;
                 type empty;
               }
               leaf receive-options-packets {
                 description "Receive IP options packets (don't send to Routing Engine)";
                 type empty;
               }
               leaf receive-ttl-exceeded {
                 description "Receive IP TTL-exceeded packets (don't send to Routing Engine)";
                 type empty;
               }
               container accounting {
                 description "Configure interface-based accounting options";
                 uses apply-advanced;
                 container source-class-usage {
                   junos:must "(!(\".. .. class-based-filtering source-class-usage\"))";
                   junos:must-message "source-class-usage is not allowed with class-based-filtering source-class-usage";
                   junos:must "(!(\".. .. source-lookup\"))";
                   junos:must-message " source-class-usage is not allowed with source-lookup";
                   description "Enable source class usage on this interface";
                   uses apply-advanced;
                   leaf input {
                     description "Specify this interface for source-class-usage input";
                     type empty;
                   }
                   leaf output {
                     description "Specify this interface for source-class-usage output";
                     type empty;
                   }
                 }
                 leaf destination-class-usage {
                   description "Enable destination class usage on this interface";
                   junos:must "(!(\".. .. class-based-filtering destination-class-usage\"))";
                   junos:must-message "destination-class-usage is not allowed with class-based-filtering destination-class-usage";
                   type empty;
                 }
               }
               container rpf-check {
                 presence "enable rpf-check";
                 junos:cli-feature "oneliner-plus";
                 description "Enable reverse-path-forwarding checks on this interface";
                 uses apply-advanced;
                 leaf fail-filter {
                   description "Name of filter applied to packets failing RPF check";
                   type string;
                 }
                 container mode {
                   junos:cli-feature "oneliner";
                   description "Mode for reverse path forwarding";
                   leaf loose {
                     description "Reverse-path-forwarding loose mode";
                     type empty;
                   }
                 }
               }
               leaf mtu {
                 description "Protocol family maximum transmission unit";
                 type union {
                   type uint32;
                   type string {
                     pattern "<.*>|$.*";
                   }
                 }
               }
               leaf arp-max-cache {
                 description "Max interface ARP nexthop cache size";
                 type union {
                   type string {
                     pattern "<.*>|$.*";
                   }
                   type uint32 {
                     range "1 .. 2000000";
                   }
                 }
               }
               leaf arp-new-hold-limit {
                 description "Max no. of new unresolved nexthops";
                 junos:must "(\".. arp-max-cache\")";
                 junos:must-message "Interface max ARP cache size must be configured";
                 type union {
                   type string {
                     pattern "<.*>|$.*";
                   }
                   type uint32 {
                     range "1 .. 2000000";
                   }
                 }
               }
               leaf no-redirects {
                 description "Do not redirect traffic";
                 type empty;
               }
               leaf nat-outside-interface {
                 description "Public interface used for NAT";
                 junos:must "(!(\"interfaces ${interface} unit ${unit} family inet6\"))";
                 junos:must-message "family inet6 is not supported with nat-outside-interface";
                 type empty;
               }
               leaf no-neighbor-learn {
                 description "Disable neighbor address learning on interface";
                 type empty;
               }
               leaf unconditional-src-learn {
                 description "Glean from arp packets even when source cannot be validated";
                 type empty;
               }
               leaf multicast-only {
                 description "Allow only multicast traffic (tunnels only)";
                 type empty;
               }
               leaf primary {
                 description "Candidate for primary interface in system";
                 type empty;
               }
               leaf ipsec-sa {
                 description "Name of security association";
                 type string {
                   length "1 .. 32";
                 }
               }
               container filter {
                 description "Packet filtering";
                 uses apply-advanced;
                 choice input_choice {
                   case case_1 {
                     container input {
                       junos:cli-feature "oneliner";
                       description "Filter to be applied to received packets";
                       leaf filter-name {
                         description "Name of the filter";
                         junos:cli-feature "nokeyword";
                         junos:must "((!(\".. .. .. rpf-check\") || (!(any \"firewall family inet filter $$ term <*> from first-byte-of-payload\") && !(any \"firewall family inet filter $$ term <*> from first-byte-of-payload-except\"))))";
                         junos:must-message "filter with first-byte-of-payload match cannot be bound on URPF";
                         type string;
                       }
                       leaf shared-name {
                         description "Filter shared-name of instances of interface-shared filter";
                         type string;
                       }
                       leaf precedence {
                         description "Precedence of the filter";
                         type union {
                           type string {
                             pattern "<.*>|$.*";
                           }
                           type uint32 {
                             range "0 .. 255";
                           }
                         }
                       }
                     }
                   }
                   case case_2 {
                     leaf-list input-list {
                       ordered-by user;
                       description "List of filter modules applied to received packets ";
                       type string;
                     }
                   }
                 }
                 choice output_choice {
                   case case_1 {
                     container output {
                       junos:cli-feature "oneliner";
                       description "Filter to be applied to transmitted packets";
                       leaf filter-name {
                         description "Name of the filter";
                         junos:cli-feature "nokeyword";
                         junos:must "((!(\".. .. .. rpf-check\") || (!(any \"firewall family inet filter $$ term <*> from first-byte-of-payload\") && !(any \"firewall family inet filter $$ term <*> from first-byte-of-payload-except\"))))";
                         junos:must-message "filter with first-byte-of-payload match cannot be bound on URPF";
                         type string;
                       }
                       leaf shared-name {
                         description "Filter shared-name of instances of interface-shared filter";
                         type string;
                       }
                       leaf precedence {
                         description "Precedence of the filter";
                         type union {
                           type string {
                             pattern "<.*>|$.*";
                           }
                           type uint32 {
                             range "0 .. 255";
                           }
                         }
                       }
                     }
                   }
                   case case_2 {
                     leaf-list output-list {
                       ordered-by user;
                       description "List of filter modules applied to transmitted packets ";
                       type string;
                     }
                   }
                 }
                 container adf {
                   description "Ascend Data Filter definition";
                   uses apply-advanced;
                   list rule {
                     key name;
                     ordered-by user;
                     description "Set of ADF rules";
                     leaf name {
                       description "Value for a single rule";
                       junos:cli-feature "nokeyword";
                       type string;
                     }
                     uses apply-advanced;
                   }
                   leaf counter {
                     description "Add a counter to each rule";
                     type empty;
                   }
                   leaf input-precedence {
                     description "Precedence of the input rules";
                     type union {
                       type string {
                         pattern "<.*>|$.*";
                       }
                       type uint32 {
                         range "0 .. 255";
                       }
                     }
                   }
                   leaf not-mandatory {
                     description "No errors will be reported if no rules are present";
                     type empty;
                   }
                   leaf output-precedence {
                     description "Precedence of the output rules";
                     type union {
                       type string {
                         pattern "<.*>|$.*";
                       }
                       type uint32 {
                         range "0 .. 255";
                       }
                     }
                   }
                 }
                 leaf group {
                   description "Group to which interface belongs";
                   type union {
                     type string {
                       pattern "<.*>|$.*";
                     }
                     type uint32;
                   }
                 }
                 leaf dialer {
                   description "Name of filter applied on dialer";
                   junos:must "(\".. .. .. .. dialer-options dial-string\")";
                   junos:must-message "Dial string is mandatory for dialer filter";
                   junos:must "(!(\".. .. .. .. dialer-options watch-list\"))";
                   junos:must-message "A dialer interface cannot have watch-list as well as dialer filter";
                   type string;
                 }
               }
               container simple-filter {
                 description "Filter for doing multifield classification";
                 uses apply-advanced;
                 leaf input {
                   description "Name of simple filter applied to received packets";
                   type string;
                 }
               }
               container policer {
                 description "Interface policing";
                 uses apply-advanced;
                 leaf arp {
                   description "Name of policer applied to received ARP packets";
                   junos:must "(!(\".. disable-arp-policer\"))";
                   junos:must-message "Interface configuration can have either disable-arp-policer or arp policer configured";
                   junos:must "((!(\".. .. .. .. peer-unit\") || (\".. .. .. .. encapsulation ethernet\" || \".. .. .. .. encapsulation vlan\")))";
                   junos:must-message "Interface encapsulation must be ethernet or vlan";
                   type string;
                 }
                 leaf input {
                   description "Name of policer applied to received packets";
                   junos:must "(!(\".. .. input-hierarchical-policer\"))";
                   junos:must-message "Both input policer and input hierarchical policer can not be applied on the same family";
                   type string;
                 }
                 leaf output {
                   description "Name of policer applied to transmitted packets";
                   type string;
                 }
               }
               container sampling {
                 junos:must "((\"forwarding-options sampling family inet\" || (\"forwarding-options packet-capture\" || any \"forwarding-options sampling instance <*> family inet\")))";
                 junos:must-message "Requires forwarding-options sampling or packet-capture config";
                 description "Interface sampling";
                 uses apply-advanced;
                 leaf input {
                   description "Sample all packets input on this interface";
                   type empty;
                 }
                 leaf output {
                   description "Sample all packets output on this interface";
                   type empty;
                 }
               }
               container service {
                 junos:must "((!(\".. rpf-check\") || \"chassis network-services enhanced-ip\"))";
                 junos:must-message "rpf-check can not be enabled with interface services";
                 description "Service operations";
                 uses apply-advanced;
                 container input {
                   junos:cli-feature "oneliner-plus";
                   description "Service sets to consider for received packets";
                   uses apply-advanced;
                   list service-set {
                     key name;
                     ordered-by user;
                     junos:cli-feature "oneliner-plus";
                     description "Service set to consider for received packets";
                     leaf name {
                       description "Name of service set";
                       junos:cli-feature "nokeyword";
                       junos:must "((!(\".. .. .. .. .. .. demux-source\") && !(\".. .. .. .. .. .. demux-destination\")))";
                       junos:must-message "Service set cannot be configured on interfaces with demux-source or demux-destination";
                       junos:must "(\"services service-set $$ interface-service\")";
                       junos:must-message "this service set must be an interface service";
                       type string {
                         junos:posix-pattern "^[[:alnum:]][[:alnum:]/.:_-]*$";
                         junos:pattern-message "Must be a string beginning with a number or letter and consisting of letters, numbers, dashes, underscores, forward slashes, colons and dots.";
                       }
                     }
                     uses apply-advanced;
                     leaf service-filter {
                       description "Name of service filter";
                       type string;
                     }
                   }
                   leaf post-service-filter {
                     description "Post-service filter to apply to received packets";
                     type string;
                   }
                 }
                 container output {
                   junos:cli-feature "oneliner-plus";
                   description "Service sets to consider for transmitted packets";
                   uses apply-advanced;
                   list service-set {
                     key name;
                     ordered-by user;
                     junos:cli-feature "oneliner-plus";
                     description "Service set to consider for transmitted packets";
                     leaf name {
                       description "Name of service set";
                       junos:cli-feature "nokeyword";
                       type string {
                         junos:posix-pattern "^[[:alnum:]][[:alnum:]/.:_-]*$";
                         junos:pattern-message "Must be a string beginning with a number or letter and consisting of letters, numbers, dashes, underscores, forward slashes, colons and dots.";
                       }
                     }
                     uses apply-advanced;
                     leaf service-filter {
                       description "Name of service filter";
                       type string;
                     }
                   }
                 }
               }
               list next-hop-tunnel {
                 key name;
                 ordered-by user;
                 junos:cli-feature "oneliner-plus";
                 description "One or more next-hop tunnel tables";
                 leaf name {
                   description "Next-hop tunnel gateway address";
                   junos:cli-feature "nokeyword";
                   type string;
                 }
                 uses apply-advanced;
                 leaf ipsec-vpn {
                   description "Name of IPSec VPN";
                   junos:must "(\"security ipsec vpn $$\")";
                   junos:must-message "Referenced IPSec vpn must be defined under [edit security ipsec vpn] hierarchy level";
                   junos:must "(unique \"interfaces st0 unit <*> family inet next-hop-tunnel <*> ipsec-vpn $$\")";
                   junos:must-message "Referenced IPSec vpn must be unique";
                   type string;
                 }
               }
               choice tunnel-termination-status {
                 case case_1 {
                   leaf tunnel-termination {
                     description "Tunnel termination";
                     type empty;
                   }
                 }
                 case case_2 {
                   leaf no-tunnel-termination {
                     description "No Tunnel termination";
                     type empty;
                   }
                 }
               }
               list address {
                 key name;
                 ordered-by user;
                 description "Interface address/destination prefix";
                 junos:must "((!(\".. unnumbered-address\") && !(\".. location-pool-address\")))";
                 junos:must-message "address cannot be defined with unnumbered-address or location-pool-address simultaneously";
                 leaf name {
                   description "Interface address/destination prefix";
                   junos:cli-feature "nokeyword";
                   type jt:ipv4prefix;
                 }
                 uses apply-advanced;
                 leaf destination {
                   description "Destination address";
                   type jt:ipv4addr;
                 }
                 leaf destination-profile {
                   description "Profile to use for destination address";
                   junos:must "(\"access group-profile $$ ppp\")";
                   junos:must-message "referenced group-profile must be defined and must contain ppp statement";
                   type string;
                 }
                 leaf broadcast {
                   description "Broadcast address";
                   type jt:ipv4addr;
                 }
                 leaf primary {
                   description "Candidate for primary address in system";
                   type empty;
                 }
                 leaf preferred {
                   description "Preferred address on interface";
                   type empty;
                 }
                 leaf master-only {
                   description "Master management IP address for router";
                   type empty;
                 }
                 container tag {
                   description "Tag used for route/local";
                   uses apply-advanced;
                   leaf tag-value {
                     description "The tag value on the address";
                     junos:cli-feature "nokeyword";
                     type union {
                       type string {
                         pattern "<.*>|$.*";
                       }
                       type uint32 {
                         range "1 .. 4294967295";
                       }
                     }
                   }
                   leaf type {
                     description "Tag type must be [1-16]";
                     type union {
                       type string {
                         pattern "<.*>|$.*";
                       }
                       type uint32 {
                         range "1 .. 16";
                       }
                     }
                   }
                 }
                 container tag2 {
                   description "Tag2 used for route/local";
                   uses apply-advanced;
                   leaf tag2-value {
                     description "The tag value on the address";
                     junos:cli-feature "nokeyword";
                     type union {
                       type string {
                         pattern "<.*>|$.*";
                       }
                       type uint32 {
                         range "1 .. 4294967295";
                       }
                     }
                   }
                   leaf type {
                     description "Tag type must be [1-16]";
                     type union {
                       type string {
                         pattern "<.*>|$.*";
                       }
                       type uint32 {
                         range "1 .. 16";
                       }
                     }
                   }
                 }
                 list multipoint-destination {
                   key name;
                   ordered-by user;
                   junos:cli-feature "oneliner-plus";
                   description "Multipoint NBMA destination";
                   leaf name {
                     description "Destination address";
                     junos:cli-feature "nokeyword";
                     type jt:ipv4addr;
                   }
                   uses apply-advanced;
                   choice link-address {
                     case case_1 {
                       leaf dlci {
                         description "Frame Relay data-link control identifier";
                         type union {
                           type string {
                             pattern "<.*>|$.*";
                           }
                           type uint32 {
                             range "1 .. 1022";
                           }
                         }
                       }
                     }
                     case case_2 {
                       leaf vci {
                         description "ATM virtual circuit identifier ([vpi.]vci)";
                         type jt:atm-vci;
                       }
                     }
                   }
                   container shaping {
                     description "Virtual circuit traffic-shaping options";
                     uses dcd_shaping_config;
                   }
                   container oam-period {
                     junos:cli-feature "oneliner";
                     description "OAM cell period";
                     choice oam_period_choices {
                       case case_1 {
                         leaf oam_period {
                           description "OAM cell period";
                           junos:cli-feature "nokeyword";
                           units "seconds";
                           type union {
                             type string {
                               pattern "<.*>|$.*";
                             }
                             type uint32 {
                               range "1 .. 900";
                             }
                           }
                         }
                       }
                       case case_2 {
                         container disable {
                           presence "enable disable";
                           junos:cli-feature "oneliner";
                           description "Disable OAM loopback";
                         }
                       }
                     }
                   }
                   container oam-liveness {
                     description "OAM virtual circuit liveness parameters";
                     uses apply-advanced;
                     leaf up-count {
                       description "Number of OAM cells to consider VC up";
                       type union {
                         type string {
                           pattern "<.*>|$.*";
                         }
                         type uint32 {
                           range "1 .. 255";
                         }
                       }
                     }
                     leaf down-count {
                       description "Number of OAM cells to consider VC down";
                       type union {
                         type string {
                           pattern "<.*>|$.*";
                         }
                         type uint32 {
                           range "1 .. 255";
                         }
                       }
                     }
                   }
                   leaf inverse-arp {
                     description "Enable inverse ARP reply messages";
                     type empty;
                   }
                   leaf transmit-weight {
                     description "ATM2 transmit weight for VC under VP tunnel";
                     type union {
                       type string {
                         pattern "<.*>|$.*";
                       }
                       type uint16 {
                         range "1 .. 32767";
                       }
                     }
                   }
                   container epd-threshold {
                     description "Early packet discard threshold for ATM2";
                     junos:cli-feature "oneliner";
                     uses epd_threshold_config;
                   }
                 }
                 list arp {
                   key name;
                   ordered-by user;
                   junos:cli-feature "oneliner";
                   description "Static Address Resolution Protocol entries";
                   leaf name {
                     description "Destination IP address";
                     junos:cli-feature "nokeyword";
                     type jt:ipv4addr;
                   }
                   leaf l2-interface {
                     description "Layer 2 interface name for ARP entry";
                     type union {
                       type jt:interface-name;
                       type string {
                         pattern "<.*>|$.*";
                       }
                     }
                   }
                   choice mac_address_type {
                     case case_1 {
                       leaf mac {
                         description "MAC address";
                         type jt:mac-unicast;
                       }
                     }
                     case case_2 {
                       leaf multicast-mac {
                         description "Multicast MAC address";
                         type jt:mac-multicast;
                       }
                     }
                   }
                   leaf publish {
                     description "Reply to ARP requests for this entry";
                     junos:must "((\".. mac\" || \".. multicast-mac\"))";
                     junos:must-message "mac or multicast-mac must be configured to publish";
                     type empty;
                   }
                   leaf flood-as-unknown-unicast {
                     description "Broadcast the packet with unicast MAC";
                     junos:must "(!(\".. l2-interface\"))";
                     junos:must-message "l2-interface cannot be configured with flood-as-unknown-unicast";
                     junos:must "(\".. mac\")";
                     junos:must-message "mac must be configured to flood-as-unknown-unicast";
                     type empty;
                   }
                 }
                 container web-authentication {
                   junos:cli-feature "oneliner-plus";
                   description "Parameters for web-based firewall-user authentication";
                   uses apply-advanced;
                   leaf http {
                     description "Enable authentication via HTTP";
                     type empty;
                   }
                   leaf https {
                     description "Enable authentication via HTTPS";
                     junos:must "(\"system services web-management https\")";
                     junos:must-message "web-management should be configured for enabling web-authentication";
                     type empty;
                   }
                   leaf redirect-to-https {
                     description "Web authentication redirect to HTTPS";
                     junos:must "(\".. https\")";
                     junos:must-message "https must be enabled";
                     type empty;
                   }
                 }
                 list vrrp-group {
                   key name;
                   ordered-by user;
                   description "VRRP group";
                   uses vrrp-group;
                 }
                 leaf virtual-gateway-address {
                   description "Virtual Gateway IP address";
                   junos:must "(!(\".. vrrp-group\"))";
                   junos:must-message "vrrp configuration incompatible with virtual gateway address";
                   type jt:ipv4addr;
                 }
               }
               container unnumbered-address {
                 junos:cli-feature "oneliner";
                 description "Unnumbered interface address/destination prefix";
                 leaf source {
                   description "Interface from which to take local address";
                   junos:cli-feature "nokeyword";
                   junos:must "(\"interfaces $$-IFL family inet address\")";
                   junos:must-message "referred interface must have address configured under family inet";
                   type union {
                     type jt:interface-unit;
                     type string {
                       pattern "<.*>|$.*";
                     }
                   }
                 }
                 leaf preferred-source-address {
                   description "Preferred address on the donor interface";
                   type string;
                 }
                 leaf destination {
                   description "Destination address";
                   type jt:ipv4addr;
                 }
                 leaf destination-profile {
                   description "Profile to use for destination address";
                   junos:must "(\"access group-profile $$ ppp\")";
                   junos:must-message "referenced group-profile must be defined and must contain ppp statement";
                   type string;
                 }
               }
               container location-pool-address {
                 presence "enable location-pool-address";
                 junos:must "((!(\".. address\") && !(\".. unnumbered-address\")))";
                 junos:must-message "location-pool-address cannot be defined with address or unnumbered-address simultaneously";
                 description "Location-based IP address pool";
                 uses apply-advanced;
                 leaf pool-name {
                   description "Pool name";
                   junos:cli-feature "nokeyword";
                   junos:must "(\"access address-assignment location-pool $$\")";
                   junos:must-message "referenced IP address location pool must be defined";
                   type string {
                     length "1 .. 64";
                   }
                 }
               }
               leaf negotiate-address {
                 description "Negotiate address with remote";
                 junos:must "(!(\".. .. .. .. encapsulation multilink-frame-relay-uni-nni\"))";
                 junos:must-message "negotiate-address is not supported with family mlfr-uni-nni ";
                 junos:must "(!(\".. .. .. encapsulation multilink-frame-relay-end-to-end\"))";
                 junos:must-message "negotiate-address is not supported with family mlfr-end-to-end ";
                 junos:must "(!(\".. location-pool-address\"))";
                 junos:must-message "negotiate-address and location-pool-address must not be defined simultaneously";
                 junos:must "(!(\".. unnumbered-address\"))";
                 junos:must-message "negotiate-address and unnumbered-address must not be defined simultaneously";
                 junos:must "(!(\".. address\"))";
                 junos:must-message "negotiate-address and address must not be defined simultaneously";
                 type empty;
               }
               leaf destination-udp-port {
                 description "Choose destination UDP port number";
                 junos:must "(\".. .. .. tunnel encapsulation udp\")";
                 junos:must-message "destination-udp-port can be configured only for encapsulation udp on fti interface";
                 type union {
                   type string {
                     pattern "<.*>|$.*";
                   }
                   type uint32 {
                     range "10000 .. 10009";
                   }
                 }
               }
               container auto-configure {
                 description "Auto configuration";
                 uses dynamic_ipv4_type;
               }
             }
             container iso {
               presence "enable iso";
               junos:must "(!(\".. .. encapsulation frame-relay-ppp\"))";
               junos:must-message "family iso is not supported on encapsulation frame-relay-ppp";
               description "OSI ISO protocol parameters";
               uses apply-advanced;
               list address {
                 key name;
                 ordered-by user;
                 description "Interface address";
                 leaf name {
                   description "Interface address";
                   junos:cli-feature "nokeyword";
                   type jt:isoaddr;
                 }
                 uses apply-advanced;
               }
               leaf mtu {
                 description "Protocol family maximum transmission unit";
                 type union {
                   type uint32;
                   type string {
                     pattern "<.*>|$.*";
                   }
                 }
               }
               leaf destination-udp-port {
                 description "Choose destination UDP port number";
                 junos:must "(\".. .. .. tunnel encapsulation udp\")";
                 junos:must-message "destination-udp-port can be configured only for encapsulation udp on fti interface";
                 type union {
                   type string {
                     pattern "<.*>|$.*";
                   }
                   type uint32 {
                     range "10030 .. 10039";
                   }
                 }
               }
             }
             container inet6 {
               presence "enable inet6";
               description "IPv6 protocol parameters";
               uses apply-advanced;
               container class-based-filtering {
                 description "Enable class based filter on interface";
                 uses apply-advanced;
               }
               container dhcpv6-client {
                 junos:must "(!(\"system services dhcp\"))";
                 junos:must-message "Incompatible with the dhcp server configured under 'system services dhcp'";
                 junos:must "(!(\"system autoinstallation\"))";
                 junos:must-message "Incompatible with 'system autoinstallation'";
                 junos:must "(!(\".. address\"))";
                 junos:must-message "Incompatible with interface assigned with address";
                 junos:must "(!(any \"forwarding-options dhcp-relay dhcpv6  group <*> interface ${interface}.${unit}\"))";
                 junos:must-message "DHCPv6 client and relay cannot be configured on the same interface ";
                 junos:must "(!(any \"system services dhcp-local-server dhcpv6 group <*> interface ${interface}.${unit}\"))";
                 junos:must-message "DHCPv6 client and server cannot be configured on the same interface ";
                 description "Dynamic Host Configuration Protocol DHCPv6 client configuration";
                 uses apply-advanced;
                 leaf client-type {
                   description "DHCPv6 client type";
                   type enumeration {
                     enum "stateful" {
                       description "Stateful client type for address assignment.";
                     }
                     enum "autoconfig" {
                       description "Autoconfig  client type for router-advertisement";
                       junos:must "(\"protocols router-advertisement interface ${interface}.${unit}\")";
                       junos:must-message "Interface for ra messages is must for auto mode";
                       junos:must "(!(\"interfaces ${interface} unit ${unit} family inet6 dhcpv6-client update-router-advertisement\"))";
                       junos:must-message "Incompatible with 'dhcpv6-client update-router-advertisement'";
                       junos:must "(!(\"interfaces ${interface} unit ${unit} family inet6 dhcpv6-client client-ia-type ia-pd\"))";
                       junos:must-message "Incompatible with 'client-ia-type ia-pd'";
                     }
                   }
                 }
                 list client-ia-type {
                   key name;
                   ordered-by user;
                   description "DHCPv6 client identity association type";
                   leaf name {
                     junos:cli-feature "nokeyword";
                     type enumeration {
                       enum "ia-na" {
                         description "Identity Association-Non-temporary Address";
                       }
                       enum "ia-pd" {
                         description "Identity Association-Prefix Address";
                       }
                     }
                   }
                   uses apply-advanced;
                 }
                 container rapid-commit {
                   presence "enable rapid-commit";
                   description "Option is used to signal the use of the two message exchange for address assignment";
                 }
                 leaf interface-identifier {
                   description "Identifier for this interface";
                   type jt:ipv6addr;
                 }
                 leaf use-ra-prefix {
                   description "Assign interface IP from RA prefix when ia-na address not received";
                   junos:must "(\"interfaces ${interface} unit ${unit} family inet6 dhcpv6-client client-ia-type ia-na\")";
                   junos:must-message "Incompatible with out 'client-ia-type ia-na'";
                   junos:must "(\"interfaces ${interface} unit ${unit} family inet6 dhcpv6-client client-type stateful\")";
                   junos:must-message "Incompatible with out 'client-type stateful'";
                   type empty;
                 }
                 container prefix-delegating {
                   junos:must "(\"interfaces ${interface} unit ${unit} family inet6 dhcpv6-client client-ia-type ia-pd\")";
                   junos:must-message "Incompatible with out 'client-ia-type ia-pd'";
                   description "Prefix delegating parameters";
                   uses apply-advanced;
                   leaf preferred-prefix-length {
                     description "Client preferred prefix length";
                     type union {
                       type string {
                         pattern "<.*>|$.*";
                       }
                       type uint32 {
                         range "0 .. 64";
                       }
                     }
                   }
                   leaf sub-prefix-length {
                     description "The sub prefix length for LAN interfaces";
                     type union {
                       type string {
                         pattern "<.*>|$.*";
                       }
                       type uint32 {
                         range "1 .. 127";
                       }
                     }
                   }
                 }
                 container client-identifier {
                   junos:cli-feature "oneliner";
                   description "DHCP Server identifies a client by client-identifier value ";
                   leaf duid-type {
                     description "DUID identifying a client";
                     type enumeration {
                       enum "duid-llt" {
                         description "Link-layer address plus time";
                       }
                       enum "vendor" {
                         description "Vendor-assigned unique ID based on Enterprise Number";
                       }
                       enum "duid-ll" {
                         description "Link-layer address";
                       }
                     }
                   }
                 }
                 leaf vendor-id {
                   description "Vendor class id for the dhcpv6 client";
                   type string {
                     length "1 .. 60";
                   }
                 }
                 list req-option {
                   key name;
                   ordered-by user;
                   description "DHCPV6 client requested option configuration";
                   leaf name {
                     junos:cli-feature "nokeyword";
                     type enumeration {
                       enum "dns-server" {
                         description "Dns-server option";
                       }
                       enum "domain" {
                         description "Dns-server option";
                       }
                       enum "ntp-server" {
                         description "Ntp-server option";
                       }
                       enum "time-zone" {
                         description "Time-zone option";
                       }
                       enum "sip-server" {
                         description "Sip-server option";
                       }
                       enum "sip-domain" {
                         description "Sip-domain option";
                       }
                       enum "nis-server" {
                         description "Nis-server option";
                       }
                       enum "nis-domain" {
                         description "Nis-domain option";
                       }
                       enum "fqdn" {
                         description "Fully-qualified-domain option";
                       }
                       enum "vendor-spec" {
                         description "Vendor-spec option";
                       }
                       enum "zero-touch-redirect" {
                         description "Zero-touch-redirect";
                       }
                       enum "bootfile-url" {
                         description "Bootfile url";
                       }
                       enum "bootfile-param" {
                         description "Bootfile param";
                       }
                     }
                   }
                   uses apply-advanced;
                 }
                 container options {
                   description "DHCP options";
                   uses apply-advanced;
                   list number {
                     key name;
                     junos:cli-feature "oneliner";
                     description "DHCP option code";
                     leaf name {
                       description "DHCP option identifier code";
                       junos:cli-feature "nokeyword";
                       type union {
                         type string {
                           pattern "<.*>|$.*";
                         }
                         type uint32 {
                           range "1 .. 254";
                         }
                       }
                     }
                     choice option-type-choice {
                       case case_1 {
                         leaf hex-string {
                           description "Hexadecimal string";
                           type string {
                             length "1 .. 510";
                             junos:posix-pattern "^[[:xdigit:]]+$";
                             junos:pattern-message "Must be hexadecimal digits (0-9, a-f, A-F)";
                           }
                         }
                       }
                     }
                   }
                 }
                 leaf retransmission-attempt {
                   description "Number of attempts to retransmit the DHCPV6 client protocol packet";
                   default "9";
                   type union {
                     type string {
                       pattern "<.*>|$.*";
                     }
                     type uint32 {
                       range "0 .. 50000";
                     }
                   }
                 }
                 container no-dns-install {
                   presence "enable no-dns-install";
                   description "Not propagate DNS to kernel";
                 }
                 container update-router-advertisement {
                   junos:must "(\"interfaces ${interface} unit ${unit} family inet6 dhcpv6-client client-ia-type $$={2}\")";
                   junos:must-message "Incompatible without 'client-ia-type ia-pd'";
                   description "Dhcpv6 client update rpd for prefix delegation";
                   uses apply-advanced;
                   list interface {
                     key name;
                     ordered-by user;
                     description "Interfaces on which to delegate prefix";
                     max-elements 3;
                     leaf name {
                       description "Interfaces-name on which to delegate prefix";
                       junos:cli-feature "nokeyword";
                       junos:must "(unique \"interfaces <*> unit 0 family inet6 dhcpv6-client update-router-advertisement interface $$\")";
                       junos:must-message "This interface is already updated by a dhcpv6-client";
                       junos:must "(!(\"protocols router-advertisement interface $$\"))";
                       junos:must-message "Incompatible with the interface configured under 'protocols router-advertisement interface'";
                       type union {
                         type jt:interface-name;
                         type string {
                           pattern "<.*>|$.*";
                         }
                       }
                     }
                     uses apply-advanced;
                     leaf interface-identifier {
                       description "Identifier for this interface";
                       type jt:ipv6addr;
                     }
                     leaf prefix-identifier {
                       description "Prefix identifier for prefix used in this interface";
                       type jt:ipv6addr;
                     }
                     choice managed-configuration-choice {
                       leaf managed-configuration {
                         description "Set managed address configuration";
                         type empty;
                       }
                       leaf no-managed-configuration {
                         description "Don't set managed address configuration";
                         type empty;
                       }
                     }
                     choice other-stateful-configuration-choice {
                       leaf other-stateful-configuration {
                         description "Set other stateful configuration";
                         type empty;
                       }
                       leaf no-other-stateful-configuration {
                         description "Don't set other stateful configuration";
                         type empty;
                       }
                     }
                     leaf max-advertisement-interval {
                       description "Maximum advertisement interval";
                       units "seconds";
                       type union {
                         type string {
                           pattern "<.*>|$.*";
                         }
                         type uint32 {
                           range "4 .. 1800";
                         }
                       }
                     }
                     leaf min-advertisement-interval {
                       description "Minimum advertisement interval";
                       units "seconds";
                       type union {
                         type string {
                           pattern "<.*>|$.*";
                         }
                         type uint32 {
                           range "3 .. 1350";
                         }
                       }
                     }
                     choice enable-recursive-dns-server-option-choice {
                       leaf enable-recursive-dns-server-option {
                         description "Enables the recursive DNS server option";
                         type empty;
                       }
                       leaf no-enable-recursive-dns-server-option {
                         description "Don't enables the recursive DNS server option";
                         type empty;
                       }
                     }
                   }
                 }
                 leaf update-server {
                   description "Propagate TCP/IP settings to DHCP server";
                   type empty;
                 }
               }
               container rpf-check {
                 presence "enable rpf-check";
                 junos:cli-feature "oneliner-plus";
                 description "Enable reverse-path-forwarding checks on this interface";
                 uses apply-advanced;
                 leaf fail-filter {
                   description "Name of filter applied to packets failing RPF check";
                   type string;
                 }
                 container mode {
                   junos:cli-feature "oneliner";
                   description "Mode for reverse path forwarding";
                   leaf loose {
                     description "Reverse-path-forwarding loose mode";
                     type empty;
                   }
                 }
               }
               container accounting {
                 description "Interface-based accounting options";
                 uses apply-advanced;
                 container source-class-usage {
                   junos:must "(!(\".. .. class-based-filtering source-class-usage\"))";
                   junos:must-message "source-class-usage is not allowed with class-based-filtering source-class-usage";
                   junos:must "(!(\".. .. source-lookup\"))";
                   junos:must-message " source-class-usage is not allowed with source-lookup";
                   uses apply-advanced;
                   leaf input {
                     description "Interface for source-class-usage input";
                     type empty;
                   }
                   leaf output {
                     description "Interface for source-class-usage output";
                     type empty;
                   }
                 }
                 leaf destination-class-usage {
                   description "Enable destination class usage on this interface";
                   junos:must "(!(\".. .. class-based-filtering destination-class-usage\"))";
                   junos:must-message "destination-class-usage is not allowed with class-based-filtering destination-class-usage";
                   type empty;
                 }
               }
               leaf mtu {
                 description "Protocol family maximum transmission unit";
                 type union {
                   type uint32;
                   type string {
                     pattern "<.*>|$.*";
                   }
                 }
               }
               leaf nd6-stale-time {
                 description "Stale time to reconfirm reachability with inet6 neighbour";
                 units "seconds";
                 type union {
                   type string {
                     pattern "<.*>|$.*";
                   }
                   type uint32 {
                     range "1 .. 18000";
                   }
                 }
               }
               leaf no-neighbor-learn {
                 description "Disable neighbor address learning on interface";
                 type empty;
               }
               container ndp-proxy {
                 description "Enable ndp proxy on interface";
                 uses apply-advanced;
                 leaf interface-restricted {
                   description "Enable ndp interface proxy restricted to interface";
                   junos:must "(!(\".. interface-unrestricted\"))";
                   junos:must-message "interface-restricted and interface-unrestricted are not allowed together";
                   type empty;
                 }
                 leaf interface-unrestricted {
                   description "Enable ndp interface proxy unrestricted to interface";
                   junos:must "(!(\".. interface-restricted\"))";
                   junos:must-message "interface-restricted and interface-unrestricted are not allowed together";
                   type empty;
                 }
               }
               container dad-proxy {
                 junos:must "(\".. ndp-proxy\")";
                 junos:must-message "ndp-proxy must be configured";
                 description "DAD proxy on interface";
                 uses apply-advanced;
                 leaf interface-restricted {
                   description "Enable DAD interface proxy restricted to interface";
                   junos:must "(!(\".. interface-unrestricted\"))";
                   junos:must-message "interface-restricted and interface-unrestricted are not allowed together";
                   junos:must "(\".. .. ndp-proxy interface-restricted\")";
                   junos:must-message "ndp-proxy interface-restricted must be configured to set this";
                   type empty;
                 }
                 leaf interface-unrestricted {
                   description "Enable DAD interface proxy unrestricted to interface";
                   junos:must "(!(\".. interface-restricted\"))";
                   junos:must-message "interface-restricted and interface-unrestricted are not allowed together";
                   junos:must "(\".. .. ndp-proxy interface-unrestricted\")";
                   junos:must-message "ndp-proxy interface-unrestricted must be configured to set this";
                   type empty;
                 }
               }
               leaf nd6-max-cache {
                 description "Max interface ND nexthop cache size";
                 type union {
                   type string {
                     pattern "<.*>|$.*";
                   }
                   type uint32 {
                     range "1 .. 2000000";
                   }
                 }
               }
               leaf nd6-new-hold-limit {
                 description "Max no. of new unresolved nexthops";
                 junos:must "(\".. nd6-max-cache\")";
                 junos:must-message "Interface max ND cache size must be configured";
                 type union {
                   type string {
                     pattern "<.*>|$.*";
                   }
                   type uint32 {
                     range "1 .. 2000000";
                   }
                 }
               }
               leaf no-redirects {
                 description "Do not redirect traffic";
                 type empty;
               }
               container filter {
                 description "Packet filtering";
                 uses apply-advanced;
                 choice input_choice {
                   case case_1 {
                     container input {
                       junos:cli-feature "oneliner";
                       description "Filter to be applied to received packets";
                       leaf filter-name {
                         description "Name of the filter";
                         junos:cli-feature "nokeyword";
                         junos:must "((!(\".. .. .. rpf-check\") || (!(any \"firewall family inet6 filter $$ term <*> from first-byte-of-payload\") && !(any \"firewall family inet6 filter $$ term <*> from first-byte-of-payload-except\"))))";
                         junos:must-message "filter with first-byte-of-payload match cannot be bound on URPF";
                         type string;
                       }
                       leaf shared-name {
                         description "Filter shared-name of instances of interface-shared filter";
                         type string;
                       }
                       leaf precedence {
                         description "Precedence of the filter";
                         type union {
                           type string {
                             pattern "<.*>|$.*";
                           }
                           type uint32 {
                             range "0 .. 255";
                           }
                         }
                       }
                     }
                   }
                   case case_2 {
                     leaf-list input-list {
                       ordered-by user;
                       description "List of filter modules applied to received packets ";
                       type string;
                     }
                   }
                 }
                 choice output_choice {
                   case case_1 {
                     container output {
                       junos:cli-feature "oneliner";
                       description "Filter to be applied to transmitted packets";
                       leaf filter-name {
                         description "Name of the filter";
                         junos:cli-feature "nokeyword";
                         type string;
                       }
                       leaf shared-name {
                         description "Filter shared-name of instances of interface-shared filter";
                         type string;
                       }
                       leaf precedence {
                         description "Precedence of the filter";
                         type union {
                           type string {
                             pattern "<.*>|$.*";
                           }
                           type uint32 {
                             range "0 .. 255";
                           }
                         }
                       }
                     }
                   }
                   case case_2 {
                     leaf-list output-list {
                       ordered-by user;
                       description "List of filter modules applied to transmitted packets ";
                       type string;
                     }
                   }
                 }
                 container adf {
                   description "Ascend Data Filter definition";
                   uses apply-advanced;
                   list rule {
                     key name;
                     ordered-by user;
                     description "Set of ADF rules";
                     leaf name {
                       description "Value for a single rule";
                       junos:cli-feature "nokeyword";
                       type string;
                     }
                     uses apply-advanced;
                   }
                   leaf counter {
                     description "Add a counter to each rule";
                     type empty;
                   }
                   leaf input-precedence {
                     description "Precedence of the input rules";
                     type union {
                       type string {
                         pattern "<.*>|$.*";
                       }
                       type uint32 {
                         range "0 .. 255";
                       }
                     }
                   }
                   leaf not-mandatory {
                     description "No errors will be reported if no rules are present";
                     type empty;
                   }
                   leaf output-precedence {
                     description "Precedence of the output rules";
                     type union {
                       type string {
                         pattern "<.*>|$.*";
                       }
                       type uint32 {
                         range "0 .. 255";
                       }
                     }
                   }
                 }
                 leaf group {
                   description "Group to which interface belongs";
                   type union {
                     type string {
                       pattern "<.*>|$.*";
                     }
                     type uint32;
                   }
                 }
                 leaf dialer {
                   description "Name of filter applied on dialer";
                   junos:must "(\".. .. .. .. dialer-options dial-string\")";
                   junos:must-message "Dial string is mandatory for dialer filter";
                   junos:must "(!(\".. .. .. .. dialer-options watch-list\"))";
                   junos:must-message "A dialer interface cannot have watch-list as well as dialer filter";
                   type string;
                 }
               }
               container policer {
                 description "Interface policing";
                 uses apply-advanced;
                 leaf input {
                   description "Name of policer applied to received packets";
                   type string;
                 }
                 leaf output {
                   description "Name of policer applied to transmitted packets";
                   type string;
                 }
               }
               container sampling {
                 junos:must "((\"forwarding-options sampling family inet6\" || (\"forwarding-options packet-capture\" || any \"forwarding-options sampling instance <*> family inet6\")))";
                 junos:must-message "Requires forwarding-options sampling or packet-capture config";
                 description "Interface sampling";
                 uses apply-advanced;
                 leaf input {
                   description "Sample all packets input on this interface";
                   type empty;
                 }
                 leaf output {
                   description "Sample all packets output on this interface";
                   type empty;
                 }
               }
               container service {
                 description "Service operations";
                 uses apply-advanced;
                 container input {
                   junos:cli-feature "oneliner-plus";
                   description "Service sets to consider for received packets";
                   uses apply-advanced;
                   list service-set {
                     key name;
                     ordered-by user;
                     junos:cli-feature "oneliner-plus";
                     description "Service set to consider for received packets";
                     leaf name {
                       description "Name of service set";
                       junos:cli-feature "nokeyword";
                       junos:must "((!(\".. .. .. .. .. .. demux-source\") && !(\".. .. .. .. .. .. demux-destination\")))";
                       junos:must-message "Service set cannot be configured on interfaces with demux-source or demux-destination";
                       junos:must "(\"services service-set $$ interface-service\")";
                       junos:must-message "this service set must be an interface service";
                       type string {
                         junos:posix-pattern "^[[:alnum:]][[:alnum:]/.:_-]*$";
                         junos:pattern-message "Must be a string beginning with a number or letter and consisting of letters, numbers, dashes, underscores, forward slashes, colons and dots.";
                       }
                     }
                     uses apply-advanced;
                     leaf service-filter {
                       description "Name of service filter";
                       type string;
                     }
                   }
                   leaf post-service-filter {
                     description "Post-service filter to apply to received packets";
                     type string;
                   }
                 }
                 container output {
                   junos:cli-feature "oneliner-plus";
                   description "Service sets to consider for transmitted packets";
                   uses apply-advanced;
                   list service-set {
                     key name;
                     ordered-by user;
                     junos:cli-feature "oneliner-plus";
                     description "Service set to consider for transmitted packets";
                     leaf name {
                       description "Name of service set";
                       junos:cli-feature "nokeyword";
                       type string {
                         junos:posix-pattern "^[[:alnum:]][[:alnum:]/.:_-]*$";
                         junos:pattern-message "Must be a string beginning with a number or letter and consisting of letters, numbers, dashes, underscores, forward slashes, colons and dots.";
                       }
                     }
                     uses apply-advanced;
                     leaf service-filter {
                       description "Name of service filter";
                       type string;
                     }
                   }
                 }
               }
               choice tunnel-termination-status {
                 case case_1 {
                   leaf tunnel-termination {
                     description "Tunnel termination";
                     type empty;
                   }
                 }
                 case case_2 {
                   leaf no-tunnel-termination {
                     description "No Tunnel termination";
                     type empty;
                   }
                 }
               }
               list address {
                 key name;
                 ordered-by user;
                 description "Interface address or destination prefix";
                 junos:must "(!(\".. unnumbered-address\"))";
                 junos:must-message "ipv6 unnumbered-address and ipv6 address must not be defined simultaneously";
                 leaf name {
                   description "Interface address or destination prefix";
                   junos:cli-feature "nokeyword";
                   type jt:ipv6prefix;
                 }
                 uses apply-advanced;
                 leaf destination {
                   description "Destination address";
                   type jt:ipv6addr;
                 }
                 leaf eui-64 {
                   description "Generate EUI-64 interface ID";
                   type empty;
                 }
                 leaf primary {
                   description "Candidate for primary address in system";
                   type empty;
                 }
                 leaf preferred {
                   description "Preferred address on interface";
                   type empty;
                 }
                 leaf master-only {
                   description "Master management IP address for router";
                   type empty;
                 }
                 container tag {
                   description "Tag used for route/local";
                   uses apply-advanced;
                   leaf tag-value {
                     description "The tag value on the address";
                     junos:cli-feature "nokeyword";
                     type union {
                       type string {
                         pattern "<.*>|$.*";
                       }
                       type uint32 {
                         range "1 .. 4294967295";
                       }
                     }
                   }
                   leaf type {
                     description "Tag type must be [1-16]";
                     type union {
                       type string {
                         pattern "<.*>|$.*";
                       }
                       type uint32 {
                         range "1 .. 16";
                       }
                     }
                   }
                 }
                 container tag2 {
                   description "Tag2 used for route/local";
                   uses apply-advanced;
                   leaf tag2-value {
                     description "The tag value on the address";
                     junos:cli-feature "nokeyword";
                     type union {
                       type string {
                         pattern "<.*>|$.*";
                       }
                       type uint32 {
                         range "1 .. 4294967295";
                       }
                     }
                   }
                   leaf type {
                     description "Tag type must be [1-16]";
                     type union {
                       type string {
                         pattern "<.*>|$.*";
                       }
                       type uint32 {
                         range "1 .. 16";
                       }
                     }
                   }
                 }
                 list ndp {
                   key name;
                   ordered-by user;
                   junos:cli-feature "oneliner";
                   description "Static Neighbor Discovery Protocol  entries";
                   leaf name {
                     description "Destination IP address";
                     junos:cli-feature "nokeyword";
                     type jt:ipv6addr;
                   }
                   leaf l2-interface {
                     description "Layer 2 interface name for NDP entry";
                     type union {
                       type jt:interface-name;
                       type string {
                         pattern "<.*>|$.*";
                       }
                     }
                   }
                   choice mac_address_type {
                     case case_1 {
                       leaf mac {
                         description "MAC address";
                         type jt:mac-unicast;
                       }
                     }
                     case case_2 {
                       leaf multicast-mac {
                         description "Multicast MAC address";
                         type jt:mac-multicast;
                       }
                     }
                   }
                   leaf publish {
                     description "Reply to NDP requests for this entry";
                     junos:must "((\".. mac\" || \".. multicast-mac\"))";
                     junos:must-message "either 'mac' or 'multicast-mac' must be configured along with 'publish' statment";
                     type empty;
                   }
                 }
                 list vrrp-inet6-group {
                   key name;
                   ordered-by user;
                   description "VRRP group";
                   junos:must "(!(\".. eui-64\"))";
                   junos:must-message "'vrrp-inet6-group' is not supported when 'eui-64' is configured";
                   uses vrrp-group;
                 }
                 container web-authentication {
                   junos:cli-feature "oneliner-plus";
                   description "Parameters for web-based firewall-user authentication";
                   uses apply-advanced;
                   leaf http {
                     description "Enable authentication via HTTP";
                     type empty;
                   }
                   leaf https {
                     description "Enable authentication via HTTPS";
                     junos:must "(\"system services web-management https\")";
                     junos:must-message "web-management should be configured for enabling web-authentication";
                     type empty;
                   }
                   leaf redirect-to-https {
                     description "Web authentication redirect to HTTPS";
                     junos:must "(\".. https\")";
                     junos:must-message "https must be enabled";
                     type empty;
                   }
                 }
                 leaf virtual-gateway-address {
                   description "Virtual Gateway IP address";
                   junos:must "(!(\".. vrrp-inet6-group\"))";
                   junos:must-message "vrrp configuration incompatible with virtual gateway address";
                   type jt:ipv6addr;
                 }
                 leaf subnet-router-anycast {
                   description "Create a subnet roter anycast address for this address.";
                   type empty;
                 }
               }
               container unnumbered-address {
                 junos:cli-feature "oneliner";
                 description "Unnumbered interface address/destination prefix";
                 leaf source {
                   description "Interface from which to take local address";
                   junos:cli-feature "nokeyword";
                   junos:must "(\"interfaces $$-IFL family inet6 address\")";
                   junos:must-message "referred interface must have address configured under family inet6";
                   type union {
                     type jt:interface-unit;
                     type string {
                       pattern "<.*>|$.*";
                     }
                   }
                 }
                 leaf preferred-source-address {
                   description "Preferred address on the donor interface";
                   type string;
                 }
               }
               choice dad-disable-choice {
                 leaf dad-disable {
                   description "Disable duplicate-address-detection";
                   type empty;
                 }
                 leaf no-dad-disable {
                   description "Don't disable duplicate-address-detection";
                   type empty;
                 }
               }
               leaf destination-udp-port {
                 description "Choose destination UDP port number";
                 junos:must "(\".. .. .. tunnel encapsulation udp\")";
                 junos:must-message "destination-udp-port can be configured only for encapsulation udp on fti interface";
                 type union {
                   type string {
                     pattern "<.*>|$.*";
                   }
                   type uint32 {
                     range "10010 .. 10019";
                   }
                 }
               }
               leaf enhanced-dad-disable {
                 description "Disable Enhanced DAD while send NS with Nonce option";
                 type empty;
               }
               container auto-configure {
                 description "Auto configuration";
                 uses dynamic_ipv6_type;
               }
               leaf negotiate-address {
                 description "Negotiate address with remote";
                 junos:must "(!(\".. unnumbered-address\"))";
                 junos:must-message "negotiate-address and unnumbered-address must not be defined simultaneously";
                 junos:must "(!(\".. address\"))";
                 junos:must-message "negotiate-address and address must not be defined simultaneously";
                 type empty;
               }
             }
             container mpls {
               presence "enable mpls";
               junos:must "(!(\".. .. encapsulation frame-relay-ppp\"))";
               junos:must-message "family mpls is not supported on encapsulation frame-relay-ppp";
               description "MPLS protocol parameters";
               uses apply-advanced;
               leaf mtu {
                 description "Protocol family maximum transmission unit";
                 type union {
                   type uint32;
                   type string {
                     pattern "<.*>|$.*";
                   }
                 }
               }
               container filter {
                 description "Packet filtering";
                 uses apply-advanced;
                 choice input_choice {
                   case case_1 {
                     leaf input {
                       description "Name of filter applied to received packets";
                       type string;
                     }
                   }
                   case case_2 {
                     leaf-list input-list {
                       ordered-by user;
                       description "List of filter modules applied to received packets ";
                       type string;
                     }
                   }
                 }
                 leaf-list input-chain {
                   ordered-by user;
                   description "List of filter modules applied to received packets ";
                   type string;
                 }
                 choice output_choice {
                   case case_1 {
                     leaf output {
                       description "Name of filter applied to transmitted packets";
                       type string;
                     }
                   }
                   case case_2 {
                     leaf-list output-list {
                       ordered-by user;
                       description "List of filter modules applied to transmitted packets ";
                       type string;
                     }
                   }
                 }
                 leaf-list output-chain {
                   ordered-by user;
                   description "List of filter modules applied to transmitted packets ";
                   type string;
                 }
                 leaf group {
                   description "Interface group to which interface belongs";
                   type union {
                     type string {
                       pattern "<.*>|$.*";
                     }
                     type uint32 {
                       range "1 .. 255";
                     }
                   }
                 }
                 leaf dialer {
                   description "Name of filter applied on dialer";
                   junos:must "(\".. .. .. .. dialer-options dial-string\")";
                   junos:must-message "Dial string is mandatory for dialer filter";
                   junos:must "(!(\".. .. .. .. dialer-options watch-list\"))";
                   junos:must-message "A dialer interface cannot have watch-list as well as dialer filter";
                   type string;
                 }
               }
               container policer {
                 description "Interface policing";
                 uses apply-advanced;
                 leaf input {
                   description "Name of policer applied to received packets";
                   type string;
                 }
                 leaf output {
                   description "Name of policer applied to transmitted packets";
                   type string;
                 }
               }
               leaf destination-udp-port {
                 description "Choose destination UDP port number";
                 junos:must "(\".. .. .. tunnel encapsulation udp\")";
                 junos:must-message "destination-udp-port can be configured only for encapsulation udp on fti interface";
                 type union {
                   type string {
                     pattern "<.*>|$.*";
                   }
                   type uint32 {
                     range "10020 .. 10029";
                   }
                 }
               }
             }
             container mlppp {
               junos:must "(!(\"interfaces ${interface} container-options\"))";
               junos:must-message "mlppp is not supported for container interfaces";
               description "Multilink PPP protocol parameters";
               uses apply-advanced;
               leaf bundle {
                 description "Logical interface name this link will join";
                 junos:must "((!(\".. .. .. dial-options\") || \"interfaces $$-IFL encapsulation multilink-ppp\"))";
                 junos:must-message "Bundle interface must be configured";
                 junos:must "((!(\".. .. .. pppoe-options\") || \"interfaces $$-IFL encapsulation multilink-ppp\"))";
                 junos:must-message "Bundle interface must be configured";
                 type string;
               }
               choice anchor-points {
                 case case_1 {
                 }
                 case case_2 {
                 }
               }
               leaf dynamic-profile {
                 description " dynamic profile for interface to use";
                 junos:must "(\"dynamic-profiles $$\")";
                 junos:must-message "referenced dynamic-profile must be defined";
                 type string {
                   length "1 .. 80";
                 }
               }
             }
             container mlfr-end-to-end {
               presence "enable mlfr-end-to-end";
               junos:must "(!(\".. .. encapsulation frame-relay-ppp\"))";
               junos:must-message "family mlfr-end-to-end is not supported on encapsulation frame-relay-ppp";
               description "Multilink Frame Relay end-to-end protocol parameters";
               uses apply-advanced;
               leaf bundle {
                 description "Logical interface name this link will join";
                 type union {
                   type jt:interface-unit;
                   type string {
                     pattern "<.*>|$.*";
                   }
                 }
               }
             }
             container mlfr-uni-nni {
               presence "enable mlfr-uni-nni";
               junos:must "(!(\".. .. encapsulation frame-relay-ppp\"))";
               junos:must-message "family mlfr-uni-uni is not supported on encapsulation frame-relay-ppp";
               description "Multilink Frame Relay UNI NNI protocol parameters";
               uses apply-advanced;
               leaf bundle {
                 description "Logical interface name this link will join";
                 type union {
                   type jt:interface-unit;
                   type string {
                     pattern "<.*>|$.*";
                   }
                 }
               }
             }
             container ccc {
               presence "enable ccc";
               junos:must "(!(\".. .. encapsulation frame-relay-ppp\"))";
               junos:must-message "family ccc is not supported on encapsulation frame-relay-ppp";
               description "Circuit cross-connect parameters";
               uses apply-advanced;
               container filter {
                 description "Packet filtering";
                 uses apply-advanced;
                 choice input_choice {
                   case case_1 {
                     leaf input {
                       description "Name of filter applied to received packets";
                       type string;
                     }
                   }
                   case case_2 {
                     leaf-list input-list {
                       ordered-by user;
                       description "List of filter modules applied to received packets ";
                       type string;
                     }
                   }
                 }
                 leaf-list input-chain {
                   ordered-by user;
                   description "List of filter modules applied to received packets ";
                   type string;
                 }
                 choice output_choice {
                   case case_1 {
                     leaf output {
                       description "Name of filter applied to transmitted packets";
                       type string;
                     }
                   }
                   case case_2 {
                     leaf-list output-list {
                       ordered-by user;
                       description "List of filter modules applied to transmitted packets ";
                       type string;
                     }
                   }
                 }
                 leaf-list output-chain {
                   ordered-by user;
                   description "List of filter modules applied to transmitted packets ";
                   type string;
                 }
                 leaf group {
                   description "Interface group to which interface belongs";
                   type union {
                     type string {
                       pattern "<.*>|$.*";
                     }
                     type uint32 {
                       range "1 .. 255";
                     }
                   }
                 }
               }
               container policer {
                 description "Interface policing";
                 uses apply-advanced;
                 leaf input {
                   description "Name of policer applied to received packets";
                   type string;
                 }
                 leaf output {
                   description "Name of policer applied to transmitted packets";
                   type string;
                 }
               }
               leaf translate-fecn-and-becn {
                 description "Translate FECN and BECN bits";
                 type empty;
               }
               choice de-or-plp {
                 case case_1 {
                   leaf translate-discard-eligible {
                     description "Translate DE bit";
                     type empty;
                   }
                 }
                 case case_2 {
                 }
               }
               leaf keep-address-and-control {
                 description "Don't strip PPP address and control bytes";
                 type empty;
               }
             }
             container tcc {
               presence "enable tcc";
               junos:must "(!(\".. .. encapsulation frame-relay-ppp\"))";
               junos:must-message "family tcc is not supported on encapsulation frame-relay-ppp";
               description "Translational cross-connect parameters";
               uses apply-advanced;
               container policer {
                 description "Interface policing";
                 uses apply-advanced;
                 leaf input {
                   description "Name of policer applied to received packets";
                   type string;
                 }
                 leaf output {
                   description "Name of policer applied to transmitted packets";
                   type string;
                 }
               }
               container proxy {
                 presence "enable proxy";
                 uses apply-advanced;
                 leaf inet-address {
                   description "Remote host address on non-Ethernet side of Ethernet TCC";
                   type jt:ipv4addr;
                 }
               }
               container remote {
                 presence "enable remote";
                 uses apply-advanced;
                 leaf inet-address {
                   description "Remote host address on Ethernet side of Ethernet TCC";
                   type jt:ipv4addr;
                 }
                 leaf mac-address {
                   description "Remote host MAC address on Ethernet side of Ethernet TCC";
                   type jt:mac-addr;
                 }
               }
             }
             container vpls {
               presence "enable vpls";
               description "Virtual private LAN service parameters";
               uses apply-advanced;
               leaf core-facing {
                 description "Interface is core facing";
                 type empty;
               }
               container filter {
                 description "Packet filtering";
                 uses apply-advanced;
                 choice input_choice {
                   case case_1 {
                     container input {
                       junos:cli-feature "oneliner";
                       description "Filter to be applied to received packets";
                       leaf filter-name {
                         description "Name of the filter";
                         junos:cli-feature "nokeyword";
                         junos:must "((!(\".. .. .. rpf-check\") || (!(any \"firewall family inet filter $$ term <*> from first-byte-of-payload\") && !(any \"firewall family inet filter $$ term <*> from first-byte-of-payload-except\"))))";
                         junos:must-message "filter with first-byte-of-payload match cannot be bound on URPF";
                         type string;
                       }
                       leaf shared-name {
                         description "Filter shared-name of instances of interface-shared filter";
                         type string;
                       }
                       leaf precedence {
                         description "Precedence of the filter";
                         type union {
                           type string {
                             pattern "<.*>|$.*";
                           }
                           type uint32 {
                             range "0 .. 255";
                           }
                         }
                       }
                     }
                   }
                   case case_2 {
                     leaf-list input-list {
                       ordered-by user;
                       description "List of filter modules applied to received packets ";
                       type string;
                     }
                   }
                 }
                 choice output_choice {
                   case case_1 {
                     container output {
                       junos:cli-feature "oneliner";
                       description "Filter to be applied to transmitted packets";
                       leaf filter-name {
                         description "Name of the filter";
                         junos:cli-feature "nokeyword";
                         junos:must "((!(\".. .. .. rpf-check\") || (!(any \"firewall family inet filter $$ term <*> from first-byte-of-payload\") && !(any \"firewall family inet filter $$ term <*> from first-byte-of-payload-except\"))))";
                         junos:must-message "filter with first-byte-of-payload match cannot be bound on URPF";
                         type string;
                       }
                       leaf shared-name {
                         description "Filter shared-name of instances of interface-shared filter";
                         type string;
                       }
                       leaf precedence {
                         description "Precedence of the filter";
                         type union {
                           type string {
                             pattern "<.*>|$.*";
                           }
                           type uint32 {
                             range "0 .. 255";
                           }
                         }
                       }
                     }
                   }
                   case case_2 {
                     leaf-list output-list {
                       ordered-by user;
                       description "List of filter modules applied to transmitted packets ";
                       type string;
                     }
                   }
                 }
                 container adf {
                   description "Ascend Data Filter definition";
                   uses apply-advanced;
                   list rule {
                     key name;
                     ordered-by user;
                     description "Set of ADF rules";
                     leaf name {
                       description "Value for a single rule";
                       junos:cli-feature "nokeyword";
                       type string;
                     }
                     uses apply-advanced;
                   }
                   leaf counter {
                     description "Add a counter to each rule";
                     type empty;
                   }
                   leaf input-precedence {
                     description "Precedence of the input rules";
                     type union {
                       type string {
                         pattern "<.*>|$.*";
                       }
                       type uint32 {
                         range "0 .. 255";
                       }
                     }
                   }
                   leaf not-mandatory {
                     description "No errors will be reported if no rules are present";
                     type empty;
                   }
                   leaf output-precedence {
                     description "Precedence of the output rules";
                     type union {
                       type string {
                         pattern "<.*>|$.*";
                       }
                       type uint32 {
                         range "0 .. 255";
                       }
                     }
                   }
                 }
                 leaf group {
                   description "Group to which interface belongs";
                   type union {
                     type string {
                       pattern "<.*>|$.*";
                     }
                     type uint32 {
                       range "1 .. 255";
                     }
                   }
                 }
               }
               container policer {
                 description "Interface policing";
                 uses apply-advanced;
                 leaf input {
                   description "Name of policer applied to received packets";
                   type string;
                 }
                 leaf output {
                   description "Name of policer applied to transmitted packets";
                   type string;
                 }
               }
             }
             container bridge {
               presence "enable bridge";
               junos:must "((!(\".. vpls\") && (!(\".. inet\") && (!(\".. inet6\") && (!(\".. ccc\") && (!(\".. ethernet-switching\") && (!(\".. iso\") && (!(\".. llc2\") && (!(\".. mpls\") && (!(\".. tcc\") && (!(\".. pppoe\") && !(\".. gre\"))))))))))))";
               junos:must-message "family bridge and rest of the families are mutually exclusive";
               description "Layer-2 bridging parameters";
               uses apply-advanced;
               leaf core-facing {
                 description "Interface is core facing";
                 type empty;
               }
               container filter {
                 description "Packet filtering";
                 uses apply-advanced;
                 choice input_choice {
                   case case_1 {
                     container input {
                       junos:cli-feature "oneliner";
                       description "Filter to be applied to received packets";
                       leaf filter-name {
                         description "Name of the filter";
                         junos:cli-feature "nokeyword";
                         junos:must "((!(\".. .. .. rpf-check\") || (!(any \"firewall family inet filter $$ term <*> from first-byte-of-payload\") && !(any \"firewall family inet filter $$ term <*> from first-byte-of-payload-except\"))))";
                         junos:must-message "filter with first-byte-of-payload match cannot be bound on URPF";
                         type string;
                       }
                       leaf shared-name {
                         description "Filter shared-name of instances of interface-shared filter";
                         type string;
                       }
                       leaf precedence {
                         description "Precedence of the filter";
                         type union {
                           type string {
                             pattern "<.*>|$.*";
                           }
                           type uint32 {
                             range "0 .. 255";
                           }
                         }
                       }
                     }
                   }
                   case case_2 {
                     leaf-list input-list {
                       ordered-by user;
                       description "List of filter modules applied to received packets ";
                       type string;
                     }
                   }
                 }
                 choice output_choice {
                   case case_1 {
                     container output {
                       junos:cli-feature "oneliner";
                       description "Filter to be applied to transmitted packets";
                       leaf filter-name {
                         description "Name of the filter";
                         junos:cli-feature "nokeyword";
                         junos:must "((!(\".. .. .. rpf-check\") || (!(any \"firewall family inet filter $$ term <*> from first-byte-of-payload\") && !(any \"firewall family inet filter $$ term <*> from first-byte-of-payload-except\"))))";
                         junos:must-message "filter with first-byte-of-payload match cannot be bound on URPF";
                         type string;
                       }
                       leaf shared-name {
                         description "Filter shared-name of instances of interface-shared filter";
                         type string;
                       }
                       leaf precedence {
                         description "Precedence of the filter";
                         type union {
                           type string {
                             pattern "<.*>|$.*";
                           }
                           type uint32 {
                             range "0 .. 255";
                           }
                         }
                       }
                     }
                   }
                   case case_2 {
                     leaf-list output-list {
                       ordered-by user;
                       description "List of filter modules applied to transmitted packets ";
                       type string;
                     }
                   }
                 }
                 container adf {
                   description "Ascend Data Filter definition";
                   uses apply-advanced;
                   list rule {
                     key name;
                     ordered-by user;
                     description "Set of ADF rules";
                     leaf name {
                       description "Value for a single rule";
                       junos:cli-feature "nokeyword";
                       type string;
                     }
                     uses apply-advanced;
                   }
                   leaf counter {
                     description "Add a counter to each rule";
                     type empty;
                   }
                   leaf input-precedence {
                     description "Precedence of the input rules";
                     type union {
                       type string {
                         pattern "<.*>|$.*";
                       }
                       type uint32 {
                         range "0 .. 255";
                       }
                     }
                   }
                   leaf not-mandatory {
                     description "No errors will be reported if no rules are present";
                     type empty;
                   }
                   leaf output-precedence {
                     description "Precedence of the output rules";
                     type union {
                       type string {
                         pattern "<.*>|$.*";
                       }
                       type uint32 {
                         range "0 .. 255";
                       }
                     }
                   }
                 }
                 leaf group {
                   description "Group to which interface belongs";
                   type union {
                     type string {
                       pattern "<.*>|$.*";
                     }
                     type uint32 {
                       range "1 .. 255";
                     }
                   }
                 }
               }
               container policer {
                 description "Interface policing";
                 uses apply-advanced;
                 leaf input {
                   description "Name of policer applied to received packets";
                   type string;
                 }
                 leaf output {
                   description "Name of policer applied to transmitted packets";
                   type string;
                 }
               }
               leaf interface-mode {
                 description "Interface mode (access or trunk)";
                 type enumeration {
                   enum "access" {
                     description "Interface mode is access";
                     junos:must "((!(\"interfaces ${interface} vlan-tagging\") && (!(\"interfaces ${interface} flexible-vlan-tagging\") && !(\"interfaces ${interface} stacked-vlan-tagging\"))))";
                     junos:must-message "interface-mode access is allowed only for untagged interfaces";
                   }
                   enum "trunk" {
                     description "Interface mode is trunk";
                     junos:must "(!(\"interfaces ${interface} no-native-vlan-insert\"))";
                     junos:must-message "'interface-mode trunk' must not be configured with 'no-native-vlan-insert'";
                     junos:must "(((\"protocols mvrp interface ${interface}\" || any \"routing-instances <*> protocols mvrp interface ${interface}\") || (\".. vlan-id-list\" || (\".. isid-list\" || (\".. inner-vlan-id-list\" || (\".. vlan members\" || (\"..inner-vlan members\" || (\".. vlan-id\" || \".. vlan-auto-sense\"))))))))";
                     junos:must-message "'interface-mode trunk' must be defined with either 'vlan-id-list','isid-list', 'inner-vlan-id-list' or the interface must be configured for 'protocols mvrp' or 'vlan-auto-sense'";
                   }
                 }
               }
               leaf vlan-auto-sense {
                 description "Enable VLAN auto sense on this interface";
                 junos:must "(\".. interface-mode trunk\")";
                 junos:must-message "vlan-auto-sense can be enabled only on trunk interfaces";
                 type empty;
               }
               leaf bridge-domain-type {
                 description "Bridge domain type (svlan or bvlan)";
                 type enumeration {
                   enum "svlan" {
                     description "Bridge domain type svlan";
                     junos:must "(\".. isid-list all-service-groups\")";
                     junos:must-message "bridge-domain-type svlan is allowed only for isid tagged interfaces";
                     junos:must "(\".. interface-mode trunk\")";
                     junos:must-message "bridge-domain-type svlan is allowed only for trunk interfaces";
                   }
                   enum "bvlan" {
                     description "Bridge domain type bvlan";
                     junos:must "(\".. isid-list all\")";
                     junos:must-message "bridge-domain-type bvlan is allowed only for isid tagged interfaces";
                     junos:must "(\".. interface-mode trunk\")";
                     junos:must-message "bridge-domain-type bvlan is allowed only for trunk interfaces";
                   }
                 }
               }
               leaf inter-switch-link {
                 description "PVLAN inter switch link";
                 junos:must "(\".. interface-mode trunk\")";
                 junos:must-message "'Inter switch link' is supported only under trunk interface mode";
                 type empty;
               }
               choice vlan_list {
                 case case_1 {
                   leaf vlan-id {
                     description "Access mode and trunk mode VLAN membership";
                     type union {
                       type string {
                         pattern "<.*>|$.*";
                       }
                       type uint32 {
                         range "1 .. 4094";
                       }
                     }
                   }
                 }
                 case case_2 {
                   leaf-list vlan-id-list {
                     description "Trunk mode VLAN membership for this interface";
                     junos:must "((!(\".. .. .. vlan-id\") && !(\".. .. .. vlan-tags\")))";
                     junos:must-message "'vlan-id-list' cannot be used on interface with vlan-id/vlan-tags";
                     junos:must "(!(\"interfaces ${interface} stacked-vlan-tagging\"))";
                     junos:must-message "'vlan-id-list' is not supported on stacked-vlan-tagging mode";
                     junos:must "(\".. interface-mode trunk\")";
                     junos:must-message "'vlan-id-list' statement supported only under trunk interface mode";
                     type jt:vlan-range;
                   }
                 }
                 case case_3 {
                   leaf-list inner-vlan-id-list {
                     description "Trunk mode VLAN membership for this interface based on inner VLAN tag";
                     junos:must "((!(\".. .. .. vlan-tags inner\") && !(\".. .. .. vlan-tags inner-range\")))";
                     junos:must-message "'inner-vlan-id-list' cannot be used on interface with vlan-tags inner/inner-range";
                     junos:must "((\".. .. .. vlan-id\" || \".. .. .. vlan-tags\"))";
                     junos:must-message "'inner-vlan-id-list' can be used only on interface with vlan-id/vlan-tags";
                     junos:must "(\"interfaces ${interface} flexible-vlan-tagging\")";
                     junos:must-message "'inner-vlan-id-list' is supported only on flexible-vlan-tagging mode";
                     junos:must "(\".. interface-mode trunk\")";
                     junos:must-message "'inner-vlan-id-list' statement supported only under trunk interface mode";
                     type jt:vlan-range;
                   }
                 }
               }
               container vlan-rewrite {
                 junos:must "((\".. inner-vlan-id-list\" || \".. vlan-id-list\"))";
                 junos:must-message "'vlan-rewrite' statement can be used only with 'vlan-id-list' or inner-vlan-id-list configured";
                 junos:must "(\".. interface-mode trunk\")";
                 junos:must-message "'vlan-rewrite' statement supported only under trunk interface mode";
                 junos:cli-feature "oneliner-plus";
                 description "Specify vlan translation";
                 uses apply-advanced;
                 list translate {
                   key name;
                   ordered-by user;
                   junos:cli-feature "oneliner";
                   description "Translate incoming VLAN tag";
                   leaf name {
                     description "Specify the incoming VLAN tag";
                     junos:cli-feature "nokeyword";
                     type union {
                       type string {
                         pattern "<.*>|$.*";
                       }
                       type uint32 {
                         range "1 .. 4094";
                       }
                     }
                   }
                   leaf to-vlan-id {
                     description "Specify the bridge-domain VLAN-ID";
                     junos:cli-feature "nokeyword";
                     type union {
                       type string {
                         pattern "<.*>|$.*";
                       }
                       type uint32 {
                         range "1 .. 4094";
                       }
                     }
                   }
                 }
               }
               choice isid_list {
                 case case_1 {
                   leaf isid-list {
                     description "Specify the ISID list";
                     type enumeration {
                       enum "all-service-groups" {
                         description "Map all ISIDs specified under the service-groups";
                         junos:must "(\".. interface-mode trunk\")";
                         junos:must-message "'all-service-groups' statement supported only under trunk interface mode";
                       }
                       enum "all" {
                         description "Map all ISIDs";
                         junos:must "(\".. interface-mode trunk\")";
                         junos:must-message "'all' statement supported only under trunk interface mode";
                       }
                     }
                   }
                 }
               }
               container recovery-timeout {
                 junos:must "(\".. storm-control\")";
                 junos:must-message "Recovery timeout should be configured only with storm-control";
                 junos:cli-feature "oneliner";
                 description "Recovery timeout for this interface";
                 leaf time-in-seconds {
                   junos:cli-feature "nokeyword";
                   units "seconds";
                   type union {
                     type string {
                       pattern "<.*>|$.*";
                     }
                     type uint32 {
                       range "10 .. 3600";
                     }
                   }
                 }
               }
             }
             container ethernet-switching {
               description "Ethernet switching parameters";
               presence "enable ethernet-switching";
               junos:must "((!(\".. vpls\") && (!(\".. inet\") && (!(\".. inet6\") && (!(\".. bridge\") && (!(\".. ccc\") && (!(\".. iso\") && (!(\".. llc2\") && (!(\".. mpls\") && (!(\".. tcc\") && (!(\".. pppoe\") && !(\".. gre\"))))))))))))";
               junos:must-message "Family ethernet-switching and rest of the families are mutually exclusive";
               junos:must "(!((\"protocols l2-learning global-mode switching\" && any \"security zones security-zone <*> interfaces ${interface}\")))";
               junos:must-message "In switching mode, ethernet-switching interface must not be in security zone.";
               junos:must "(!((\"interfaces ${interface} vlan-tagging\" && !(\"protocols l2-learning global-mode transparent-bridge\"))))";
               junos:must-message "An interface cannot have both family ethernet-switching and vlan-tagging configured";
               junos:must "(!((\"interfaces ${interface} vlan-tagging\" && \"protocols l2-learning global-mode switching\")))";
               junos:must-message "An interface cannot have both family ethernet-switching and vlan-tagging configured";
               junos:must "(!((!(\"protocols l2-learning global-mode transparent-bridge\") && any \"security zones security-zone <*> interfaces ${interface}\")))";
               junos:must-message "In switching mode, ethernet-switching interface must not be in security zone.";
               uses ethernet-switching-type;
             }
             container pppoe {
               description "PPP over Ethernet underlying interface-specific options";
               presence "enable pppoe";
               junos:must "(!(\"forwarding-options hyper-mode\"))";
               junos:must-message "To configure family pppoe, 'forwarding-options hyper-mode' should not be configured";
               junos:must "((!(\".. vpls\") && (!(\".. ccc\") && (!(\".. ethernet-switching\") && (!(\".. iso\") && (!(\".. llc2\") && (!(\".. mpls\") && (!(\".. tcc\") && (!(\".. bridge\") && !(\".. gre\"))))))))))";
               junos:must-message "Invalid family type configured with family pppoe";
               junos:must "(!(\".. .. pppoe-underlying-options\"))";
               junos:must-message "family pppoe is mutually exclusive with pppoe-underlying-options";
               uses pppoe_underlying_options_type;
             }
             container any {
               presence "enable any";
               description "Parameters for 'any' family";
               uses apply-advanced;
               container filter {
                 description "Layer 2 packet filtering";
                 uses apply-advanced;
                 leaf input {
                   description "Name of filter applied to received packets";
                   junos:must "((\"firewall family any filter $$\" || (!(\"firewall\") && \".. .. .. .. .. .. firewall family any filter $$\")))";
                   junos:must-message "referenced filter must be defined under firewall family any";
                   type string {
                     junos:posix-pattern "!^((__.*)|(.{65,}))$";
                     junos:pattern-message "Must be a non-reserved string of 64 characters or less";
                   }
                 }
                 leaf group {
                   description "Group to which interface belongs";
                   type union {
                     type string {
                       pattern "<.*>|$.*";
                     }
                     type uint32 {
                       range "1 .. 255";
                     }
                   }
                 }
               }
             }
             uses apply-advanced;
           }
           leaf service-domain {
             description "Service domain to which interface belongs";
             type enumeration {
               enum "inside" {
                 description "Inside network";
               }
               enum "outside" {
                 description "Outside network";
               }
             }
           }
           leaf copy-tos-to-outer-ip-header {
             description "Copy IP payload header's ToS field to GRE delivery header";
             type empty;
           }
           container load-balancing-options {
             junos:must "(!(\".. .. load-balancing-options high-availability-options one-to-one\"))";
             junos:must-message "load-balancing-options are used when number of active members is more than one";
             description "AMS subunit load balancing options";
             uses apply-advanced;
             leaf preferred-active {
               description "Preferred active Interface name";
               junos:must "((\".. .. .. load-balancing-options member-interface $$\" && !(\".. .. .. load-balancing-options high-availability-options many-to-one preferred-backup $$\")))";
               junos:must-message "Active should be one of member-interfaces excluding preferred-backup";
               type union {
                 type jt:interface-device;
                 type string {
                   pattern "<.*>|$.*";
                 }
               }
             }
             leaf disable-hash {
               description "Hash based distribution is not needed for this subunit";
               junos:must "(\".. .. service-domain\")";
               junos:must-message "service-domain must be configured if disable-hash is enabled";
               junos:must "(!(\".. hash-keys\"))";
               junos:must-message "hash-keys must not be configured if disable-hash is enabled";
               type empty;
             }
             leaf modulo-key {
               description "Modulo based distribution";
               junos:must "(!(\".. .. .. load-balancing-options member-failure-options redistribute-all-traffic\"))";
               junos:must-message "redistribute-all-traffic can not be configured with modulo-key";
               junos:must "(!(\".. disable-hash\"))";
               junos:must-message "disable-hash can not be configured with modulo-key";
               junos:must "(\".. .. service-domain\")";
               junos:must-message "service-domain must be configured with modulo-key";
               junos:must "(!(\".. hash-keys\"))";
               junos:must-message "hash-keys can not be configured with modulo-key";
               type enumeration {
                 enum "source-ip" {
                   description "Source Ip Address";
                 }
                 enum "destination-ip" {
                   description "Destination Ip Address";
                 }
               }
             }
             container hash-keys {
               uses apply-advanced;
               leaf-list ingress-key {
                 ordered-by user;
                 description "Hash Key for the ingress direction";
                 type enumeration {
                   enum "source-ip" {
                     description "Source Ip Address";
                   }
                   enum "destination-ip" {
                     description "Destination Ip Address";
                   }
                   enum "protocol" {
                     description "Protocol";
                   }
                   enum "iif" {
                     description "Incoming Interface";
                   }
                 }
               }
               leaf-list egress-key {
                 ordered-by user;
                 description "Hash Key for the egress direction";
                 status deprecated;
                 type enumeration {
                   enum "source-ip" {
                     description "Source Ip Address";
                     status deprecated;
                   }
                   enum "destination-ip" {
                     description "Destination Ip Address";
                     status deprecated;
                   }
                   enum "protocol" {
                     description "Protocol";
                     status deprecated;
                   }
                   enum "oif" {
                     description "Outgoing Interface";
                     status deprecated;
                   }
                 }
               }
               leaf ipv6-source-prefix-length {
                 description "IPv6 source prefix length for hash computation";
                 type enumeration {
                   enum "56" {
                     description "56 bit IPv6 address prefix";
                   }
                   enum "64" {
                     description "64 bit IPv6 address prefix";
                   }
                   enum "96" {
                     description "96 bit IPv6 address prefix";
                   }
                   enum "128" {
                     description "Complete 128 bit IPv6 address";
                   }
                 }
               }
             }
           }
           container interface-state {
             description "IRB interface state computation";
             uses apply-advanced;
             choice state {
               case case_1 {
                 leaf local {
                   description "IRB State computation based on local interface state";
                   type empty;
                 }
               }
               case case_2 {
                 leaf remote {
                   description "IRB State computation based on remote reachability";
                   type empty;
                 }
               }
               case case_3 {
                 leaf local-remote {
                   description "IRB State computation based on local or remote reachability";
                   type empty;
                 }
               }
               case case_4 {
                 leaf local-interface {
                   description "IRB State computation based on loopback AE port state";
                   type union {
                     type jt:interface-name;
                     type string {
                       pattern "<.*>|$.*";
                     }
                   }
                 }
               }
             }
             leaf local-count {
               description "Minimum number of local layer2 link in up state to consider IRB up";
               junos:must "(!(\".. remote\"))";
               junos:must-message "Must configure local, local-remote or keep default";
               type union {
                 type uint16;
                 type string {
                   pattern "<.*>|$.*";
                 }
               }
             }
             leaf vtep-count {
               description "Minimum number of VTEP link in up state to consider IRB up";
               junos:must "(!(\".. local\"))";
               junos:must-message "Must configure remote,local-remote or keep default";
               type union {
                 type uint16;
                 type string {
                   pattern "<.*>|$.*";
                 }
               }
             }
             container hold-time {
               description "Delay before marking interface up or down for defect";
               uses apply-advanced;
               leaf up {
                 description "Delay in seconds before marking IRB interface up";
                 units "seconds";
                 type union {
                   type uint32;
                   type string {
                     pattern "<.*>|$.*";
                   }
                 }
               }
               leaf down {
                 description "Delay in seconds before marking IRB interface down";
                 units "seconds";
                 type union {
                   type uint32;
                   type string {
                     pattern "<.*>|$.*";
                   }
                 }
               }
             }
           }
           leaf mac {
             description "Configure logical interface MAC address";
             type jt:mac-unicast;
           }
           leaf virtual-gateway-v4-mac {
             description "Configure virtual gateway IPV4 virtual MAC address";
             type jt:mac-unicast;
           }
           leaf virtual-gateway-v6-mac {
             description "Configure virtual gateway IPV6 virtual MAC address";
             type jt:mac-unicast;
           }
           leaf no-dhcp-flood {
             description "Disable dhcp flooding";
             type empty;
           }
           leaf etree-ac-role {
             description "ETREE attachment circuit role";
             type enumeration {
               enum "root" {
                 description "ETREE root interface";
               }
               enum "leaf" {
                 description "ETREE leaf interface";
               }
             }
           }
           container dialer-options {
             presence "enable dialer-options";
             description "Dialer options";
             uses apply-advanced;
             leaf pool {
               description "Dialer pool";
               junos:must "((!(\"interfaces umd0 dialer-options pool $$\") || !(\".. callback\")))";
               junos:must-message "callback is not supported if the subordinate interface is umd0";
               junos:must "(any \"interfaces <*> dialer-options pool $$\")";
               junos:must-message "Pool not configured in any subordinate interface";
               junos:must "(unique \"interfaces <dl*>\")";
               junos:must-message "Only one dl interface can be configured";
               type string {
                 length "1 .. 64";
               }
             }
             leaf-list dial-string {
               ordered-by user;
               description "String to dial out";
               type string {
                 length "1 .. 63";
               }
               max-elements 15;
             }
             container incoming-map {
               description "Map incoming call to dialer";
               uses apply-advanced;
               choice caller-type {
                 case case_1 {
                   list caller {
                     key name;
                     ordered-by user;
                     junos:cli-feature "oneliner";
                     description "Caller Id to be screened";
                     max-elements 300;
                     leaf name {
                       description "Caller ID (upto 15 digits)";
                       junos:cli-feature "nokeyword";
                       type string {
                         junos:posix-pattern "^([0-9]{1,15})$";
                         junos:pattern-message "Can contain up to 15 digits";
                       }
                     }
                   }
                 }
                 case case_2 {
                   leaf accept-all {
                     description "Accept all incoming calls";
                     type empty;
                   }
                 }
               }
             }
             leaf callback {
               description "Call back on any incoming call to the dialer";
               junos:must "(!(\".. watch-list \"))";
               junos:must-message "A dialer interface cannot have callback enabled and watch-list at the same time";
               junos:must "(\".. dial-string\")";
               junos:must-message "Dial string is mandatory for callback";
               junos:must "(\".. incoming-map\")";
               junos:must-message "incoming-map is mandatory for callback";
               type empty;
             }
             leaf callback-wait-period {
               description "Time to wait before calling back";
               units "seconds";
               junos:must "(\".. callback\")";
               junos:must-message "Callback needs to be configured";
               type union {
                 type string {
                   pattern "<.*>|$.*";
                 }
                 type uint32 {
                   range "2 .. 255";
                 }
               }
             }
             leaf redial-delay {
               description "Time to wait before redialing";
               units "seconds";
               type union {
                 type string {
                   pattern "<.*>|$.*";
                 }
                 type uint32 {
                   range "2 .. 255";
                 }
               }
             }
             leaf idle-timeout {
               description "Delay before taking down the interface";
               default "120";
               units "seconds";
               junos:must "((\".. .. family inet  filter dialer\" || (\".. .. family inet6 filter dialer\" || \".. .. family mpls  filter dialer\")))";
               junos:must-message "Dialer filter must be configured";
               type union {
                 type string {
                   pattern "<.*>|$.*";
                 }
                 type uint32 {
                   range "0 .. 4294967295";
                 }
               }
             }
             list watch-list {
               key name;
               junos:cli-feature "homogeneous";
               description "Dialer watch list";
               junos:must "(\".. dial-string\")";
               junos:must-message "dial-string is mandatory for watch-list";
               leaf name {
                 description "Address prefix";
                 junos:cli-feature "nokeyword";
                 type jt:ipprefix-only;
               }
               uses apply-advanced;
             }
             leaf load-threshold {
               description "Load threshold for adding interfaces";
               junos:must "(\".. .. .. encapsulation multilink-ppp\")";
               junos:must-message "Encapsulation must be multilink-ppp";
               type union {
                 type string {
                   pattern "<.*>|$.*";
                 }
                 type uint32 {
                   range "0 .. 100";
                 }
               }
             }
             leaf load-interval {
               description "Interval used to calculate average load";
               units "seconds";
               junos:must "(\".. .. .. encapsulation multilink-ppp\")";
               junos:must-message "Encapsulation must be multilink-ppp";
               type union {
                 type string {
                   pattern "<.*>|$.*";
                 }
                 type uint32 {
                   range "20 .. 180";
                 }
               }
             }
             leaf activation-delay {
               description "Activation delay";
               units "seconds";
               junos:must "(!((\".. .. family inet  filter dialer\" || (\".. .. family inet6 filter dialer\" || \".. .. family mpls  filter dialer\"))))";
               junos:must-message "Activation delay cannot be configured for dialer filter";
               type union {
                 type string {
                   pattern "<.*>|$.*";
                 }
                 type uint32 {
                   range "1 .. 4294967295";
                 }
               }
             }
             leaf deactivation-delay {
               description "Deactivation delay";
               units "seconds";
               junos:must "(!((\".. .. family inet  filter dialer\" || (\".. .. family inet6 filter dialer\" || \".. .. family mpls  filter dialer\"))))";
               junos:must-message "Deactivation delay cannot be configured for dialer filter";
               type union {
                 type string {
                   pattern "<.*>|$.*";
                 }
                 type uint32 {
                   range "1 .. 4294967295";
                 }
               }
             }
             leaf initial-route-check {
               description "Delay to check primary after the router is up";
               default "120";
               units "seconds";
               junos:must "(\".. watch-list\")";
               junos:must-message "No watch list specified under dialer options";
               type union {
                 type string {
                   pattern "<.*>|$.*";
                 }
                 type uint16 {
                   range "1 .. 300";
                 }
               }
             }
             leaf-list route {
               ordered-by user;
               description "Route on dialer";
               type jt:ipprefix;
             }
             leaf always-on {
               description "Always keep on-line";
               junos:must "(!((\".. .. family inet  filter dialer\" || (\".. .. family inet6 filter dialer\" || \".. .. family mpls  filter dialer\"))))";
               junos:must-message "A dialer interface cannot have always-on enabled and filter at the same time";
               type empty;
             }
             leaf self-recover-time {
               description "Sub-interface self-recover time";
               units "seconds";
               type union {
                 type string {
                   pattern "<.*>|$.*";
                 }
                 type uint32 {
                   range "2 .. 120";
                 }
               }
             }
           }
           container backup-options {
             description "Backup interface configuration options";
             uses apply-advanced;
             leaf interface {
               description "Backup interface";
               junos:must "(\"interfaces $$-IFL dialer-options dial-string\")";
               junos:must-message "No dial-string configured in backup dialer interface";
               junos:must "(!(\"interfaces $$-IFL dialer-options callback \"))";
               junos:must-message "A dialer interface cannot be backup as well as have callback";
               junos:must "(!((\"interfaces $$-IFL family inet  filter dialer\" || (\"interfaces $$-IFL family inet6 filter dialer\" || \"interfaces $$-IFL family mpls  filter dialer\"))))";
               junos:must-message "A dialer interface cannot be backup as well as have dialer filter";
               junos:must "(!(\"interfaces $$-IFL dialer-options watch-list \"))";
               junos:must-message "A dialer interface cannot be backup as well as have watch list";
               junos:must "(\"interfaces $$-IFL dialer-options\")";
               junos:must-message "No dialer options configured in backup dialer interface";
               junos:must "(!(\"interfaces $$-IFL dialer-options always-on\"))";
               junos:must-message "A dialer interface cannot be backup as well as always-on";
               type union {
                 type jt:interface-name;
                 type string {
                   pattern "<.*>|$.*";
                 }
               }
             }
           }
           container dynamic-call-admission-control {
             description "Dynamic call admission control configuration";
             uses apply-advanced;
             leaf bearer-bandwidth-limit {
               description "Bearer bandwidth limit";
               units "kilobits per second";
               type union {
                 type string {
                   pattern "<.*>|$.*";
                 }
                 type uint16 {
                   range "0 .. 9999";
                 }
               }
             }
             leaf activation-priority {
               description "Priority assigned to bearer bandwidth limit";
               default "50";
               type union {
                 type string {
                   pattern "<.*>|$.*";
                 }
                 type uint8 {
                   range "0 .. 255";
                 }
               }
             }
           }
           container explicit-proxy {
             presence "enable explicit-proxy";
             description "Attach explicit proxy profiles";
             uses apply-advanced;
             leaf-list profile {
               description "Explicit proxy profile name";
               type string {
                 length "1 .. 63";
               }
             }
           }
         }
         container no-partition {
           junos:cli-feature "oneliner";
           description "Use channelizable interface as clear channel";
           leaf interface-type {
             description "Interface type";
             type enumeration {
               enum "e1" {
                 description "E1 interface";
               }
               enum "t1" {
                 description "T1 interface";
               }
               enum "at" {
                 description "ATM interface";
               }
               enum "t3" {
                 description "T3 interface";
               }
               enum "e3" {
                 description "E3 interface";
               }
               enum "ct3" {
                 description "Channelized T3 interface";
               }
               enum "so" {
                 description "SONET interface";
               }
               enum "cau4" {
                 description "CAU4 interface";
               }
             }
           }
         }
         list partition {
           key name;
           ordered-by user;
           junos:cli-feature "oneliner";
           description "Channelized interface partition";
           junos:must "(!(\".. no-partition\"))";
           junos:must-message "cannot set partitions with no-partition attribute turned on";
           leaf name {
             description "Sublevel interface partition index (for example, 1, 3-4)";
             junos:cli-feature "nokeyword";
             type string;
           }
           leaf oc-slice {
             description "Range of SONET/SDH slices (for example, 1, 7-9)";
             type string;
           }
           leaf timeslots {
             description "Timeslots [(1..24) for T1, (1..31) for E1]; for example, 1-3,4,9,22-24 (no spaces)";
             type string;
           }
           leaf interface-type {
             description "Sublevel interface type";
             type enumeration {
               enum "ds" {
                 description "DS0 interface";
               }
               enum "e1" {
                 description "E1 interface";
               }
               enum "t1" {
                 description "T1 interface";
               }
               enum "at" {
                 description "ATM interface";
               }
               enum "ct1" {
                 description "Channelized T1 interface";
               }
               enum "ce1" {
                 description "Channelized E1 interface";
               }
               enum "t3" {
                 description "T3 interface";
               }
               enum "ct3" {
                 description "Channelized T3 interface";
               }
               enum "e3" {
                 description "E3 interface";
               }
               enum "so" {
                 description "SONET interface";
               }
               enum "coc1" {
                 description "Channelized OC1 interface";
               }
               enum "cau4" {
                 description "Channelized AU4 interface";
               }
               enum "dc" {
                 description "D channel interface";
                 junos:must "(any \".. .. partition <*> interface-type bc\")";
                 junos:must-message "BC partition must be defined for PRI";
               }
               enum "bc" {
                 description "B channel interface";
                 junos:must "(any \".. .. partition <*> interface-type dc\")";
                 junos:must-message "DC partition must be defined for PRI";
               }
             }
           }
         }
         container modem-options {
           description "MODEM interface-specific options";
           uses apply-advanced;
           leaf init-command-string {
             description "AT command string to initialize modem";
             type string {
               length "1 .. 127";
             }
           }
           leaf dialin {
             default "console";
             type enumeration {
               enum "console" {
                 description "Management console access";
               }
               enum "routable" {
                 description "Routable access";
               }
             }
           }
         }
         container isdn-options {
           description "ISDN interface-specific options";
           uses apply-advanced;
           leaf switch-type {
             description "ISDN switch type";
             type enumeration {
               enum "ni1" {
                 description "NI1 BRI variant";
               }
               enum "etsi" {
                 description "ETSI variant";
               }
               enum "att5e" {
                 description "ATT5E variant";
               }
               enum "ntdms100" {
                 description "NTDMS100 variant";
               }
               enum "ntt" {
                 description "INS NET (NTT) PRI/BRI variant";
               }
               enum "ni2" {
                 description "NI2 PRI variant";
               }
             }
           }
           leaf media-type {
             description "IDSN media type - voice, data or both";
             default "data";
             type enumeration {
               enum "data" {
                 description "Data";
               }
               enum "voice" {
                 description "Voice";
               }
               enum "combined" {
                 description "Combined";
               }
             }
           }
           leaf spid1 {
             description "Service profile identifier";
             type string {
               length "1 .. 20";
             }
           }
           leaf spid2 {
             description "Additional service profile identifier";
             type string {
               length "1 .. 20";
             }
           }
           leaf calling-number {
             description "Calling number included in outgoing calls";
             type string {
               junos:posix-pattern "^([0-9A-DLPTWS*#!,@;^$/]{1,15})$|^([0-9A-DLPTWS*#!,@;^$/]{1,15}:[0-9A-DLPTWS*#!,@;^$/]{1,40})$";
               junos:pattern-message "Can contain up to 15 digits, alphanumeric or special characters; optional subaddress can contain up to 40 alphanumeric and special characters with the colon (:) used as the separator";
             }
           }
           list incoming-called-number {
             key name;
             ordered-by user;
             junos:cli-feature "oneliner";
             description "Incoming called number to be screened";
             max-elements 30;
             leaf name {
               description "Number called (upto 15 digits)";
               junos:cli-feature "nokeyword";
               type string {
                 junos:posix-pattern "^([0-9]{1,15})$";
                 junos:pattern-message "Can contain up to 15 digits";
               }
             }
             leaf reject {
               description "Reject the called number";
               type empty;
             }
           }
           leaf tei-option {
             description "ISDN terminal endpoint identifier negotiation options";
             type enumeration {
               enum "first-call" {
                 description "Terminal endpoint identifier negotiation during first call";
               }
               enum "power-up" {
                 description "Terminal endpoint identifier negotiation during power-up";
               }
             }
           }
           leaf static-tei-val {
             description "Static TEI value";
             type union {
               type string {
                 pattern "<.*>|$.*";
               }
               type uint32 {
                 range "0 .. 63";
               }
             }
           }
           leaf t310 {
             description "Timer T310 value";
             units "seconds";
             type union {
               type string {
                 pattern "<.*>|$.*";
               }
               type uint32 {
                 range "1 .. 65536";
               }
             }
           }
           leaf bchannel-allocation {
             description "Allocate PRI dialout b-channel in ascending/descending order";
             default "descending";
             type enumeration {
               enum "ascending" {
                 description "Allocate b-channel in ascending order";
               }
               enum "descending" {
                 description "Allocate b-channel in descending order";
               }
             }
           }
         }
         container dialer-options {
           presence "enable dialer-options";
           description "Dialer options";
           uses apply-advanced;
           list pool {
             key name;
             junos:cli-feature "oneliner";
             description "Dialer pool";
             max-elements 30;
             leaf name {
               description "Dialer pool identifier";
               junos:cli-feature "nokeyword";
               type string {
                 length "1 .. 64";
               }
             }
             leaf priority {
               description "Dialer pool priority";
               type union {
                 type string {
                   pattern "<.*>|$.*";
                 }
                 type uint32 {
                   range "1 .. 255";
                 }
               }
             }
           }
         }
         leaf act-sim {
           description "Default SIM slot to connect LTE network";
           type union {
             type string {
               pattern "<.*>|$.*";
             }
             type uint32;
           }
         }
         container cellular-options {
           presence "enable cellular-options";
           description "Cellular interface specific options";
           uses apply-advanced;
           list sim {
             key name;
             description "SIM slot to connect LTE network";
             leaf name {
               description "SIM slot number";
               junos:cli-feature "nokeyword";
               type union {
                 type string {
                   pattern "<.*>|$.*";
                 }
                 type uint32;
               }
             }
             uses apply-advanced;
             container select-profile {
               junos:cli-feature "oneliner";
               description "Profile to be applied";
               leaf profile-id {
                 description "Profile to be used for data calls";
                 type union {
                   type string {
                     pattern "<.*>|$.*";
                   }
                   type uint32 {
                     range "1 .. 16";
                   }
                 }
               }
             }
             container radio-access {
               junos:cli-feature "oneliner";
               description "Select radio access technology";
               choice rat-value {
                 case case_1 {
                   leaf automatic {
                     description "Automatically selects radio access type";
                     type empty;
                   }
                 }
                 case case_2 {
                   leaf umts-3g-only {
                     description "3G only";
                     type empty;
                   }
                 }
                 case case_3 {
                   leaf umts-3g-preferred {
                     description "UMTS 3G Preferred";
                     type empty;
                   }
                 }
                 case case_4 {
                   leaf lte-only {
                     description "Only LTE";
                     type empty;
                   }
                 }
                 case case_5 {
                   leaf lte-preferred {
                     description "LTE Preferred";
                     type empty;
                   }
                 }
               }
             }
             leaf encrypted-sim-unlock-code {
               description "Encrypted PIN";
               type jt:unreadable;
             }
             leaf gateway {
               description "Set customer gateway for LTE network";
               type jt:ipprefix;
             }
           }
         }
         container redundant-pseudo-interface-options {
           description "Pseudo interface redundancy options";
           uses apply-advanced;
           leaf redundancy-group {
             description "Redundancy group of this interface";
             junos:must "(\"chassis cluster redundancy-group $$\")";
             junos:must-message "A redundancy group should be defined";
             type union {
               type string {
                 pattern "<.*>|$.*";
               }
               type uint16 {
                 range "0 .. 255";
               }
             }
           }
         }
       }
       list interface {
         key name;
         uses interfaces_type;
         junos:cli-feature "nokeyword";
         junos:cli-feature "homogeneous";
       }
     }
   }
   grouping aggregate-load-balance {
     description "Load balancing parameters";
     uses apply-advanced;
     choice adaptive_option {
       case case_1 {
       }
       case case_2 {
       }
       case case_3 {
       }
     }
   }
   grouping apply-advanced {
     description "Apply advanced configuration logic";
     leaf-list apply-groups {
       ordered-by user;
       description "Groups from which to inherit configuration data";
       type string;
     }
     leaf-list apply-groups-except {
       ordered-by user;
       description "Don't inherit configuration data from these groups";
       type string;
     }
     list apply-macro {
       key name;
       ordered-by user;
       description "Macro and parameters for commit script expansion";
       uses apply-macro-type;
     }
   }
   grouping apply-macro-type {
     description "Macro data for commit-script expansion";
     leaf name {
       description "Name of the macro to be expanded";
       junos:cli-feature "nokeyword";
       type string;
     }
     list data {
       key name;
       uses macro-data-type;
       junos:cli-feature "nokeyword";
       junos:cli-feature "homogeneous";
       junos:cli-feature "oneliner";
     }
   }
   grouping aps_type {
     uses apply-advanced;
     choice aps_mode {
       case case_1 {
         leaf working-circuit {
           description "Working circuit group name";
           type string;
         }
       }
       case case_2 {
         leaf protect-circuit {
           description "Protect circuit group name";
           type string;
         }
       }
     }
     leaf annex-b {
       description "Annex-b mode";
       junos:must "(!(\".. paired-group\"))";
       junos:must-message "paired-group configuration not supported in annex-b mode";
       junos:must "(!(\".. exercise\"))";
       junos:must-message "exercise request not supported in annex-b mode";
       junos:must "(!(\".. request\"))";
       junos:must-message "manual request not supported in annex-b mode";
       junos:must "(!(\".. revert-time\"))";
       junos:must-message "revert-time not supported in annex-b mode";
       junos:must "(!(\".. switching-mode unidirectional\"))";
       junos:must-message "unidirectional mode not supported in annex-b mode";
       type empty;
     }
     leaf wait-to-restore-time {
       description "Circuit wait-to-restore time for annex-b";
       units "seconds";
       junos:must "(\".. annex-b\")";
       junos:must-message "wait-to-restore-time only supported for annex-b mode";
       type union {
         type string {
           pattern "<.*>|$.*";
         }
         type uint32 {
           range "1 .. 4294967295";
         }
       }
     }
     leaf preserve-interface {
       description "Preserve interface state for fast failover";
       junos:must "(!(\".. paired-group\"))";
       junos:must-message "preserve-interface and paired-group cannot co-exist";
       type empty;
     }
     leaf neighbor {
       description "Neighbor address";
       type jt:ipv4addr;
     }
     leaf paired-group {
       description "Name of paired APS group";
       type string;
     }
     container authentication-key {
       presence "enable authentication-key";
       junos:cli-feature "oneliner";
       description "Authentication parameters";
       leaf auth_key {
         description "Authentication key";
         junos:cli-feature "nokeyword";
         type jt:unreadable;
       }
     }
     leaf switching-mode {
       description "APS switching mode";
       type enumeration {
         enum "bidirectional" {
           description "Bidirectional";
         }
         enum "unidirectional" {
           description "Unidirectional";
         }
       }
     }
     leaf advertise-interval {
       description "Advertise interval";
       units "milliseconds";
       type union {
         type string {
           pattern "<.*>|$.*";
         }
         type uint32 {
           range "1 .. 65534";
         }
       }
     }
     leaf hold-time {
       description "Hold time";
       units "milliseconds";
       type union {
         type string {
           pattern "<.*>|$.*";
         }
         type uint32 {
           range "1 .. 65534";
         }
       }
     }
     leaf revert-time {
       description "Circuit revert time";
       units "seconds";
       junos:must "(!(\".. switching-mode unidirectional\"))";
       junos:must-message "revert-time not supported in unidirectional mode";
       type union {
         type string {
           pattern "<.*>|$.*";
         }
         type uint32 {
           range "0 .. 65534";
         }
       }
     }
     choice break-before-make-choice {
       leaf break-before-make {
         description "Ensure only one interface is active at a time";
         type empty;
       }
       leaf no-break-before-make {
         description "Don't ensure only one interface is active at a time";
         type empty;
       }
     }
     choice manual_mode {
       case case_1 {
         leaf request {
           description "Request circuit state";
           type enumeration {
             enum "protect" {
               description "Request protect circuit";
             }
             enum "working" {
               description "Request working circuit";
             }
           }
         }
       }
       case case_2 {
         leaf force {
           description "Force circuit state";
           type enumeration {
             enum "protect" {
               description "Force protect circuit";
             }
             enum "working" {
               description "Force working circuit";
             }
           }
         }
       }
       case case_3 {
         leaf lockout {
           description "Lockout protection";
           type empty;
         }
       }
     }
     leaf fast-aps-switch {
       description "Fast aps switch";
       type empty;
     }
   }
   grouping cos_policer {
     description "Define a CoS based policer";
     leaf name {
       description "Policer name";
       junos:cli-feature "nokeyword";
       type string {
         junos:posix-pattern "^.{1,64}$";
         junos:pattern-message "Must be a string of 64 characters or less";
       }
     }
     uses apply-advanced;
     container premium {
       description "Policer to apply to premium traffic";
       presence "enable premium";
       uses ethernet_policer;
     }
     container aggregate {
       description "Policer to apply to aggregate traffic";
       presence "enable aggregate";
       uses ethernet_policer;
     }
   }
   grouping cos_policer_input_priority_map {
     description "Input policer priority map";
     uses apply-advanced;
     container ieee-802.1p {
       description "Use IEEE 802.1p to determine policer priority map";
       uses apply-advanced;
       leaf-list premium {
         ordered-by user;
         description "Input traffic's IEEE 802.1p value to which premium policer is applied";
         type union {
           type string {
             pattern "<.*>|$.*";
           }
           type uint32 {
             range "0 .. 7";
           }
         }
       }
     }
   }
   grouping cos_policer_output_priority_map {
     description "Output policer priority map";
     uses apply-advanced;
     container classifier {
       description "Use classifier as policer priority map";
       uses apply-advanced;
       container premium {
         description "Output traffic classifier to which premium policer is applied";
         uses apply-advanced;
         list forwarding-class {
           key name;
           ordered-by user;
           description "Select a classification for this priority map";
           leaf name {
             description "Forwarding class name";
             junos:cli-feature "nokeyword";
             type string {
               junos:posix-pattern "^.{1,64}$";
               junos:pattern-message "Must be string of 64 characters or less";
             }
           }
           uses apply-advanced;
           list loss-priority {
             key name;
             ordered-by user;
             junos:cli-feature "oneliner";
             description "Select a loss priority";
             leaf name {
               junos:cli-feature "nokeyword";
               type enumeration {
                 enum "low" {
                   description "Select low loss priority as premium policer";
                 }
                 enum "high" {
                   description "Select high loss priority as premium policer";
                 }
               }
             }
           }
         }
       }
     }
   }
   grouping dcd_rx_bucket_config {
     uses apply-advanced;
     leaf overflow {
       description "Overflow behavior";
       type enumeration {
         enum "tag" {
           description "Tag and count overflow packets";
         }
         enum "discard" {
           description "Discard overflow packets";
         }
       }
     }
     leaf rate {
       description "Bucket rate";
       type union {
         type string {
           pattern "<.*>|$.*";
         }
         type uint32 {
           range "0 .. 100";
         }
       }
     }
     leaf threshold {
       description "Bucket threshold";
       type union {
         type string {
           pattern "<.*>|$.*";
         }
         type uint32 {
           range "0 .. 65535";
         }
       }
     }
   }
   grouping dcd_shaping_config {
     description "Traffic-shaping profile";
     uses apply-advanced;
     choice useless_shaping_choice {
       case case_1 {
         container cbr {
           presence "enable cbr";
           junos:cli-feature "oneliner";
           description "Constant bandwidth utilization";
           leaf cbr-value {
             description "Constant bandwidth utilization";
             junos:cli-feature "nokeyword";
             type string;
           }
           leaf cdvt {
             description "Cell Delay Variation Tolerance";
             units "microseconds";
             type union {
               type string {
                 pattern "<.*>|$.*";
               }
               type uint32 {
                 range "1 .. 9999";
               }
             }
           }
         }
       }
       case case_2 {
         container vbr {
           junos:cli-feature "oneliner";
           description "Variable bandwidth utilization";
           leaf peak {
             description "Peak rate";
             type string;
           }
           leaf sustained {
             description "Sustained rate";
             type string;
           }
           leaf burst {
             description "Burst size";
             type string;
           }
           leaf cdvt {
             description "Cell Delay Variation Tolerance";
             units "microseconds";
             type union {
               type string {
                 pattern "<.*>|$.*";
               }
               type uint32 {
                 range "1 .. 9999";
               }
             }
           }
         }
       }
       case case_3 {
         container rtvbr {
           junos:cli-feature "oneliner";
           description "ATM2 real-time variable bandwidth utilization";
           leaf peak {
             description "Peak rate";
             type string;
           }
           leaf sustained {
             description "Sustained rate";
             type string;
           }
           leaf burst {
             description "Burst size";
             type string;
           }
         }
       }
     }
     leaf queue-length {
       description "Queue length";
       type union {
         type string {
           pattern "<.*>|$.*";
         }
         type uint32 {
           range "1 .. 16383";
         }
       }
     }
   }
   grouping dcd_tx_bucket_config {
     uses apply-advanced;
     leaf overflow {
       description "Overflow behavior";
       type enumeration {
         enum "discard" {
           description "Discard overflow packets";
         }
       }
     }
     leaf rate {
       description "Bucket rate";
       type union {
         type string {
           pattern "<.*>|$.*";
         }
         type uint32 {
           range "0 .. 100";
         }
       }
     }
     leaf threshold {
       description "Bucket threshold";
       type union {
         type string {
           pattern "<.*>|$.*";
         }
         type uint32 {
           range "0 .. 65535";
         }
       }
     }
   }
   grouping dhcp-client-type {
     description "Dynamic Host Configuration Protocol client configuration";
     uses apply-advanced;
     container client-identifier {
       description "DHCP server identifies a client by client-identifier value ";
       uses apply-advanced;
       choice client-identifier-choice {
         case case_1 {
           leaf ascii {
             description "Client identifier as an ASCII string";
             type string;
           }
         }
         case case_2 {
           leaf hexadecimal {
             description "Client identifier as a hexadecimal string";
             type string {
               junos:posix-pattern "^[[:xdigit:]]+$";
               junos:pattern-message "Must be hexadecimal digits (0-9, a-f, A-F)";
             }
           }
         }
       }
       container user-id {
         junos:cli-feature "oneliner";
         description "Add user id to client-id option ";
         choice user-id-choice {
           case case_1 {
             leaf ascii {
               description "Client identifier as an ASCII string";
               type string;
             }
           }
           case case_2 {
             leaf hexadecimal {
               description "Client identifier as a hexadecimal string";
               type string {
                 junos:posix-pattern "^[[:xdigit:]]+$";
                 junos:pattern-message "Must be hexadecimal digits (0-9, a-f, A-F)";
               }
             }
           }
         }
       }
       container prefix {
         description "Add prefix to client-id option";
         uses apply-advanced;
         leaf host-name {
           description "Add router host name to client-id option";
           type empty;
         }
         leaf logical-system-name {
           description "Add logical system name to client-id option";
           type empty;
         }
         leaf routing-instance-name {
           description "Add routing instance name to client-id option";
           type empty;
         }
       }
       leaf use-interface-description {
         description "Use the interface description";
         type enumeration {
           enum "logical" {
             description "Use the logical interface description";
           }
           enum "device" {
             description "Use the device interface description";
           }
         }
       }
       leaf hardware-type {
         description "Hardware type";
         default "0";
         type union {
           type string {
             pattern "<.*>|$.*";
           }
           type uint8 {
             range "0 .. 255";
           }
         }
       }
     }
     container no-dns-install {
       presence "enable no-dns-install";
       description "Do not install DNS information learned from DHCP server";
     }
     leaf lease-time {
       description "Lease time in seconds requested in DHCP client protocol packet";
       units "seconds";
       type string;
     }
     leaf retransmission-attempt {
       description "Number of attempts to retransmit the DHCP client protocol packet";
       default "4";
       type union {
         type string {
           pattern "<.*>|$.*";
         }
         type uint32 {
           range "0 .. 50000";
         }
       }
     }
     leaf retransmission-interval {
       description "Number of seconds between successive retransmission";
       default "4";
       units "seconds";
       type union {
         type string {
           pattern "<.*>|$.*";
         }
         type uint32 {
           range "4 .. 64";
         }
       }
     }
     leaf metric {
       description "Client initiated default-route metric";
       default "0";
       type union {
         type string {
           pattern "<.*>|$.*";
         }
         type uint32 {
           range "0 .. 255";
         }
       }
     }
     leaf server-address {
       description "DHCP Server-address";
       type jt:ipv4addr;
     }
     leaf update-server {
       description "Propagate TCP/IP settings to DHCP server";
       type empty;
     }
     leaf vendor-id {
       description "Vendor class id for the DHCP Client";
       type string {
         length "1 .. 60";
       }
     }
     leaf force-discover {
       description "Send DHCPDISCOVER after DHCPREQUEST retransmission failure";
       type empty;
     }
     leaf request-unicast-replies {
       description "Set broadcast bit to 0 in the DHCP discover and request packets";
       type empty;
     }
     container options {
       description "DHCP options";
       uses apply-advanced;
       list number {
         key name;
         junos:cli-feature "oneliner";
         description "DHCP option code";
         leaf name {
           description "DHCP option identifier code";
           junos:cli-feature "nokeyword";
           type union {
             type string {
               pattern "<.*>|$.*";
             }
             type uint32 {
               range "1 .. 254";
             }
           }
         }
         choice option-type-choice {
           case case_1 {
             leaf hex-string {
               description "Hexadecimal string";
               type string {
                 length "1 .. 510";
                 junos:posix-pattern "^[[:xdigit:]]+$";
                 junos:pattern-message "Must be hexadecimal digits (0-9, a-f, A-F)";
               }
             }
           }
         }
       }
       leaf no-hostname {
         description "Do not carry hostname (RFC option code is 12) in packet";
         type empty;
       }
     }
     list requested-options {
       key name;
       junos:cli-feature "homogeneous";
       junos:cli-feature "oneliner";
       description "DHCP options";
       leaf name {
         description "DHCP option identifier code";
         junos:cli-feature "nokeyword";
         type union {
           type string {
             pattern "<.*>|$.*";
           }
           type uint32 {
             range "1 .. 254";
           }
         }
       }
     }
   }
   grouping dynamic_ifbw_parms_type {
     junos:cli-feature "oneliner-plus";
     uses apply-advanced;
     leaf capacity {
       description "Weight of current (vs. maximum) data rate";
       status deprecated;
       units "percent";
       type union {
         type string {
           pattern "<.*>|$.*";
         }
         type uint32 {
           range "0 .. 100";
         }
       }
     }
     leaf margin {
       description "Maximum reduction in bandwidth due to low link quality";
       status deprecated;
       units "percent";
       type union {
         type string {
           pattern "<.*>|$.*";
         }
         type uint32 {
           range "0 .. 100";
         }
       }
     }
     leaf delay {
       description "Bandwidth reduction when delay is announced as 1 second";
       status deprecated;
       units "bits per second";
       type string;
     }
     leaf bandwidth {
       description "Weight of current (vs. maximum) data rate";
       type union {
         type string {
           pattern "<.*>|$.*";
         }
         type uint32 {
           range "0 .. 100";
         }
       }
     }
     leaf resource {
       description "Resource weight";
       type union {
         type string {
           pattern "<.*>|$.*";
         }
         type uint32 {
           range "0 .. 100";
         }
       }
     }
     leaf latency {
       description "Latency weight";
       type union {
         type string {
           pattern "<.*>|$.*";
         }
         type uint32 {
           range "0 .. 100";
         }
       }
     }
     leaf quality {
       description "Relative Link Quality weight";
       type union {
         type string {
           pattern "<.*>|$.*";
         }
         type uint32 {
           range "0 .. 100";
         }
       }
     }
     leaf data-rate {
       description "Data rate weight";
       type union {
         type string {
           pattern "<.*>|$.*";
         }
         type uint32 {
           range "0 .. 100";
         }
       }
     }
     leaf threshold {
       description "Percentage bandwidth change required for routing updates";
       units "percent";
       type union {
         type string {
           pattern "<.*>|$.*";
         }
         type uint32 {
           range "0 .. 100";
         }
       }
     }
     container credit {
       presence "enable credit";
       junos:cli-feature "oneliner-plus";
       description "Credit-based scheduling parameters";
       uses apply-advanced;
       leaf interval {
         description "Grant rate interval in 100mS steps";
         type union {
           type string {
             pattern "<.*>|$.*";
           }
           type uint16 {
             range "1 .. 60";
           }
         }
       }
     }
   }
   grouping dynamic_ipv4_type {
     description "Packet triggered subscribers";
     uses apply-advanced;
     container address-ranges {
       description "Packet triggered subscribers configuration";
       uses apply-advanced;
       list dynamic-profile {
         key name;
         ordered-by user;
         description "Attach dynamic-profile to packet triggered subscriber ranges";
         max-elements 16;
         leaf name {
           description "Profile name";
           junos:cli-feature "nokeyword";
           junos:must "(\"dynamic-profiles $$\")";
           junos:must-message "Dynamic-profile must be defined in the [edit dynamic-profiles] hierarchy";
           type string;
         }
         uses apply-advanced;
         list network {
           key name;
           ordered-by user;
           description "IPv4 Network address";
           max-elements 16;
           leaf name {
             description "Specify the network address";
             junos:cli-feature "nokeyword";
             type jt:ipv4prefix;
           }
           uses apply-advanced;
           list range {
             key name;
             ordered-by user;
             description "Configure demux interface based on source IP address range";
             max-elements 16;
             leaf name {
               description "Name of range";
               junos:cli-feature "nokeyword";
               type string;
             }
             uses apply-advanced;
             leaf low {
               description "Lower limit of address range";
               type jt:ipv4prefix;
             }
             leaf high {
               description "Upper limit of address range";
               type jt:ipv4prefix;
             }
           }
         }
       }
       container authentication {
         description "Auto-configure packet triggered subscriber authentication";
         uses dynamic_ip_authentication_type;
       }
       leaf session-timeout {
         description "Self destruct or auto clear timeout in seconds";
         type union {
           type string {
             pattern "<.*>|$.*";
           }
           type uint32 {
             range "600 .. 6000";
           }
         }
       }
     }
   }
   grouping dynamic_ip_authentication_type {
     description "Autoconf packet trigger subscriber authentication";
     uses apply-advanced;
     leaf password {
       description "Username password";
       type string {
         length "1 .. 64";
       }
     }
     container username-include {
       description "Username options";
       uses apply-advanced;
       leaf delimiter {
         description "Delimiter/separator character";
         type string {
           length 1;
         }
       }
       leaf domain-name {
         description "Domain name";
         type string {
           length "1 .. 64";
         }
       }
       leaf user-prefix {
         description "User defined prefix";
         type string {
           length "1 .. 64";
         }
       }
       leaf auth-server-realm {
         description "Authentication server realm name";
         type string {
           length "1 .. 64";
         }
       }
       leaf interface-name {
         description "Interface name";
         type empty;
       }
       leaf source-address {
         description "Source address";
         type empty;
       }
     }
   }
   grouping dynamic_ipv6_type {
     description "Packet triggered subscribers";
     uses apply-advanced;
     container prefix-ranges {
       description "Packet triggered subscribers configuration";
       uses apply-advanced;
       list dynamic-profile {
         key name;
         ordered-by user;
         description "Attach dynamic-profile to packet triggered subscriber ranges";
         max-elements 16;
         leaf name {
           description "Profile name";
           junos:cli-feature "nokeyword";
           junos:must "(\"dynamic-profiles $$\")";
           junos:must-message "Dynamic-profile must be defined in the [edit dynamic-profiles] hierarchy";
           type string;
         }
         uses apply-advanced;
         list prefix {
           key name;
           ordered-by user;
           description "IPv6 Network prefix ";
           max-elements 16;
           leaf name {
             description "Specify the network prefix";
             junos:cli-feature "nokeyword";
             type jt:ipv6prefix;
           }
           uses apply-advanced;
           list range {
             key name;
             ordered-by user;
             description "Configure demux interface based on source IP address range";
             max-elements 16;
             leaf name {
               description "Name of range";
               junos:cli-feature "nokeyword";
               type string;
             }
             uses apply-advanced;
             leaf low {
               description "Lower limit of prefix range";
               type jt:ipv6prefix;
             }
             leaf high {
               description "Upper limit of prefix range";
               type jt:ipv6prefix;
             }
           }
         }
       }
       container authentication {
         description "Auto-configure packet triggered subscriber authentication";
         uses dynamic_ip_authentication_type;
       }
       leaf session-timeout {
         description "Self destruct or auto clear timeout in seconds";
         type union {
           type string {
             pattern "<.*>|$.*";
           }
           type uint32 {
             range "600 .. 6000";
           }
         }
       }
     }
   }
   grouping epd_threshold_config {
     junos:cli-feature "oneliner";
     uses apply-advanced;
     leaf epd-threshold-plp0 {
       description "Early packet discard threshold value";
       junos:cli-feature "nokeyword";
       units "cells";
       type string;
     }
     leaf plp1 {
       description "Early packet drop threshold value for PLP 1";
       units "cells";
       type string;
     }
   }
   grouping ethernet-switching-type {
     description "Ethernet switching family";
     uses apply-advanced;
     leaf port-mode {
       description "Type of port mode";
       type enumeration {
         enum "access" {
           description "Interface mode is access";
         }
         enum "tagged-access" {
           description "Interface mode is tagged-access";
         }
         enum "trunk" {
           description "Interface mode is trunk";
         }
       }
     }
     leaf interface-mode {
       description "Type of interface mode";
       default "access";
       type enumeration {
         enum "access" {
           description "Interface mode is access";
           junos:must "((!(\"interfaces ${interface} vlan-tagging\") && (!(\"interfaces ${interface} flexible-vlan-tagging\") && (!(\"interfaces ${interface} stacked-vlan-tagging\") && !(\"interfaces ${interface} encapsulation extended-vlan-bridge\")))))";
           junos:must-message "interface-mode access is allowed only for untagged interfaces, also not allowed with flexible-vlan-tagging and extended-vlan-bridge";
         }
         enum "trunk" {
           description "Interface mode is trunk";
           junos:must "(!(\"interfaces ${interface} no-native-vlan-insert\"))";
           junos:must-message "'interface-mode trunk' must not be configured with 'no-native-vlan-insert'";
           junos:must "(!(\"interfaces ${interface} encapsulation extended-vlan-bridge\"))";
           junos:must-message "interface-mode is not allowed for extended-vlan-bridge";
         }
       }
     }
     leaf inter-switch-link {
       description "PVLAN inter switch link";
       junos:must "(\".. interface-mode trunk\")";
       junos:must-message "'Inter switch link' is supported only under trunk interface mode";
       type empty;
     }
     leaf reflective-relay {
       description "Reflective-relay mode for this interface";
       junos:must "(\".. port-mode tagged-access\")";
       junos:must-message "Reflective relay is supported only on tagged-access port";
       type empty;
     }
     choice vlan_choice_list {
       case case_1 {
         container vlan {
           description "Virtual LAN parameters";
           uses apply-advanced;
           leaf-list members {
             ordered-by user;
             description "Membership for this interface (name or id)";
             type string;
           }
         }
       }
       case case_2 {
         container inner-vlan {
           description "Trunk mode vlan membership for this interface";
           uses apply-advanced;
           leaf-list members {
             ordered-by user;
             description "Membership for this interface (name or id)";
             type string;
           }
         }
       }
       case case_3 {
         leaf-list inner-vlan-id-list {
           description "Trunk mode VLAN membership for this interface based on inner VLAN tag";
           junos:must "((!(\".. .. .. vlan-tags inner\") && !(\".. .. .. vlan-tags inner-range\")))";
           junos:must-message "'inner-vlan-id-list' cannot be used on interface with vlan-tags inner or inner-range configured";
           junos:must "((\".. .. .. vlan-id\" || \".. .. .. vlan-tags\"))";
           junos:must-message "'inner-vlan-id-list' can be used only on interface with vlan-id/vlan-tags";
           junos:must "(\"interfaces ${interface} flexible-vlan-tagging\")";
           junos:must-message "'inner-vlan-id-list' is supported only on flexible-vlan-tagging mode";
           junos:must "(\".. interface-mode trunk\")";
           junos:must-message "'inner-vlan-id-list' statement supported only under trunk interface mode";
           type jt:vlan-range;
         }
       }
     }
     leaf vlan-auto-sense {
       description "Enable VLAN auto sense on this interface";
       junos:must "(\".. interface-mode trunk\")";
       junos:must-message "vlan-auto-sense can be enabled only on trunk ports";
       type empty;
     }
     leaf bridge-domain-type {
       description "Bridge domain type";
       type enumeration {
         enum "svlan" {
           description "Bridge domain type SVLAN";
           junos:must "(\".. isid-list all-service-groups\")";
           junos:must-message "bridge-domain-type SVLAN is allowed only for ISID tagged interfaces";
           junos:must "(\".. interface-mode trunk\")";
           junos:must-message "bridge-domain-type SVLAN is allowed only for trunk interfaces";
         }
         enum "bvlan" {
           description "Bridge domain type BVLAN";
           junos:must "(\".. isid-list all\")";
           junos:must-message "bridge-domain-type BVLAN is allowed only for ISID tagged interfaces";
           junos:must "(\".. interface-mode trunk\")";
           junos:must-message "bridge-domain-type BVLAN is allowed only for trunk interfaces";
         }
       }
     }
     container vlan-rewrite {
       junos:must "((\".. inner-vlan-id-list\" || \".. vlan members\"))";
       junos:must-message "'vlan-rewrite' statement can be used only with 'vlan members' or inner-vlan-id-list configured";
       junos:must "(\".. interface-mode trunk\")";
       junos:must-message "'vlan-rewrite' statement supported only under trunk interface mode";
       junos:cli-feature "oneliner-plus";
       description "Specify VLAN translation";
       uses apply-advanced;
       list translate {
         key name;
         ordered-by user;
         junos:cli-feature "oneliner";
         description "Translate incoming VLAN tag";
         leaf name {
           description "Specify the incoming VLAN tag";
           junos:cli-feature "nokeyword";
           type union {
             type string {
               pattern "<.*>|$.*";
             }
             type uint32 {
               range "1 .. 4094";
             }
           }
         }
         leaf to-vlan-id {
           description "Specify the bridge-domain VLAN-ID";
           junos:cli-feature "nokeyword";
           type union {
             type string {
               pattern "<.*>|$.*";
             }
             type uint32 {
               range "1 .. 4094";
             }
           }
         }
       }
     }
     leaf native-vlan-id {
       description "Untagged packets on a trunk/tagged-access interface belong to this vlan";
       type string {
       }
     }
     choice isid_list {
       case case_1 {
         leaf isid-list {
           description "Specify the ISID list";
           type enumeration {
             enum "all-service-groups" {
               description "Map all ISIDs specified under the service-groups";
               junos:must "(\".. interface-mode trunk\")";
               junos:must-message "'all-service-groups' statement supported only under trunk interface mode";
             }
             enum "all" {
               description "Map all ISIDs";
               junos:must "(\".. interface-mode trunk\")";
               junos:must-message "'all' statement supported only under trunk interface mode";
             }
           }
         }
       }
     }
     leaf core-facing {
       description "Interface is core facing";
       type empty;
     }
     container filter {
       description "Packet filtering";
       uses apply-advanced;
       leaf input {
         description "Name of filter applied to received packets";
         type string;
       }
       leaf input-precedence {
         description "Precedence of the filter";
         type union {
           type string {
             pattern "<.*>|$.*";
           }
           type uint32 {
             range "0 .. 255";
           }
         }
       }
       leaf-list input-list {
         ordered-by user;
         description "List of filter modules applied to received packets ";
         type string;
       }
       leaf output {
         description "Name of filter applied to transmitted packets";
         type string;
       }
       leaf output-precedence {
         description "Precedence of the filter";
         type union {
           type string {
             pattern "<.*>|$.*";
           }
           type uint32 {
             range "0 .. 255";
           }
         }
       }
       leaf-list output-list {
         ordered-by user;
         description "List of filter modules applied to transmitted packets ";
         type string;
       }
       container adf {
         description "Ascend Data Filter definition";
         uses apply-advanced;
         list rule {
           key name;
           ordered-by user;
           description "Set of ADF rules";
           leaf name {
             description "Value for a single rule";
             junos:cli-feature "nokeyword";
             type string;
           }
           uses apply-advanced;
         }
         leaf counter {
           description "Add a counter to each rule";
           type empty;
         }
         leaf input-precedence {
           description "Precedence of the input rules";
           type union {
             type string {
               pattern "<.*>|$.*";
             }
             type uint32 {
               range "0 .. 255";
             }
           }
         }
         leaf not-mandatory {
           description "No errors will be reported if no rules are present";
           type empty;
         }
         leaf output-precedence {
           description "Precedence of the output rules";
           type union {
             type string {
               pattern "<.*>|$.*";
             }
             type uint32 {
               range "0 .. 255";
             }
           }
         }
       }
       leaf group {
         description "Group to which interface belongs";
         type union {
           type string {
             pattern "<.*>|$.*";
           }
           type uint32 {
             range "1 .. 255";
           }
         }
       }
     }
     container policer {
       description "Interface policing";
       uses apply-advanced;
       leaf input {
         description "Name of policer applied to received packets";
         type string;
       }
       leaf output {
         description "Name of policer applied to transmitted packets";
         type string;
       }
     }
     container storm-control {
       junos:cli-feature "oneliner-plus";
       description "Storm control profile name to bind";
       uses apply-advanced;
       leaf profile-name {
         description "Profile name";
         junos:cli-feature "nokeyword";
         junos:must "(\"forwarding-options storm-control-profiles $$\")";
         junos:must-message "Storm profile name must be defined in the [edit forwarding-options storm-control-profiles] hierarchy";
         type string;
       }
     }
     container recovery-timeout {
       junos:cli-feature "oneliner";
       description "Recovery timeout for this interface";
       leaf time-in-seconds {
         junos:cli-feature "nokeyword";
         units "seconds";
         type union {
           type string {
             pattern "<.*>|$.*";
           }
           type uint32 {
             range "10 .. 3600";
           }
         }
       }
     }
   }
   grouping ethernet_policer {
     description "Define a policer";
     uses apply-advanced;
     choice bandwidth {
       case case_1 {
         leaf bandwidth-limit {
           description "Bandwidth limit";
           units "bits per second";
           type string;
         }
       }
     }
     leaf burst-size-limit {
       description "Burst size limit";
       units "bytes";
       type string;
     }
   }
   grouping ett-attributes {
     description "Transport ethernet configuration attributes";
     uses apply-advanced;
     leaf rate {
       description "Ethernet client signal rate";
       type enumeration {
         enum "100ge" {
           description "100 gigabit ethernet";
         }
       }
     }
   }
   grouping interfaces_type {
     junos:cli-feature "nokeyword";
     junos:cli-feature "homogeneous";
     description "Physical interface";
     leaf name {
       junos:cli-feature "nokeyword";
       junos:must "(!(\".. es-options backup-interface $$\"))";
       junos:must-message "Primary and backup ES PIC interfaces must be different";
       type string;
     }
     uses apply-advanced;
     leaf description {
       description "Text description of interface";
       type string;
     }
     leaf external-model-name {
       description "Name for interface as configured using 3rd-party model";
       type string;
     }
     container management-ethernet-redundancy {
       presence "enable management-ethernet-redundancy";
       description "Management Interface Redundancy";
       uses apply-advanced;
       choice enable_choice {
         case case_1 {
           leaf redundancy-enable {
             description "Enable Managment Ethernet Redundancy";
             type empty;
           }
         }
         case case_2 {
           leaf redundancy-disable {
             description "Disable  Managment Ethernet Redundancy";
             type empty;
           }
         }
       }
       leaf connectivity-test-interval {
         description "Connectivity test interval";
         default "5";
         units "seconds";
         type union {
           type string {
             pattern "<.*>|$.*";
           }
           type uint32 {
             range "1 .. 10";
           }
         }
       }
       leaf connectivity-test-response-interval {
         description "Connectivity test response wait time";
         default "5";
         units "seconds";
         type union {
           type string {
             pattern "<.*>|$.*";
           }
           type uint32 {
             range "1 .. 10";
           }
         }
       }
       leaf remote-ipv4-address {
         description "Destination IPV4 address to reach remote ";
         default "nil";
         type jt:ipv4addr;
       }
       leaf remote-ipv6-address {
         description "Destination IPV6 address to reach remote";
         default "nil";
         type jt:ipv6addr;
       }
       leaf number-of-connectivity-retries {
         description "Number of Connectivity retries ";
         default "2";
         type union {
           type string {
             pattern "<.*>|$.*";
           }
           type uint32 {
             range "1 .. 8";
           }
         }
       }
     }
     choice enable-disable {
       case case_1 {
         leaf disable {
           description "Disable this interface";
           type empty;
         }
       }
     }
     leaf promiscuous-mode {
       description "Enable promiscuous mode for L3 interface";
       type empty;
     }
     leaf port-mirror-instance {
       description "Port-mirror the packet to specified instance";
       junos:must "(\"forwarding-options port-mirroring instance $$\")";
       junos:must-message "Referenced port-mirroring instance does not exist";
       type string {
         length "1 .. 64";
       }
     }
     container fabric-options {
       description "Fabric interface specific options";
       uses apply-advanced;
       list member-interfaces {
         key name;
         junos:cli-feature "homogeneous";
         description "Member interface for the fabric interface";
         leaf name {
           description "Interface name of member";
           junos:cli-feature "nokeyword";
           junos:must "(!((\"interfaces $$ flexible-vlan-tagging\" || (\"interfaces $$ stacked-vlan-tagging\" || (\"interfaces $$ vlan-vci-tagging\" || \"interfaces $$ vlan-tagging\")))))";
           junos:must-message "VLAN configuration is not allowed on fabric member";
           junos:must "(!(\"interfaces $$ disable\"))";
           junos:must-message "fabric member device disable setting is not allowed";
           junos:must "(!(\"interfaces $$ encapsulation\"))";
           junos:must-message "fabric member device encapsulation is not allowed";
           junos:must "(!(\"interfaces $$ mac\"))";
           junos:must-message "fabric member device mac address setting is not allowed";
           junos:must "(!(\"interfaces $$ mtu\"))";
           junos:must-message "fabric member device mtu setting and vlan-tagging is not allowed";
           junos:must "(!(\"interfaces $$ passive-monitor-mode\"))";
           junos:must-message "Fabric member cannot be configured in passive monitor mode";
           junos:must "(!(\"interfaces $$ gigether-options 802.3ad\"))";
           junos:must-message "Fabric member cannot be part of aggregated ethernet";
           junos:must "(!(\"interfaces $$ gigether-options redundant-parent\"))";
           junos:must-message "Fabric member cannot be part of redundant ethernet";
           junos:must "(!(\"interfaces $$ unit\"))";
           junos:must-message "Logical unit is not allowed on fabric member";
           junos:must "(!(\"system autoinstallation\"))";
           junos:must-message "incompatible with 'system autoinstallation'";
           type union {
             type jt:interface-device;
             type string {
               pattern "<.*>|$.*";
             }
           }
         }
         uses apply-advanced;
       }
       container remote-chassis {
         presence "enable remote-chassis";
         description "Remote chassis reachability";
         uses apply-advanced;
         leaf destination {
           description "Destination IP address to reach remote chassis";
           type jt:ipv4addr;
         }
       }
     }
     container traceoptions {
       presence "enable traceoptions";
       description "Interface trace options";
       uses apply-advanced;
       list flag {
         key name;
         ordered-by user;
         junos:cli-feature "oneliner";
         description "Tracing parameters";
         leaf name {
           junos:cli-feature "nokeyword";
           type enumeration {
             enum "ipc" {
               description "Trace interface IPC messages";
             }
             enum "event" {
               description "Trace interface events";
             }
             enum "media" {
               description "Trace interface media changes";
             }
             enum "all" {
               description "Enable all interface trace flags";
             }
             enum "q921" {
               description "Trace ISDN Q.921 frames";
             }
             enum "q931" {
               description "Trace ISDN Q.931 frames";
             }
           }
         }
       }
       container file {
         presence "enable file";
         description "Trace file information for ISDN decoded frames";
         uses apply-advanced;
         leaf filename {
           description "Name of file in which to write trace information";
           junos:cli-feature "nokeyword";
           type string {
             length "1 .. 1024";
             junos:posix-pattern "![/ %]";
             junos:pattern-message "Must not contain \'/\', % or a space";
           }
         }
         leaf size {
           description "Maximum trace file size";
           default "128k";
           type string;
         }
         leaf files {
           description "Maximum number of trace files";
           default "10";
           type union {
             type uint32;
             type string {
               pattern "<.*>|$.*";
             }
           }
         }
         choice world-readable-choice {
           leaf world-readable {
             description "Allow any user to read the log file";
             type empty;
           }
           leaf no-world-readable {
             description "Don't allow any user to read the log file";
             type empty;
           }
         }
       }
     }
     leaf passive-monitor-mode {
       description "Use interface to tap packets from another router";
       junos:must "(!((\"services nat ipv6-multicast-interfaces $$={all}\" || \"services nat ipv6-multicast-interfaces ${interface}\")))";
       junos:must-message "Can not configure 'services nat ipv6-multicast-interfaces' when passive montioring is enabled for the interface";
       junos:must "(!((\".. encapsulation ethernet-ccc\" || (\".. encapsulation ethernet-tcc\" || (\".. encapsulation ethernet-bridge\" || (\".. encapsulation ethernet-vpls\" || (\".. encapsulation extended-vlan-ccc\" || (\".. encapsulation extended-vlan-tcc\" || (\".. encapsulation extended-vlan-vpls\" || (\".. encapsulation extended-vlan-bridge\" || (\".. encapsulation flexible-ethernet-services\" || (\".. encapsulation vlan-ccc\" || (\".. encapsulation vlan-vci-ccc\" || \".. encapsulation vlan-vpls\")))))))))))))";
       junos:must-message "Not compatible with specified 'encapsulation`";
       type empty;
     }
     choice keepalive_choices {
       case case_1 {
         container keepalives {
           description "Send or demand keepalive messages";
           presence "enable keepalives";
           junos:cli-feature "oneliner";
           uses keepalives_type;
         }
       }
       case case_2 {
         leaf no-keepalives {
           description "Do not send keepalive messages";
           type empty;
         }
       }
     }
     choice traps-choice {
       leaf traps {
         description "Enable SNMP notifications on state changes";
         type empty;
       }
       leaf no-traps {
         description "Don't enable SNMP notifications on state changes";
         type empty;
       }
     }
     choice interface-mib-choice {
       leaf interface-mib {
         description "Enable interface-related MIBs";
         type empty;
       }
       leaf no-interface-mib {
         description "Don't enable interface-related MIBs";
         type empty;
       }
     }
     leaf accounting-profile {
       description "Accounting profile name";
       junos:must "((\"accounting-options interface-profile $$\" || \"accounting-options flat-file-profile $$\"))";
       junos:must-message "referenced accounting profile must be defined";
       type string;
     }
     choice scheduler_type {
       case case_1 {
         choice per-unit-scheduler-choice {
           leaf per-unit-scheduler {
             description "Enable subunit queuing on Frame Relay or VLAN IQ interface";
             type empty;
           }
           leaf no-per-unit-scheduler {
             description "Don't enable subunit queuing on Frame Relay or VLAN IQ interface";
             type empty;
           }
         }
       }
       case case_2 {
         leaf shared-scheduler {
           description "Enabled shared queuing on an IQ2 interface";
           junos:must "((\".. vlan-tagging\" || (\".. stacked-vlan-tagging\" || (\".. flexible-vlan-tagging\" || \".. vlan-vci-tagging\"))))";
           junos:must-message "vlan tagging needs to be enabled for shared scheduler";
           type empty;
         }
       }
       case case_3 {
         container hierarchical-scheduler {
           presence "enable hierarchical-scheduler";
           junos:cli-feature "oneliner";
           description "Enable hierarchical scheduling";
           leaf maximum-hierarchy-levels {
             description "Maximum hierarchy levels";
             type union {
               type string {
                 pattern "<.*>|$.*";
               }
               type uint32;
             }
           }
           leaf implicit-hierarchy {
             description "Implicit hierarchy (follows interface hierarchy)";
             type empty;
           }
         }
       }
     }
     leaf l2tp-maximum-session {
       description "Maximum L2TP session";
       type union {
         type string {
           pattern "<.*>|$.*";
         }
         type uint32 {
           range "0 .. 64000";
         }
       }
     }
     leaf schedulers {
       description "Number of schedulers to allocate for interface";
       type union {
         type uint32;
         type string {
           pattern "<.*>|$.*";
         }
       }
     }
     leaf port-extender-cascade-port {
       description "NGPE Cascade port";
       junos:must "(!(\".. shared-scheduler\"))";
       junos:must-message "NGPE cascade-port cannot have shared-scheduler config";
       junos:must "(!(\".. hierarchical-scheduler\"))";
       junos:must-message "NGPE cascade-port cannot have hierarchical-scheduler config";
       type empty;
     }
     leaf dce {
       description "Respond to Frame Relay status enquiry messages";
       type empty;
     }
     choice vlan_tag_mode {
       case case_1 {
         leaf vlan-tagging {
           description "802.1q VLAN tagging support";
           type empty;
         }
       }
       case case_2 {
         leaf stacked-vlan-tagging {
           description "Stacked 802.1q VLAN tagging support";
           junos:must "(!((\".. passive-monitor-mode\" || \".. 802.3ad\")))";
           junos:must-message "Not compatible with passive-monitor-mode statement";
           type empty;
         }
       }
       case case_3 {
         leaf flexible-vlan-tagging {
           description "Support for no tagging, or single and double 802.1q VLAN tagging";
           junos:must "(!(\"system autoinstallation\"))";
           junos:must-message "incompatible with 'system autoinstallation'";
           junos:must "((\".. encapsulation vlan-vpls\" || (\".. encapsulation extended-vlan-vpls\" || (\".. encapsulation extended-vlan-bridge\" || !(\".. encapsulation\")))))";
           junos:must-message "Only compatible with vpls vlan encapsulations or no encapsulation";
           type empty;
         }
       }
       case case_4 {
       }
     }
     leaf native-vlan-id {
       description "Virtual LAN identifier for untagged frames";
       junos:must "((\".. flexible-vlan-tagging\" || (\".. unit $$={0} family bridge interface-mode trunk\" || any \".. unit <*> family ethernet-switching interface-mode trunk\")))";
       junos:must-message "native-vlan-id can be specified with flexible-vlan-tagging mode or with interface-mode trunk";
       junos:must "((\".. flexible-vlan-tagging\" || (any \".. unit <*> family bridge interface-mode trunk\" || any \".. unit <*> family ethernet-switching interface-mode trunk\")))";
       junos:must-message "native-vlan-id can be specified with flexible-vlan-tagging mode or with interface-mode trunk";
       type union {
         type string {
           pattern "<.*>|$.*";
         }
         type uint32 {
           range "0 .. 4094";
         }
       }
     }
     leaf input-native-vlan-push {
       description "Control native-vlan-id insertion to untagged frames when input-vlan-map push is configured";
       junos:must "(any \"interfaces ${interface}  unit <*> input-vlan-map push \")";
       junos:must-message "input-native-vlan-push can be set only when input-vlan-map push is configured";
       type enumeration {
         enum "disable" {
           description "Disable input-native-vlan-push";
         }
         enum "enable" {
           description "Enable input-native-vlan-push";
         }
       }
     }
     leaf number-of-sub-ports {
       description "Number of channels to create for a port";
       type union {
         type string {
           pattern "<.*>|$.*";
         }
         type uint32 {
           range "1 .. 8";
         }
       }
     }
     leaf speed {
       description "Link speed";
       type enumeration {
         enum "auto" {
           description "Enable auto negotiation of interface speed";
           junos:must "((!(\"interfaces ${interface} gigether-options 802.3ad\") || !(\"interfaces ${interface} ether-options 802.3ad\")))";
           junos:must-message "Auto speed cannot be configured for an aggregated ethernet member link";
           junos:must "((\"interfaces ${interface} gigether-options auto-negotiation\" || \"interfaces ${interface} ether-options auto-negotiation\"))";
           junos:must-message "gigether-options/ether-options auto-negotiation must be enabled";
         }
         enum "auto-10m-100m" {
           description "Enable auto negotiation of limiting interface speed to 10m/100m";
           junos:must "((!(\"interfaces ${interface} gigether-options 802.3ad\") || !(\"interfaces ${interface} ether-options 802.3ad\")))";
           junos:must-message "Auto speed cannot be configured for an aggregated ethernet member link";
           junos:must "((\"interfaces ${interface} gigether-options auto-negotiation\" || \"interfaces ${interface} ether-options auto-negotiation\"))";
           junos:must-message "gigether-options/ether-options auto-negotiation must be enabled";
         }
         enum "10m" {
         }
         enum "100m" {
         }
         enum "1g" {
         }
         enum "2.5g" {
         }
         enum "5g" {
         }
         enum "10g" {
         }
         enum "25g" {
         }
         enum "40g" {
         }
         enum "50g" {
         }
         enum "100g" {
         }
         enum "200g" {
         }
         enum "400g" {
         }
         enum "800g" {
         }
         enum "oc3" {
         }
         enum "oc12" {
         }
         enum "oc48" {
         }
         enum "1.6t" {
         }
       }
     }
     leaf mtu {
       description "Maximum transmit packet size";
       junos:must "(!(\"interfaces ${interface} container-options container-list\"))";
       junos:must-message "mtu is not supported for container child interfaces";
       type union {
         type string {
           pattern "<.*>|$.*";
         }
         type uint32;
       }
     }
     container hold-time {
       junos:cli-feature "oneliner";
       description "Hold time for link up and link down";
       leaf up {
         description "Link up hold time";
         units "milliseconds";
         type union {
           type uint32;
           type string {
             pattern "<.*>|$.*";
           }
         }
       }
       leaf down {
         description "Link down hold time";
         units "milliseconds";
         type union {
           type uint32;
           type string {
             pattern "<.*>|$.*";
           }
         }
       }
     }
     container port-extender {
       description "Tunnel binding information for the extended port";
       uses apply-advanced;
       container vxlan {
         presence "enable vxlan";
         description "VXLAN binding information for the extended port";
         uses apply-advanced;
         leaf end-point {
           description "Satellite loopback IP address";
           type jt:ipaddr;
         }
         leaf vni {
           description "VNI of the satellite extended-port";
           type union {
             type string {
               pattern "<.*>|$.*";
             }
             type uint32 {
               range "0 .. 16777214";
             }
           }
         }
       }
     }
     container link-degrade-monitor {
       presence "enable link-degrade-monitor";
       description "Enable link degrade monitoring";
       uses apply-advanced;
       choice enable_choice {
         case case_1 {
           leaf link-degrade-monitor-enable {
             description "Enable Link Degrade Monitoring";
             type empty;
           }
         }
         case case_2 {
           leaf no-link-degrade-monitor-enable {
             description "Disable Link Degrade Monitoring";
             type empty;
           }
         }
       }
       container actions {
         description "Action upon link degrade event";
         uses apply-advanced;
         choice action_choice {
           case case_1 {
             leaf media-based {
               description "Media based";
               type empty;
             }
           }
         }
       }
       container recovery {
         description "Link degrade recovery mechanism";
         uses apply-advanced;
         leaf timer {
           description "Auto recovery timer in seconds";
           default "1800";
           junos:must "(!(\".. manual\"))";
           junos:must-message "Recovery mechanism must be auto to configure recovery timer";
           type union {
             type uint32;
             type string {
               pattern "<.*>|$.*";
             }
           }
         }
         choice receovery_choice {
           case case_1 {
             leaf auto {
               description "Automatic recovery";
               type empty;
             }
           }
           case case_2 {
             leaf manual {
               description "Manual recovery";
               type empty;
             }
           }
         }
       }
       container thresholds {
         description "Link degrade threshold parameters";
         uses apply-advanced;
         leaf set {
           description "BER at which link considered degraded(1..16)";
           default "1e-7";
           type string {
             junos:posix-pattern "^1e-(1[0-6]?|[2-9])$";
             junos:pattern-message "Ber threshold value in format: 1e-n, n = 1..16";
           }
         }
         leaf clear {
           description "BER at which link considered improved(1..16)";
           default "1e-12";
           type string {
             junos:posix-pattern "^1e-(1[0-6]?|[2-9])$";
             junos:pattern-message "Ber threshold value in format: 1e-n, n = 1..16";
           }
         }
         leaf warning-set {
           description "BER at which link degrade warning raised(1..16)";
           default "1e-9";
           type string {
             junos:posix-pattern "^1e-(1[0-6]?|[2-9])$";
             junos:pattern-message "Ber threshold value in format: 1e-n, n = 1..16";
           }
         }
         leaf warning-clear {
           description "BER at which link degrade warning cleared(1..16)";
           default "1e-11";
           type string {
             junos:posix-pattern "^1e-(1[0-6]?|[2-9])$";
             junos:pattern-message "Ber threshold value in format: 1e-n, n = 1..16";
           }
         }
         leaf interval {
           description "Consecutive link degrade events";
           default "10";
           type union {
             type string {
               pattern "<.*>|$.*";
             }
             type uint32 {
               range "1 .. 256";
             }
           }
         }
       }
     }
     container satop-options {
       junos:must "((!(\".. t1-options framing\") && !(\".. e1-options framing\")))";
       junos:must-message "SAToP & Framing cannot be configured on same interface";
       junos:must "(!(\".. ima-link-options\"))";
       junos:must-message "SAToP & IMA cannot be configured on same interface";
       junos:must "((!(\"interfaces ${interface} container-options\") || (\"interfaces ${interface} container-options container-type\" || \"interfaces ${interface} container-options allow-configuration-override\")))";
       junos:must-message "satop-options cannot be configured without allow-configuration-override";
       junos:cli-feature "oneliner-plus";
       description "Structure-Agnostic TDM over Packet protocol options";
       uses apply-advanced;
       leaf idle-pattern {
         description "An 8-bit hexadecimal pattern to replace TDM data in a lost packet";
         type union {
           type string {
             pattern "<.*>|$.*";
           }
           type uint32 {
             range "0 .. 255";
           }
         }
       }
       leaf payload-size {
         description "Number of payload bytes per packet";
         type union {
           type string {
             pattern "<.*>|$.*";
           }
           type uint32 {
             range "64 .. 1024";
           }
         }
       }
       container excessive-packet-loss-rate {
         junos:cli-feature "oneliner-plus";
         description "Packet loss options";
         uses apply-advanced;
         leaf threshold {
           description "Percentile designating the threshold of excessive packet loss rate";
           type union {
             type string {
               pattern "<.*>|$.*";
             }
             type uint8 {
               range "1 .. 100";
             }
           }
         }
         leaf sample-period {
           description "Number of milliseconds over which excessive packet loss rate is calculated";
           type union {
             type string {
               pattern "<.*>|$.*";
             }
             type uint32 {
               range "1000 .. 65535";
             }
           }
         }
       }
       choice jitter-buffer-size {
         case case_1 {
           leaf jitter-buffer-packets {
             description "Number of packets in jitter buffer before packet data is played out in the line";
             type union {
               type string {
                 pattern "<.*>|$.*";
               }
               type uint32 {
                 range "1 .. 64";
               }
             }
           }
         }
         case case_2 {
           leaf jitter-buffer-latency {
             description "Number of milliseconds delay in jitter buffer before packet data is played out in the line";
             units "milliseconds";
             type union {
               type string {
                 pattern "<.*>|$.*";
               }
               type uint32 {
                 range "1 .. 1000";
               }
             }
           }
         }
         case case_3 {
           leaf jitter-buffer-auto-adjust {
             description "Automatically adjust jitter buffer";
             type empty;
           }
         }
       }
       leaf bit-rate {
         description "In multiples of DS0";
         type union {
           type string {
             pattern "<.*>|$.*";
           }
           type uint32 {
             range "1 .. 10240";
           }
         }
       }
     }
     container cesopsn-options {
       junos:must "((!(\"interfaces ${interface} container-options\") || (\"interfaces ${interface} container-options container-type\" || \"interfaces ${interface} container-options allow-configuration-override\")))";
       junos:must-message "cesopsn-options cannot be configured without allow-configuration-override";
       junos:cli-feature "oneliner-plus";
       description "Structure-Aware TDM over Packet protocol options";
       uses apply-advanced;
       leaf idle-pattern {
         description "An 8-bit hexadecimal pattern to replace TDM data in a lost packet";
         type union {
           type string {
             pattern "<.*>|$.*";
           }
           type uint32 {
             range "0 .. 255";
           }
         }
       }
       leaf packetization-latency {
         description "Number of microseconds to create packets";
         units "microseconds";
         type union {
           type string {
             pattern "<.*>|$.*";
           }
           type uint32 {
             range "1000 .. 8000";
           }
         }
       }
       leaf payload-size {
         description "Number of payload bytes per packet";
         type union {
           type string {
             pattern "<.*>|$.*";
           }
           type uint32 {
             range "64 .. 1024";
           }
         }
       }
       container excessive-packet-loss-rate {
         junos:cli-feature "oneliner-plus";
         description "Packet loss options";
         uses apply-advanced;
         leaf threshold {
           description "Percentile designating the threshold of excessive packet loss rate";
           type union {
             type string {
               pattern "<.*>|$.*";
             }
             type uint8 {
               range "1 .. 100";
             }
           }
         }
         leaf sample-period {
           description "Number of milliseconds over which excessive packet loss rate is calculated";
           type union {
             type string {
               pattern "<.*>|$.*";
             }
             type uint32 {
               range "1000 .. 65535";
             }
           }
         }
       }
       choice jitter-buffer-size {
         case case_1 {
           leaf jitter-buffer-packets {
             description "Number of packets in jitter buffer before packet data is played out in the line";
             type union {
               type string {
                 pattern "<.*>|$.*";
               }
               type uint32 {
                 range "1 .. 64";
               }
             }
           }
         }
         case case_2 {
           leaf jitter-buffer-latency {
             description "Number of milliseconds delay in jitter buffer before packet data is played out in the line";
             units "milliseconds";
             type union {
               type string {
                 pattern "<.*>|$.*";
               }
               type uint32 {
                 range "1 .. 1000";
               }
             }
           }
         }
         case case_3 {
           leaf jitter-buffer-auto-adjust {
             description "Automatically adjust jitter buffer";
             type empty;
           }
         }
       }
       leaf bit-rate {
         description "In multiples of DS0";
         type union {
           type string {
             pattern "<.*>|$.*";
           }
           type uint32 {
             range "1 .. 10240";
           }
         }
       }
     }
     container clocking {
       junos:cli-feature "oneliner";
       description "Interface clock source";
       choice clocking_choices {
         case case_1 {
           leaf internal {
             description "Clocking provided by local system";
             type empty;
           }
         }
         case case_2 {
           container external {
             presence "enable external";
             description "Clocking provided by DCE (loop timing)";
             uses apply-advanced;
             leaf interface {
               description "Interface that acts as clock source";
               junos:must "(!(\"interfaces $$ clocking external interface\"))";
               junos:must-message "Interface should not have clock input interface configured";
               junos:must "(\"interfaces $$\")";
               junos:must-message "Referenced clock input interface must be defined";
               type union {
                 type jt:interface-device;
                 type string {
                   pattern "<.*>|$.*";
                 }
               }
             }
           }
         }
       }
       uses apply-advanced;
     }
     leaf link-mode {
       description "Link operational mode";
       type enumeration {
         enum "automatic" {
           description "Automatically negotiate duplex";
         }
         enum "half-duplex" {
           description "Half-duplex operation";
         }
         enum "full-duplex" {
           description "Full-duplex operation";
         }
       }
     }
     leaf media-type {
       description "Interface media type (copper or fiber)";
       type enumeration {
         enum "copper" {
           description "Copper as media";
         }
         enum "fiber" {
           description "Fiber as media";
         }
       }
     }
     leaf encapsulation {
       description "Physical link-layer encapsulation";
       junos:must "(!(\"interfaces ${interface} container-options container-list\"))";
       junos:must-message "encapsulation is not supported for container child interfaces";
       type enumeration {
         enum "ethernet" {
           description "Ethernet physical media";
         }
         enum "fddi" {
           description "FDDI physical media";
         }
         enum "token-ring" {
           description "Token Ring physical media";
         }
         enum "ppp" {
           description "Serial PPP device";
         }
         enum "ppp-ccc" {
           description "Serial PPP device for a cross-connect";
         }
         enum "ppp-tcc" {
           description "Serial PPP device for a translational cross-connect";
         }
         enum "ether-vpls-ppp" {
           description "Ethernet VPLS over PPP (bridging) device";
         }
         enum "frame-relay" {
           description "Frame Relay encapsulation";
         }
         enum "frame-relay-ccc" {
           description "Frame Relay for cross-connect";
         }
         enum "frame-relay-tcc" {
           description "Frame Relay for translational cross-connect";
         }
         enum "extended-frame-relay-ccc" {
           description "Any Frame Relay DLCI for cross-connect";
         }
         enum "extended-frame-relay-tcc" {
           description "Any Frame Relay DLCI for translational cross-connect";
         }
         enum "flexible-frame-relay" {
           description "Multiple Frame Relay encapsulations";
         }
         enum "frame-relay-port-ccc" {
           description "Frame Relay port encapsulation for a cross-connect";
         }
         enum "frame-relay-ether-type" {
           description "Cisco-compatible Frame Relay encapsulation";
         }
         enum "frame-relay-ether-type-tcc" {
           description "Cisco-compatible Frame Relay encapsulation for translational cross-connect";
         }
         enum "extended-frame-relay-ether-type-tcc" {
           description "Cisco-compatible Frame Relay encapsulation any DLCI for translational cross-connect";
         }
         enum "cisco-hdlc" {
           description "Cisco-compatible HDLC framing";
         }
         enum "cisco-hdlc-ccc" {
           description "Cisco-compatible HDLC framing for a cross-connect";
         }
         enum "cisco-hdlc-tcc" {
           description "Cisco-compatible HDLC framing for a translational cross-connect";
         }
         enum "vlan-ccc" {
           description "802.1q tagging for a cross-connect";
         }
         enum "extended-vlan-ccc" {
           description "Nonstandard TPID tagging for a cross-connect";
         }
         enum "ethernet-ccc" {
           description "Ethernet cross-connect";
         }
         enum "flexible-ethernet-services" {
           description "Allows per-unit Ethernet encapsulation configuration";
         }
         enum "smds-dxi" {
           description "SMDS DXI framing";
         }
         enum "atm-pvc" {
           description "ATM permanent virtual circuits";
         }
         enum "atm-ccc-cell-relay" {
           description "ATM cell relay encapsulation for cross-connect";
         }
         enum "ethernet-over-atm" {
           description "Ethernet over ATM encapsulation";
         }
         enum "ethernet-tcc" {
           description "Ethernet translational cross-connect";
         }
         enum "extended-vlan-tcc" {
           description "802.1q tagging for a translational cross-connect";
         }
         enum "multilink-frame-relay-uni-nni" {
           description "Multilink Frame Relay UNI NNI (FRF.16) encapsulation";
         }
         enum "satop" {
           description "Structure-Agnostic TDM over Packet encapsulation";
           junos:must "((!(\".. t1-options framing\") && !(\".. e1-options framing\")))";
           junos:must-message "SAToP & Framing cannot be configured on same interface";
           junos:must "(!(\".. ima-link-options\"))";
           junos:must-message "SAToP & IMA cannot be configured on same interface";
         }
         enum "cesopsn" {
           description "Structure-Agnostic TDM over Packet encapsulation";
         }
         enum "ima" {
           description "Inverse Multiplexing for ATM";
           junos:must "(!(\".. satop-options\"))";
           junos:must-message "SAToP & IMA cannot be configured on same interface";
         }
         enum "ethernet-vpls" {
           description "Ethernet virtual private LAN service";
         }
         enum "ethernet-bridge" {
           description "Ethernet layer-2 bridging";
         }
         enum "vlan-vpls" {
           description "VLAN virtual private LAN service";
         }
         enum "vlan-vci-ccc" {
           description "CCC for VLAN Q-in-Q and ATM VPI/VCI interworking";
           junos:must "(\"interfaces ${interface} vlan-vci-tagging\")";
           junos:must-message "valid only with vlan-vci-tagging mode";
         }
         enum "extended-vlan-vpls" {
           description "Extended VLAN virtual private LAN service";
         }
         enum "extended-vlan-bridge" {
           description "VLAN layer-2 bridging";
         }
         enum "multilink-ppp" {
           description "Multilink PPP";
         }
         enum "generic-services" {
           description "Generic services";
         }
       }
     }
     leaf network-isolation-profile {
       description "Attach a network isolation profile on this interface";
       junos:must "(!((\".. .. .. protocols network-isolation group $$ service-tracking-action lacp-out-of-sync\" && !(\".. aggregated-ether-options lacp\"))))";
       junos:must-message "lacp-out-of-sync is allowed only on LACP interfaces";
       junos:must "(\".. .. .. protocols network-isolation group $$ service-tracking-action\")";
       junos:must-message "service-tracking-action must be configured";
       junos:must "((\".. .. .. protocols network-isolation group $$ detection service-tracking\" || \".. .. .. protocols network-isolation group $$ detection link-tracking\"))";
       junos:must-message "service-tracking or link-tracking must be configured";
       type string;
     }
     container framing {
       description "Frame type";
       uses apply-advanced;
       choice frame {
         case case_1 {
           leaf lan-phy {
             description "802.3ae 10-Gbps LAN-mode interface";
             type empty;
           }
         }
         case case_2 {
           leaf wan-phy {
             description "802.3ae 10-Gbps WAN-mode interface";
             type empty;
           }
         }
         case case_3 {
           leaf sonet {
             description "SONET framing";
             type empty;
           }
         }
         case case_4 {
           leaf sdh {
             description "SDH framing";
             type empty;
           }
         }
       }
     }
     container lmi {
       description "Local Management Interface settings";
       uses apply-advanced;
       leaf n391dte {
         description "DTE full status polling interval";
         junos:must "(!((\".. .. dce\" || \".. .. loose-ncp\")))";
         junos:must-message "LMI DTE options not valid for DCE interface";
         type union {
           type string {
             pattern "<.*>|$.*";
           }
           type uint16 {
             range "1 .. 255";
           }
         }
       }
       leaf n392dce {
         description "DCE error threshold";
         junos:must "((\".. .. dce\" || \".. .. loose-ncp\"))";
         junos:must-message "LMI DCE options not valid for DTE interface";
         type union {
           type string {
             pattern "<.*>|$.*";
           }
           type uint16 {
             range "1 .. 10";
           }
         }
       }
       leaf n392dte {
         description "DTE error threshold";
         junos:must "(!((\".. .. dce\" || \".. .. loose-ncp\")))";
         junos:must-message "LMI DTE options not valid for DCE interface";
         type union {
           type string {
             pattern "<.*>|$.*";
           }
           type uint16 {
             range "1 .. 10";
           }
         }
       }
       leaf n393dce {
         description "DCE monitored event count";
         junos:must "((\".. .. dce\" || \".. .. loose-ncp\"))";
         junos:must-message "LMI DCE options not valid for DTE interface.";
         type union {
           type string {
             pattern "<.*>|$.*";
           }
           type uint16 {
             range "1 .. 10";
           }
         }
       }
       leaf n393dte {
         description "DTE monitored event count";
         junos:must "(!((\".. .. dce\" || \".. .. loose-ncp\")))";
         junos:must-message "LMI DTE options not valid for DCE interface";
         type union {
           type string {
             pattern "<.*>|$.*";
           }
           type uint16 {
             range "1 .. 10";
           }
         }
       }
       leaf t391dte {
         description "DTE polling timer";
         units "seconds";
         junos:must "(!((\".. .. dce\" || \".. .. loose-ncp\")))";
         junos:must-message "LMI DTE options not valid for DCE interface";
         type union {
           type string {
             pattern "<.*>|$.*";
           }
           type uint16 {
             range "5 .. 30";
           }
         }
       }
       leaf t392dce {
         description "DCE polling verification timer";
         units "seconds";
         junos:must "((\".. .. dce\" || \".. .. loose-ncp\"))";
         junos:must-message "LMI DCE options not valid for DTE interface.";
         type union {
           type string {
             pattern "<.*>|$.*";
           }
           type uint16 {
             range "5 .. 30";
           }
         }
       }
       leaf lmi-type {
         description "Specify the Frame Relay LMI type";
         type enumeration {
           enum "ansi" {
             description "Use ANSI Annex D LMI";
           }
           enum "itu" {
             description "Use ITU Q933a Annex A LMI";
           }
           enum "c-lmi" {
             description "Use Consortium LMI";
           }
         }
       }
     }
     container mlfr-uni-nni-bundle-options {
       description "Multilink Frame Relay UNI NNI (FRF.16) management settings";
       uses apply-advanced;
       container cisco-interoperability {
         description "FRF.16 Cisco interoperability settings";
         uses apply-advanced;
         leaf send-lip-remove-link-for-link-reject {
           description "Send Link Integrity Protocol remove link on receiving add-link rejection";
           type empty;
         }
       }
       leaf mrru {
         description "Maximum received reconstructed unit";
         units "bytes";
         type union {
           type string {
             pattern "<.*>|$.*";
           }
           type uint16 {
             range "1500 .. 4500";
           }
         }
       }
       leaf yellow-differential-delay {
         description "Yellow differential delay among bundle links to give warning";
         units "milliseconds";
         type union {
           type string {
             pattern "<.*>|$.*";
           }
           type uint16 {
             range "3 .. 2000";
           }
         }
       }
       leaf red-differential-delay {
         description "Red differential delay among bundle links to take action";
         units "milliseconds";
         type union {
           type string {
             pattern "<.*>|$.*";
           }
           type uint16 {
             range "5 .. 2000";
           }
         }
       }
       leaf action-red-differential-delay {
         description "Type of actions when differential delay exceeds red limit";
         type enumeration {
           enum "remove-link" {
             description "Remove bundle link from service when exceeding red limit";
           }
           enum "disable-tx" {
             description "Disable transfer of bundle link when exceeding red limit";
           }
         }
       }
       leaf fragment-threshold {
         description "Fragmentation threshold";
         units "bytes";
         type union {
           type string {
             pattern "<.*>|$.*";
           }
           type uint32 {
             range "64 .. 16320";
           }
         }
       }
       leaf drop-timeout {
         description "Drop timeout";
         units "milliseconds";
         type union {
           type string {
             pattern "<.*>|$.*";
           }
           type uint16 {
             range "0 .. 2000";
           }
         }
       }
       leaf link-layer-overhead {
         description "Link layer bit stuffing overhead (0.0 .. 50.0 percent)";
         type jt:unsigned-float;
       }
       leaf lmi-type {
         description "Specify the multilink Frame Relay UNI NNI LMI type";
         type enumeration {
           enum "ansi" {
             description "Use ANSI Annex D LMI";
           }
           enum "itu" {
             description "Use ITU Q933a Annex A LMI";
           }
           enum "c-lmi" {
             description "Use Consortium LMI";
           }
         }
       }
       leaf minimum-links {
         description "Minimum number of links to sustain the bundle";
         type union {
           type string {
             pattern "<.*>|$.*";
           }
           type uint16 {
             range "1 .. 8";
           }
         }
       }
       leaf hello-timer {
         description "LIP hello timer";
         type union {
           type string {
             pattern "<.*>|$.*";
           }
           type uint16 {
             range "5 .. 180";
           }
         }
       }
       leaf acknowledge-timer {
         description "LIP ack timer";
         type union {
           type string {
             pattern "<.*>|$.*";
           }
           type uint16 {
             range "1 .. 10";
           }
         }
       }
       leaf acknowledge-retries {
         description "LIP ack retry times";
         type union {
           type string {
             pattern "<.*>|$.*";
           }
           type uint16 {
             range "1 .. 5";
           }
         }
       }
       leaf n391 {
         description "Multilink Frame Relay UNI NNI full status polling counter";
         type union {
           type string {
             pattern "<.*>|$.*";
           }
           type uint16 {
             range "1 .. 255";
           }
         }
       }
       leaf n392 {
         description "Multilink Frame Relay UNI NNI LMI error threshold";
         type union {
           type string {
             pattern "<.*>|$.*";
           }
           type uint16 {
             range "1 .. 10";
           }
         }
       }
       leaf n393 {
         description "Multilink Frame Relay UNI NNI LMI monitored event count";
         type union {
           type string {
             pattern "<.*>|$.*";
           }
           type uint16 {
             range "1 .. 10";
           }
         }
       }
       leaf t391 {
         description "Multilink Frame Relay UNI NNI link integrity verify polling timer";
         type union {
           type string {
             pattern "<.*>|$.*";
           }
           type uint16 {
             range "5 .. 30";
           }
         }
       }
       leaf t392 {
         description "Multilink Frame Relay UNI NNI polling verification timer";
         type union {
           type string {
             pattern "<.*>|$.*";
           }
           type uint16 {
             range "5 .. 30";
           }
         }
       }
     }
     leaf mac {
       description "Hardware MAC address";
       type jt:mac-unicast;
     }
     container receive-bucket {
       description "Set receive bucket parameters";
       uses dcd_rx_bucket_config;
     }
     container transmit-bucket {
       description "Set transmit bucket parameters";
       uses dcd_tx_bucket_config;
     }
     leaf shared-interface {
       description "Enable shared interface on the interface";
       type empty;
     }
     container sonet-options {
       description "SONET interface-specific options";
       junos:must "((!(\"interfaces ${interface} container-options\") || (\"interfaces ${interface} container-options container-type\" || \"interfaces ${interface} container-options allow-configuration-override\")))";
       junos:must-message "sonet-options cannot be configured without allow-configuration-override";
       uses sonet_options_type;
     }
     container logical-tunnel-options {
       description "Logical Tunnel interface-specific options";
       uses apply-advanced;
       container link-protection {
         presence "enable link-protection";
         junos:must "(any \"interfaces ${interface} redundancy-group member-interface <*> active\")";
         junos:must-message "Active and Backup child links must be configured to use link-protection";
         description "Enable link protection mode";
         uses apply-advanced;
         leaf revertive {
           description "Revert back (Default mode) from active backup link to primary, if primary is UP";
           junos:must "(!(\"interfaces ${interface} logical-tunnel-options link-protection non-revertive\"))";
           junos:must-message "link-protection revertive and non-revertive are mutually exclusive";
           junos:must "(any \"interfaces ${interface} redundancy-group member-interface <*> active\")";
           junos:must-message "link-protection mode can be configured only when link-protection is enabled";
           type empty;
         }
         leaf non-revertive {
           description "Do not revert back from active backup link to primary, if primary is UP";
           junos:must "(!(\"interfaces ${interface} logical-tunnel-options link-protection revertive\"))";
           junos:must-message "link-protection revertive and non-revertive are mutually exclusive";
           junos:must "(any \"interfaces ${interface} redundancy-group member-interface <*> active\")";
           junos:must-message "link-protection mode can be configured only when link-protection is enabled";
           type empty;
         }
       }
       leaf per-unit-mac-disable {
         description "Disable the creation of per unit mac address on LT IFLs for VPLS/CCC encaps";
         type empty;
       }
     }
     container aggregated-sonet-options {
       description "Aggregated SONET interface-specific options";
       uses apply-advanced;
       leaf minimum-links {
         description "Minimum number of aggregated links";
         type union {
           type string {
             pattern "<.*>|$.*";
           }
           type uint16;
         }
       }
       leaf link-speed {
         description "Aggregated links speed";
         type enumeration {
           enum "oc3" {
             description "Links are OC-3c or STM-1c";
           }
           enum "oc12" {
             description "Links are OC-12c or STM-4c";
           }
           enum "oc48" {
             description "Links are OC-48c or STM-16c";
           }
           enum "oc192" {
             description "Links are OC-192c or STM-64c";
           }
           enum "oc768" {
             description "Links are OC-768c or STM-256c";
           }
           enum "mixed" {
             description "Links are various speeds";
           }
         }
       }
       leaf minimum-bandwidth {
         description "Minimum bandwidth necessary to sustain bundle";
         units "bps";
         type union {
           type string {
             pattern "<.*>|$.*";
           }
           type uint64 {
             range "0 .. 159232000000";
           }
         }
       }
     }
     container atm-options {
       junos:must "((!(\"interfaces ${interface} container-options\") || (\"interfaces ${interface} container-options container-type\" || !(\"interfaces ${interface} container-options container-list\"))))";
       junos:must-message "atm-options cannot be configured on container children";
       description "ATM interface-specific options";
       uses apply-advanced;
       leaf pic-type {
         description "Type of ATM PIC (ATM I, ATM II or ATM CE)";
         type enumeration {
           enum "atm-ce" {
             description "CE PIC";
           }
           enum "atm2" {
             description "ATM II IQ PIC";
           }
           enum "atm1" {
             description "ATM I PIC";
             junos:must "(!(\"interfaces ${interface} container-options\"))";
             junos:must-message "Only ATM-II pics are supported as container member link";
           }
         }
       }
       leaf cell-bundle-size {
         description "L2 circuit cell bundle size";
         units "cells";
         type union {
           type string {
             pattern "<.*>|$.*";
           }
           type uint32 {
             range "1 .. 176";
           }
         }
       }
       leaf cell-bundle-timeout {
         description "L2 circuit cell bundle timeout";
         units "microseconds";
         type union {
           type string {
             pattern "<.*>|$.*";
           }
           type uint32 {
             range "1 .. 512";
           }
         }
       }
       leaf plp-to-clp {
         description "Enable ATM2 PLP to CLP copy";
         type empty;
       }
       leaf use-null-cw {
         description "Always insert/strip null control words with cell-relay";
         type empty;
       }
       container promiscuous-mode {
         presence "enable promiscuous-mode";
         description "Set ATM interface to promiscuous mode";
         uses apply-advanced;
         list vpi {
           key name;
           ordered-by user;
           junos:cli-feature "oneliner";
           description "Open this VPI in promiscuous mode";
           leaf name {
             description "Virtual path index";
             junos:cli-feature "nokeyword";
             type union {
               type string {
                 pattern "<.*>|$.*";
               }
               type uint32 {
                 range "0 .. 255";
               }
             }
           }
         }
       }
       list vpi {
         key name;
         ordered-by user;
         description "Define a virtual path";
         leaf name {
           description "Virtual path index";
           junos:cli-feature "nokeyword";
           type union {
             type string {
               pattern "<.*>|$.*";
             }
             type uint32 {
               range "0 .. 255";
             }
           }
         }
         uses apply-advanced;
         leaf maximum-vcs {
           description "Maximum number of virtual circuits on this VP";
           junos:must "(!(\"interfaces ${interface} container-options\"))";
           junos:must-message "Only ATM-II pics are supported as container member link";
           type union {
             type uint32;
             type string {
               pattern "<.*>|$.*";
             }
           }
         }
         container shaping {
           description "Virtual path traffic-shaping options";
           uses dcd_shaping_config;
         }
         container oam-period {
           junos:cli-feature "oneliner";
           description "F4 OAM cell period";
           choice oam_period_choices {
             case case_1 {
               leaf oam-period {
                 description "F4 OAM cell period";
                 junos:cli-feature "nokeyword";
                 units "seconds";
                 type union {
                   type string {
                     pattern "<.*>|$.*";
                   }
                   type uint32 {
                     range "1 .. 900";
                   }
                 }
               }
             }
             case case_2 {
               container disable {
                 presence "enable disable";
                 junos:cli-feature "oneliner";
                 description "Disable F4 OAM loopback";
               }
             }
           }
         }
         container oam-liveness {
           description "F4 OAM virtual path liveness parameters";
           uses apply-advanced;
           leaf up-count {
             description "Number of F4 OAM cells to consider VP up";
             type union {
               type string {
                 pattern "<.*>|$.*";
               }
               type uint32 {
                 range "1 .. 255";
               }
             }
           }
           leaf down-count {
             description "Number of F4 OAM cells to consider VP down";
             type union {
               type string {
                 pattern "<.*>|$.*";
               }
               type uint32 {
                 range "1 .. 255";
               }
             }
           }
         }
       }
       container ilmi {
         presence "enable ilmi";
         description "Enable Interim Local Management Interface";
         uses apply-advanced;
       }
       list linear-red-profiles {
         key name;
         ordered-by user;
         junos:cli-feature "homogeneous";
         junos:cli-feature "oneliner";
         description "ATM2 CoS virtual circuit drop profiles";
         leaf name {
           description "Linear RED profile name";
           junos:cli-feature "nokeyword";
           type string {
             junos:posix-pattern "^.{1,64}$";
             junos:pattern-message "Must be string of 64 characters or less";
           }
         }
         leaf queue-depth {
           description "Maximum queue depth";
           units "cells";
           type string;
         }
         leaf high-plp-threshold {
           description "Fill level percentage when linear RED is applied for high PLP";
           type union {
             type string {
               pattern "<.*>|$.*";
             }
             type uint32 {
               range "0 .. 100";
             }
           }
         }
         leaf low-plp-threshold {
           description "Fill level percentage when linear RED is applied for low PLP";
           type union {
             type string {
               pattern "<.*>|$.*";
             }
             type uint32 {
               range "0 .. 100";
             }
           }
         }
         leaf high-plp-max-threshold {
           description "Fill level percentage with 100 percent packet drop for high PLP";
           type union {
             type string {
               pattern "<.*>|$.*";
             }
             type uint32 {
               range "0 .. 100";
             }
           }
         }
         leaf low-plp-max-threshold {
           description "Fill level percentage with 100 percent packet drop for low PLP";
           type union {
             type string {
               pattern "<.*>|$.*";
             }
             type uint32 {
               range "0 .. 100";
             }
           }
         }
       }
       list scheduler-maps {
         key name;
         ordered-by user;
         junos:cli-feature "homogeneous";
         description "ATM2 CoS parameters assigned to forwarding classes";
         leaf name {
           description "ATM2 CoS scheduler map name";
           junos:cli-feature "nokeyword";
           type string {
             junos:posix-pattern "^((default)|(.{1,64}))$";
             junos:pattern-message "Must be a string of 64 characters or less and not \'default\'";
           }
         }
         uses apply-advanced;
         leaf vc-cos-mode {
           description "ATM2 virtual circuit CoS mode";
           type enumeration {
             enum "strict" {
               description "Always schedule high priority queue first";
             }
             enum "alternate" {
               description "Every other packet from high priority queue (default)";
             }
           }
         }
         list forwarding-class {
           key name;
           ordered-by user;
           description "Scheduling parameters associated with forwarding class";
           leaf name {
             description "Forwarding class name";
             junos:cli-feature "nokeyword";
             type string {
               junos:posix-pattern "^.{1,64}$";
               junos:pattern-message "Must be string of 64 characters or less";
             }
           }
           uses apply-advanced;
           leaf priority {
             description "Queuing priority assigned to forwarding class";
             type enumeration {
               enum "low" {
                 description "Low priority queuing";
               }
               enum "high" {
                 description "High priority queuing";
               }
             }
           }
           container transmit-weight {
             junos:cli-feature "oneliner";
             description "Transmit weight";
             choice weight-method {
               case case_1 {
                 leaf percent {
                   description "Transmit weight as percentage";
                   type union {
                     type string {
                       pattern "<.*>|$.*";
                     }
                     type uint32 {
                       range "5 .. 100";
                     }
                   }
                 }
               }
               case case_2 {
                 leaf cells {
                   description "Transmit weight by cells count";
                   type string;
                 }
               }
             }
           }
           choice drop-profile-method {
             case case_1 {
               container epd-threshold {
                 description "Early packet discard threshold for ATM2";
                 junos:cli-feature "oneliner";
                 uses epd_threshold_config;
               }
             }
             case case_2 {
               leaf linear-red-profile {
                 description "Linear RED profile profile name";
                 type string;
               }
             }
           }
         }
       }
       container mpls {
         description "MPLS options";
         uses mpls_ifd_options;
       }
       choice payload-scrambler-choice {
         leaf payload-scrambler {
           description "Enable payload scrambling";
           type empty;
         }
         leaf no-payload-scrambler {
           description "Don't enable payload scrambling";
           type empty;
         }
       }
     }
     container multiservice-options {
       description "Multiservice interface-specific options";
       uses apply-advanced;
       choice syslog-choice {
         leaf syslog {
           description "Enable system logging on this interface";
           type empty;
         }
         leaf no-syslog {
           description "Don't enable system logging on this interface";
           type empty;
         }
       }
       choice core-dump-choice {
         leaf core-dump {
           description "Enable core dumping on this interface";
           type empty;
         }
         leaf no-core-dump {
           description "Don't enable core dumping on this interface";
           type empty;
         }
       }
       choice dump-on-flow-control-choice {
         leaf dump-on-flow-control {
           description "Enable dumping for this interface on prolonged flow-control";
           status deprecated;
           type empty;
         }
         leaf no-dump-on-flow-control {
           description "Don't enable dumping for this interface on prolonged flow-control";
           status deprecated;
           type empty;
         }
       }
       choice reset-on-flow-control-choice {
         leaf reset-on-flow-control {
           description "Enable resetting this interface on prolonged flow-control";
           status deprecated;
           type empty;
         }
         leaf no-reset-on-flow-control {
           description "Don't enable resetting this interface on prolonged flow-control";
           status deprecated;
           type empty;
         }
       }
       container flow-control-options {
         description "Flow control configuration";
         uses apply-advanced;
         leaf dump-on-flow-control {
           description "Cause core dump during prolonged flow-control";
           junos:must "(!(\".. up-on-flow-control\"))";
           junos:must-message "Option not valid with up-on-flow-control";
           junos:must "(!(\".. down-on-flow-control\"))";
           junos:must-message "Option not valid with down-on-flow-control";
           junos:must "(!(\".. reset-on-flow-control\"))";
           junos:must-message "Option not valid with reset-on-flow-control";
           type empty;
         }
         leaf reset-on-flow-control {
           description "Reset interface during prolonged flow-control";
           junos:must "(!(\".. up-on-flow-control\"))";
           junos:must-message "Option not valid with up-on-flow-control";
           junos:must "(!(\".. down-on-flow-control\"))";
           junos:must-message "Option not valid with down-on-flow-control";
           junos:must "(!(\".. dump-on-flow-control\"))";
           junos:must-message "Option not valid with dump-on-flow-control";
           type empty;
         }
         leaf down-on-flow-control {
           description "Bring interface down during prolonged flow-control";
           junos:must "(!(\".. up-on-flow-control\"))";
           junos:must-message "Option not valid with up-on-flow-control";
           junos:must "(!(\".. reset-on-flow-control\"))";
           junos:must-message "Option not valid with reset-on-flow-control";
           junos:must "(!(\".. dump-on-flow-control\"))";
           junos:must-message "Option not valid with dump-on-flow-control";
           type empty;
         }
         leaf up-on-flow-control {
           description "Keep interface up during prolonged flow-control";
           junos:must "(!(\".. down-on-flow-control\"))";
           junos:must-message "Option not valid with down-on-flow-control";
           junos:must "(!(\".. reset-on-flow-control\"))";
           junos:must-message "Option not valid with reset-on-flow-control";
           junos:must "(!(\".. dump-on-flow-control\"))";
           junos:must-message "Option not valid with dump-on-flow-control";
           type empty;
         }
       }
     }
     container ggsn-options {
       description "GGSN interface-specific options";
       uses apply-advanced;
       choice syslog-choice {
         leaf syslog {
           description "Enable system logging on this interface";
           type empty;
         }
         leaf no-syslog {
           description "Don't enable system logging on this interface";
           type empty;
         }
       }
       choice core-dump-choice {
         leaf core-dump {
           description "Enable core dumping on this interface";
           type empty;
         }
         leaf no-core-dump {
           description "Don't enable core dumping on this interface";
           type empty;
         }
       }
     }
     container ppp-options {
       description "Point-to-Point Protocol (PPP) interface-specific options";
       junos:must "((\".. encapsulation ppp\" || (\".. encapsulation ether-vpls-ppp\" || !(\".. encapsulation\"))))";
       junos:must-message "invalid encapsulation";
       uses ppp_options_type;
     }
     container lsq-failure-options {
       description "Link services queuing failure options";
       uses apply-advanced;
       list trigger-link-failure {
         key name;
         ordered-by user;
         junos:cli-feature "oneliner-plus";
         description "Link on which to trigger failure";
         leaf name {
           description "Interface name";
           junos:cli-feature "nokeyword";
           type union {
             type jt:interface-device;
             type string {
               pattern "<.*>|$.*";
             }
           }
         }
         uses apply-advanced;
       }
       choice no-termination-request-choice {
         leaf no-termination-request {
           description "Do not send PPP termination requests";
           type empty;
         }
         leaf no-no-termination-request {
           description "Don't do not send PPP termination requests";
           type empty;
         }
       }
     }
     container services-options {
       description "Services interface-specific options";
       uses apply-advanced;
       container syslog {
         description "Define system log parameters";
         uses log-object;
       }
       container jflow-log {
         description "Define Jflow-log parameters.";
         uses apply-advanced;
         leaf message-rate-limit {
           description "Maximum jflow-log NAT error events allowed per second from this interface";
           units "messages per second";
           type union {
             type string {
               pattern "<.*>|$.*";
             }
             type uint32 {
               range "1 .. 2147483647";
             }
           }
         }
       }
       container deterministic-nat-configuration-log-interval {
         presence "enable deterministic-nat-configuration-log-interval";
         description "Define Deterministic NAT parameters";
         uses apply-advanced;
         leaf interval {
           description "Interval in which deterministic NAT logs are generated";
           units "seconds";
           type union {
             type string {
               pattern "<.*>|$.*";
             }
             type uint32 {
               range "1800 .. 86400";
             }
           }
         }
       }
       leaf open-timeout {
         description "Timeout period for TCP session establishment";
         units "seconds";
         type union {
           type string {
             pattern "<.*>|$.*";
           }
           type uint32 {
             range "4 .. 300";
           }
         }
       }
       leaf close-timeout {
         description "Timeout period for TCP session tear-down";
         units "seconds";
         type union {
           type string {
             pattern "<.*>|$.*";
           }
           type uint32 {
             range "2 .. 300";
           }
         }
       }
       leaf inactivity-timeout {
         description "Inactivity timeout period for established sessions (4..86400)";
         units "seconds";
         type union {
           type uint32;
           type string {
             pattern "<.*>|$.*";
           }
         }
       }
       leaf inactivity-tcp-timeout {
         description "Inactivity timeout period for TCP established sessions";
         units "seconds";
         type union {
           type string {
             pattern "<.*>|$.*";
           }
           type uint32 {
             range "4 .. 86400";
           }
         }
       }
       leaf inactivity-asymm-tcp-timeout {
         description "Inactivity timeout period for asymmetric TCP established sessions";
         units "seconds";
         type union {
           type string {
             pattern "<.*>|$.*";
           }
           type uint32 {
             range "4 .. 86400";
           }
         }
       }
       leaf inactivity-non-tcp-timeout {
         description "Inactivity timeout period for non-TCP established sessions";
         units "seconds";
         type union {
           type string {
             pattern "<.*>|$.*";
           }
           type uint32 {
             range "4 .. 86400";
           }
         }
       }
       leaf session-timeout {
         description "Session timeout period for established sessions";
         units "seconds";
         type union {
           type string {
             pattern "<.*>|$.*";
           }
           type uint32 {
             range "4 .. 86400";
           }
         }
       }
       leaf disable-global-timeout-override {
         description "Disallow overriding  global inactivity or session timeout";
         type empty;
       }
       leaf tcp-tickles {
         description "Number of TCP keep-alive packets to be sent for bi-directional TCP flows";
         default "4";
         type union {
           type string {
             pattern "<.*>|$.*";
           }
           type uint8 {
             range "0 .. 30";
           }
         }
       }
       leaf fragment-limit {
         description "Maximum number of fragments allowed for a packet";
         default "64";
         type union {
           type string {
             pattern "<.*>|$.*";
           }
           type uint8 {
             range "1 .. 250";
           }
         }
       }
       leaf reassembly-timeout {
         description "Re-assembly timeout (seconds) for fragments of a packet";
         default "4";
         units "seconds";
         type union {
           type string {
             pattern "<.*>|$.*";
           }
           type uint8 {
             range "1 .. 60";
           }
         }
       }
       leaf cgn-pic {
         description "PIC will be used for Carrier Grade NAT configuration only";
         type empty;
       }
       leaf pba-interim-logging-interval {
         description "Interim logging interval in seconds";
         default "0";
         units "seconds";
         type union {
           type string {
             pattern "<.*>|$.*";
           }
           type uint32 {
             range "0 .. 86400";
           }
         }
       }
       container session-limit {
         presence "enable session-limit";
         description "Session limit";
         uses apply-advanced;
         leaf maximum {
           description "Maximum number of sessions allowed simultaneously";
           type string;
         }
         leaf rate {
           description "Maximum number of new sessions allowed per second";
           type string;
         }
         leaf cpu-load-threshold {
           description "CPU limit in percentage for auto-tuning of session rate";
           units "percent";
           type union {
             type string {
               pattern "<.*>|$.*";
             }
             type uint8 {
               range "1 .. 100";
             }
           }
         }
       }
       leaf enable-subscriber-analysis {
         description "Enable subscriber analysis on the interface";
         junos:must "(!(\".. disable-subscriber-analysis\"))";
         junos:must-message "can not set with enable-subscriber-analysis";
         type empty;
       }
       leaf disable-subscriber-analysis {
         description "Disable subscriber analysis on the interface";
         junos:must "(!(\".. enable-subscriber-analysis\"))";
         junos:must-message "can not set with disable-subscriber-analysis";
         type empty;
       }
       leaf disable-usp-tracing {
         description "Disable usp tracing on this pic";
         type empty;
       }
       leaf disable-drop-flows {
         description "Disable drop flows on this pic";
         type empty;
       }
       container ignore-errors {
         presence "enable ignore-errors";
         junos:cli-feature "oneliner";
         description "Ignore anomalies or errors";
         leaf tcp {
           description "TCP protocol errors";
           type empty;
         }
         leaf alg {
           description "ALG anomalies or errors";
           type empty;
         }
       }
       container capture {
         description "Packet capture for SFW and NAT on the Services PIC";
         uses apply-advanced;
         leaf capture-size {
           description "The number of packets to store";
           type union {
             type string {
               pattern "<.*>|$.*";
             }
             type uint32 {
               range "1 .. 344000";
             }
           }
         }
         leaf pkt-size {
           description "Number of bytes to be saved from each packet";
           type union {
             type string {
               pattern "<.*>|$.*";
             }
             type uint16 {
               range "64 .. 15000";
             }
           }
         }
         leaf logs-per-packet {
           description "The number of trace messages stored for each packet";
           type union {
             type string {
               pattern "<.*>|$.*";
             }
             type uint16 {
               range "0 .. 500";
             }
           }
         }
         leaf max-log-line-size {
           description "The maximum length of a stored trace message";
           type union {
             type uint8;
             type string {
               pattern "<.*>|$.*";
             }
           }
         }
         container filter {
           presence "enable filter";
           description "Filtering options for the packet capture";
           uses apply-advanced;
           container source-ip {
             junos:cli-feature "oneliner";
             description "Filter based on source-ip (and wildcard)";
             leaf ip {
               description "Source IP";
               junos:cli-feature "nokeyword";
               type jt:ipaddr;
             }
             leaf wildcard {
               description "Source IP wildcard";
               type jt:ipaddr;
             }
           }
           container dest-ip {
             junos:cli-feature "oneliner";
             description "Filter based on dest-ip (and wildcard)";
             leaf ip {
               description "Dest IP";
               junos:cli-feature "nokeyword";
               type jt:ipaddr;
             }
             leaf wildcard {
               description "Dest IP wildcard";
               type jt:ipaddr;
             }
           }
           container sw-sip {
             junos:cli-feature "oneliner";
             description "Filter based on source softwire ip (and wildcard)";
             leaf ip {
               description "Source softwire IP";
               junos:cli-feature "nokeyword";
               type jt:ipv6addr;
             }
             leaf wildcard {
               description "Source IP wildcard";
               type jt:ipv6addr;
             }
           }
           container sw-dip {
             junos:cli-feature "oneliner";
             description "Filter based on destination softwire ip (and wildcard)";
             leaf ip {
               description "Destination softwire IP";
               junos:cli-feature "nokeyword";
               type jt:ipaddr;
             }
             leaf wildcard {
               description "Destination IP wildcard";
               type jt:ipaddr;
             }
           }
           container sport-range {
             junos:cli-feature "oneliner";
             description "Filter based on source port";
             leaf low {
               description "Source port range start";
               type union {
                 type uint16;
                 type string {
                   pattern "<.*>|$.*";
                 }
               }
             }
             leaf high {
               description "Source port range end";
               type union {
                 type uint16;
                 type string {
                   pattern "<.*>|$.*";
                 }
               }
             }
           }
           container dport-range {
             junos:cli-feature "oneliner";
             description "Filter based on destination port";
             leaf low {
               description "Destination port range start";
               type union {
                 type uint16;
                 type string {
                   pattern "<.*>|$.*";
                 }
               }
             }
             leaf high {
               description "Destination port range end";
               type union {
                 type uint16;
                 type string {
                   pattern "<.*>|$.*";
                 }
               }
             }
           }
           leaf proto {
             description "Filter based on L4 protocol";
             type enumeration {
               enum "icmp" {
               }
               enum "tcp" {
               }
               enum "udp" {
               }
             }
           }
         }
       }
       container flow {
         description "Define flow parameters";
         uses apply-advanced;
         container traceoptions {
           description "Trace options for flow services";
         }
       }
       leaf fpc-pic-information {
         description "Include FPC and PIC slot number in the syslogs";
         type empty;
       }
       leaf utc-timestamp {
         description "Use UTC time for security log timestamps";
         type empty;
       }
       leaf syslog-local-system-timestamp {
         description "Use local system time for services syslog timestamp";
         type empty;
       }
     }
     container t3-options {
       junos:must "((!(\"interfaces ${interface} container-options\") || (\"interfaces ${interface} container-options container-type\" || \"interfaces ${interface} container-options allow-configuration-override\")))";
       junos:must-message "t1-options cannot be configured without allow-configuration-override";
       description "T3 interface-specific options";
       uses apply-advanced;
       leaf loopback {
         description "Loopback mode";
         type enumeration {
           enum "local" {
             description "Local loopback";
           }
           enum "remote" {
             description "Remote loopback";
           }
           enum "payload" {
             description "Payload loopback";
           }
         }
       }
       choice long-buildout-choice {
         leaf long-buildout {
           description "Set hardware to drive line longer than 255 feet";
           type empty;
         }
         leaf no-long-buildout {
           description "Don't set hardware to drive line longer than 255 feet";
           type empty;
         }
       }
       choice loop-timing-choice {
         leaf loop-timing {
           description "Set loop timing for T3";
           type empty;
         }
         leaf no-loop-timing {
           description "Don't set loop timing for T3";
           type empty;
         }
       }
       choice unframed-choice {
         leaf unframed {
           description "Enable unframed mode";
           type empty;
         }
         leaf no-unframed {
           description "Don't enable unframed mode";
           type empty;
         }
       }
       container compatibility-mode {
         junos:cli-feature "oneliner";
         description "Set CSU compatibility mode";
         choice vendor {
           case case_1 {
             container larscom {
               presence "enable larscom";
               junos:must "(!(\".. .. unframed\"))";
               junos:must-message "unframed and larscom cannot coexist";
               junos:cli-feature "oneliner";
               description "Compatible with Larscom CSU";
               leaf subrate {
                 description "Set subrate value";
                 type union {
                   type string {
                     pattern "<.*>|$.*";
                   }
                   type uint32 {
                     range "1 .. 14";
                   }
                 }
               }
             }
           }
           case case_2 {
             container verilink {
               presence "enable verilink";
               junos:must "(!(\".. .. unframed\"))";
               junos:must-message "unframed and verilink cannot coexist";
               junos:cli-feature "oneliner";
               description "Compatible with Verilink CSU (not on 2/4-port T3 PIC)";
               leaf subrate {
                 description "Set subrate value";
                 type union {
                   type string {
                     pattern "<.*>|$.*";
                   }
                   type uint32 {
                     range "1 .. 28";
                   }
                 }
               }
             }
           }
           case case_3 {
             container adtran {
               presence "enable adtran";
               junos:must "(!(\".. .. unframed\"))";
               junos:must-message "unframed and adtran cannot coexist";
               junos:cli-feature "oneliner";
               description "Compatible with Adtran CSU (not on 2/4-port T3 PIC)";
               leaf subrate {
                 description "Set subrate value";
                 type union {
                   type string {
                     pattern "<.*>|$.*";
                   }
                   type uint32 {
                     range "1 .. 588";
                   }
                 }
               }
             }
           }
           case case_4 {
             container kentrox {
               presence "enable kentrox";
               junos:cli-feature "oneliner";
               description "Compatible with Kentrox CSU";
               leaf subrate {
                 description "Set subrate value (not on 2/4-port T3 PIC)";
                 type union {
                   type string {
                     pattern "<.*>|$.*";
                   }
                   type uint32 {
                     range "1 .. 69";
                   }
                 }
               }
             }
           }
           case case_5 {
             container digital-link {
               presence "enable digital-link";
               junos:must "(!(\".. .. unframed\"))";
               junos:must-message "unframed and digital-link cannot coexist";
               junos:cli-feature "oneliner";
               description "Compatible with Digital Link CSU";
               leaf subrate {
                 description "Set subrate value";
                 type enumeration {
                   enum "301Kb" {
                     description "301 Kbps";
                   }
                   enum "601Kb" {
                     description "601 Kbps";
                   }
                   enum "902Kb" {
                     description "902 Kbps";
                   }
                   enum "1.2Mb" {
                     description "1.2 Mbps";
                   }
                   enum "1.5Mb" {
                     description "1.5 Mbps";
                   }
                   enum "1.8Mb" {
                     description "1.8 Mbps";
                   }
                   enum "2.1Mb" {
                     description "2.1 Mbps";
                   }
                   enum "2.4Mb" {
                     description "2.4 Mbps";
                   }
                   enum "2.7Mb" {
                     description "2.7 Mbps";
                   }
                   enum "3.0Mb" {
                     description "3.0 Mbps";
                   }
                   enum "3.3Mb" {
                     description "3.3 Mbps";
                   }
                   enum "3.6Mb" {
                     description "3.6 Mbps";
                   }
                   enum "3.9Mb" {
                     description "3.9 Mbps";
                   }
                   enum "4.2Mb" {
                     description "4.2 Mbps";
                   }
                   enum "4.5Mb" {
                     description "4.5 Mbps";
                   }
                   enum "4.8Mb" {
                     description "4.8 Mbps";
                   }
                   enum "5.1Mb" {
                     description "5.1 Mbps";
                   }
                   enum "5.4Mb" {
                     description "5.4 Mbps";
                   }
                   enum "5.7Mb" {
                     description "5.7 Mbps";
                   }
                   enum "6.0Mb" {
                     description "6.0 Mbps";
                   }
                   enum "6.3Mb" {
                     description "6.3 Mbps";
                   }
                   enum "6.6Mb" {
                     description "6.6 Mbps";
                   }
                   enum "6.9Mb" {
                     description "6.9 Mbps";
                   }
                   enum "7.2Mb" {
                     description "7.2 Mbps";
                   }
                   enum "7.5Mb" {
                     description "7.5 Mbps";
                   }
                   enum "7.8Mb" {
                     description "7.8 Mbps";
                   }
                   enum "8.1Mb" {
                     description "8.1 Mbps";
                   }
                   enum "8.4Mb" {
                     description "8.4 Mbps";
                   }
                   enum "8.7Mb" {
                     description "8.7 Mbps";
                   }
                   enum "9.0Mb" {
                     description "9.0 Mbps";
                   }
                   enum "9.3Mb" {
                     description "9.3 Mbps";
                   }
                   enum "9.6Mb" {
                     description "9.6 Mbps";
                   }
                   enum "9.9Mb" {
                     description "9.9 Mbps";
                   }
                   enum "10.2Mb" {
                     description "10.2 Mbps";
                   }
                   enum "10.5Mb" {
                     description "10.5 Mbps";
                   }
                   enum "10.8Mb" {
                     description "10.8 Mbps";
                   }
                   enum "11.1Mb" {
                     description "11.1 Mbps";
                   }
                   enum "11.4Mb" {
                     description "11.4 Mbps";
                   }
                   enum "11.7Mb" {
                     description "11.7 Mbps";
                   }
                   enum "12.0Mb" {
                     description "12.0 Mbps";
                   }
                   enum "12.3Mb" {
                     description "12.3 Mbps";
                   }
                   enum "12.6Mb" {
                     description "12.6 Mbps";
                   }
                   enum "12.9Mb" {
                     description "12.9 Mbps";
                   }
                   enum "13.2Mb" {
                     description "13.2 Mbps";
                   }
                   enum "13.5Mb" {
                     description "13.5 Mbps";
                   }
                   enum "13.8Mb" {
                     description "13.8 Mbps";
                   }
                   enum "14.1Mb" {
                     description "14.1 Mbps";
                   }
                   enum "14.4Mb" {
                     description "14.4 Mbps";
                   }
                   enum "14.7Mb" {
                     description "14.7 Mbps";
                   }
                   enum "15.0Mb" {
                     description "15.0 Mbps";
                   }
                   enum "15.3Mb" {
                     description "15.3 Mbps";
                   }
                   enum "15.6Mb" {
                     description "15.6 Mbps";
                   }
                   enum "15.9Mb" {
                     description "15.9 Mbps";
                   }
                   enum "16.2Mb" {
                     description "16.2 Mbps";
                   }
                   enum "16.5Mb" {
                     description "16.5 Mbps";
                   }
                   enum "16.8Mb" {
                     description "16.8 Mbps";
                   }
                   enum "17.1Mb" {
                     description "17.1 Mbps";
                   }
                   enum "17.4Mb" {
                     description "17.4 Mbps";
                   }
                   enum "17.7Mb" {
                     description "17.7 Mbps";
                   }
                   enum "18.0Mb" {
                     description "18.0 Mbps";
                   }
                   enum "18.3Mb" {
                     description "18.3 Mbps";
                   }
                   enum "18.6Mb" {
                     description "18.6 Mbps";
                   }
                   enum "18.9Mb" {
                     description "18.9 Mbps";
                   }
                   enum "19.2Mb" {
                     description "19.2 Mbps";
                   }
                   enum "19.5Mb" {
                     description "19.5 Mbps";
                   }
                   enum "19.8Mb" {
                     description "19.8 Mbps";
                   }
                   enum "20.1Mb" {
                     description "20.1 Mbps";
                   }
                   enum "20.5Mb" {
                     description "20.5 Mbps";
                   }
                   enum "20.8Mb" {
                     description "20.8 Mbps";
                   }
                   enum "21.1Mb" {
                     description "21.1 Mbps";
                   }
                   enum "21.4Mb" {
                     description "21.4 Mbps";
                   }
                   enum "21.7Mb" {
                     description "21.7 Mbps";
                   }
                   enum "22.0Mb" {
                     description "22.0 Mbps";
                   }
                   enum "22.3Mb" {
                     description "22.3 Mbps";
                   }
                   enum "22.6Mb" {
                     description "22.6 Mbps";
                   }
                   enum "22.9Mb" {
                     description "22.9 Mbps";
                   }
                   enum "23.2Mb" {
                     description "23.2 Mbps";
                   }
                   enum "23.5Mb" {
                     description "23.5 Mbps";
                   }
                   enum "23.8Mb" {
                     description "23.8 Mbps";
                   }
                   enum "24.1Mb" {
                     description "24.1 Mbps";
                   }
                   enum "24.4Mb" {
                     description "24.4 Mbps";
                   }
                   enum "24.7Mb" {
                     description "24.7 Mbps";
                   }
                   enum "25.0Mb" {
                     description "25.0 Mbps";
                   }
                   enum "25.3Mb" {
                     description "25.3 Mbps";
                   }
                   enum "25.6Mb" {
                     description "25.6 Mbps";
                   }
                   enum "25.9Mb" {
                     description "25.9 Mbps";
                   }
                   enum "26.2Mb" {
                     description "26.2 Mbps";
                   }
                   enum "26.5Mb" {
                     description "26.5 Mbps";
                   }
                   enum "26.8Mb" {
                     description "26.8 Mbps";
                   }
                   enum "27.1Mb" {
                     description "27.1 Mbps";
                   }
                   enum "27.4Mb" {
                     description "27.4 Mbps";
                   }
                   enum "27.7Mb" {
                     description "27.7 Mbps";
                   }
                   enum "28.0Mb" {
                     description "28.0 Mbps";
                   }
                   enum "28.3Mb" {
                     description "28.3 Mbps";
                   }
                   enum "28.6Mb" {
                     description "28.6 Mbps";
                   }
                   enum "28.9Mb" {
                     description "28.9 Mbps";
                   }
                   enum "29.2Mb" {
                     description "29.2 Mbps";
                   }
                   enum "29.5Mb" {
                     description "29.5 Mbps";
                   }
                   enum "29.8Mb" {
                     description "29.8 Mbps";
                   }
                   enum "30.1Mb" {
                     description "30.1 Mbps";
                   }
                   enum "30.4Mb" {
                     description "30.4 Mbps";
                   }
                   enum "30.7Mb" {
                     description "30.7 Mbps";
                   }
                   enum "31.0Mb" {
                     description "31.0 Mbps";
                   }
                   enum "31.3Mb" {
                     description "31.3 Mbps";
                   }
                   enum "31.6Mb" {
                     description "31.6 Mbps";
                   }
                   enum "31.9Mb" {
                     description "31.9 Mbps";
                   }
                   enum "32.2Mb" {
                     description "32.2 Mbps";
                   }
                   enum "32.5Mb" {
                     description "32.5 Mbps";
                   }
                   enum "32.8Mb" {
                     description "32.8 Mbps";
                   }
                   enum "33.1Mb" {
                     description "33.1 Mbps";
                   }
                   enum "33.4Mb" {
                     description "33.4 Mbps";
                   }
                   enum "33.7Mb" {
                     description "33.7 Mbps";
                   }
                   enum "34.0Mb" {
                     description "34.0 Mbps";
                   }
                   enum "34.3Mb" {
                     description "34.3 Mbps";
                   }
                   enum "34.6Mb" {
                     description "34.6 Mbps";
                   }
                   enum "34.9Mb" {
                     description "34.9 Mbps";
                   }
                   enum "35.2Mb" {
                     description "35.2 Mbps";
                   }
                   enum "35.5Mb" {
                     description "35.5 Mbps";
                   }
                   enum "35.8Mb" {
                     description "35.8 Mbps";
                   }
                   enum "36.1Mb" {
                     description "36.1 Mbps";
                   }
                   enum "36.4Mb" {
                     description "36.4 Mbps";
                   }
                   enum "36.7Mb" {
                     description "36.7 Mbps";
                   }
                   enum "37.0Mb" {
                     description "37.0 Mbps";
                   }
                   enum "37.3Mb" {
                     description "37.3 Mbps";
                   }
                   enum "37.6Mb" {
                     description "37.6 Mbps";
                   }
                   enum "37.9Mb" {
                     description "37.9 Mbps";
                   }
                   enum "38.2Mb" {
                     description "38.2 Mbps";
                   }
                   enum "38.5Mb" {
                     description "38.5 Mbps";
                   }
                   enum "38.8Mb" {
                     description "38.8 Mbps";
                   }
                   enum "39.1Mb" {
                     description "39.1 Mbps";
                   }
                   enum "39.4Mb" {
                     description "39.4 Mbps";
                   }
                   enum "39.7Mb" {
                     description "39.7 Mbps";
                   }
                   enum "40.0Mb" {
                     description "40.0 Mbps";
                   }
                   enum "40.3Mb" {
                     description "40.3 Mbps";
                   }
                   enum "40.6Mb" {
                     description "40.6 Mbps";
                   }
                   enum "40.9Mb" {
                     description "40.9 Mbps";
                   }
                   enum "41.2Mb" {
                     description "41.2 Mbps";
                   }
                   enum "41.5Mb" {
                     description "41.5 Mbps";
                   }
                   enum "41.8Mb" {
                     description "41.8 Mbps";
                   }
                   enum "42.1Mb" {
                     description "42.1 Mbps";
                   }
                   enum "42.4Mb" {
                     description "42.4 Mbps";
                   }
                   enum "42.7Mb" {
                     description "42.7 Mbps";
                   }
                   enum "43.0Mb" {
                     description "43.0 Mbps";
                   }
                   enum "43.3Mb" {
                     description "43.3 Mbps";
                   }
                   enum "43.6Mb" {
                     description "43.6 Mbps";
                   }
                   enum "43.9Mb" {
                     description "43.9 Mbps";
                   }
                   enum "44.2Mb" {
                     description "44.2 Mbps";
                   }
                 }
               }
             }
           }
         }
       }
       choice payload-scrambler-choice {
         leaf payload-scrambler {
           description "Enable payload scrambling";
           type empty;
         }
         leaf no-payload-scrambler {
           description "Don't enable payload scrambling";
           type empty;
         }
       }
       choice cbit-parity-choice {
         leaf cbit-parity {
           description "Enable C-bit parity mode";
           junos:must "(!(\".. unframed\"))";
           junos:must-message "cbit-parity and unframed cannot coexist";
           type empty;
         }
         leaf no-cbit-parity {
           description "Don't enable C-bit parity mode";
           junos:must "(!(\".. unframed\"))";
           junos:must-message "cbit-parity and unframed cannot coexist";
           type empty;
         }
       }
       leaf fcs {
         description "Frame checksum";
         type enumeration {
           enum "32" {
             description "32-bit mode";
           }
           enum "16" {
             description "16-bit mode";
           }
         }
       }
       leaf idle-cycle-flag {
         description "Value to transmit in idle cycles";
         type enumeration {
           enum "flags" {
             description "Transmit 0x7E in idle cycles";
           }
           enum "ones" {
             description "Transmit 0xFF (all ones) in idle cycles";
           }
         }
       }
       leaf start-end-flag {
         description "Set start/end flags on transmission";
         type enumeration {
           enum "shared" {
             description "Share start/end flags on transmit";
           }
           enum "filler" {
             description "Send two idle cycles between start/end flags";
           }
         }
       }
       choice feac-loop-respond-choice {
         leaf feac-loop-respond {
           description "Respond to FEAC loop requests";
           type empty;
         }
         leaf no-feac-loop-respond {
           description "Don't respond to FEAC loop requests";
           type empty;
         }
       }
       leaf bert-algorithm {
         description "Set BERT algorithm";
         type enumeration {
           enum "pseudo-2e3" {
             description "Pattern is 2^3 - 1";
           }
           enum "pseudo-2e4" {
             description "Pattern is 2^4 - 1";
           }
           enum "pseudo-2e5" {
             description "Pattern is 2^5 - 1";
           }
           enum "pseudo-2e6" {
             description "Pattern is 2^6 - 1";
           }
           enum "pseudo-2e7" {
             description "Pattern is 2^7 - 1";
           }
           enum "pseudo-2e9-o153" {
             description "Pattern is 2^9 - 1 (per O.153 standard)";
           }
           enum "pseudo-2e10" {
             description "Pattern is 2^10 - 1";
           }
           enum "pseudo-2e11-o152" {
             description "Pattern is 2^11 -1 (per O.152 standard)";
           }
           enum "pseudo-2e15-o151" {
             description "Pattern is 2^15 - 1 (per O.151 standard)";
           }
           enum "pseudo-2e17" {
             description "Pattern is 2^17 - 1";
           }
           enum "pseudo-2e18" {
             description "Pattern is 2^18 - 1";
           }
           enum "pseudo-2e20-o153" {
             description "Pattern is 2^20 - 1 (per O.153 standard)";
           }
           enum "pseudo-2e20-o151" {
             description "Pattern is 2^20 - 1 (per O.151 standard)";
           }
           enum "pseudo-2e21" {
             description "Pattern is 2^21 - 1";
           }
           enum "pseudo-2e22" {
             description "Pattern is 2^22 - 1";
           }
           enum "pseudo-2e23-o151" {
             description "Pattern is 2^23 (per O.151 standard)";
           }
           enum "pseudo-2e25" {
             description "Pattern is 2^25 - 1";
           }
           enum "pseudo-2e28" {
             description "Pattern is 2^28 - 1";
           }
           enum "pseudo-2e29" {
             description "Pattern is 2^29 - 1";
           }
           enum "pseudo-2e31" {
             description "Pattern is 2^31 - 1";
           }
           enum "pseudo-2e32" {
             description "Pattern is 2^32 - 1";
           }
           enum "all-ones-repeating" {
             description "Repeating one bits";
           }
           enum "all-zeros-repeating" {
             description "Repeating zero bits";
           }
           enum "alternating-ones-zeros" {
             description "Alternating ones and zeros";
           }
           enum "alternating-double-ones-zeros" {
             description "Alternating pairs of ones and zeros";
           }
           enum "repeating-3-in-24" {
             description "3 bits in 24 are set";
           }
           enum "repeating-1-in-8" {
             description "1 bit in 8 is set";
           }
           enum "repeating-1-in-4" {
             description "1 bit in 4 is set";
           }
         }
       }
       leaf bert-error-rate {
         description "Bit error rate (10^-n for n > 0, and zero for n = 0)";
         type union {
           type string {
             pattern "<.*>|$.*";
           }
           type uint32 {
             range "0 .. 7";
           }
         }
       }
       leaf bert-period {
         description "Length of BERT test";
         units "seconds";
         type union {
           type string {
             pattern "<.*>|$.*";
           }
           type uint32 {
             range "1 .. 240";
           }
         }
       }
       leaf buildout {
         description "Line buildout";
         units "feet";
         type union {
           type string {
             pattern "<.*>|$.*";
           }
           type uint32 {
             range "0 .. 450";
           }
         }
       }
       leaf atm-encapsulation {
         description "DS-3 interface encapsulation";
         type enumeration {
           enum "plcp" {
             description "PLCP encapsulation";
           }
           enum "direct" {
             description "ATM direct mapping";
           }
         }
       }
     }
     container e3-options {
       junos:must "((!(\"interfaces ${interface} container-options\") || (\"interfaces ${interface} container-options container-type\" || \"interfaces ${interface} container-options allow-configuration-override\")))";
       junos:must-message "t1-options cannot be configured without allow-configuration-override";
       description "E3 interface-specific options";
       uses apply-advanced;
       leaf loopback {
         description "Loopback mode";
         type enumeration {
           enum "local" {
             description "Local loopback";
           }
           enum "remote" {
             description "Remote loopback";
           }
         }
       }
       choice unframed-choice {
         leaf unframed {
           description "Enable unframed mode";
           type empty;
         }
         leaf no-unframed {
           description "Don't enable unframed mode";
           type empty;
         }
       }
       container compatibility-mode {
         junos:cli-feature "oneliner";
         description "Set CSU compatibility mode";
         choice vendor {
           case case_1 {
             leaf larscom {
               description "Compatible with Larscom CSU (only non IQ E3 interfaces)";
               type empty;
             }
           }
           case case_2 {
             container digital-link {
               presence "enable digital-link";
               junos:must "(!(\".. .. unframed\"))";
               junos:must-message "unframed and digital-link cannot coexist";
               junos:cli-feature "oneliner";
               description "Compatible with Digital Link CSU";
               leaf subrate {
                 description "Set subrate value";
                 type enumeration {
                   enum "358Kb" {
                     description "358 Kbps";
                   }
                   enum "716Kb" {
                     description "716 Kbps";
                   }
                   enum "1.1Mb" {
                     description "1.1 Mbps";
                   }
                   enum "1.4Mb" {
                     description "1.4 Mbps";
                   }
                   enum "1.8Mb" {
                     description "1.8 Mbps";
                   }
                   enum "2.1Mb" {
                     description "2.1 Mbps";
                   }
                   enum "2.5Mb" {
                     description "2.5 Mbps";
                   }
                   enum "2.9Mb" {
                     description "2.9 Mbps";
                   }
                   enum "3.2Mb" {
                     description "3.2 Mbps";
                   }
                   enum "3.6Mb" {
                     description "3.6 Mbps";
                   }
                   enum "3.9Mb" {
                     description "3.9 Mbps";
                   }
                   enum "4.3Mb" {
                     description "4.3 Mbps";
                   }
                   enum "4.7Mb" {
                     description "4.7 Mbps";
                   }
                   enum "5.0Mb" {
                     description "5.0 Mbps";
                   }
                   enum "5.4Mb" {
                     description "5.4 Mbps";
                   }
                   enum "5.7Mb" {
                     description "5.7 Mbps";
                   }
                   enum "6.1Mb" {
                     description "6.1 Mbps";
                   }
                   enum "6.4Mb" {
                     description "6.4 Mbps";
                   }
                   enum "6.8Mb" {
                     description "6.8 Mbps";
                   }
                   enum "7.2Mb" {
                     description "7.2 Mbps";
                   }
                   enum "7.5Mb" {
                     description "7.5 Mbps";
                   }
                   enum "7.9Mb" {
                     description "7.9 Mbps";
                   }
                   enum "8.2Mb" {
                     description "8.2 Mbps";
                   }
                   enum "8.6Mb" {
                     description "8.6 Mbps";
                   }
                   enum "9.0Mb" {
                     description "9.0 Mbps";
                   }
                   enum "9.3Mb" {
                     description "9.3 Mbps";
                   }
                   enum "9.7Mb" {
                     description "9.7 Mbps";
                   }
                   enum "10.0Mb" {
                     description "10.0 Mbps";
                   }
                   enum "10.4Mb" {
                     description "10.4 Mbps";
                   }
                   enum "10.7Mb" {
                     description "10.7 Mbps";
                   }
                   enum "11.1Mb" {
                     description "11.1 Mbps";
                   }
                   enum "11.5Mb" {
                     description "11.5 Mbps";
                   }
                   enum "11.8Mb" {
                     description "11.8 Mbps";
                   }
                   enum "12.2Mb" {
                     description "12.2 Mbps";
                   }
                   enum "12.5Mb" {
                     description "12.5 Mbps";
                   }
                   enum "12.9Mb" {
                     description "12.9 Mbps";
                   }
                   enum "13.2Mb" {
                     description "13.2 Mbps";
                   }
                   enum "13.6Mb" {
                     description "13.6 Mbps";
                   }
                   enum "14.0Mb" {
                     description "14.0 Mbps";
                   }
                   enum "14.3Mb" {
                     description "14.3 Mbps";
                   }
                   enum "14.7Mb" {
                     description "14.7 Mbps";
                   }
                   enum "15.0Mb" {
                     description "15.0 Mbps";
                   }
                   enum "15.4Mb" {
                     description "15.4 Mbps";
                   }
                   enum "15.8Mb" {
                     description "15.8 Mbps";
                   }
                   enum "16.1Mb" {
                     description "16.1 Mbps";
                   }
                   enum "16.5Mb" {
                     description "16.5 Mbps";
                   }
                   enum "16.8Mb" {
                     description "16.8 Mbps";
                   }
                   enum "17.2Mb" {
                     description "17.2 Mbps";
                   }
                   enum "17.5Mb" {
                     description "17.5 Mbps";
                   }
                   enum "17.9Mb" {
                     description "17.9 Mbps";
                   }
                   enum "18.3Mb" {
                     description "18.3 Mbps";
                   }
                   enum "18.6Mb" {
                     description "18.6 Mbps";
                   }
                   enum "19.0Mb" {
                     description "19.0 Mbps";
                   }
                   enum "19.3Mb" {
                     description "19.3 Mbps";
                   }
                   enum "19.7Mb" {
                     description "19.7 Mbps";
                   }
                   enum "20.0Mb" {
                     description "20.0 Mbps";
                   }
                   enum "20.4Mb" {
                     description "20.4 Mbps";
                   }
                   enum "20.8Mb" {
                     description "20.8 Mbps";
                   }
                   enum "21.1Mb" {
                     description "21.1 Mbps";
                   }
                   enum "21.5Mb" {
                     description "21.5 Mbps";
                   }
                   enum "21.8Mb" {
                     description "21.8 Mbps";
                   }
                   enum "22.2Mb" {
                     description "22.2 Mbps";
                   }
                   enum "22.6Mb" {
                     description "22.6 Mbps";
                   }
                   enum "22.9Mb" {
                     description "22.9 Mbps";
                   }
                   enum "23.3Mb" {
                     description "23.3 Mbps";
                   }
                   enum "23.6Mb" {
                     description "23.6 Mbps";
                   }
                   enum "24.0Mb" {
                     description "24.0 Mbps";
                   }
                   enum "24.3Mb" {
                     description "24.3 Mbps";
                   }
                   enum "24.7Mb" {
                     description "24.7 Mbps";
                   }
                   enum "25.1Mb" {
                     description "25.1 Mbps";
                   }
                   enum "25.4Mb" {
                     description "25.4 Mbps";
                   }
                   enum "25.8Mb" {
                     description "25.8 Mbps";
                   }
                   enum "26.1Mb" {
                     description "26.1 Mbps";
                   }
                   enum "26.5Mb" {
                     description "26.5 Mbps";
                   }
                   enum "26.9Mb" {
                     description "26.9 Mbps";
                   }
                   enum "27.2Mb" {
                     description "27.2 Mbps";
                   }
                   enum "27.6Mb" {
                     description "27.6 Mbps";
                   }
                   enum "27.9Mb" {
                     description "27.9 Mbps";
                   }
                   enum "28.3Mb" {
                     description "28.3 Mbps";
                   }
                   enum "28.6Mb" {
                     description "28.6 Mbps";
                   }
                   enum "29.0Mb" {
                     description "29.0 Mbps";
                   }
                   enum "29.4Mb" {
                     description "29.4 Mbps";
                   }
                   enum "29.7Mb" {
                     description "29.7 Mbps";
                   }
                   enum "30.1Mb" {
                     description "30.1 Mbps";
                   }
                   enum "30.4Mb" {
                     description "30.4 Mbps";
                   }
                   enum "30.8Mb" {
                     description "30.8 Mbps";
                   }
                   enum "31.1Mb" {
                     description "31.1 Mbps";
                   }
                   enum "31.5Mb" {
                     description "31.5 Mbps";
                   }
                   enum "31.9Mb" {
                     description "31.9 Mbps";
                   }
                   enum "32.2Mb" {
                     description "32.2 Mbps";
                   }
                   enum "32.6Mb" {
                     description "32.6 Mbps";
                   }
                   enum "32.9Mb" {
                     description "32.9 Mbps";
                   }
                   enum "33.3Mb" {
                     description "33.3 Mbps";
                   }
                   enum "33.7Mb" {
                     description "33.7 Mbps";
                   }
                   enum "34.0Mb" {
                     description "34.0 Mbps";
                   }
                 }
               }
             }
           }
           case case_3 {
             container kentrox {
               presence "enable kentrox";
               junos:cli-feature "oneliner";
               description "Compatible with Kentrox CSU";
               leaf subrate {
                 description "Set subrate value (only for E3 IQ interfaces)";
                 type union {
                   type string {
                     pattern "<.*>|$.*";
                   }
                   type uint32 {
                     range "1 .. 48";
                   }
                 }
               }
             }
           }
         }
       }
       choice payload-scrambler-choice {
         leaf payload-scrambler {
           description "Enable payload scrambling";
           type empty;
         }
         leaf no-payload-scrambler {
           description "Don't enable payload scrambling";
           type empty;
         }
       }
       leaf fcs {
         description "Frame checksum";
         type enumeration {
           enum "32" {
             description "32-bit mode";
           }
           enum "16" {
             description "16-bit mode";
           }
         }
       }
       leaf idle-cycle-flag {
         description "Value to transmit in idle cycles";
         type enumeration {
           enum "flags" {
             description "Transmit 0x7E in idle cycles";
           }
           enum "ones" {
             description "Transmit 0xFF (all ones) in idle cycles";
           }
         }
       }
       leaf invert-data {
         description "Invert data";
         type empty;
       }
       leaf start-end-flag {
         description "Set start/end flags on transmission";
         type enumeration {
           enum "shared" {
             description "Share start/end flags on transmit";
           }
           enum "filler" {
             description "Send two idle cycles between start/end flags";
           }
         }
       }
       leaf bert-algorithm {
         description "Set BERT algorithm";
         type enumeration {
           enum "pseudo-2e3" {
             description "Pattern is 2^3 - 1";
           }
           enum "pseudo-2e4" {
             description "Pattern is 2^4 - 1";
           }
           enum "pseudo-2e5" {
             description "Pattern is 2^5 - 1";
           }
           enum "pseudo-2e6" {
             description "Pattern is 2^6 - 1";
           }
           enum "pseudo-2e7" {
             description "Pattern is 2^7 - 1";
           }
           enum "pseudo-2e9-o153" {
             description "Pattern is 2^9 - 1 (per O.153 standard)";
           }
           enum "pseudo-2e10" {
             description "Pattern is 2^10 - 1";
           }
           enum "pseudo-2e11-o152" {
             description "Pattern is 2^11 -1 (per O.152 standard)";
           }
           enum "pseudo-2e15-o151" {
             description "Pattern is 2^15 - 1 (per O.151 standard)";
           }
           enum "pseudo-2e17" {
             description "Pattern is 2^17 - 1";
           }
           enum "pseudo-2e18" {
             description "Pattern is 2^18 - 1";
           }
           enum "pseudo-2e20-o153" {
             description "Pattern is 2^20 - 1 (per O.153 standard)";
           }
           enum "pseudo-2e20-o151" {
             description "Pattern is 2^20 - 1 (per O.151 standard)";
           }
           enum "pseudo-2e21" {
             description "Pattern is 2^21 - 1";
           }
           enum "pseudo-2e22" {
             description "Pattern is 2^22 - 1";
           }
           enum "pseudo-2e23-o151" {
             description "Pattern is 2^23 (per O.151 standard)";
           }
           enum "pseudo-2e25" {
             description "Pattern is 2^25 - 1";
           }
           enum "pseudo-2e28" {
             description "Pattern is 2^28 - 1";
           }
           enum "pseudo-2e29" {
             description "Pattern is 2^29 - 1";
           }
           enum "pseudo-2e31" {
             description "Pattern is 2^31 - 1";
           }
           enum "pseudo-2e32" {
             description "Pattern is 2^32 - 1";
           }
           enum "all-ones-repeating" {
             description "Repeating one bits";
           }
           enum "all-zeros-repeating" {
             description "Repeating zero bits";
           }
           enum "alternating-ones-zeros" {
             description "Alternating ones and zeros";
           }
           enum "alternating-double-ones-zeros" {
             description "Alternating pairs of ones and zeros";
           }
           enum "repeating-3-in-24" {
             description "3 bits in 24 are set";
           }
           enum "repeating-1-in-8" {
             description "1 bit in 8 is set";
           }
           enum "repeating-1-in-4" {
             description "1 bit in 4 is set";
           }
         }
       }
       leaf bert-error-rate {
         description "Bit error rate (10^-n for n > 0, and zero for n = 0)";
         type union {
           type string {
             pattern "<.*>|$.*";
           }
           type uint32 {
             range "0 .. 7";
           }
         }
       }
       leaf bert-period {
         description "Length of BERT test";
         units "seconds";
         type union {
           type string {
             pattern "<.*>|$.*";
           }
           type uint32 {
             range "1 .. 240";
           }
         }
       }
       leaf buildout {
         description "Line buildout";
         units "feet";
         type union {
           type string {
             pattern "<.*>|$.*";
           }
           type uint32 {
             range "0 .. 450";
           }
         }
       }
       leaf atm-encapsulation {
         description "E3 interface encapsulation";
         type enumeration {
           enum "plcp" {
             description "PLCP encapsulation";
           }
           enum "direct" {
             description "ATM direct mapping";
           }
         }
       }
       leaf framing {
         description "E3 line format";
         type enumeration {
           enum "g.751" {
             description "G.751 format";
           }
           enum "g.832" {
             description "G.832 format";
           }
         }
       }
     }
     container e1-options {
       junos:must "((!(\"interfaces ${interface} container-options\") || (\"interfaces ${interface} container-options container-type\" || \"interfaces ${interface} container-options allow-configuration-override\")))";
       junos:must-message "e1-options cannot be configured without allow-configuration-override";
       description "E1 interface-specific options";
       uses apply-advanced;
       leaf timeslots {
         description "Timeslots (1..32); for example, 1-4,6,9-11,32 (no space)";
         type string;
       }
       leaf loopback {
         description "Loopback mode";
         type enumeration {
           enum "local" {
             description "Local loopback";
           }
           enum "remote" {
             description "Remote loopback";
           }
         }
       }
       leaf framing {
         description "Framing mode";
         type enumeration {
           enum "g704" {
             description "G704 mode with CRC4";
           }
           enum "unframed" {
             description "Unframed mode";
           }
           enum "g704-no-crc4" {
             description "G704 mode without CRC4";
           }
         }
       }
       leaf fcs {
         description "Frame checksum";
         type enumeration {
           enum "32" {
             description "32-bit mode";
           }
           enum "16" {
             description "16-bit mode";
           }
         }
       }
       leaf invert-data {
         description "Invert data";
         type empty;
       }
       leaf idle-cycle-flag {
         description "Value to transmit in idle cycles";
         type enumeration {
           enum "flags" {
             description "Transmit 0x7E in idle cycles";
           }
           enum "ones" {
             description "Transmit 0xFF (all ones) in idle cycles";
           }
         }
       }
       leaf start-end-flag {
         description "Set start/end flags on transmission";
         type enumeration {
           enum "shared" {
             description "Share start/end flags on transmit";
           }
           enum "filler" {
             description "Send two idle cycles between start/end flags";
           }
         }
       }
       leaf bert-algorithm {
         description "Set BERT algorithm";
         type enumeration {
           enum "pseudo-2e3" {
             description "Pattern is 2^3 - 1";
           }
           enum "pseudo-2e4" {
             description "Pattern is 2^4 - 1";
           }
           enum "pseudo-2e5" {
             description "Pattern is 2^5 - 1";
           }
           enum "pseudo-2e6" {
             description "Pattern is 2^6 - 1";
           }
           enum "pseudo-2e7" {
             description "Pattern is 2^7 - 1";
           }
           enum "pseudo-2e9-o153" {
             description "Pattern is 2^9 - 1 (per O.153 standard)";
           }
           enum "pseudo-2e10" {
             description "Pattern is 2^10 - 1";
           }
           enum "pseudo-2e11-o152" {
             description "Pattern is 2^11 -1 (per O.152 standard)";
           }
           enum "pseudo-2e15-o151" {
             description "Pattern is 2^15 - 1 (per O.151 standard)";
           }
           enum "pseudo-2e17" {
             description "Pattern is 2^17 - 1";
           }
           enum "pseudo-2e18" {
             description "Pattern is 2^18 - 1";
           }
           enum "pseudo-2e20-o153" {
             description "Pattern is 2^20 - 1 (per O.153 standard)";
           }
           enum "pseudo-2e20-o151" {
             description "Pattern is 2^20 - 1 (per O.151 standard)";
           }
           enum "pseudo-2e21" {
             description "Pattern is 2^21 - 1";
           }
           enum "pseudo-2e22" {
             description "Pattern is 2^22 - 1";
           }
           enum "pseudo-2e23-o151" {
             description "Pattern is 2^23 (per O.151 standard)";
           }
           enum "pseudo-2e25" {
             description "Pattern is 2^25 - 1";
           }
           enum "pseudo-2e28" {
             description "Pattern is 2^28 - 1";
           }
           enum "pseudo-2e29" {
             description "Pattern is 2^29 - 1";
           }
           enum "pseudo-2e31" {
             description "Pattern is 2^31 - 1";
           }
           enum "pseudo-2e32" {
             description "Pattern is 2^32 - 1";
           }
           enum "all-ones-repeating" {
             description "Repeating one bits";
           }
           enum "all-zeros-repeating" {
             description "Repeating zero bits";
           }
           enum "alternating-ones-zeros" {
             description "Alternating ones and zeros";
           }
           enum "alternating-double-ones-zeros" {
             description "Alternating pairs of ones and zeros";
           }
           enum "repeating-3-in-24" {
             description "3 bits in 24 are set";
           }
           enum "repeating-1-in-8" {
             description "1 bit in 8 is set";
           }
           enum "repeating-1-in-4" {
             description "1 bit in 4 is set";
           }
         }
       }
       leaf bert-error-rate {
         description "Bit error rate (10^-n for n > 0, and zero for n = 0)";
         type union {
           type string {
             pattern "<.*>|$.*";
           }
           type uint32 {
             range "0 .. 7";
           }
         }
       }
       leaf bert-period {
         description "Length of BERT test";
         units "seconds";
         type union {
           type string {
             pattern "<.*>|$.*";
           }
           type uint32 {
             range "1 .. 86400";
           }
         }
       }
     }
     container t1-options {
       junos:must "((!(\"interfaces ${interface} container-options\") || (\"interfaces ${interface} container-options container-type\" || \"interfaces ${interface} container-options allow-configuration-override\")))";
       junos:must-message "t1-options cannot be configured without allow-configuration-override";
       description "T1 interface-specific options";
       uses apply-advanced;
       leaf timeslots {
         description "Timeslots (1..24; for example, 1-3,4,9,22-24 (no space)";
         type string;
       }
       leaf voice-timeslots {
         description "Voice timeslots (1..24),for example, 1-3,4,9,22-24 (no space)";
         type string;
       }
       leaf loopback {
         description "Loopback mode";
         type enumeration {
           enum "local" {
             description "Local loopback";
           }
           enum "remote" {
             description "Remote loopback";
           }
           enum "payload" {
             description "Payload loopback";
           }
         }
       }
       leaf buildout {
         description "Line buildout";
         type enumeration {
           enum "0-132" {
             description "Line buildout is between 0-132 feet";
           }
           enum "133-265" {
             description "Line buildout is between 133-265 feet";
           }
           enum "266-398" {
             description "Line buildout is between 266-398 feet";
           }
           enum "399-531" {
             description "Line buildout is between 399-531 feet";
           }
           enum "532-655" {
             description "Line buildout is between 532-655 feet";
           }
           enum "long-0db" {
             description "Long buildout with 0 dB transmit attenuation";
           }
           enum "long-7.5db" {
             description "Long buildout with 7.5 dB transmit attenuation";
           }
           enum "long-15db" {
             description "Long buildout with 15 dB transmit attenuation";
           }
           enum "long-22.5db" {
             description "Long buildout with 22.5 dB transmit attenuation";
           }
         }
       }
       leaf byte-encoding {
         description "Byte encoding";
         type enumeration {
           enum "nx64" {
             description "8 bits per byte";
           }
           enum "nx56" {
             description "7 bits per byte";
           }
         }
       }
       leaf line-encoding {
         description "Line encoding";
         type enumeration {
           enum "ami" {
             description "Automatic mark inversion";
           }
           enum "b8zs" {
             description "8-bit zero suppression";
           }
         }
       }
       leaf invert-data {
         description "Invert data";
         type empty;
       }
       leaf framing {
         description "Framing mode";
         type enumeration {
           enum "sf" {
             description "Super frame";
           }
           enum "esf" {
             description "Extended super frame";
           }
         }
       }
       leaf fcs {
         description "Frame checksum";
         type enumeration {
           enum "32" {
             description "32-bit mode";
           }
           enum "16" {
             description "16-bit mode";
           }
         }
       }
       leaf idle-cycle-flag {
         description "Value to transmit in idle cycles";
         type enumeration {
           enum "flags" {
             description "Transmit 0x7E in idle cycles";
           }
           enum "ones" {
             description "Transmit 0xFF (all ones) in idle cycles";
           }
         }
       }
       leaf start-end-flag {
         description "Set start/end flags on transmission";
         type enumeration {
           enum "shared" {
             description "Share start/end flags on transmit";
           }
           enum "filler" {
             description "Send two idle cycles between start/end flags";
           }
         }
       }
       leaf bert-algorithm {
         description "Set BERT algorithm";
         type enumeration {
           enum "pseudo-2e3" {
             description "Pattern is 2^3 - 1";
           }
           enum "pseudo-2e4" {
             description "Pattern is 2^4 - 1";
           }
           enum "pseudo-2e5" {
             description "Pattern is 2^5 - 1";
           }
           enum "pseudo-2e6" {
             description "Pattern is 2^6 - 1";
           }
           enum "pseudo-2e7" {
             description "Pattern is 2^7 - 1";
           }
           enum "pseudo-2e9-o153" {
             description "Pattern is 2^9 - 1 (per O.153 standard)";
           }
           enum "pseudo-2e10" {
             description "Pattern is 2^10 - 1";
           }
           enum "pseudo-2e11-o152" {
             description "Pattern is 2^11 -1 (per O.152 standard)";
           }
           enum "pseudo-2e15-o151" {
             description "Pattern is 2^15 - 1 (per O.151 standard)";
           }
           enum "pseudo-2e17" {
             description "Pattern is 2^17 - 1";
           }
           enum "pseudo-2e18" {
             description "Pattern is 2^18 - 1";
           }
           enum "pseudo-2e20-o153" {
             description "Pattern is 2^20 - 1 (per O.153 standard)";
           }
           enum "pseudo-2e20-o151" {
             description "Pattern is 2^20 - 1 (per O.151 standard)";
           }
           enum "pseudo-2e21" {
             description "Pattern is 2^21 - 1";
           }
           enum "pseudo-2e22" {
             description "Pattern is 2^22 - 1";
           }
           enum "pseudo-2e23-o151" {
             description "Pattern is 2^23 (per O.151 standard)";
           }
           enum "pseudo-2e25" {
             description "Pattern is 2^25 - 1";
           }
           enum "pseudo-2e28" {
             description "Pattern is 2^28 - 1";
           }
           enum "pseudo-2e29" {
             description "Pattern is 2^29 - 1";
           }
           enum "pseudo-2e31" {
             description "Pattern is 2^31 - 1";
           }
           enum "pseudo-2e32" {
             description "Pattern is 2^32 - 1";
           }
           enum "all-ones-repeating" {
             description "Repeating one bits";
           }
           enum "all-zeros-repeating" {
             description "Repeating zero bits";
           }
           enum "alternating-ones-zeros" {
             description "Alternating ones and zeros";
           }
           enum "alternating-double-ones-zeros" {
             description "Alternating pairs of ones and zeros";
           }
           enum "repeating-3-in-24" {
             description "3 bits in 24 are set";
           }
           enum "repeating-1-in-8" {
             description "1 bit in 8 is set";
           }
           enum "repeating-1-in-4" {
             description "1 bit in 4 is set";
           }
         }
       }
       leaf bert-error-rate {
         description "Bit error rate (10^-n for n > 0, and zero for n = 0)";
         type union {
           type string {
             pattern "<.*>|$.*";
           }
           type uint32 {
             range "0 .. 7";
           }
         }
       }
       leaf bert-period {
         description "Length of BERT test";
         units "seconds";
         type union {
           type string {
             pattern "<.*>|$.*";
           }
           type uint32 {
             range "1 .. 86400";
           }
         }
       }
       leaf remote-loopback-respond {
         description "Respond to loop requests from remote end";
         type empty;
       }
       leaf crc-major-alarm-threshold {
         description "CRC Major alarm threshold value";
         default "5e-5";
         type enumeration {
           enum "1e-3" {
             description "1 crc error in 10^3 bits";
           }
           enum "5e-4" {
             description "5 crc errors in 10^4 bits";
           }
           enum "1e-4" {
             description "1 crc error in 10^4 bits";
           }
           enum "5e-5" {
             description "5 crc errors in 10^5 bits";
           }
           enum "1e-5" {
             description "1 crc error in 10^5 bits";
           }
         }
       }
       leaf crc-minor-alarm-threshold {
         description "CRC Minor alarm threshold value";
         default "5e-6";
         type enumeration {
           enum "1e-3" {
             description "1 crc error in 10^3 bits";
           }
           enum "5e-4" {
             description "5 crc errors in 10^4 bits";
           }
           enum "1e-4" {
             description "1 crc error in 10^4 bits";
           }
           enum "5e-5" {
             description "5 crc errors in 10^5 bits";
           }
           enum "1e-5" {
             description "1 crc error in 10^5 bits";
           }
           enum "5e-6" {
             description "5 crc errors in 10^6 bits";
           }
           enum "1e-6" {
             description "1 crc error in 10^6 bits";
           }
         }
       }
       leaf alarm-compliance {
         description "Enforce standard for alarm reporting";
         type enumeration {
           enum "accunet-t1-5-service" {
             description "T1.5 interface specification";
           }
         }
       }
     }
     container ds0-options {
       junos:must "((!(\"interfaces ${interface} container-options\") || (\"interfaces ${interface} container-options container-type\" || \"interfaces ${interface} container-options allow-configuration-override\")))";
       junos:must-message "ds0-options cannot be configured without allow-configuration-override";
       description "DS-0 interface-specific options";
       uses apply-advanced;
       leaf loopback {
         description "Loopback mode";
         type enumeration {
           enum "payload" {
             description "Payload loopback";
           }
         }
       }
       leaf byte-encoding {
         description "Byte encoding";
         type enumeration {
           enum "nx64" {
             description "8 bits per byte";
           }
           enum "nx56" {
             description "7 bits per byte";
           }
         }
       }
       leaf invert-data {
         description "Invert data";
         type empty;
       }
       leaf fcs {
         description "Frame checksum";
         type enumeration {
           enum "32" {
             description "32-bit mode";
           }
           enum "16" {
             description "16-bit mode";
           }
         }
       }
       leaf idle-cycle-flag {
         description "Value to transmit in idle cycles";
         type enumeration {
           enum "flags" {
             description "Transmit 0x7E in idle cycles";
           }
           enum "ones" {
             description "Transmit 0xFF (all ones) in idle cycles";
           }
         }
       }
       leaf start-end-flag {
         description "Set start/end flags on transmission";
         type enumeration {
           enum "shared" {
             description "Share start/end flags on transmit";
           }
           enum "filler" {
             description "Send two idle cycles between start/end flags";
           }
         }
       }
       leaf bert-algorithm {
         description "Set BERT algorithm";
         type enumeration {
           enum "pseudo-2e11-o152" {
             description "Pattern is 2^11 -1 (per O.152 standard)";
           }
           enum "pseudo-2e15-o151" {
             description "Pattern is 2^15 - 1 (per O.151 standard)";
           }
           enum "pseudo-2e20-o153" {
             description "Pattern is 2^20 - 1 (per O.153 standard)";
           }
           enum "pseudo-2e20-o151" {
             description "Pattern is 2^20 - 1 (per O.151 standard)";
           }
           enum "all-ones-repeating" {
             description "Repeating one bits";
           }
           enum "all-zeros-repeating" {
             description "Repeating zero bits";
           }
           enum "alternating-ones-zeros" {
             description "Alternating ones and zeros";
           }
           enum "alternating-double-ones-zeros" {
             description "Alternating pairs of ones and zeros";
           }
           enum "repeating-3-in-24" {
             description "3 bits in 24 are set";
           }
           enum "repeating-1-in-8" {
             description "1 bit in 8 is set";
           }
           enum "repeating-1-in-4" {
             description "1 bit in 4 is set";
           }
           enum "repeating-1-in-16" {
             description "1 bit in 16 is set";
           }
         }
       }
       leaf bert-error-rate {
         description "Bit error rate (10^-n for n > 0, and zero for n = 0)";
         type union {
           type string {
             pattern "<.*>|$.*";
           }
           type uint32 {
             range "0 .. 7";
           }
         }
       }
       leaf bert-period {
         description "Length of BERT test";
         units "seconds";
         type union {
           type string {
             pattern "<.*>|$.*";
           }
           type uint32 {
             range "1 .. 240";
           }
         }
       }
     }
     container serial-options {
       description "Serial interface-specific options";
       uses apply-advanced;
       leaf line-protocol {
         description "Line protocol to be used";
         default "eia530";
         type enumeration {
           enum "eia530" {
             description "Line protocol EIA530";
           }
           enum "v.35" {
             description "Line protocol V.35";
           }
           enum "x.21" {
             description "Line protocol X.21";
           }
         }
       }
       choice control_leads_choice {
         case case_1 {
           container dte-options {
             description "DTE options/control leads";
             uses apply-advanced;
             leaf ignore-all {
               description "Ignore all control leads";
               junos:must "(!(\".. indication\"))";
               junos:must-message "SERIAL: ignore-all configured when indication explicitly configured";
               junos:must "(!(\".. cts\"))";
               junos:must-message "SERIAL: ignore-all configured when cts explicitly configured";
               junos:must "(!(\".. dsr\"))";
               junos:must-message "SERIAL: ignore-all configured when dsr explicitly configured";
               junos:must "(!(\".. tm\"))";
               junos:must-message "SERIAL: ignore-all configured when tm explicitly configured";
               junos:must "(!(\".. dcd\"))";
               junos:must-message "SERIAL: ignore-all configured when dcd explicitly configured";
               type empty;
             }
             container dtr {
               junos:cli-feature "oneliner";
               description "Data Transmit Ready signal handling";
               choice dtr_choices {
                 case case_1 {
                   leaf assert {
                     description "Assert DTR signal";
                     type empty;
                   }
                 }
                 case case_2 {
                   leaf de-assert {
                     description "Deassert DTR signal";
                     type empty;
                   }
                 }
                 case case_3 {
                   leaf normal {
                     description "Normal DTR signal";
                     type empty;
                   }
                 }
                 case case_4 {
                   container auto-synchronize {
                     presence "enable auto-synchronize";
                     description "Normal DTR signal, with autoresynchronization";
                     uses apply-advanced;
                     leaf duration {
                       description "Duration of autoresynchronization";
                       units "milliseconds";
                       type union {
                         type string {
                           pattern "<.*>|$.*";
                         }
                         type uint16 {
                           range "1 .. 1000";
                         }
                       }
                     }
                     leaf interval {
                       description "Interval for autoresynchronization";
                       units "seconds";
                       type union {
                         type string {
                           pattern "<.*>|$.*";
                         }
                         type uint16 {
                           range "1 .. 31";
                         }
                       }
                     }
                   }
                 }
               }
             }
             leaf control-signal {
               description "X.21 control signal handling";
               junos:must "(!(\".. .. line-protocol eia530\"))";
               junos:must-message "Control signal  invalid on line-protocol eia530";
               junos:must "(!(\".. .. line-protocol v.35\"))";
               junos:must-message "Control signal invalid on line-protocol v.35";
               type enumeration {
                 enum "assert" {
                   description "Assert control signal";
                 }
                 enum "de-assert" {
                   description "Deassert control signal";
                 }
                 enum "normal" {
                   description "Normal control signal";
                 }
               }
             }
             leaf rts {
               description "Request To Send signal handling";
               junos:must "(!(\".. .. line-protocol x.21\"))";
               junos:must-message "rts invalid on line-protocol x.21";
               type enumeration {
                 enum "assert" {
                   description "Assert RTS signal";
                 }
                 enum "de-assert" {
                   description "Deassert RTS signal";
                 }
                 enum "normal" {
                   description "Normal RTS signal";
                 }
               }
             }
             leaf dcd {
               description "Data Carrier Detect signal handling";
               type enumeration {
                 enum "require" {
                   description "Require DCD signal";
                 }
                 enum "ignore" {
                   description "Ignore DCD signal";
                 }
                 enum "normal" {
                   description "Normal DCD signal";
                 }
               }
             }
             leaf dsr {
               description "Data Set Ready signal handling";
               type enumeration {
                 enum "require" {
                   description "Require DSR signal";
                 }
                 enum "ignore" {
                   description "Ignore DSR signal";
                 }
                 enum "normal" {
                   description "Normal DSR signal";
                 }
               }
             }
             leaf cts {
               description "Clear To Send signal handling";
               junos:must "(!(\".. .. line-protocol x.21\"))";
               junos:must-message "cts invalid on line-protocol x.21";
               type enumeration {
                 enum "require" {
                   description "Require CTS signal";
                 }
                 enum "ignore" {
                   description "Ignore CTS signal";
                 }
                 enum "normal" {
                   description "Normal CTS signal";
                 }
               }
             }
             leaf indication {
               description "X.21 Indication signal handling";
               junos:must "(!(\".. .. line-protocol eia530\"))";
               junos:must-message "Indication   invalid on line-protocol eia530";
               junos:must "(!(\".. .. line-protocol v.35\"))";
               junos:must-message "Indication invalid on line-protocol v.35";
               type enumeration {
                 enum "require" {
                   description "Require Indication signal";
                 }
                 enum "ignore" {
                   description "Ignore Indication signal";
                 }
                 enum "normal" {
                   description "Normal Indication signal";
                 }
               }
             }
             leaf tm {
               description "Test Mode signal handling";
               type enumeration {
                 enum "require" {
                   description "Require TM signal";
                 }
                 enum "ignore" {
                   description "Ignore TM signal";
                 }
                 enum "normal" {
                   description "Normal TM signal";
                 }
               }
             }
           }
         }
         case case_2 {
           container dce-options {
             junos:must "(!(\".. clocking-mode dce\"))";
             junos:must-message "SERIAL DCE clocking cannot be set when dce-options is configured";
             junos:must "(!(\".. loopback dce-local\"))";
             junos:must-message "dce-local cannot be set when dce-options is configured";
             description "DCE options";
             uses apply-advanced;
             leaf ignore-all {
               description "Ignore all control leads";
               junos:must "(!(\".. cts\"))";
               junos:must-message "SERIAL: ignore-all configured when cts explicitly configured";
               junos:must "(!(\".. dsr\"))";
               junos:must-message "SERIAL: ignore-all configured when dsr explicitly configured";
               junos:must "(!(\".. dcd\"))";
               junos:must-message "SERIAL: ignore-all configured when dcd explicitly configured";
               junos:must "(!(\".. tm\"))";
               junos:must-message "SERIAL: ignore-all configured when tm explicitly configured";
               junos:must "(!(\".. dtr\"))";
               junos:must-message "SERIAL: ignore-all configured when dtr explicitly configured";
               junos:must "(!(\".. rts\"))";
               junos:must-message "SERIAL: ignore-all configured when rts explicitly configured";
               type empty;
             }
             leaf dtr {
               description "Data Transmit Ready signal handling";
               type enumeration {
                 enum "require" {
                   description "Require Data Carrier Detect (DCD) signal";
                 }
                 enum "ignore" {
                   description "Ignore Data Carrier Detect (DCD) signal";
                 }
                 enum "normal" {
                   description "Normal Data Carrier Detect (DCD) signal";
                 }
               }
             }
             leaf rts {
               description "Request To Send signal handling";
               type enumeration {
                 enum "require" {
                   description "Require Data Carrier Detect (DCD) signal";
                 }
                 enum "ignore" {
                   description "Ignore Data Carrier Detect (DCD) signal";
                 }
                 enum "normal" {
                   description "Normal Data Carrier Detect (DCD) signal";
                 }
               }
             }
             leaf dcd {
               description "Data Carrier Detect signal handling";
               type enumeration {
                 enum "assert" {
                   description "Assert Request To Send (RTS) signal";
                 }
                 enum "de-assert" {
                   description "Deassert Request To Send (RTS) signal";
                 }
                 enum "normal" {
                   description "Normal Request To Send (RTS) signal";
                 }
               }
             }
             leaf dsr {
               description "Data Set Ready signal handling";
               type enumeration {
                 enum "assert" {
                   description "Assert Request To Send (RTS) signal";
                 }
                 enum "de-assert" {
                   description "Deassert Request To Send (RTS) signal";
                 }
                 enum "normal" {
                   description "Normal Request To Send (RTS) signal";
                 }
               }
             }
             leaf cts {
               description "Clear To Send signal handling";
               type enumeration {
                 enum "assert" {
                   description "Assert Request To Send (RTS) signal";
                 }
                 enum "de-assert" {
                   description "Deassert Request To Send (RTS) signal";
                 }
                 enum "normal" {
                   description "Normal Request To Send (RTS) signal";
                 }
               }
             }
             leaf tm {
               description "Test Mode signal handling";
               type enumeration {
                 enum "require" {
                   description "Require TM signal";
                 }
                 enum "ignore" {
                   description "Ignore TM signal";
                 }
                 enum "normal" {
                   description "Normal TM signal";
                 }
               }
             }
             leaf dce-loopback-override {
               description "DCE loopback override";
               type empty;
             }
           }
         }
       }
       leaf dtr-circuit {
         description "Data Transmit Ready circuit mode";
         junos:must "(!(\".. line-protocol x.21\"))";
         junos:must-message "dtr-circuit invalid with line protocol x.21";
         type enumeration {
           enum "balanced" {
             description "Balanced signal";
           }
           enum "unbalanced" {
             description "Unbalanced signal";
           }
         }
       }
       leaf dtr-polarity {
         description "Data Transmit Ready signal polarity";
         junos:must "(!(\".. line-protocol x.21\"))";
         junos:must-message "dtr-polarity invalid with line protocol x.21";
         type enumeration {
           enum "positive" {
             description "Positive polarity";
           }
           enum "negative" {
             description "Negative polarity";
           }
         }
       }
       leaf rts-polarity {
         description "Request To Send signal polarity";
         junos:must "(!(\".. line-protocol x.21\"))";
         junos:must-message "rts invalid on line-protocol x.21";
         type enumeration {
           enum "positive" {
             description "Positive polarity";
           }
           enum "negative" {
             description "Negative polarity";
           }
         }
       }
       leaf control-polarity {
         description "X.21 Control signal polarity";
         junos:must "(!(\".. line-protocol eia530\"))";
         junos:must-message "Control signal  invalid on line-protocol eia530";
         junos:must "(!(\".. line-protocol v.35\"))";
         junos:must-message "Control signal invalid on line-protocol v.35";
         type enumeration {
           enum "positive" {
             description "Positive polarity";
           }
           enum "negative" {
             description "Negative polarity";
           }
         }
       }
       leaf dcd-polarity {
         description "Data Carrier Detect signal polarity";
         junos:must "(!(\".. line-protocol x.21\"))";
         junos:must-message "dcd-polarity invalid with line protocol x.21";
         type enumeration {
           enum "positive" {
             description "Positive polarity";
           }
           enum "negative" {
             description "Negative polarity";
           }
         }
       }
       leaf dsr-polarity {
         description "Data Set Ready signal polarity";
         junos:must "(!(\".. line-protocol x.21\"))";
         junos:must-message "dsr-polarity invalid with line protocol x.21";
         type enumeration {
           enum "positive" {
             description "Positive polarity";
           }
           enum "negative" {
             description "Negative polarity";
           }
         }
       }
       leaf cts-polarity {
         description "Clear To Send signal polarity";
         junos:must "(!(\".. line-protocol x.21\"))";
         junos:must-message "cts invalid on line-protocol x.21";
         type enumeration {
           enum "positive" {
             description "Positive polarity";
           }
           enum "negative" {
             description "Negative polarity";
           }
         }
       }
       leaf indication-polarity {
         description "X.21 Indication signal polarity";
         junos:must "(!(\".. line-protocol eia530\"))";
         junos:must-message "Indication  invalid on line-protocol eia530";
         junos:must "(!(\".. line-protocol v.35\"))";
         junos:must-message "Indication invalid on line-protocol v.35";
         type enumeration {
           enum "positive" {
             description "Positive polarity";
           }
           enum "negative" {
             description "Negative polarity";
           }
         }
       }
       leaf tm-polarity {
         description "Test Mode signal polarity";
         junos:must "(!(\".. line-protocol x.21\"))";
         junos:must-message "tm-polarity invalid for line protocol x.21";
         junos:must "(!(\".. line-protocol v.35\"))";
         junos:must-message "tm-polarity invalid for line protocol v.35";
         type enumeration {
           enum "positive" {
             description "Positive polarity";
           }
           enum "negative" {
             description "Negative polarity";
           }
         }
       }
       leaf clocking-mode {
         description "Clock mode";
         type enumeration {
           enum "dce" {
             description "DCE timing (DTE mode only, not valid for X.21)";
           }
           enum "internal" {
             description "Internal baud timing";
           }
           enum "loop" {
             description "Loop timing";
           }
         }
       }
       leaf transmit-clock {
         description "Transmit clock phase";
         type enumeration {
           enum "invert" {
             description "Shift clock phase 180 degrees";
           }
         }
       }
       leaf clock-rate {
         description "Interface clock rate";
         type enumeration {
           enum "2.048mhz" {
             description "2.048 MHz";
           }
           enum "2.341mhz" {
             description "2.341 MHz";
           }
           enum "2.731mhz" {
             description "2.731 MHz";
           }
           enum "3.277mhz" {
             description "3.277 MHz";
           }
           enum "4.096mhz" {
             description "4.096 MHz";
           }
           enum "5.461mhz" {
             description "5.461 MHz";
           }
           enum "8.192mhz" {
             description "8.192 MHz";
           }
           enum "16.384mhz" {
             description "16.384 MHz";
           }
           enum "1.2khz" {
             description "1.2 KHz";
           }
           enum "2.4khz" {
             description "2.4 KHz";
           }
           enum "9.6khz" {
             description "9.6 KHz";
           }
           enum "19.2khz" {
             description "19.2 KHz";
           }
           enum "38.4khz" {
             description "38.4 KHz";
           }
           enum "56.0khz" {
             description "56.0 KHz";
           }
           enum "64.0khz" {
             description "64.0 KHz";
           }
           enum "72.0khz" {
             description "72.0 KHz";
           }
           enum "125.0khz" {
             description "125.0 KHz";
           }
           enum "148.0khz" {
             description "148.0 KHz";
           }
           enum "250.0khz" {
             description "250.0 KHz";
           }
           enum "500.0khz" {
             description "500.0 KHz";
           }
           enum "800.0khz" {
             description "800.0 KHz";
           }
           enum "1.0mhz" {
             description "1.0 MHz";
           }
           enum "1.3mhz" {
             description "1.3 MHz";
           }
           enum "2.0mhz" {
             description "2.0 MHz";
           }
           enum "4.0mhz" {
             description "4.0 MHz";
           }
           enum "8.0mhz" {
             description "8.0 MHz";
           }
         }
       }
       leaf loopback {
         description "Loopback mode";
         type enumeration {
           enum "local" {
             description "Local loopback";
           }
           enum "remote" {
             description "Remote/LIU loopback";
           }
           enum "dce-local" {
             description "DCE local loopback (DTE mode only)";
           }
           enum "dce-remote" {
             description "DCE remote loopback";
           }
         }
       }
       leaf encoding {
         description "Line encoding";
         type enumeration {
           enum "nrz" {
             description "Non-Return-To-Zero";
           }
           enum "nrzi" {
             description "Non-Return-To-Zero-Invertible";
           }
         }
       }
       leaf idle-cycle-flag {
         description "Value to transmit in idle cycles";
         type enumeration {
           enum "flags" {
             description "Transmit 0x7E in idle cycles";
           }
           enum "ones" {
             description "Transmit 0xFF (all ones) in idle cycles";
           }
         }
       }
     }
     choice gratuitous-arp-reply-choice {
       leaf gratuitous-arp-reply {
         description "Enable gratuitous ARP reply";
         type empty;
       }
       leaf no-gratuitous-arp-reply {
         description "Don't enable gratuitous ARP reply";
         type empty;
       }
     }
     choice no-gratuitous-arp-request-choice {
       leaf no-gratuitous-arp-request {
         description "Ignore gratuitous ARP request";
         type empty;
       }
       leaf no-no-gratuitous-arp-request {
         description "Don't ignore gratuitous ARP request";
         type empty;
       }
     }
     container ether-options {
       description "Ethernet interface-specific options";
       uses apply-advanced;
       choice loopback-choice {
         leaf loopback {
           description "Enable loopback";
           type empty;
         }
         leaf no-loopback {
           description "Don't enable loopback";
           type empty;
         }
       }
       leaf loopback-remote {
         description "Enable remote loopback";
         junos:must "(!(\".. .. optics-options loopback\"))";
         junos:must-message "'optics-options loopback' and loopback-remote are mutually exclusive";
         junos:must "(!(\".. loopback\"))";
         junos:must-message "loopback and loopback-remote are mutually exclusive";
         type empty;
       }
       choice source-filtering-choice {
         leaf source-filtering {
           description "Enable source address filtering";
           type empty;
         }
         leaf no-source-filtering {
           description "Don't enable source address filtering";
           type empty;
         }
       }
       container ethernet-switch-profile {
         description "Ethernet virtual LAN/media access control-level options";
         uses apply-advanced;
         leaf-list tag-protocol-id {
           ordered-by user;
           description "IEEE 802.1q Tag Protocol Identifier values for VLAN-tagged frames";
           type string;
           max-elements 1;
         }
         container ethernet-policer-profile {
           description "Ethernet level CoS-based policer configuration";
           uses apply-advanced;
           container input-priority-map {
             description "Input policer priority map";
             uses cos_policer_input_priority_map;
           }
           container output-priority-map {
             description "Output policer priority map";
             uses cos_policer_output_priority_map;
           }
           list policer {
             key name;
             ordered-by user;
             description "Policer template definition";
             uses cos_policer;
           }
         }
         container storm-control {
           junos:cli-feature "oneliner-plus";
           description "Storm control profile name to bind";
           uses apply-advanced;
           leaf profile-name {
             description "Profile name";
             junos:cli-feature "nokeyword";
             junos:must "(\"forwarding-options storm-control-profiles $$\")";
             junos:must-message "Storm profile name must be defined in the [edit forwarding-options storm-control-profiles] hierarchy";
             type string;
           }
         }
         container recovery-timeout {
           junos:cli-feature "oneliner";
           description "Recovery timeout for this interface";
           leaf time-in-seconds {
             junos:cli-feature "nokeyword";
             units "seconds";
             type union {
               type string {
                 pattern "<.*>|$.*";
               }
               type uint32 {
                 range "10 .. 3600";
               }
             }
           }
         }
         choice mac-learn-enable-choice {
           leaf mac-learn-enable {
             description "Learn MAC addresses dynamically";
             type empty;
           }
           leaf no-mac-learn-enable {
             description "Don't learn MAC addresses dynamically";
             type empty;
           }
         }
       }
       leaf asynchronous-notification {
         description "Enable sending asynchronous notification to peer on CCC-down";
         type empty;
       }
       list source-address-filter {
         key name;
         junos:cli-feature "homogeneous";
         junos:cli-feature "oneliner";
         description "Source address filters";
         leaf name {
           description "Remote MAC address";
           junos:cli-feature "nokeyword";
           type jt:mac-addr;
         }
       }
       choice auto-negotiation-choice {
         leaf auto-negotiation {
           description "Enable auto-negotiation";
           type empty;
         }
         leaf no-auto-negotiation {
           description "Don't enable auto-negotiation";
           type empty;
         }
       }
       choice flow-control-choice {
         leaf flow-control {
           description "Enable flow control";
           type empty;
         }
         leaf no-flow-control {
           description "Don't enable flow control";
           type empty;
         }
       }
       leaf link-mode {
         description "Link duplex";
         type enumeration {
           enum "automatic" {
             description "Automatic negotiate duplex ";
           }
           enum "half-duplex" {
             description "Half-duplex operation";
           }
           enum "full-duplex" {
             description "Full-duplex operation";
           }
         }
       }
       container mpls {
         description "MPLS options";
         uses mpls_ifd_options;
       }
       leaf ignore-l3-incompletes {
         description "Ignore L3 incomplete errors";
         type empty;
       }
       leaf no-auto-mdix {
         description "Disable auto MDI/MDIX";
         type empty;
       }
       leaf fec {
         description "Forward Error Correction mode";
         type enumeration {
           enum "none" {
             description "FEC disabled";
           }
           enum "fec91" {
             description "IEEE 802.3bj Clause 91, Reed-Solomon FEC (RS-FEC)";
           }
           enum "fec74" {
             description "FEC74 enabled";
           }
           enum "fec108" {
             description "IEEE 802.3by Clause 108, Reed-Solomon FEC (RS-FEC) on 25g links";
           }
           enum "fec161" {
             description "IEEE 802.3ck Clause 161 for 100G electrical links";
           }
         }
       }
       container speed {
         description "Specify speed";
         choice automatic {
           case case_1 {
             container auto-negotiation {
               presence "enable auto-negotiation";
               junos:cli-feature "oneliner";
               description "Enable auto-negotiation";
               leaf auto-negotiate-10-100 {
                 description "Limits the auto-negotiation to 10m/100m only";
                 type empty;
               }
             }
           }
           case case_2 {
             leaf ethernet-10m {
               description "10Mbps";
               type empty;
             }
           }
           case case_3 {
             leaf ethernet-100m {
               description "100Mbps";
               type empty;
             }
           }
           case case_4 {
             leaf ethernet-1g {
               description "1Gbps";
               type empty;
             }
           }
           case case_5 {
             leaf ethernet-10g {
               description "10Gbps";
               type empty;
             }
           }
         }
       }
       container ieee-802.3ad {
         junos:must "(!(\"system autoinstallation\"))";
         junos:must-message "incompatible with 'system autoinstallation'";
         junos:cli-feature "oneliner-plus";
         description "IEEE 802.3ad";
         uses apply-advanced;
         container lacp {
           description "Link Aggregation Control Protocol configuration";
           uses apply-advanced;
           leaf force-up {
             description "Keep the port up in absence of received LACPDU";
             type empty;
           }
           leaf port-priority {
             description "Priority of the port (0 ... 65535)";
             type union {
               type uint16;
               type string {
                 pattern "<.*>|$.*";
               }
             }
           }
         }
         leaf bundle {
           description "Join an aggregated Ethernet interface";
           junos:cli-feature "nokeyword";
           junos:must "(!(\"class-of-service interfaces ${interface} dynamic-threshold-profile\"))";
           junos:must-message "dynamic-threshold-profile config cannot be applied on ae child";
           junos:must "(!(any \"class-of-service interfaces ${interface} unit <*> rewrite-rules\"))";
           junos:must-message "rewrite config can not be applied on ae child";
           junos:must "(!(any \"class-of-service interfaces ${interface} unit <*> classifiers\"))";
           junos:must-message "classifier config can not be applied on ae child";
           junos:must "(!(any \"class-of-service interfaces ${interface} unit <*> output-traffic-control-profile\"))";
           junos:must-message "output-traffic-control-profile config can not be applied on ae child";
           junos:must "(!(\"class-of-service interfaces ${interface} output-traffic-control-profile\"))";
           junos:must-message "output-traffic-control-profile config can not be applied on ae child";
           junos:must "(!(\"class-of-service interfaces ${interface} shaping-rate\"))";
           junos:must-message "shaping-rate config can not be applied on ae child";
           junos:must "(!(\"class-of-service interfaces ${interface} scheduler-map\"))";
           junos:must-message "scheduler-map config can not be applied on ae child";
           junos:must "(!(\".. .. .. gigether-options 802.3ad\"))";
           junos:must-message "Member link cannot be a part of multiple aggregation group";
           junos:must "(!(\".. .. .. vlan-offload\"))";
           junos:must-message "ae child device vlan-offload is not allowed";
           junos:must "(!(\".. .. .. flow-control\"))";
           junos:must-message "Setting flow-control on ae child device is not allowed";
           junos:must "(!(\".. .. .. mtu\"))";
           junos:must-message "Setting mtu on ae child device is not allowed";
           junos:must "(!(\".. .. .. vlan-vci-tagging\"))";
           junos:must-message "ae child device vlan-vci-tagging is not allowed";
           junos:must "(!(\".. .. .. stacked-vlan-tagging\"))";
           junos:must-message "ae child device stacked-vlan-tagging is not allowed";
           junos:must "(!(\".. .. .. flexible-vlan-tagging\"))";
           junos:must-message "ae child device flexible-vlan-tagging is not allowed";
           junos:must "(!(\".. .. .. vlan-tagging\"))";
           junos:must-message "ae child device vlan-tagging is not allowed";
           junos:must "(!(\".. .. .. passive-monitor-mode\"))";
           junos:must-message "802.3ad not valid for passive-monitor-mode";
           type union {
             type jt:interface-device;
             type string {
               pattern "<.*>|$.*";
             }
           }
         }
         choice type {
           case case_1 {
             leaf primary {
               description "Primary interface for link-protection mode";
               type empty;
             }
           }
           case case_2 {
             leaf backup {
               description "Backup interface for link-protection mode";
               type empty;
             }
           }
         }
       }
       leaf ieee-802-3az-eee {
         description "IEEE 802.3az Energy Efficient Ethernet(EEE)";
         type empty;
       }
       leaf mdi-mode {
         description "Cable cross-over mode";
         type enumeration {
           enum "auto" {
             description "Automatic mdi/mdi-x mode";
           }
           enum "force" {
             description "Enable auto-MDIX always";
           }
           enum "mdi" {
             description "MDI(straight through) mode";
           }
           enum "mdix" {
             description "MDI Cross-over mode";
           }
         }
       }
       container redundant-parent {
         junos:must "(!(\".. .. unit\"))";
         junos:must-message "Logical unit is not allowed on redundant-ethernet member";
         junos:cli-feature "oneliner-plus";
         description " Parent of this interface";
         uses apply-advanced;
         leaf parent {
           description "Join a redundant ethernet interface";
           junos:cli-feature "nokeyword";
           junos:must "(!(any \"interfaces <*> fastether-options redundant-parent $$\"))";
           junos:must-message "All children must be of the same ethernet type";
           junos:must "(!(any \"interfaces <*> gigether-options redundant-parent $$\"))";
           junos:must-message "All children must be of the same ethernet type";
           type union {
             type jt:interface-device;
             type string {
               pattern "<.*>|$.*";
             }
           }
         }
       }
       leaf autostate-exclude {
         description "Interface will not contribute to IRB state";
         type empty;
       }
     }
     container fibrechannel-options {
       description "Fibre Channel interface-specific options";
       uses apply-advanced;
       choice loopback-choice {
         leaf loopback {
           description "Enable loopback";
           type empty;
         }
         leaf no-loopback {
           description "Don't enable loopback";
           type empty;
         }
       }
       leaf bb-sc-n {
         description "B2B state change number";
         type union {
           type string {
             pattern "<.*>|$.*";
           }
           type uint16 {
             range "0 .. 15";
           }
         }
       }
       leaf speed {
         description "Specify speed";
         type enumeration {
           enum "auto-negotiation" {
             description "Enable auto-negotiation";
           }
           enum "1g" {
             description "1Gbps";
           }
           enum "2g" {
             description "2Gbps";
           }
           enum "4g" {
             description "4Gbps";
           }
           enum "8g" {
             description "8Gbps";
           }
         }
       }
     }
     container gigether-options {
       description "Gigabit Ethernet interface-specific options";
       uses apply-advanced;
       choice loopback-choice {
         leaf loopback {
           description "Enable loopback";
           type empty;
         }
         leaf no-loopback {
           description "Don't enable loopback";
           type empty;
         }
       }
       leaf loopback-remote {
         description "Enable remote loopback";
         junos:must "(!(\".. .. optics-options loopback\"))";
         junos:must-message "'optics-options loopback' and loopback-remote are mutually exclusive";
         junos:must "(!(\".. loopback\"))";
         junos:must-message "loopback and loopback-remote are mutually exclusive";
         type empty;
       }
       choice flow-control-choice {
         leaf flow-control {
           description "Enable flow control";
           type empty;
         }
         leaf no-flow-control {
           description "Don't enable flow control";
           type empty;
         }
       }
       choice source-filtering-choice {
         leaf source-filtering {
           description "Enable source address filtering";
           type empty;
         }
         leaf no-source-filtering {
           description "Don't enable source address filtering";
           type empty;
         }
       }
       choice auto_negotiation_option {
         case case_1 {
           leaf no-auto-negotiation {
             description "Disable auto-negotiation";
             type empty;
           }
         }
         case case_2 {
           container auto-negotiation {
             presence "enable auto-negotiation";
             junos:cli-feature "oneliner";
             description "Enable auto-negotiation";
             leaf remote-fault {
               type enumeration {
                 enum "local-interface-offline" {
                   description "Disable local interface";
                 }
                 enum "local-interface-online" {
                   description "Enable local interface";
                 }
               }
             }
           }
         }
       }
       leaf mac-mode {
         description "Physical layer protocol of MAC's SERDES interface";
         type enumeration {
           enum "sgmii" {
             description "Serial Gigabit Media Independent Interface (10/100/1000 Mbps)";
           }
           enum "mac-mode-1000base-x" {
             description "1000Base-X (1000 Mbps)";
             junos:must "(\".. auto-negotiation\")";
             junos:must-message "Auto-negotiation must be enabled for 1000Base-X SERDES interface";
             junos:must "(\".. .. link-mode full-duplex\")";
             junos:must-message "Link operational mode must be full-duplex to enable 1000Base-X SERDES interface";
             junos:must "(\".. .. speed 1g\")";
             junos:must-message "Link speed must be 1g to enable 1000Base-X SERDES interface";
           }
         }
       }
       leaf asynchronous-notification {
         description "Enable sending asynchronous notification to peer on CCC-down";
         type empty;
       }
       list source-address-filter {
         key name;
         junos:cli-feature "homogeneous";
         junos:cli-feature "oneliner";
         description "Source address filters";
         leaf name {
           description "Remote MAC address";
           junos:cli-feature "nokeyword";
           type jt:mac-addr;
         }
       }
       container redundant-parent {
         junos:must "(!(\".. .. passive-monitor-mode\"))";
         junos:must-message "Redundant-ethernet member cannot be in passive-monitor-mode";
         junos:must "(!((\".. .. flexible-vlan-tagging\" || (\".. .. stacked-vlan-tagging\" || (\".. .. vlan-vci-tagging\" || \".. .. vlan-tagging\")))))";
         junos:must-message "Tagging is not allowed on redundant-ethernet member";
         junos:must "(!(\".. 802.3ad\"))";
         junos:must-message "Redundant-ethernet member cannot be part of 802.3ad";
         junos:must "(!(\".. .. unit\"))";
         junos:must-message "Logical unit is not allowed on redundant-ethernet member";
         junos:cli-feature "oneliner-plus";
         description "Parent of this interface";
         uses apply-advanced;
         leaf parent {
           description "Join a redundant-ethernet interface";
           junos:cli-feature "nokeyword";
           junos:must "(!(any \"interfaces <*> ether-options redundant-parent $$\"))";
           junos:must-message "All the children must be of same ethernet type";
           junos:must "(!(any \"interfaces <*> fastether-options redundant-parent $$\"))";
           junos:must-message "All the children must be of same ethernet type";
           type union {
             type jt:interface-device;
             type string {
               pattern "<.*>|$.*";
             }
           }
         }
       }
       container ieee-802.3ad {
         junos:must "(!(\"system autoinstallation\"))";
         junos:must-message "incompatible with 'system autoinstallation'";
         junos:cli-feature "oneliner-plus";
         description "IEEE 802.3ad";
         uses apply-advanced;
         container lacp {
           description "Link Aggregation Control Protocol configuration";
           uses apply-advanced;
           leaf port-priority {
             description "Priority of the port (0 ... 65535)";
             type union {
               type uint16;
               type string {
                 pattern "<.*>|$.*";
               }
             }
           }
         }
         leaf bundle {
           description "Join an aggregated Ethernet interface";
           junos:cli-feature "nokeyword";
           junos:must "(!(any \"class-of-service interfaces ${interface} unit <*> rewrite-rules\"))";
           junos:must-message "rewrite config can not be applied on ae child";
           junos:must "(!(any \"class-of-service interfaces ${interface} unit <*> classifiers\"))";
           junos:must-message "classifier config can not be applied on ae child";
           junos:must "(!(any \"class-of-service interfaces ${interface} unit <*> output-traffic-control-profile\"))";
           junos:must-message "output-traffic-control-profile config can not be applied on ae child";
           junos:must "(!(\"class-of-service interfaces ${interface} output-traffic-control-profile\"))";
           junos:must-message "output-traffic-control-profile config can not be applied on ae child";
           junos:must "(!(\"class-of-service interfaces ${interface} shaping-rate\"))";
           junos:must-message "shaping-rate config can not be applied on ae child";
           junos:must "(!(\"class-of-service interfaces ${interface} scheduler-map\"))";
           junos:must-message "scheduler-map config can not be applied on ae child";
           junos:must "(!(\".. .. .. ether-options 802.3ad\"))";
           junos:must-message "Member link cannot be a part of multiple aggregation group";
           junos:must "(!(\".. .. .. vlan-offload\"))";
           junos:must-message "ae child device vlan-offload is not allowed";
           junos:must "(!(\".. .. .. flow-control\"))";
           junos:must-message "Setting flow-control on ae child device is not allowed";
           junos:must "(!(\".. .. .. mtu\"))";
           junos:must-message "Setting mtu on ae child device is not allowed";
           junos:must "(!(\".. .. .. vlan-vci-tagging\"))";
           junos:must-message "ae child device vlan-vci-tagging is not allowed";
           junos:must "(!(\".. .. .. stacked-vlan-tagging\"))";
           junos:must-message "ae child device stacked-vlan-tagging is not allowed";
           junos:must "(!(\".. .. .. flexible-vlan-tagging\"))";
           junos:must-message "ae child device flexible-vlan-tagging is not allowed";
           junos:must "(!(\".. .. .. vlan-tagging\"))";
           junos:must-message "ae child device vlan-tagging is not allowed";
           junos:must "(!(\".. .. .. passive-monitor-mode\"))";
           junos:must-message "802.3ad not valid for passive-monitor-mode";
           type union {
             type jt:interface-device;
             type string {
               pattern "<.*>|$.*";
             }
           }
         }
         choice type {
           case case_1 {
             leaf primary {
               description "Primary interface for link-protection mode";
               type empty;
             }
           }
           case case_2 {
             leaf backup {
               description "Backup interface for link-protection mode";
               type empty;
             }
           }
         }
       }
       container ethernet-switch-profile {
         description "Ethernet virtual LAN/media access control-level options";
         uses apply-advanced;
         leaf-list tag-protocol-id {
           ordered-by user;
           description "IEEE 802.1q Tag Protocol Identifier values for VLAN-tagged frames";
           type string;
         }
         container ethernet-policer-profile {
           description "Ethernet level CoS-based policer configuration";
           uses apply-advanced;
           container ieee802.1-priority-map {
             presence "enable ieee802.1-priority-map";
             description "Premium priority values for IEEE 802.1p bits";
             status deprecated;
             uses apply-advanced;
             leaf-list premium {
               ordered-by user;
               description "Premium policer priority map";
               type union {
                 type string {
                   pattern "<.*>|$.*";
                 }
                 type uint32 {
                   range "0 .. 7";
                 }
               }
             }
           }
           container input-priority-map {
             description "Input policer priority map";
             uses cos_policer_input_priority_map;
           }
           container output-priority-map {
             description "Output policer priority map";
             uses cos_policer_output_priority_map;
           }
           list policer {
             key name;
             ordered-by user;
             description "Policer template definition";
             uses cos_policer;
           }
         }
         container accept-from {
           description "Accept traffic from or to specified remote MAC";
           status deprecated;
           uses apply-advanced;
           list mac-address {
             key name;
             description "Remote MAC";
             uses mac_list;
           }
         }
         choice reject-the-rest-choice {
           leaf reject-the-rest {
             description "Accept traffic from only the specified MAC addresses";
             status deprecated;
             type empty;
           }
           leaf no-reject-the-rest {
             description "Don't accept traffic from only the specified MAC addresses";
             status deprecated;
             type empty;
           }
         }
         leaf mac-learn-enable {
           description "Learn MAC addresses dynamically";
           type empty;
         }
       }
       container mpls {
         description "MPLS options";
         uses mpls_ifd_options;
       }
       leaf ignore-l3-incompletes {
         description "Ignore L3 incomplete errors";
         type empty;
       }
       leaf ieee-802-3az-eee {
         description "IEEE 802.3az Energy Efficient Ethernet(EEE)";
         type empty;
       }
       leaf mru {
         description "Maximum receive packet size";
         type union {
           type string {
             pattern "<.*>|$.*";
           }
           type uint32;
         }
       }
       leaf fec {
         description "Forward Error Correction mode";
         type enumeration {
           enum "none" {
             description "FEC disabled";
           }
           enum "fec91" {
             description "IEEE 802.3bj Clause 91, Reed-Solomon FEC (RS-FEC)";
           }
           enum "fec74" {
             description "FEC74 enabled";
           }
           enum "fec108" {
             description "IEEE 802.3by Clause 108, Reed-Solomon FEC (RS-FEC) on 25g links";
           }
           enum "fec161" {
             description "IEEE 802.3ck Clause 161 for 100G electrical links";
           }
         }
       }
       leaf speed {
         description "Speed mode";
         type enumeration {
           enum "1g" {
             description "Speed 1g";
             junos:must "((\".. auto-negotiation\" || \".. no-auto-negotiation\"))";
             junos:must-message "Enabling gigether-options auto-negotiation is highly recommended to prevent traffic drops due to RF peer link up. But if needed, no-auto-negotiation can be enabled";
           }
           enum "10g" {
             description "Speed 10g";
           }
         }
       }
     }
     container optics-options {
       description "Optics options";
       uses apply-advanced;
       leaf wavelength {
         description "Wavelength of the optics (nanometers) for 50Ghz/100Ghz spacing";
         type enumeration {
           enum "1568.77" {
             description "1568.77 nm/191.1003 THz 50/100Ghz spacing";
           }
           enum "1568.36" {
             description "1568.36 nm/191.150000 THz 3.125/6.25/12.5/50GHz spacing";
           }
           enum "1568.34" {
             description "1568.34 nm/191.153125 THz 3.125GHz spacing";
           }
           enum "1568.31" {
             description "1568.31 nm/191.156250 THz 3.125/6.25GHz spacing";
           }
           enum "1568.29" {
             description "1568.29 nm/191.159375 THz 3.125GHz spacing";
           }
           enum "1568.26" {
             description "1568.26 nm/191.162500 THz 3.125/6.25/12.5GHz spacing";
           }
           enum "1568.23" {
             description "1568.23 nm/191.165625 THz 3.125GHz spacing";
           }
           enum "1568.21" {
             description "1568.21 nm/191.168750 THz 3.125/6.25GHz spacing";
           }
           enum "1568.18" {
             description "1568.18 nm/191.171875 THz 3.125GHz spacing";
           }
           enum "1568.16" {
             description "1568.16 nm/191.175000 THz 3.125/6.25/12.5/75GHz spacing";
           }
           enum "1568.13" {
             description "1568.13 nm/191.178125 THz 3.125GHz spacing";
           }
           enum "1568.11" {
             description "1568.11 nm/191.181250 THz 3.125/6.25GHz spacing";
           }
           enum "1568.08" {
             description "1568.08 nm/191.184375 THz 3.125GHz spacing";
           }
           enum "1568.05" {
             description "1568.05 nm/191.187500 THz 3.125/6.25/12.5GHz spacing";
           }
           enum "1568.03" {
             description "1568.03 nm/191.190625 THz 3.125GHz spacing";
           }
           enum "1568.00" {
             description "1568.00 nm/191.193750 THz 3.125/6.25GHz spacing";
           }
           enum "1567.98" {
             description "1567.98 nm/191.196875 THz 3.125GHz spacing";
           }
           enum "1567.95" {
             description "1567.95 nm/191.200000 THz 3.125/6.25/12.5/100GHz spacing";
           }
           enum "1567.93" {
             description "1567.93 nm/191.203125 THz 3.125GHz spacing";
           }
           enum "1567.90" {
             description "1567.90 nm/191.206250 THz 3.125/6.25GHz spacing";
           }
           enum "1567.88" {
             description "1567.88 nm/191.209375 THz 3.125GHz spacing";
           }
           enum "1567.85" {
             description "1567.85 nm/191.212500 THz 3.125/6.25/12.5GHz spacing";
           }
           enum "1567.82" {
             description "1567.82 nm/191.215625 THz 3.125GHz spacing";
           }
           enum "1567.80" {
             description "1567.80 nm/191.218750 THz 3.125/6.25GHz spacing";
           }
           enum "1567.77" {
             description "1567.77 nm/191.221875 THz 3.125GHz spacing";
           }
           enum "1567.75" {
             description "1567.75 nm/191.225000 THz 3.125/6.25/12.5GHz spacing";
           }
           enum "1567.72" {
             description "1567.72 nm/191.228125 THz 3.125GHz spacing";
           }
           enum "1567.70" {
             description "1567.70 nm/191.231250 THz 3.125/6.25GHz spacing";
           }
           enum "1567.67" {
             description "1567.67 nm/191.234375 THz 3.125GHz spacing";
           }
           enum "1567.64" {
             description "1567.64 nm/191.237500 THz 3.125/6.25/12.5GHz spacing";
           }
           enum "1567.62" {
             description "1567.62 nm/191.240625 THz 3.125GHz spacing";
           }
           enum "1567.59" {
             description "1567.59 nm/191.243750 THz 3.125/6.25GHz spacing";
           }
           enum "1567.57" {
             description "1567.57 nm/191.246875 THz 3.125GHz spacing";
           }
           enum "1567.54" {
             description "1567.54 nm/191.250000 THz 3.125/6.25/12.5/50/75GHz spacing";
           }
           enum "1567.52" {
             description "1567.52 nm/191.253125 THz 3.125GHz spacing";
           }
           enum "1567.49" {
             description "1567.49 nm/191.256250 THz 3.125/6.25GHz spacing";
           }
           enum "1567.47" {
             description "1567.47 nm/191.259375 THz 3.125GHz spacing";
           }
           enum "1567.44" {
             description "1567.44 nm/191.262500 THz 3.125/6.25/12.5GHz spacing";
           }
           enum "1567.41" {
             description "1567.41 nm/191.265625 THz 3.125GHz spacing";
           }
           enum "1567.39" {
             description "1567.39 nm/191.268750 THz 3.125/6.25GHz spacing";
           }
           enum "1567.36" {
             description "1567.36 nm/191.271875 THz 3.125GHz spacing";
           }
           enum "1567.34" {
             description "1567.34 nm/191.275000 THz 3.125/6.25/12.5GHz spacing";
           }
           enum "1567.31" {
             description "1567.31 nm/191.278125 THz 3.125GHz spacing";
           }
           enum "1567.29" {
             description "1567.29 nm/191.281250 THz 3.125/6.25GHz spacing";
           }
           enum "1567.26" {
             description "1567.26 nm/191.284375 THz 3.125GHz spacing";
           }
           enum "1567.23" {
             description "1567.23 nm/191.287500 THz 3.125/6.25/12.5GHz spacing";
           }
           enum "1567.21" {
             description "1567.21 nm/191.290625 THz 3.125GHz spacing";
           }
           enum "1567.18" {
             description "1567.18 nm/191.293750 THz 3.125/6.25GHz spacing";
           }
           enum "1567.16" {
             description "1567.16 nm/191.296875 THz 3.125GHz spacing";
           }
           enum "1567.13" {
             description "1567.13 nm/191.300000 THz 3.125/6.25/12.5/100GHz spacing";
           }
           enum "1567.11" {
             description "1567.11 nm/191.303125 THz 3.125GHz spacing";
           }
           enum "1567.08" {
             description "1567.08 nm/191.306250 THz 3.125/6.25GHz spacing";
           }
           enum "1567.06" {
             description "1567.06 nm/191.309375 THz 3.125GHz spacing";
           }
           enum "1567.03" {
             description "1567.03 nm/191.312500 THz 3.125/6.25/12.5GHz spacing";
           }
           enum "1567.00" {
             description "1567.00 nm/191.315625 THz 3.125GHz spacing";
           }
           enum "1566.98" {
             description "1566.98 nm/191.318750 THz 3.125/6.25GHz spacing";
           }
           enum "1566.95" {
             description "1566.95 nm/191.321875 THz 3.125GHz spacing";
           }
           enum "1566.93" {
             description "1566.93 nm/191.325000 THz 3.125/6.25/12.5/75GHz spacing";
           }
           enum "1566.90" {
             description "1566.90 nm/191.328125 THz 3.125GHz spacing";
           }
           enum "1566.88" {
             description "1566.88 nm/191.331250 THz 3.125/6.25GHz spacing";
           }
           enum "1566.85" {
             description "1566.85 nm/191.334375 THz 3.125GHz spacing";
           }
           enum "1566.83" {
             description "1566.83 nm/191.337500 THz 3.125/6.25/12.5GHz spacing";
           }
           enum "1566.80" {
             description "1566.80 nm/191.340625 THz 3.125GHz spacing";
           }
           enum "1566.77" {
             description "1566.77 nm/191.343750 THz 3.125/6.25GHz spacing";
           }
           enum "1566.75" {
             description "1566.75 nm/191.346875 THz 3.125GHz spacing";
           }
           enum "1566.72" {
             description "1566.72 nm/191.350000 THz 3.125/6.25/12.5/50GHz spacing";
           }
           enum "1566.70" {
             description "1566.70 nm/191.353125 THz 3.125GHz spacing";
           }
           enum "1566.67" {
             description "1566.67 nm/191.356250 THz 3.125/6.25GHz spacing";
           }
           enum "1566.65" {
             description "1566.65 nm/191.359375 THz 3.125GHz spacing";
           }
           enum "1566.62" {
             description "1566.62 nm/191.362500 THz 3.125/6.25/12.5GHz spacing";
           }
           enum "1566.60" {
             description "1566.60 nm/191.365625 THz 3.125GHz spacing";
           }
           enum "1566.57" {
             description "1566.57 nm/191.368750 THz 3.125/6.25GHz spacing";
           }
           enum "1566.54" {
             description "1566.54 nm/191.371875 THz 3.125GHz spacing";
           }
           enum "1566.52" {
             description "1566.52 nm/191.375000 THz 3.125/6.25/12.5GHz spacing";
           }
           enum "1566.49" {
             description "1566.49 nm/191.378125 THz 3.125GHz spacing";
           }
           enum "1566.47" {
             description "1566.47 nm/191.381250 THz 3.125/6.25GHz spacing";
           }
           enum "1566.44" {
             description "1566.44 nm/191.384375 THz 3.125GHz spacing";
           }
           enum "1566.42" {
             description "1566.42 nm/191.387500 THz 3.125/6.25/12.5GHz spacing";
           }
           enum "1566.39" {
             description "1566.39 nm/191.390625 THz 3.125GHz spacing";
           }
           enum "1566.36" {
             description "1566.36 nm/191.393750 THz 3.125/6.25GHz spacing";
           }
           enum "1566.34" {
             description "1566.34 nm/191.396875 THz 3.125GHz spacing";
           }
           enum "1566.31" {
             description "1566.31 nm/191.400000 THz 3.125/6.25/12.5/50/75/100GHz spacing";
           }
           enum "1566.29" {
             description "1566.29 nm/191.403125 THz 3.125GHz spacing";
           }
           enum "1566.26" {
             description "1566.26 nm/191.406250 THz 3.125/6.25GHz spacing";
           }
           enum "1566.24" {
             description "1566.24 nm/191.409375 THz 3.125GHz spacing";
           }
           enum "1566.21" {
             description "1566.21 nm/191.412500 THz 3.125/6.25/12.5GHz spacing";
           }
           enum "1566.19" {
             description "1566.19 nm/191.415625 THz 3.125GHz spacing";
           }
           enum "1566.16" {
             description "1566.16 nm/191.418750 THz 3.125/6.25GHz spacing";
           }
           enum "1566.13" {
             description "1566.13 nm/191.421875 THz 3.125GHz spacing";
           }
           enum "1566.11" {
             description "1566.11 nm/191.425000 THz 3.125/6.25/12.5GHz spacing";
           }
           enum "1566.08" {
             description "1566.08 nm/191.428125 THz 3.125GHz spacing";
           }
           enum "1566.06" {
             description "1566.06 nm/191.431250 THz 3.125/6.25GHz spacing";
           }
           enum "1566.03" {
             description "1566.03 nm/191.434375 THz 3.125GHz spacing";
           }
           enum "1566.01" {
             description "1566.01 nm/191.437500 THz 3.125/6.25/12.5GHz spacing";
           }
           enum "1565.98" {
             description "1565.98 nm/191.440625 THz 3.125GHz spacing";
           }
           enum "1565.96" {
             description "1565.96 nm/191.443750 THz 3.125/6.25GHz spacing";
           }
           enum "1565.93" {
             description "1565.93 nm/191.446875 THz 3.125GHz spacing";
           }
           enum "1565.90" {
             description "1565.90 nm/191.450000 THz 3.125/6.25/12.5/50GHz spacing";
           }
           enum "1565.88" {
             description "1565.88 nm/191.453125 THz 3.125GHz spacing";
           }
           enum "1565.85" {
             description "1565.85 nm/191.456250 THz 3.125/6.25GHz spacing";
           }
           enum "1565.83" {
             description "1565.83 nm/191.459375 THz 3.125GHz spacing";
           }
           enum "1565.80" {
             description "1565.80 nm/191.462500 THz 3.125/6.25/12.5GHz spacing";
           }
           enum "1565.78" {
             description "1565.78 nm/191.465625 THz 3.125GHz spacing";
           }
           enum "1565.75" {
             description "1565.75 nm/191.468750 THz 3.125/6.25GHz spacing";
           }
           enum "1565.73" {
             description "1565.73 nm/191.471875 THz 3.125GHz spacing";
           }
           enum "1565.70" {
             description "1565.70 nm/191.475000 THz 3.125/6.25/12.5/75GHz spacing";
           }
           enum "1565.67" {
             description "1565.67 nm/191.478125 THz 3.125GHz spacing";
           }
           enum "1565.65" {
             description "1565.65 nm/191.481250 THz 3.125/6.25GHz spacing";
           }
           enum "1565.62" {
             description "1565.62 nm/191.484375 THz 3.125GHz spacing";
           }
           enum "1565.60" {
             description "1565.60 nm/191.487500 THz 3.125/6.25/12.5GHz spacing";
           }
           enum "1565.57" {
             description "1565.57 nm/191.490625 THz 3.125GHz spacing";
           }
           enum "1565.55" {
             description "1565.55 nm/191.493750 THz 3.125/6.25GHz spacing";
           }
           enum "1565.52" {
             description "1565.52 nm/191.496875 THz 3.125GHz spacing";
           }
           enum "1565.50" {
             description "1565.50 nm/191.500000 THz 3.125/6.25/12.5/100GHz spacing";
           }
           enum "1565.47" {
             description "1565.47 nm/191.503125 THz 3.125GHz spacing";
           }
           enum "1565.44" {
             description "1565.44 nm/191.506250 THz 3.125/6.25GHz spacing";
           }
           enum "1565.42" {
             description "1565.42 nm/191.509375 THz 3.125GHz spacing";
           }
           enum "1565.39" {
             description "1565.39 nm/191.512500 THz 3.125/6.25/12.5GHz spacing";
           }
           enum "1565.37" {
             description "1565.37 nm/191.515625 THz 3.125GHz spacing";
           }
           enum "1565.34" {
             description "1565.34 nm/191.518750 THz 3.125/6.25GHz spacing";
           }
           enum "1565.32" {
             description "1565.32 nm/191.521875 THz 3.125GHz spacing";
           }
           enum "1565.29" {
             description "1565.29 nm/191.525000 THz 3.125/6.25/12.5GHz spacing";
           }
           enum "1565.27" {
             description "1565.27 nm/191.528125 THz 3.125GHz spacing";
           }
           enum "1565.24" {
             description "1565.24 nm/191.531250 THz 3.125/6.25GHz spacing";
           }
           enum "1565.21" {
             description "1565.21 nm/191.534375 THz 3.125GHz spacing";
           }
           enum "1565.19" {
             description "1565.19 nm/191.537500 THz 3.125/6.25/12.5GHz spacing";
           }
           enum "1565.16" {
             description "1565.16 nm/191.540625 THz 3.125GHz spacing";
           }
           enum "1565.14" {
             description "1565.14 nm/191.543750 THz 3.125/6.25GHz spacing";
           }
           enum "1565.11" {
             description "1565.11 nm/191.546875 THz 3.125GHz spacing";
           }
           enum "1565.09" {
             description "1565.09 nm/191.550000 THz 3.125/6.25/12.5/50/75GHz spacing";
           }
           enum "1565.06" {
             description "1565.06 nm/191.553125 THz 3.125GHz spacing";
           }
           enum "1565.04" {
             description "1565.04 nm/191.556250 THz 3.125/6.25GHz spacing";
           }
           enum "1565.01" {
             description "1565.01 nm/191.559375 THz 3.125GHz spacing";
           }
           enum "1564.99" {
             description "1564.99 nm/191.562500 THz 3.125/6.25/12.5GHz spacing";
           }
           enum "1564.96" {
             description "1564.96 nm/191.565625 THz 3.125GHz spacing";
           }
           enum "1564.93" {
             description "1564.93 nm/191.568750 THz 3.125/6.25GHz spacing";
           }
           enum "1564.91" {
             description "1564.91 nm/191.571875 THz 3.125GHz spacing";
           }
           enum "1564.88" {
             description "1564.88 nm/191.575000 THz 3.125/6.25/12.5GHz spacing";
           }
           enum "1564.86" {
             description "1564.86 nm/191.578125 THz 3.125GHz spacing";
           }
           enum "1564.83" {
             description "1564.83 nm/191.581250 THz 3.125/6.25GHz spacing";
           }
           enum "1564.81" {
             description "1564.81 nm/191.584375 THz 3.125GHz spacing";
           }
           enum "1564.78" {
             description "1564.78 nm/191.587500 THz 3.125/6.25/12.5GHz spacing";
           }
           enum "1564.76" {
             description "1564.76 nm/191.590625 THz 3.125GHz spacing";
           }
           enum "1564.73" {
             description "1564.73 nm/191.593750 THz 3.125/6.25GHz spacing";
           }
           enum "1564.70" {
             description "1564.70 nm/191.596875 THz 3.125GHz spacing";
           }
           enum "1564.68" {
             description "1564.68 nm/191.600000 THz 3.125/6.25/12.5/100GHz spacing";
           }
           enum "1564.65" {
             description "1564.65 nm/191.603125 THz 3.125GHz spacing";
           }
           enum "1564.63" {
             description "1564.63 nm/191.606250 THz 3.125/6.25GHz spacing";
           }
           enum "1564.60" {
             description "1564.60 nm/191.609375 THz 3.125GHz spacing";
           }
           enum "1564.58" {
             description "1564.58 nm/191.612500 THz 3.125/6.25/12.5GHz spacing";
           }
           enum "1564.55" {
             description "1564.55 nm/191.615625 THz 3.125GHz spacing";
           }
           enum "1564.53" {
             description "1564.53 nm/191.618750 THz 3.125/6.25GHz spacing";
           }
           enum "1564.50" {
             description "1564.50 nm/191.621875 THz 3.125GHz spacing";
           }
           enum "1564.47" {
             description "1564.47 nm/191.625000 THz 3.125/6.25/12.5/75GHz spacing";
           }
           enum "1564.45" {
             description "1564.45 nm/191.628125 THz 3.125GHz spacing";
           }
           enum "1564.42" {
             description "1564.42 nm/191.631250 THz 3.125/6.25GHz spacing";
           }
           enum "1564.40" {
             description "1564.40 nm/191.634375 THz 3.125GHz spacing";
           }
           enum "1564.37" {
             description "1564.37 nm/191.637500 THz 3.125/6.25/12.5GHz spacing";
           }
           enum "1564.35" {
             description "1564.35 nm/191.640625 THz 3.125GHz spacing";
           }
           enum "1564.32" {
             description "1564.32 nm/191.643750 THz 3.125/6.25GHz spacing";
           }
           enum "1564.30" {
             description "1564.30 nm/191.646875 THz 3.125GHz spacing";
           }
           enum "1564.27" {
             description "1564.27 nm/191.650000 THz 3.125/6.25/12.5/50GHz spacing";
           }
           enum "1564.25" {
             description "1564.25 nm/191.653125 THz 3.125GHz spacing";
           }
           enum "1564.22" {
             description "1564.22 nm/191.656250 THz 3.125/6.25GHz spacing";
           }
           enum "1564.19" {
             description "1564.19 nm/191.659375 THz 3.125GHz spacing";
           }
           enum "1564.17" {
             description "1564.17 nm/191.662500 THz 3.125/6.25/12.5GHz spacing";
           }
           enum "1564.14" {
             description "1564.14 nm/191.665625 THz 3.125GHz spacing";
           }
           enum "1564.12" {
             description "1564.12 nm/191.668750 THz 3.125/6.25GHz spacing";
           }
           enum "1564.09" {
             description "1564.09 nm/191.671875 THz 3.125GHz spacing";
           }
           enum "1564.07" {
             description "1564.07 nm/191.675000 THz 3.125/6.25/12.5GHz spacing";
           }
           enum "1564.04" {
             description "1564.04 nm/191.678125 THz 3.125GHz spacing";
           }
           enum "1564.02" {
             description "1564.02 nm/191.681250 THz 3.125/6.25GHz spacing";
           }
           enum "1563.99" {
             description "1563.99 nm/191.684375 THz 3.125GHz spacing";
           }
           enum "1563.96" {
             description "1563.96 nm/191.687500 THz 3.125/6.25/12.5GHz spacing";
           }
           enum "1563.94" {
             description "1563.94 nm/191.690625 THz 3.125GHz spacing";
           }
           enum "1563.91" {
             description "1563.91 nm/191.693750 THz 3.125/6.25GHz spacing";
           }
           enum "1563.89" {
             description "1563.89 nm/191.696875 THz 3.125GHz spacing";
           }
           enum "1563.86" {
             description "1563.86 nm/191.700000 THz 3.125/6.25/12.5/50/75/100GHz spacing";
           }
           enum "1563.84" {
             description "1563.84 nm/191.703125 THz 3.125GHz spacing";
           }
           enum "1563.81" {
             description "1563.81 nm/191.706250 THz 3.125/6.25GHz spacing";
           }
           enum "1563.79" {
             description "1563.79 nm/191.709375 THz 3.125GHz spacing";
           }
           enum "1563.76" {
             description "1563.76 nm/191.712500 THz 3.125/6.25/12.5GHz spacing";
           }
           enum "1563.74" {
             description "1563.74 nm/191.715625 THz 3.125GHz spacing";
           }
           enum "1563.71" {
             description "1563.71 nm/191.718750 THz 3.125/6.25GHz spacing";
           }
           enum "1563.68" {
             description "1563.68 nm/191.721875 THz 3.125GHz spacing";
           }
           enum "1563.66" {
             description "1563.66 nm/191.725000 THz 3.125/6.25/12.5GHz spacing";
           }
           enum "1563.63" {
             description "1563.63 nm/191.728125 THz 3.125GHz spacing";
           }
           enum "1563.61" {
             description "1563.61 nm/191.731250 THz 3.125/6.25GHz spacing";
           }
           enum "1563.58" {
             description "1563.58 nm/191.734375 THz 3.125GHz spacing";
           }
           enum "1563.56" {
             description "1563.56 nm/191.737500 THz 3.125/6.25/12.5GHz spacing";
           }
           enum "1563.53" {
             description "1563.53 nm/191.740625 THz 3.125GHz spacing";
           }
           enum "1563.51" {
             description "1563.51 nm/191.743750 THz 3.125/6.25GHz spacing";
           }
           enum "1563.48" {
             description "1563.48 nm/191.746875 THz 3.125GHz spacing";
           }
           enum "1563.45" {
             description "1563.45 nm/191.750000 THz 3.125/6.25/12.5/50GHz spacing";
           }
           enum "1563.43" {
             description "1563.43 nm/191.753125 THz 3.125GHz spacing";
           }
           enum "1563.40" {
             description "1563.40 nm/191.756250 THz 3.125/6.25GHz spacing";
           }
           enum "1563.38" {
             description "1563.38 nm/191.759375 THz 3.125GHz spacing";
           }
           enum "1563.35" {
             description "1563.35 nm/191.762500 THz 3.125/6.25/12.5GHz spacing";
           }
           enum "1563.33" {
             description "1563.33 nm/191.765625 THz 3.125GHz spacing";
           }
           enum "1563.30" {
             description "1563.30 nm/191.768750 THz 3.125/6.25GHz spacing";
           }
           enum "1563.28" {
             description "1563.28 nm/191.771875 THz 3.125GHz spacing";
           }
           enum "1563.25" {
             description "1563.25 nm/191.775000 THz 3.125/6.25/12.5/75GHz spacing";
           }
           enum "1563.23" {
             description "1563.23 nm/191.778125 THz 3.125GHz spacing";
           }
           enum "1563.20" {
             description "1563.20 nm/191.781250 THz 3.125/6.25GHz spacing";
           }
           enum "1563.17" {
             description "1563.17 nm/191.784375 THz 3.125GHz spacing";
           }
           enum "1563.15" {
             description "1563.15 nm/191.787500 THz 3.125/6.25/12.5GHz spacing";
           }
           enum "1563.12" {
             description "1563.12 nm/191.790625 THz 3.125GHz spacing";
           }
           enum "1563.10" {
             description "1563.10 nm/191.793750 THz 3.125/6.25GHz spacing";
           }
           enum "1563.07" {
             description "1563.07 nm/191.796875 THz 3.125GHz spacing";
           }
           enum "1563.05" {
             description "1563.05 nm/191.800000 THz 3.125/6.25/12.5/100GHz spacing";
           }
           enum "1563.02" {
             description "1563.02 nm/191.803125 THz 3.125GHz spacing";
           }
           enum "1563.00" {
             description "1563.00 nm/191.806250 THz 3.125/6.25GHz spacing";
           }
           enum "1562.97" {
             description "1562.97 nm/191.809375 THz 3.125GHz spacing";
           }
           enum "1562.95" {
             description "1562.95 nm/191.812500 THz 3.125/6.25/12.5GHz spacing";
           }
           enum "1562.92" {
             description "1562.92 nm/191.815625 THz 3.125GHz spacing";
           }
           enum "1562.89" {
             description "1562.89 nm/191.818750 THz 3.125/6.25GHz spacing";
           }
           enum "1562.87" {
             description "1562.87 nm/191.821875 THz 3.125GHz spacing";
           }
           enum "1562.84" {
             description "1562.84 nm/191.825000 THz 3.125/6.25/12.5GHz spacing";
           }
           enum "1562.82" {
             description "1562.82 nm/191.828125 THz 3.125GHz spacing";
           }
           enum "1562.79" {
             description "1562.79 nm/191.831250 THz 3.125/6.25GHz spacing";
           }
           enum "1562.77" {
             description "1562.77 nm/191.834375 THz 3.125GHz spacing";
           }
           enum "1562.74" {
             description "1562.74 nm/191.837500 THz 3.125/6.25/12.5GHz spacing";
           }
           enum "1562.72" {
             description "1562.72 nm/191.840625 THz 3.125GHz spacing";
           }
           enum "1562.69" {
             description "1562.69 nm/191.843750 THz 3.125/6.25GHz spacing";
           }
           enum "1562.67" {
             description "1562.67 nm/191.846875 THz 3.125GHz spacing";
           }
           enum "1562.64" {
             description "1562.64 nm/191.850000 THz 3.125/6.25/12.5/50/75GHz spacing";
           }
           enum "1562.61" {
             description "1562.61 nm/191.853125 THz 3.125GHz spacing";
           }
           enum "1562.59" {
             description "1562.59 nm/191.856250 THz 3.125/6.25GHz spacing";
           }
           enum "1562.56" {
             description "1562.56 nm/191.859375 THz 3.125GHz spacing";
           }
           enum "1562.54" {
             description "1562.54 nm/191.862500 THz 3.125/6.25/12.5GHz spacing";
           }
           enum "1562.51" {
             description "1562.51 nm/191.865625 THz 3.125GHz spacing";
           }
           enum "1562.49" {
             description "1562.49 nm/191.868750 THz 3.125/6.25GHz spacing";
           }
           enum "1562.46" {
             description "1562.46 nm/191.871875 THz 3.125GHz spacing";
           }
           enum "1562.44" {
             description "1562.44 nm/191.875000 THz 3.125/6.25/12.5GHz spacing";
           }
           enum "1562.41" {
             description "1562.41 nm/191.878125 THz 3.125GHz spacing";
           }
           enum "1562.39" {
             description "1562.39 nm/191.881250 THz 3.125/6.25GHz spacing";
           }
           enum "1562.36" {
             description "1562.36 nm/191.884375 THz 3.125GHz spacing";
           }
           enum "1562.33" {
             description "1562.33 nm/191.887500 THz 3.125/6.25/12.5GHz spacing";
           }
           enum "1562.31" {
             description "1562.31 nm/191.890625 THz 3.125GHz spacing";
           }
           enum "1562.28" {
             description "1562.28 nm/191.893750 THz 3.125/6.25GHz spacing";
           }
           enum "1562.26" {
             description "1562.26 nm/191.896875 THz 3.125GHz spacing";
           }
           enum "1562.23" {
             description "1562.23 nm/191.900000 THz 3.125/6.25/12.5/100GHz spacing";
           }
           enum "1562.21" {
             description "1562.21 nm/191.903125 THz 3.125GHz spacing";
           }
           enum "1562.18" {
             description "1562.18 nm/191.906250 THz 3.125/6.25GHz spacing";
           }
           enum "1562.16" {
             description "1562.16 nm/191.909375 THz 3.125GHz spacing";
           }
           enum "1562.13" {
             description "1562.13 nm/191.912500 THz 3.125/6.25/12.5GHz spacing";
           }
           enum "1562.11" {
             description "1562.11 nm/191.915625 THz 3.125GHz spacing";
           }
           enum "1562.08" {
             description "1562.08 nm/191.918750 THz 3.125/6.25GHz spacing";
           }
           enum "1562.05" {
             description "1562.05 nm/191.921875 THz 3.125GHz spacing";
           }
           enum "1562.03" {
             description "1562.03 nm/191.925000 THz 3.125/6.25/12.5/75GHz spacing";
           }
           enum "1562.00" {
             description "1562.00 nm/191.928125 THz 3.125GHz spacing";
           }
           enum "1561.98" {
             description "1561.98 nm/191.931250 THz 3.125/6.25GHz spacing";
           }
           enum "1561.95" {
             description "1561.95 nm/191.934375 THz 3.125GHz spacing";
           }
           enum "1561.93" {
             description "1561.93 nm/191.937500 THz 3.125/6.25/12.5GHz spacing";
           }
           enum "1561.90" {
             description "1561.90 nm/191.940625 THz 3.125GHz spacing";
           }
           enum "1561.88" {
             description "1561.88 nm/191.943750 THz 3.125/6.25GHz spacing";
           }
           enum "1561.85" {
             description "1561.85 nm/191.946875 THz 3.125GHz spacing";
           }
           enum "1561.83" {
             description "1561.83 nm/191.950000 THz 3.125/6.25/12.5/50GHz spacing";
           }
           enum "1561.80" {
             description "1561.80 nm/191.953125 THz 3.125GHz spacing";
           }
           enum "1561.77" {
             description "1561.77 nm/191.956250 THz 3.125/6.25GHz spacing";
           }
           enum "1561.75" {
             description "1561.75 nm/191.959375 THz 3.125GHz spacing";
           }
           enum "1561.72" {
             description "1561.72 nm/191.962500 THz 3.125/6.25/12.5GHz spacing";
           }
           enum "1561.70" {
             description "1561.70 nm/191.965625 THz 3.125GHz spacing";
           }
           enum "1561.67" {
             description "1561.67 nm/191.968750 THz 3.125/6.25GHz spacing";
           }
           enum "1561.65" {
             description "1561.65 nm/191.971875 THz 3.125GHz spacing";
           }
           enum "1561.62" {
             description "1561.62 nm/191.975000 THz 3.125/6.25/12.5GHz spacing";
           }
           enum "1561.60" {
             description "1561.60 nm/191.978125 THz 3.125GHz spacing";
           }
           enum "1561.57" {
             description "1561.57 nm/191.981250 THz 3.125/6.25GHz spacing";
           }
           enum "1561.55" {
             description "1561.55 nm/191.984375 THz 3.125GHz spacing";
           }
           enum "1561.52" {
             description "1561.52 nm/191.987500 THz 3.125/6.25/12.5GHz spacing";
           }
           enum "1561.50" {
             description "1561.50 nm/191.990625 THz 3.125GHz spacing";
           }
           enum "1561.47" {
             description "1561.47 nm/191.993750 THz 3.125/6.25GHz spacing";
           }
           enum "1561.44" {
             description "1561.44 nm/191.996875 THz 3.125GHz spacing";
           }
           enum "1561.42" {
             description "1561.42 nm/192.000000 THz 3.125/6.25/12.5/50/75/100GHz spacing";
           }
           enum "1561.39" {
             description "1561.39 nm/192.003125 THz 3.125GHz spacing";
           }
           enum "1561.37" {
             description "1561.37 nm/192.006250 THz 3.125/6.25GHz spacing";
           }
           enum "1561.34" {
             description "1561.34 nm/192.009375 THz 3.125GHz spacing";
           }
           enum "1561.32" {
             description "1561.32 nm/192.012500 THz 3.125/6.25/12.5GHz spacing";
           }
           enum "1561.29" {
             description "1561.29 nm/192.015625 THz 3.125GHz spacing";
           }
           enum "1561.27" {
             description "1561.27 nm/192.018750 THz 3.125/6.25GHz spacing";
           }
           enum "1561.24" {
             description "1561.24 nm/192.021875 THz 3.125GHz spacing";
           }
           enum "1561.22" {
             description "1561.22 nm/192.025000 THz 3.125/6.25/12.5GHz spacing";
           }
           enum "1561.19" {
             description "1561.19 nm/192.028125 THz 3.125GHz spacing";
           }
           enum "1561.16" {
             description "1561.16 nm/192.031250 THz 3.125/6.25GHz spacing";
           }
           enum "1561.14" {
             description "1561.14 nm/192.034375 THz 3.125GHz spacing";
           }
           enum "1561.11" {
             description "1561.11 nm/192.037500 THz 3.125/6.25/12.5GHz spacing";
           }
           enum "1561.09" {
             description "1561.09 nm/192.040625 THz 3.125GHz spacing";
           }
           enum "1561.06" {
             description "1561.06 nm/192.043750 THz 3.125/6.25GHz spacing";
           }
           enum "1561.04" {
             description "1561.04 nm/192.046875 THz 3.125GHz spacing";
           }
           enum "1561.01" {
             description "1561.01 nm/192.050000 THz 3.125/6.25/12.5/50GHz spacing";
           }
           enum "1560.99" {
             description "1560.99 nm/192.053125 THz 3.125GHz spacing";
           }
           enum "1560.96" {
             description "1560.96 nm/192.056250 THz 3.125/6.25GHz spacing";
           }
           enum "1560.94" {
             description "1560.94 nm/192.059375 THz 3.125GHz spacing";
           }
           enum "1560.91" {
             description "1560.91 nm/192.062500 THz 3.125/6.25/12.5GHz spacing";
           }
           enum "1560.89" {
             description "1560.89 nm/192.065625 THz 3.125GHz spacing";
           }
           enum "1560.86" {
             description "1560.86 nm/192.068750 THz 3.125/6.25GHz spacing";
           }
           enum "1560.83" {
             description "1560.83 nm/192.071875 THz 3.125GHz spacing";
           }
           enum "1560.81" {
             description "1560.81 nm/192.075000 THz 3.125/6.25/12.5/75GHz spacing";
           }
           enum "1560.78" {
             description "1560.78 nm/192.078125 THz 3.125GHz spacing";
           }
           enum "1560.76" {
             description "1560.76 nm/192.081250 THz 3.125/6.25GHz spacing";
           }
           enum "1560.73" {
             description "1560.73 nm/192.084375 THz 3.125GHz spacing";
           }
           enum "1560.71" {
             description "1560.71 nm/192.087500 THz 3.125/6.25/12.5GHz spacing";
           }
           enum "1560.68" {
             description "1560.68 nm/192.090625 THz 3.125GHz spacing";
           }
           enum "1560.66" {
             description "1560.66 nm/192.093750 THz 3.125/6.25GHz spacing";
           }
           enum "1560.63" {
             description "1560.63 nm/192.096875 THz 3.125GHz spacing";
           }
           enum "1560.61" {
             description "1560.61 nm/192.100000 THz 3.125/6.25/12.5/100GHz spacing";
           }
           enum "1560.58" {
             description "1560.58 nm/192.103125 THz 3.125GHz spacing";
           }
           enum "1560.56" {
             description "1560.56 nm/192.106250 THz 3.125/6.25GHz spacing";
           }
           enum "1560.53" {
             description "1560.53 nm/192.109375 THz 3.125GHz spacing";
           }
           enum "1560.50" {
             description "1560.50 nm/192.112500 THz 3.125/6.25/12.5GHz spacing";
           }
           enum "1560.48" {
             description "1560.48 nm/192.115625 THz 3.125GHz spacing";
           }
           enum "1560.45" {
             description "1560.45 nm/192.118750 THz 3.125/6.25GHz spacing";
           }
           enum "1560.43" {
             description "1560.43 nm/192.121875 THz 3.125GHz spacing";
           }
           enum "1560.40" {
             description "1560.40 nm/192.125000 THz 3.125/6.25/12.5GHz spacing";
           }
           enum "1560.38" {
             description "1560.38 nm/192.128125 THz 3.125GHz spacing";
           }
           enum "1560.35" {
             description "1560.35 nm/192.131250 THz 3.125/6.25GHz spacing";
           }
           enum "1560.33" {
             description "1560.33 nm/192.134375 THz 3.125GHz spacing";
           }
           enum "1560.30" {
             description "1560.30 nm/192.137500 THz 3.125/6.25/12.5GHz spacing";
           }
           enum "1560.28" {
             description "1560.28 nm/192.140625 THz 3.125GHz spacing";
           }
           enum "1560.25" {
             description "1560.25 nm/192.143750 THz 3.125/6.25GHz spacing";
           }
           enum "1560.23" {
             description "1560.23 nm/192.146875 THz 3.125GHz spacing";
           }
           enum "1560.20" {
             description "1560.20 nm/192.150000 THz 3.125/6.25/12.5/50/75GHz spacing";
           }
           enum "1560.17" {
             description "1560.17 nm/192.153125 THz 3.125GHz spacing";
           }
           enum "1560.15" {
             description "1560.15 nm/192.156250 THz 3.125/6.25GHz spacing";
           }
           enum "1560.12" {
             description "1560.12 nm/192.159375 THz 3.125GHz spacing";
           }
           enum "1560.10" {
             description "1560.10 nm/192.162500 THz 3.125/6.25/12.5GHz spacing";
           }
           enum "1560.07" {
             description "1560.07 nm/192.165625 THz 3.125GHz spacing";
           }
           enum "1560.05" {
             description "1560.05 nm/192.168750 THz 3.125/6.25GHz spacing";
           }
           enum "1560.02" {
             description "1560.02 nm/192.171875 THz 3.125GHz spacing";
           }
           enum "1560.00" {
             description "1560.00 nm/192.175000 THz 3.125/6.25/12.5GHz spacing";
           }
           enum "1559.97" {
             description "1559.97 nm/192.178125 THz 3.125GHz spacing";
           }
           enum "1559.95" {
             description "1559.95 nm/192.181250 THz 3.125/6.25GHz spacing";
           }
           enum "1559.92" {
             description "1559.92 nm/192.184375 THz 3.125GHz spacing";
           }
           enum "1559.90" {
             description "1559.90 nm/192.187500 THz 3.125/6.25/12.5GHz spacing";
           }
           enum "1559.87" {
             description "1559.87 nm/192.190625 THz 3.125GHz spacing";
           }
           enum "1559.84" {
             description "1559.84 nm/192.193750 THz 3.125/6.25GHz spacing";
           }
           enum "1559.82" {
             description "1559.82 nm/192.196875 THz 3.125GHz spacing";
           }
           enum "1559.79" {
             description "1559.79 nm/192.200000 THz 3.125/6.25/12.5/100GHz spacing";
           }
           enum "1559.77" {
             description "1559.77 nm/192.203125 THz 3.125GHz spacing";
           }
           enum "1559.74" {
             description "1559.74 nm/192.206250 THz 3.125/6.25GHz spacing";
           }
           enum "1559.72" {
             description "1559.72 nm/192.209375 THz 3.125GHz spacing";
           }
           enum "1559.69" {
             description "1559.69 nm/192.212500 THz 3.125/6.25/12.5GHz spacing";
           }
           enum "1559.67" {
             description "1559.67 nm/192.215625 THz 3.125GHz spacing";
           }
           enum "1559.64" {
             description "1559.64 nm/192.218750 THz 3.125/6.25GHz spacing";
           }
           enum "1559.62" {
             description "1559.62 nm/192.221875 THz 3.125GHz spacing";
           }
           enum "1559.59" {
             description "1559.59 nm/192.225000 THz 3.125/6.25/12.5/75GHz spacing";
           }
           enum "1559.57" {
             description "1559.57 nm/192.228125 THz 3.125GHz spacing";
           }
           enum "1559.54" {
             description "1559.54 nm/192.231250 THz 3.125/6.25GHz spacing";
           }
           enum "1559.52" {
             description "1559.52 nm/192.234375 THz 3.125GHz spacing";
           }
           enum "1559.49" {
             description "1559.49 nm/192.237500 THz 3.125/6.25/12.5GHz spacing";
           }
           enum "1559.46" {
             description "1559.46 nm/192.240625 THz 3.125GHz spacing";
           }
           enum "1559.44" {
             description "1559.44 nm/192.243750 THz 3.125/6.25GHz spacing";
           }
           enum "1559.41" {
             description "1559.41 nm/192.246875 THz 3.125GHz spacing";
           }
           enum "1559.39" {
             description "1559.39 nm/192.250000 THz 3.125/6.25/12.5/50GHz spacing";
           }
           enum "1559.36" {
             description "1559.36 nm/192.253125 THz 3.125GHz spacing";
           }
           enum "1559.34" {
             description "1559.34 nm/192.256250 THz 3.125/6.25GHz spacing";
           }
           enum "1559.31" {
             description "1559.31 nm/192.259375 THz 3.125GHz spacing";
           }
           enum "1559.29" {
             description "1559.29 nm/192.262500 THz 3.125/6.25/12.5GHz spacing";
           }
           enum "1559.26" {
             description "1559.26 nm/192.265625 THz 3.125GHz spacing";
           }
           enum "1559.24" {
             description "1559.24 nm/192.268750 THz 3.125/6.25GHz spacing";
           }
           enum "1559.21" {
             description "1559.21 nm/192.271875 THz 3.125GHz spacing";
           }
           enum "1559.19" {
             description "1559.19 nm/192.275000 THz 3.125/6.25/12.5GHz spacing";
           }
           enum "1559.16" {
             description "1559.16 nm/192.278125 THz 3.125GHz spacing";
           }
           enum "1559.14" {
             description "1559.14 nm/192.281250 THz 3.125/6.25GHz spacing";
           }
           enum "1559.11" {
             description "1559.11 nm/192.284375 THz 3.125GHz spacing";
           }
           enum "1559.08" {
             description "1559.08 nm/192.287500 THz 3.125/6.25/12.5GHz spacing";
           }
           enum "1559.06" {
             description "1559.06 nm/192.290625 THz 3.125GHz spacing";
           }
           enum "1559.03" {
             description "1559.03 nm/192.293750 THz 3.125/6.25GHz spacing";
           }
           enum "1559.01" {
             description "1559.01 nm/192.296875 THz 3.125GHz spacing";
           }
           enum "1558.98" {
             description "1558.98 nm/192.300000 THz 3.125/6.25/12.5/50/75/100GHz spacing";
           }
           enum "1558.96" {
             description "1558.96 nm/192.303125 THz 3.125GHz spacing";
           }
           enum "1558.93" {
             description "1558.93 nm/192.306250 THz 3.125/6.25GHz spacing";
           }
           enum "1558.91" {
             description "1558.91 nm/192.309375 THz 3.125GHz spacing";
           }
           enum "1558.88" {
             description "1558.88 nm/192.312500 THz 3.125/6.25/12.5GHz spacing";
           }
           enum "1558.86" {
             description "1558.86 nm/192.315625 THz 3.125GHz spacing";
           }
           enum "1558.83" {
             description "1558.83 nm/192.318750 THz 3.125/6.25GHz spacing";
           }
           enum "1558.81" {
             description "1558.81 nm/192.321875 THz 3.125GHz spacing";
           }
           enum "1558.78" {
             description "1558.78 nm/192.325000 THz 3.125/6.25/12.5GHz spacing";
           }
           enum "1558.76" {
             description "1558.76 nm/192.328125 THz 3.125GHz spacing";
           }
           enum "1558.73" {
             description "1558.73 nm/192.331250 THz 3.125/6.25GHz spacing";
           }
           enum "1558.70" {
             description "1558.70 nm/192.334375 THz 3.125GHz spacing";
           }
           enum "1558.68" {
             description "1558.68 nm/192.337500 THz 3.125/6.25/12.5GHz spacing";
           }
           enum "1558.65" {
             description "1558.65 nm/192.340625 THz 3.125GHz spacing";
           }
           enum "1558.63" {
             description "1558.63 nm/192.343750 THz 3.125/6.25GHz spacing";
           }
           enum "1558.60" {
             description "1558.60 nm/192.346875 THz 3.125GHz spacing";
           }
           enum "1558.58" {
             description "1558.58 nm/192.350000 THz 3.125/6.25/12.5/50GHz spacing";
           }
           enum "1558.55" {
             description "1558.55 nm/192.353125 THz 3.125GHz spacing";
           }
           enum "1558.53" {
             description "1558.53 nm/192.356250 THz 3.125/6.25GHz spacing";
           }
           enum "1558.50" {
             description "1558.50 nm/192.359375 THz 3.125GHz spacing";
           }
           enum "1558.48" {
             description "1558.48 nm/192.362500 THz 3.125/6.25/12.5GHz spacing";
           }
           enum "1558.45" {
             description "1558.45 nm/192.365625 THz 3.125GHz spacing";
           }
           enum "1558.43" {
             description "1558.43 nm/192.368750 THz 3.125/6.25GHz spacing";
           }
           enum "1558.40" {
             description "1558.40 nm/192.371875 THz 3.125GHz spacing";
           }
           enum "1558.38" {
             description "1558.38 nm/192.375000 THz 3.125/6.25/12.5/75GHz spacing";
           }
           enum "1558.35" {
             description "1558.35 nm/192.378125 THz 3.125GHz spacing";
           }
           enum "1558.32" {
             description "1558.32 nm/192.381250 THz 3.125/6.25GHz spacing";
           }
           enum "1558.30" {
             description "1558.30 nm/192.384375 THz 3.125GHz spacing";
           }
           enum "1558.27" {
             description "1558.27 nm/192.387500 THz 3.125/6.25/12.5GHz spacing";
           }
           enum "1558.25" {
             description "1558.25 nm/192.390625 THz 3.125GHz spacing";
           }
           enum "1558.22" {
             description "1558.22 nm/192.393750 THz 3.125/6.25GHz spacing";
           }
           enum "1558.20" {
             description "1558.20 nm/192.396875 THz 3.125GHz spacing";
           }
           enum "1558.17" {
             description "1558.17 nm/192.400000 THz 3.125/6.25/12.5/100GHz spacing";
           }
           enum "1558.15" {
             description "1558.15 nm/192.403125 THz 3.125GHz spacing";
           }
           enum "1558.12" {
             description "1558.12 nm/192.406250 THz 3.125/6.25GHz spacing";
           }
           enum "1558.10" {
             description "1558.10 nm/192.409375 THz 3.125GHz spacing";
           }
           enum "1558.07" {
             description "1558.07 nm/192.412500 THz 3.125/6.25/12.5GHz spacing";
           }
           enum "1558.05" {
             description "1558.05 nm/192.415625 THz 3.125GHz spacing";
           }
           enum "1558.02" {
             description "1558.02 nm/192.418750 THz 3.125/6.25GHz spacing";
           }
           enum "1558.00" {
             description "1558.00 nm/192.421875 THz 3.125GHz spacing";
           }
           enum "1557.97" {
             description "1557.97 nm/192.425000 THz 3.125/6.25/12.5GHz spacing";
           }
           enum "1557.95" {
             description "1557.95 nm/192.428125 THz 3.125GHz spacing";
           }
           enum "1557.92" {
             description "1557.92 nm/192.431250 THz 3.125/6.25GHz spacing";
           }
           enum "1557.89" {
             description "1557.89 nm/192.434375 THz 3.125GHz spacing";
           }
           enum "1557.87" {
             description "1557.87 nm/192.437500 THz 3.125/6.25/12.5GHz spacing";
           }
           enum "1557.84" {
             description "1557.84 nm/192.440625 THz 3.125GHz spacing";
           }
           enum "1557.82" {
             description "1557.82 nm/192.443750 THz 3.125/6.25GHz spacing";
           }
           enum "1557.79" {
             description "1557.79 nm/192.446875 THz 3.125GHz spacing";
           }
           enum "1557.77" {
             description "1557.77 nm/192.450000 THz 3.125/6.25/12.5/50/75GHz spacing";
           }
           enum "1557.74" {
             description "1557.74 nm/192.453125 THz 3.125GHz spacing";
           }
           enum "1557.72" {
             description "1557.72 nm/192.456250 THz 3.125/6.25GHz spacing";
           }
           enum "1557.69" {
             description "1557.69 nm/192.459375 THz 3.125GHz spacing";
           }
           enum "1557.67" {
             description "1557.67 nm/192.462500 THz 3.125/6.25/12.5GHz spacing";
           }
           enum "1557.64" {
             description "1557.64 nm/192.465625 THz 3.125GHz spacing";
           }
           enum "1557.62" {
             description "1557.62 nm/192.468750 THz 3.125/6.25GHz spacing";
           }
           enum "1557.59" {
             description "1557.59 nm/192.471875 THz 3.125GHz spacing";
           }
           enum "1557.57" {
             description "1557.57 nm/192.475000 THz 3.125/6.25/12.5GHz spacing";
           }
           enum "1557.54" {
             description "1557.54 nm/192.478125 THz 3.125GHz spacing";
           }
           enum "1557.52" {
             description "1557.52 nm/192.481250 THz 3.125/6.25GHz spacing";
           }
           enum "1557.49" {
             description "1557.49 nm/192.484375 THz 3.125GHz spacing";
           }
           enum "1557.46" {
             description "1557.46 nm/192.487500 THz 3.125/6.25/12.5GHz spacing";
           }
           enum "1557.44" {
             description "1557.44 nm/192.490625 THz 3.125GHz spacing";
           }
           enum "1557.41" {
             description "1557.41 nm/192.493750 THz 3.125/6.25GHz spacing";
           }
           enum "1557.39" {
             description "1557.39 nm/192.496875 THz 3.125GHz spacing";
           }
           enum "1557.36" {
             description "1557.36 nm/192.500000 THz 3.125/6.25/12.5/100GHz spacing";
           }
           enum "1557.34" {
             description "1557.34 nm/192.503125 THz 3.125GHz spacing";
           }
           enum "1557.31" {
             description "1557.31 nm/192.506250 THz 3.125/6.25GHz spacing";
           }
           enum "1557.29" {
             description "1557.29 nm/192.509375 THz 3.125GHz spacing";
           }
           enum "1557.26" {
             description "1557.26 nm/192.512500 THz 3.125/6.25/12.5GHz spacing";
           }
           enum "1557.24" {
             description "1557.24 nm/192.515625 THz 3.125GHz spacing";
           }
           enum "1557.21" {
             description "1557.21 nm/192.518750 THz 3.125/6.25GHz spacing";
           }
           enum "1557.19" {
             description "1557.19 nm/192.521875 THz 3.125GHz spacing";
           }
           enum "1557.16" {
             description "1557.16 nm/192.525000 THz 3.125/6.25/12.5/75GHz spacing";
           }
           enum "1557.14" {
             description "1557.14 nm/192.528125 THz 3.125GHz spacing";
           }
           enum "1557.11" {
             description "1557.11 nm/192.531250 THz 3.125/6.25GHz spacing";
           }
           enum "1557.09" {
             description "1557.09 nm/192.534375 THz 3.125GHz spacing";
           }
           enum "1557.06" {
             description "1557.06 nm/192.537500 THz 3.125/6.25/12.5GHz spacing";
           }
           enum "1557.03" {
             description "1557.03 nm/192.540625 THz 3.125GHz spacing";
           }
           enum "1557.01" {
             description "1557.01 nm/192.543750 THz 3.125/6.25GHz spacing";
           }
           enum "1556.98" {
             description "1556.98 nm/192.546875 THz 3.125GHz spacing";
           }
           enum "1556.96" {
             description "1556.96 nm/192.550000 THz 3.125/6.25/12.5/50GHz spacing";
           }
           enum "1556.93" {
             description "1556.93 nm/192.553125 THz 3.125GHz spacing";
           }
           enum "1556.91" {
             description "1556.91 nm/192.556250 THz 3.125/6.25GHz spacing";
           }
           enum "1556.88" {
             description "1556.88 nm/192.559375 THz 3.125GHz spacing";
           }
           enum "1556.86" {
             description "1556.86 nm/192.562500 THz 3.125/6.25/12.5GHz spacing";
           }
           enum "1556.83" {
             description "1556.83 nm/192.565625 THz 3.125GHz spacing";
           }
           enum "1556.81" {
             description "1556.81 nm/192.568750 THz 3.125/6.25GHz spacing";
           }
           enum "1556.78" {
             description "1556.78 nm/192.571875 THz 3.125GHz spacing";
           }
           enum "1556.76" {
             description "1556.76 nm/192.575000 THz 3.125/6.25/12.5GHz spacing";
           }
           enum "1556.73" {
             description "1556.73 nm/192.578125 THz 3.125GHz spacing";
           }
           enum "1556.71" {
             description "1556.71 nm/192.581250 THz 3.125/6.25GHz spacing";
           }
           enum "1556.68" {
             description "1556.68 nm/192.584375 THz 3.125GHz spacing";
           }
           enum "1556.66" {
             description "1556.66 nm/192.587500 THz 3.125/6.25/12.5GHz spacing";
           }
           enum "1556.63" {
             description "1556.63 nm/192.590625 THz 3.125GHz spacing";
           }
           enum "1556.61" {
             description "1556.61 nm/192.593750 THz 3.125/6.25GHz spacing";
           }
           enum "1556.58" {
             description "1556.58 nm/192.596875 THz 3.125GHz spacing";
           }
           enum "1556.55" {
             description "1556.55 nm/192.600000 THz 3.125/6.25/12.5/50/75/100GHz spacing";
           }
           enum "1556.53" {
             description "1556.53 nm/192.603125 THz 3.125GHz spacing";
           }
           enum "1556.50" {
             description "1556.50 nm/192.606250 THz 3.125/6.25GHz spacing";
           }
           enum "1556.48" {
             description "1556.48 nm/192.609375 THz 3.125GHz spacing";
           }
           enum "1556.45" {
             description "1556.45 nm/192.612500 THz 3.125/6.25/12.5GHz spacing";
           }
           enum "1556.43" {
             description "1556.43 nm/192.615625 THz 3.125GHz spacing";
           }
           enum "1556.40" {
             description "1556.40 nm/192.618750 THz 3.125/6.25GHz spacing";
           }
           enum "1556.38" {
             description "1556.38 nm/192.621875 THz 3.125GHz spacing";
           }
           enum "1556.35" {
             description "1556.35 nm/192.625000 THz 3.125/6.25/12.5GHz spacing";
           }
           enum "1556.33" {
             description "1556.33 nm/192.628125 THz 3.125GHz spacing";
           }
           enum "1556.30" {
             description "1556.30 nm/192.631250 THz 3.125/6.25GHz spacing";
           }
           enum "1556.28" {
             description "1556.28 nm/192.634375 THz 3.125GHz spacing";
           }
           enum "1556.25" {
             description "1556.25 nm/192.637500 THz 3.125/6.25/12.5GHz spacing";
           }
           enum "1556.23" {
             description "1556.23 nm/192.640625 THz 3.125GHz spacing";
           }
           enum "1556.20" {
             description "1556.20 nm/192.643750 THz 3.125/6.25GHz spacing";
           }
           enum "1556.18" {
             description "1556.18 nm/192.646875 THz 3.125GHz spacing";
           }
           enum "1556.15" {
             description "1556.15 nm/192.650000 THz 3.125/6.25/12.5/50GHz spacing";
           }
           enum "1556.13" {
             description "1556.13 nm/192.653125 THz 3.125GHz spacing";
           }
           enum "1556.10" {
             description "1556.10 nm/192.656250 THz 3.125/6.25GHz spacing";
           }
           enum "1556.08" {
             description "1556.08 nm/192.659375 THz 3.125GHz spacing";
           }
           enum "1556.05" {
             description "1556.05 nm/192.662500 THz 3.125/6.25/12.5GHz spacing";
           }
           enum "1556.02" {
             description "1556.02 nm/192.665625 THz 3.125GHz spacing";
           }
           enum "1556.00" {
             description "1556.00 nm/192.668750 THz 3.125/6.25GHz spacing";
           }
           enum "1555.97" {
             description "1555.97 nm/192.671875 THz 3.125GHz spacing";
           }
           enum "1555.95" {
             description "1555.95 nm/192.675000 THz 3.125/6.25/12.5/75GHz spacing";
           }
           enum "1555.92" {
             description "1555.92 nm/192.678125 THz 3.125GHz spacing";
           }
           enum "1555.90" {
             description "1555.90 nm/192.681250 THz 3.125/6.25GHz spacing";
           }
           enum "1555.87" {
             description "1555.87 nm/192.684375 THz 3.125GHz spacing";
           }
           enum "1555.85" {
             description "1555.85 nm/192.687500 THz 3.125/6.25/12.5GHz spacing";
           }
           enum "1555.82" {
             description "1555.82 nm/192.690625 THz 3.125GHz spacing";
           }
           enum "1555.80" {
             description "1555.80 nm/192.693750 THz 3.125/6.25GHz spacing";
           }
           enum "1555.77" {
             description "1555.77 nm/192.696875 THz 3.125GHz spacing";
           }
           enum "1555.75" {
             description "1555.75 nm/192.700000 THz 3.125/6.25/12.5/100GHz spacing";
           }
           enum "1555.72" {
             description "1555.72 nm/192.703125 THz 3.125GHz spacing";
           }
           enum "1555.70" {
             description "1555.70 nm/192.706250 THz 3.125/6.25GHz spacing";
           }
           enum "1555.67" {
             description "1555.67 nm/192.709375 THz 3.125GHz spacing";
           }
           enum "1555.65" {
             description "1555.65 nm/192.712500 THz 3.125/6.25/12.5GHz spacing";
           }
           enum "1555.62" {
             description "1555.62 nm/192.715625 THz 3.125GHz spacing";
           }
           enum "1555.60" {
             description "1555.60 nm/192.718750 THz 3.125/6.25GHz spacing";
           }
           enum "1555.57" {
             description "1555.57 nm/192.721875 THz 3.125GHz spacing";
           }
           enum "1555.55" {
             description "1555.55 nm/192.725000 THz 3.125/6.25/12.5GHz spacing";
           }
           enum "1555.52" {
             description "1555.52 nm/192.728125 THz 3.125GHz spacing";
           }
           enum "1555.49" {
             description "1555.49 nm/192.731250 THz 3.125/6.25GHz spacing";
           }
           enum "1555.47" {
             description "1555.47 nm/192.734375 THz 3.125GHz spacing";
           }
           enum "1555.44" {
             description "1555.44 nm/192.737500 THz 3.125/6.25/12.5GHz spacing";
           }
           enum "1555.42" {
             description "1555.42 nm/192.740625 THz 3.125GHz spacing";
           }
           enum "1555.39" {
             description "1555.39 nm/192.743750 THz 3.125/6.25GHz spacing";
           }
           enum "1555.37" {
             description "1555.37 nm/192.746875 THz 3.125GHz spacing";
           }
           enum "1555.34" {
             description "1555.34 nm/192.750000 THz 3.125/6.25/12.5/50/75GHz spacing";
           }
           enum "1555.32" {
             description "1555.32 nm/192.753125 THz 3.125GHz spacing";
           }
           enum "1555.29" {
             description "1555.29 nm/192.756250 THz 3.125/6.25GHz spacing";
           }
           enum "1555.27" {
             description "1555.27 nm/192.759375 THz 3.125GHz spacing";
           }
           enum "1555.24" {
             description "1555.24 nm/192.762500 THz 3.125/6.25/12.5GHz spacing";
           }
           enum "1555.22" {
             description "1555.22 nm/192.765625 THz 3.125GHz spacing";
           }
           enum "1555.19" {
             description "1555.19 nm/192.768750 THz 3.125/6.25GHz spacing";
           }
           enum "1555.17" {
             description "1555.17 nm/192.771875 THz 3.125GHz spacing";
           }
           enum "1555.14" {
             description "1555.14 nm/192.775000 THz 3.125/6.25/12.5GHz spacing";
           }
           enum "1555.12" {
             description "1555.12 nm/192.778125 THz 3.125GHz spacing";
           }
           enum "1555.09" {
             description "1555.09 nm/192.781250 THz 3.125/6.25GHz spacing";
           }
           enum "1555.07" {
             description "1555.07 nm/192.784375 THz 3.125GHz spacing";
           }
           enum "1555.04" {
             description "1555.04 nm/192.787500 THz 3.125/6.25/12.5GHz spacing";
           }
           enum "1555.02" {
             description "1555.02 nm/192.790625 THz 3.125GHz spacing";
           }
           enum "1554.99" {
             description "1554.99 nm/192.793750 THz 3.125/6.25GHz spacing";
           }
           enum "1554.97" {
             description "1554.97 nm/192.796875 THz 3.125GHz spacing";
           }
           enum "1554.94" {
             description "1554.94 nm/192.800000 THz 3.125/6.25/12.5/100GHz spacing";
           }
           enum "1554.91" {
             description "1554.91 nm/192.803125 THz 3.125GHz spacing";
           }
           enum "1554.89" {
             description "1554.89 nm/192.806250 THz 3.125/6.25GHz spacing";
           }
           enum "1554.86" {
             description "1554.86 nm/192.809375 THz 3.125GHz spacing";
           }
           enum "1554.84" {
             description "1554.84 nm/192.812500 THz 3.125/6.25/12.5GHz spacing";
           }
           enum "1554.81" {
             description "1554.81 nm/192.815625 THz 3.125GHz spacing";
           }
           enum "1554.79" {
             description "1554.79 nm/192.818750 THz 3.125/6.25GHz spacing";
           }
           enum "1554.76" {
             description "1554.76 nm/192.821875 THz 3.125GHz spacing";
           }
           enum "1554.74" {
             description "1554.74 nm/192.825000 THz 3.125/6.25/12.5/75GHz spacing";
           }
           enum "1554.71" {
             description "1554.71 nm/192.828125 THz 3.125GHz spacing";
           }
           enum "1554.69" {
             description "1554.69 nm/192.831250 THz 3.125/6.25GHz spacing";
           }
           enum "1554.66" {
             description "1554.66 nm/192.834375 THz 3.125GHz spacing";
           }
           enum "1554.64" {
             description "1554.64 nm/192.837500 THz 3.125/6.25/12.5GHz spacing";
           }
           enum "1554.61" {
             description "1554.61 nm/192.840625 THz 3.125GHz spacing";
           }
           enum "1554.59" {
             description "1554.59 nm/192.843750 THz 3.125/6.25GHz spacing";
           }
           enum "1554.56" {
             description "1554.56 nm/192.846875 THz 3.125GHz spacing";
           }
           enum "1554.54" {
             description "1554.54 nm/192.850000 THz 3.125/6.25/12.5/50GHz spacing";
           }
           enum "1554.51" {
             description "1554.51 nm/192.853125 THz 3.125GHz spacing";
           }
           enum "1554.49" {
             description "1554.49 nm/192.856250 THz 3.125/6.25GHz spacing";
           }
           enum "1554.46" {
             description "1554.46 nm/192.859375 THz 3.125GHz spacing";
           }
           enum "1554.44" {
             description "1554.44 nm/192.862500 THz 3.125/6.25/12.5GHz spacing";
           }
           enum "1554.41" {
             description "1554.41 nm/192.865625 THz 3.125GHz spacing";
           }
           enum "1554.39" {
             description "1554.39 nm/192.868750 THz 3.125/6.25GHz spacing";
           }
           enum "1554.36" {
             description "1554.36 nm/192.871875 THz 3.125GHz spacing";
           }
           enum "1554.34" {
             description "1554.34 nm/192.875000 THz 3.125/6.25/12.5GHz spacing";
           }
           enum "1554.31" {
             description "1554.31 nm/192.878125 THz 3.125GHz spacing";
           }
           enum "1554.29" {
             description "1554.29 nm/192.881250 THz 3.125/6.25GHz spacing";
           }
           enum "1554.26" {
             description "1554.26 nm/192.884375 THz 3.125GHz spacing";
           }
           enum "1554.23" {
             description "1554.23 nm/192.887500 THz 3.125/6.25/12.5GHz spacing";
           }
           enum "1554.21" {
             description "1554.21 nm/192.890625 THz 3.125GHz spacing";
           }
           enum "1554.18" {
             description "1554.18 nm/192.893750 THz 3.125/6.25GHz spacing";
           }
           enum "1554.16" {
             description "1554.16 nm/192.896875 THz 3.125GHz spacing";
           }
           enum "1554.13" {
             description "1554.13 nm/192.900000 THz 3.125/6.25/12.5/50/75/100GHz spacing";
           }
           enum "1554.11" {
             description "1554.11 nm/192.903125 THz 3.125GHz spacing";
           }
           enum "1554.08" {
             description "1554.08 nm/192.906250 THz 3.125/6.25GHz spacing";
           }
           enum "1554.06" {
             description "1554.06 nm/192.909375 THz 3.125GHz spacing";
           }
           enum "1554.03" {
             description "1554.03 nm/192.912500 THz 3.125/6.25/12.5GHz spacing";
           }
           enum "1554.01" {
             description "1554.01 nm/192.915625 THz 3.125GHz spacing";
           }
           enum "1553.98" {
             description "1553.98 nm/192.918750 THz 3.125/6.25GHz spacing";
           }
           enum "1553.96" {
             description "1553.96 nm/192.921875 THz 3.125GHz spacing";
           }
           enum "1553.93" {
             description "1553.93 nm/192.925000 THz 3.125/6.25/12.5GHz spacing";
           }
           enum "1553.91" {
             description "1553.91 nm/192.928125 THz 3.125GHz spacing";
           }
           enum "1553.88" {
             description "1553.88 nm/192.931250 THz 3.125/6.25GHz spacing";
           }
           enum "1553.86" {
             description "1553.86 nm/192.934375 THz 3.125GHz spacing";
           }
           enum "1553.83" {
             description "1553.83 nm/192.937500 THz 3.125/6.25/12.5GHz spacing";
           }
           enum "1553.81" {
             description "1553.81 nm/192.940625 THz 3.125GHz spacing";
           }
           enum "1553.78" {
             description "1553.78 nm/192.943750 THz 3.125/6.25GHz spacing";
           }
           enum "1553.76" {
             description "1553.76 nm/192.946875 THz 3.125GHz spacing";
           }
           enum "1553.73" {
             description "1553.73 nm/192.950000 THz 3.125/6.25/12.5/50GHz spacing";
           }
           enum "1553.71" {
             description "1553.71 nm/192.953125 THz 3.125GHz spacing";
           }
           enum "1553.68" {
             description "1553.68 nm/192.956250 THz 3.125/6.25GHz spacing";
           }
           enum "1553.66" {
             description "1553.66 nm/192.959375 THz 3.125GHz spacing";
           }
           enum "1553.63" {
             description "1553.63 nm/192.962500 THz 3.125/6.25/12.5GHz spacing";
           }
           enum "1553.61" {
             description "1553.61 nm/192.965625 THz 3.125GHz spacing";
           }
           enum "1553.58" {
             description "1553.58 nm/192.968750 THz 3.125/6.25GHz spacing";
           }
           enum "1553.56" {
             description "1553.56 nm/192.971875 THz 3.125GHz spacing";
           }
           enum "1553.53" {
             description "1553.53 nm/192.975000 THz 3.125/6.25/12.5/75GHz spacing";
           }
           enum "1553.50" {
             description "1553.50 nm/192.978125 THz 3.125GHz spacing";
           }
           enum "1553.48" {
             description "1553.48 nm/192.981250 THz 3.125/6.25GHz spacing";
           }
           enum "1553.45" {
             description "1553.45 nm/192.984375 THz 3.125GHz spacing";
           }
           enum "1553.43" {
             description "1553.43 nm/192.987500 THz 3.125/6.25/12.5GHz spacing";
           }
           enum "1553.40" {
             description "1553.40 nm/192.990625 THz 3.125GHz spacing";
           }
           enum "1553.38" {
             description "1553.38 nm/192.993750 THz 3.125/6.25GHz spacing";
           }
           enum "1553.35" {
             description "1553.35 nm/192.996875 THz 3.125GHz spacing";
           }
           enum "1553.33" {
             description "1553.33 nm/193.000000 THz 3.125/6.25/12.5/100GHz spacing";
           }
           enum "1553.30" {
             description "1553.30 nm/193.003125 THz 3.125GHz spacing";
           }
           enum "1553.28" {
             description "1553.28 nm/193.006250 THz 3.125/6.25GHz spacing";
           }
           enum "1553.25" {
             description "1553.25 nm/193.009375 THz 3.125GHz spacing";
           }
           enum "1553.23" {
             description "1553.23 nm/193.012500 THz 3.125/6.25/12.5GHz spacing";
           }
           enum "1553.20" {
             description "1553.20 nm/193.015625 THz 3.125GHz spacing";
           }
           enum "1553.18" {
             description "1553.18 nm/193.018750 THz 3.125/6.25GHz spacing";
           }
           enum "1553.15" {
             description "1553.15 nm/193.021875 THz 3.125GHz spacing";
           }
           enum "1553.13" {
             description "1553.13 nm/193.025000 THz 3.125/6.25/12.5GHz spacing";
           }
           enum "1553.10" {
             description "1553.10 nm/193.028125 THz 3.125GHz spacing";
           }
           enum "1553.08" {
             description "1553.08 nm/193.031250 THz 3.125/6.25GHz spacing";
           }
           enum "1553.05" {
             description "1553.05 nm/193.034375 THz 3.125GHz spacing";
           }
           enum "1553.03" {
             description "1553.03 nm/193.037500 THz 3.125/6.25/12.5GHz spacing";
           }
           enum "1553.00" {
             description "1553.00 nm/193.040625 THz 3.125GHz spacing";
           }
           enum "1552.98" {
             description "1552.98 nm/193.043750 THz 3.125/6.25GHz spacing";
           }
           enum "1552.95" {
             description "1552.95 nm/193.046875 THz 3.125GHz spacing";
           }
           enum "1552.93" {
             description "1552.93 nm/193.050000 THz 3.125/6.25/12.5/50/75GHz spacing";
           }
           enum "1552.90" {
             description "1552.90 nm/193.053125 THz 3.125GHz spacing";
           }
           enum "1552.88" {
             description "1552.88 nm/193.056250 THz 3.125/6.25GHz spacing";
           }
           enum "1552.85" {
             description "1552.85 nm/193.059375 THz 3.125GHz spacing";
           }
           enum "1552.83" {
             description "1552.83 nm/193.062500 THz 3.125/6.25/12.5GHz spacing";
           }
           enum "1552.80" {
             description "1552.80 nm/193.065625 THz 3.125GHz spacing";
           }
           enum "1552.78" {
             description "1552.78 nm/193.068750 THz 3.125/6.25GHz spacing";
           }
           enum "1552.75" {
             description "1552.75 nm/193.071875 THz 3.125GHz spacing";
           }
           enum "1552.73" {
             description "1552.73 nm/193.075000 THz 3.125/6.25/12.5GHz spacing";
           }
           enum "1552.70" {
             description "1552.70 nm/193.078125 THz 3.125GHz spacing";
           }
           enum "1552.68" {
             description "1552.68 nm/193.081250 THz 3.125/6.25GHz spacing";
           }
           enum "1552.65" {
             description "1552.65 nm/193.084375 THz 3.125GHz spacing";
           }
           enum "1552.62" {
             description "1552.62 nm/193.087500 THz 3.125/6.25/12.5GHz spacing";
           }
           enum "1552.60" {
             description "1552.60 nm/193.090625 THz 3.125GHz spacing";
           }
           enum "1552.57" {
             description "1552.57 nm/193.093750 THz 3.125/6.25GHz spacing";
           }
           enum "1552.55" {
             description "1552.55 nm/193.096875 THz 3.125GHz spacing";
           }
           enum "1552.52" {
             description "1552.52 nm/193.100000 THz 3.125/6.25/12.5/100GHz spacing";
           }
           enum "1552.50" {
             description "1552.50 nm/193.103125 THz 3.125GHz spacing";
           }
           enum "1552.47" {
             description "1552.47 nm/193.106250 THz 3.125/6.25GHz spacing";
           }
           enum "1552.45" {
             description "1552.45 nm/193.109375 THz 3.125GHz spacing";
           }
           enum "1552.42" {
             description "1552.42 nm/193.112500 THz 3.125/6.25/12.5GHz spacing";
           }
           enum "1552.40" {
             description "1552.40 nm/193.115625 THz 3.125GHz spacing";
           }
           enum "1552.37" {
             description "1552.37 nm/193.118750 THz 3.125/6.25GHz spacing";
           }
           enum "1552.35" {
             description "1552.35 nm/193.121875 THz 3.125GHz spacing";
           }
           enum "1552.32" {
             description "1552.32 nm/193.125000 THz 3.125/6.25/12.5/75GHz spacing";
           }
           enum "1552.30" {
             description "1552.30 nm/193.128125 THz 3.125GHz spacing";
           }
           enum "1552.27" {
             description "1552.27 nm/193.131250 THz 3.125/6.25GHz spacing";
           }
           enum "1552.25" {
             description "1552.25 nm/193.134375 THz 3.125GHz spacing";
           }
           enum "1552.22" {
             description "1552.22 nm/193.137500 THz 3.125/6.25/12.5GHz spacing";
           }
           enum "1552.20" {
             description "1552.20 nm/193.140625 THz 3.125GHz spacing";
           }
           enum "1552.17" {
             description "1552.17 nm/193.143750 THz 3.125/6.25GHz spacing";
           }
           enum "1552.15" {
             description "1552.15 nm/193.146875 THz 3.125GHz spacing";
           }
           enum "1552.12" {
             description "1552.12 nm/193.150000 THz 3.125/6.25/12.5/50GHz spacing";
           }
           enum "1552.10" {
             description "1552.10 nm/193.153125 THz 3.125GHz spacing";
           }
           enum "1552.07" {
             description "1552.07 nm/193.156250 THz 3.125/6.25GHz spacing";
           }
           enum "1552.05" {
             description "1552.05 nm/193.159375 THz 3.125GHz spacing";
           }
           enum "1552.02" {
             description "1552.02 nm/193.162500 THz 3.125/6.25/12.5GHz spacing";
           }
           enum "1552.00" {
             description "1552.00 nm/193.165625 THz 3.125GHz spacing";
           }
           enum "1551.97" {
             description "1551.97 nm/193.168750 THz 3.125/6.25GHz spacing";
           }
           enum "1551.95" {
             description "1551.95 nm/193.171875 THz 3.125GHz spacing";
           }
           enum "1551.92" {
             description "1551.92 nm/193.175000 THz 3.125/6.25/12.5GHz spacing";
           }
           enum "1551.90" {
             description "1551.90 nm/193.178125 THz 3.125GHz spacing";
           }
           enum "1551.87" {
             description "1551.87 nm/193.181250 THz 3.125/6.25GHz spacing";
           }
           enum "1551.85" {
             description "1551.85 nm/193.184375 THz 3.125GHz spacing";
           }
           enum "1551.82" {
             description "1551.82 nm/193.187500 THz 3.125/6.25/12.5GHz spacing";
           }
           enum "1551.80" {
             description "1551.80 nm/193.190625 THz 3.125GHz spacing";
           }
           enum "1551.77" {
             description "1551.77 nm/193.193750 THz 3.125/6.25GHz spacing";
           }
           enum "1551.75" {
             description "1551.75 nm/193.196875 THz 3.125GHz spacing";
           }
           enum "1551.72" {
             description "1551.72 nm/193.200000 THz 3.125/6.25/12.5/50/75/100GHz spacing";
           }
           enum "1551.70" {
             description "1551.70 nm/193.203125 THz 3.125GHz spacing";
           }
           enum "1551.67" {
             description "1551.67 nm/193.206250 THz 3.125/6.25GHz spacing";
           }
           enum "1551.65" {
             description "1551.65 nm/193.209375 THz 3.125GHz spacing";
           }
           enum "1551.62" {
             description "1551.62 nm/193.212500 THz 3.125/6.25/12.5GHz spacing";
           }
           enum "1551.60" {
             description "1551.60 nm/193.215625 THz 3.125GHz spacing";
           }
           enum "1551.57" {
             description "1551.57 nm/193.218750 THz 3.125/6.25GHz spacing";
           }
           enum "1551.55" {
             description "1551.55 nm/193.221875 THz 3.125GHz spacing";
           }
           enum "1551.52" {
             description "1551.52 nm/193.225000 THz 3.125/6.25/12.5GHz spacing";
           }
           enum "1551.49" {
             description "1551.49 nm/193.228125 THz 3.125GHz spacing";
           }
           enum "1551.47" {
             description "1551.47 nm/193.231250 THz 3.125/6.25GHz spacing";
           }
           enum "1551.44" {
             description "1551.44 nm/193.234375 THz 3.125GHz spacing";
           }
           enum "1551.42" {
             description "1551.42 nm/193.237500 THz 3.125/6.25/12.5GHz spacing";
           }
           enum "1551.39" {
             description "1551.39 nm/193.240625 THz 3.125GHz spacing";
           }
           enum "1551.37" {
             description "1551.37 nm/193.243750 THz 3.125/6.25GHz spacing";
           }
           enum "1551.34" {
             description "1551.34 nm/193.246875 THz 3.125GHz spacing";
           }
           enum "1551.32" {
             description "1551.32 nm/193.250000 THz 3.125/6.25/12.5/50GHz spacing";
           }
           enum "1551.29" {
             description "1551.29 nm/193.253125 THz 3.125GHz spacing";
           }
           enum "1551.27" {
             description "1551.27 nm/193.256250 THz 3.125/6.25GHz spacing";
           }
           enum "1551.24" {
             description "1551.24 nm/193.259375 THz 3.125GHz spacing";
           }
           enum "1551.22" {
             description "1551.22 nm/193.262500 THz 3.125/6.25/12.5GHz spacing";
           }
           enum "1551.19" {
             description "1551.19 nm/193.265625 THz 3.125GHz spacing";
           }
           enum "1551.17" {
             description "1551.17 nm/193.268750 THz 3.125/6.25GHz spacing";
           }
           enum "1551.14" {
             description "1551.14 nm/193.271875 THz 3.125GHz spacing";
           }
           enum "1551.12" {
             description "1551.12 nm/193.275000 THz 3.125/6.25/12.5/75GHz spacing";
           }
           enum "1551.09" {
             description "1551.09 nm/193.278125 THz 3.125GHz spacing";
           }
           enum "1551.07" {
             description "1551.07 nm/193.281250 THz 3.125/6.25GHz spacing";
           }
           enum "1551.04" {
             description "1551.04 nm/193.284375 THz 3.125GHz spacing";
           }
           enum "1551.02" {
             description "1551.02 nm/193.287500 THz 3.125/6.25/12.5GHz spacing";
           }
           enum "1550.99" {
             description "1550.99 nm/193.290625 THz 3.125GHz spacing";
           }
           enum "1550.97" {
             description "1550.97 nm/193.293750 THz 3.125/6.25GHz spacing";
           }
           enum "1550.94" {
             description "1550.94 nm/193.296875 THz 3.125GHz spacing";
           }
           enum "1550.92" {
             description "1550.92 nm/193.300000 THz 3.125/6.25/12.5/100GHz spacing";
           }
           enum "1550.89" {
             description "1550.89 nm/193.303125 THz 3.125GHz spacing";
           }
           enum "1550.87" {
             description "1550.87 nm/193.306250 THz 3.125/6.25GHz spacing";
           }
           enum "1550.84" {
             description "1550.84 nm/193.309375 THz 3.125GHz spacing";
           }
           enum "1550.82" {
             description "1550.82 nm/193.312500 THz 3.125/6.25/12.5GHz spacing";
           }
           enum "1550.79" {
             description "1550.79 nm/193.315625 THz 3.125GHz spacing";
           }
           enum "1550.77" {
             description "1550.77 nm/193.318750 THz 3.125/6.25GHz spacing";
           }
           enum "1550.74" {
             description "1550.74 nm/193.321875 THz 3.125GHz spacing";
           }
           enum "1550.72" {
             description "1550.72 nm/193.325000 THz 3.125/6.25/12.5GHz spacing";
           }
           enum "1550.69" {
             description "1550.69 nm/193.328125 THz 3.125GHz spacing";
           }
           enum "1550.67" {
             description "1550.67 nm/193.331250 THz 3.125/6.25GHz spacing";
           }
           enum "1550.64" {
             description "1550.64 nm/193.334375 THz 3.125GHz spacing";
           }
           enum "1550.62" {
             description "1550.62 nm/193.337500 THz 3.125/6.25/12.5GHz spacing";
           }
           enum "1550.59" {
             description "1550.59 nm/193.340625 THz 3.125GHz spacing";
           }
           enum "1550.57" {
             description "1550.57 nm/193.343750 THz 3.125/6.25GHz spacing";
           }
           enum "1550.54" {
             description "1550.54 nm/193.346875 THz 3.125GHz spacing";
           }
           enum "1550.52" {
             description "1550.52 nm/193.350000 THz 3.125/6.25/12.5/50/75GHz spacing";
           }
           enum "1550.49" {
             description "1550.49 nm/193.353125 THz 3.125GHz spacing";
           }
           enum "1550.47" {
             description "1550.47 nm/193.356250 THz 3.125/6.25GHz spacing";
           }
           enum "1550.44" {
             description "1550.44 nm/193.359375 THz 3.125GHz spacing";
           }
           enum "1550.42" {
             description "1550.42 nm/193.362500 THz 3.125/6.25/12.5GHz spacing";
           }
           enum "1550.39" {
             description "1550.39 nm/193.365625 THz 3.125GHz spacing";
           }
           enum "1550.37" {
             description "1550.37 nm/193.368750 THz 3.125/6.25GHz spacing";
           }
           enum "1550.34" {
             description "1550.34 nm/193.371875 THz 3.125GHz spacing";
           }
           enum "1550.32" {
             description "1550.32 nm/193.375000 THz 3.125/6.25/12.5GHz spacing";
           }
           enum "1550.29" {
             description "1550.29 nm/193.378125 THz 3.125GHz spacing";
           }
           enum "1550.27" {
             description "1550.27 nm/193.381250 THz 3.125/6.25GHz spacing";
           }
           enum "1550.24" {
             description "1550.24 nm/193.384375 THz 3.125GHz spacing";
           }
           enum "1550.22" {
             description "1550.22 nm/193.387500 THz 3.125/6.25/12.5GHz spacing";
           }
           enum "1550.19" {
             description "1550.19 nm/193.390625 THz 3.125GHz spacing";
           }
           enum "1550.17" {
             description "1550.17 nm/193.393750 THz 3.125/6.25GHz spacing";
           }
           enum "1550.14" {
             description "1550.14 nm/193.396875 THz 3.125GHz spacing";
           }
           enum "1550.12" {
             description "1550.12 nm/193.400000 THz 3.125/6.25/12.5/100GHz spacing";
           }
           enum "1550.09" {
             description "1550.09 nm/193.403125 THz 3.125GHz spacing";
           }
           enum "1550.07" {
             description "1550.07 nm/193.406250 THz 3.125/6.25GHz spacing";
           }
           enum "1550.04" {
             description "1550.04 nm/193.409375 THz 3.125GHz spacing";
           }
           enum "1550.02" {
             description "1550.02 nm/193.412500 THz 3.125/6.25/12.5GHz spacing";
           }
           enum "1549.99" {
             description "1549.99 nm/193.415625 THz 3.125GHz spacing";
           }
           enum "1549.97" {
             description "1549.97 nm/193.418750 THz 3.125/6.25GHz spacing";
           }
           enum "1549.94" {
             description "1549.94 nm/193.421875 THz 3.125GHz spacing";
           }
           enum "1549.92" {
             description "1549.92 nm/193.425000 THz 3.125/6.25/12.5/75GHz spacing";
           }
           enum "1549.89" {
             description "1549.89 nm/193.428125 THz 3.125GHz spacing";
           }
           enum "1549.87" {
             description "1549.87 nm/193.431250 THz 3.125/6.25GHz spacing";
           }
           enum "1549.84" {
             description "1549.84 nm/193.434375 THz 3.125GHz spacing";
           }
           enum "1549.82" {
             description "1549.82 nm/193.437500 THz 3.125/6.25/12.5GHz spacing";
           }
           enum "1549.79" {
             description "1549.79 nm/193.440625 THz 3.125GHz spacing";
           }
           enum "1549.77" {
             description "1549.77 nm/193.443750 THz 3.125/6.25GHz spacing";
           }
           enum "1549.74" {
             description "1549.74 nm/193.446875 THz 3.125GHz spacing";
           }
           enum "1549.72" {
             description "1549.72 nm/193.450000 THz 3.125/6.25/12.5/50GHz spacing";
           }
           enum "1549.69" {
             description "1549.69 nm/193.453125 THz 3.125GHz spacing";
           }
           enum "1549.67" {
             description "1549.67 nm/193.456250 THz 3.125/6.25GHz spacing";
           }
           enum "1549.64" {
             description "1549.64 nm/193.459375 THz 3.125GHz spacing";
           }
           enum "1549.62" {
             description "1549.62 nm/193.462500 THz 3.125/6.25/12.5GHz spacing";
           }
           enum "1549.59" {
             description "1549.59 nm/193.465625 THz 3.125GHz spacing";
           }
           enum "1549.57" {
             description "1549.57 nm/193.468750 THz 3.125/6.25GHz spacing";
           }
           enum "1549.54" {
             description "1549.54 nm/193.471875 THz 3.125GHz spacing";
           }
           enum "1549.52" {
             description "1549.52 nm/193.475000 THz 3.125/6.25/12.5GHz spacing";
           }
           enum "1549.49" {
             description "1549.49 nm/193.478125 THz 3.125GHz spacing";
           }
           enum "1549.47" {
             description "1549.47 nm/193.481250 THz 3.125/6.25GHz spacing";
           }
           enum "1549.44" {
             description "1549.44 nm/193.484375 THz 3.125GHz spacing";
           }
           enum "1549.42" {
             description "1549.42 nm/193.487500 THz 3.125/6.25/12.5GHz spacing";
           }
           enum "1549.39" {
             description "1549.39 nm/193.490625 THz 3.125GHz spacing";
           }
           enum "1549.37" {
             description "1549.37 nm/193.493750 THz 3.125/6.25GHz spacing";
           }
           enum "1549.34" {
             description "1549.34 nm/193.496875 THz 3.125GHz spacing";
           }
           enum "1549.32" {
             description "1549.32 nm/193.500000 THz 3.125/6.25/12.5/50/75/100GHz spacing";
           }
           enum "1549.29" {
             description "1549.29 nm/193.503125 THz 3.125GHz spacing";
           }
           enum "1549.26" {
             description "1549.26 nm/193.506250 THz 3.125/6.25GHz spacing";
           }
           enum "1549.24" {
             description "1549.24 nm/193.509375 THz 3.125GHz spacing";
           }
           enum "1549.21" {
             description "1549.21 nm/193.512500 THz 3.125/6.25/12.5GHz spacing";
           }
           enum "1549.19" {
             description "1549.19 nm/193.515625 THz 3.125GHz spacing";
           }
           enum "1549.16" {
             description "1549.16 nm/193.518750 THz 3.125/6.25GHz spacing";
           }
           enum "1549.14" {
             description "1549.14 nm/193.521875 THz 3.125GHz spacing";
           }
           enum "1549.11" {
             description "1549.11 nm/193.525000 THz 3.125/6.25/12.5GHz spacing";
           }
           enum "1549.09" {
             description "1549.09 nm/193.528125 THz 3.125GHz spacing";
           }
           enum "1549.06" {
             description "1549.06 nm/193.531250 THz 3.125/6.25GHz spacing";
           }
           enum "1549.04" {
             description "1549.04 nm/193.534375 THz 3.125GHz spacing";
           }
           enum "1549.01" {
             description "1549.01 nm/193.537500 THz 3.125/6.25/12.5GHz spacing";
           }
           enum "1548.99" {
             description "1548.99 nm/193.540625 THz 3.125GHz spacing";
           }
           enum "1548.96" {
             description "1548.96 nm/193.543750 THz 3.125/6.25GHz spacing";
           }
           enum "1548.94" {
             description "1548.94 nm/193.546875 THz 3.125GHz spacing";
           }
           enum "1548.91" {
             description "1548.91 nm/193.550000 THz 3.125/6.25/12.5/50GHz spacing";
           }
           enum "1548.89" {
             description "1548.89 nm/193.553125 THz 3.125GHz spacing";
           }
           enum "1548.86" {
             description "1548.86 nm/193.556250 THz 3.125/6.25GHz spacing";
           }
           enum "1548.84" {
             description "1548.84 nm/193.559375 THz 3.125GHz spacing";
           }
           enum "1548.81" {
             description "1548.81 nm/193.562500 THz 3.125/6.25/12.5GHz spacing";
           }
           enum "1548.79" {
             description "1548.79 nm/193.565625 THz 3.125GHz spacing";
           }
           enum "1548.76" {
             description "1548.76 nm/193.568750 THz 3.125/6.25GHz spacing";
           }
           enum "1548.74" {
             description "1548.74 nm/193.571875 THz 3.125GHz spacing";
           }
           enum "1548.71" {
             description "1548.71 nm/193.575000 THz 3.125/6.25/12.5/75GHz spacing";
           }
           enum "1548.69" {
             description "1548.69 nm/193.578125 THz 3.125GHz spacing";
           }
           enum "1548.66" {
             description "1548.66 nm/193.581250 THz 3.125/6.25GHz spacing";
           }
           enum "1548.64" {
             description "1548.64 nm/193.584375 THz 3.125GHz spacing";
           }
           enum "1548.61" {
             description "1548.61 nm/193.587500 THz 3.125/6.25/12.5GHz spacing";
           }
           enum "1548.59" {
             description "1548.59 nm/193.590625 THz 3.125GHz spacing";
           }
           enum "1548.56" {
             description "1548.56 nm/193.593750 THz 3.125/6.25GHz spacing";
           }
           enum "1548.54" {
             description "1548.54 nm/193.596875 THz 3.125GHz spacing";
           }
           enum "1548.51" {
             description "1548.51 nm/193.600000 THz 3.125/6.25/12.5/100GHz spacing";
           }
           enum "1548.49" {
             description "1548.49 nm/193.603125 THz 3.125GHz spacing";
           }
           enum "1548.46" {
             description "1548.46 nm/193.606250 THz 3.125/6.25GHz spacing";
           }
           enum "1548.44" {
             description "1548.44 nm/193.609375 THz 3.125GHz spacing";
           }
           enum "1548.41" {
             description "1548.41 nm/193.612500 THz 3.125/6.25/12.5GHz spacing";
           }
           enum "1548.39" {
             description "1548.39 nm/193.615625 THz 3.125GHz spacing";
           }
           enum "1548.36" {
             description "1548.36 nm/193.618750 THz 3.125/6.25GHz spacing";
           }
           enum "1548.34" {
             description "1548.34 nm/193.621875 THz 3.125GHz spacing";
           }
           enum "1548.31" {
             description "1548.31 nm/193.625000 THz 3.125/6.25/12.5GHz spacing";
           }
           enum "1548.29" {
             description "1548.29 nm/193.628125 THz 3.125GHz spacing";
           }
           enum "1548.26" {
             description "1548.26 nm/193.631250 THz 3.125/6.25GHz spacing";
           }
           enum "1548.24" {
             description "1548.24 nm/193.634375 THz 3.125GHz spacing";
           }
           enum "1548.21" {
             description "1548.21 nm/193.637500 THz 3.125/6.25/12.5GHz spacing";
           }
           enum "1548.19" {
             description "1548.19 nm/193.640625 THz 3.125GHz spacing";
           }
           enum "1548.16" {
             description "1548.16 nm/193.643750 THz 3.125/6.25GHz spacing";
           }
           enum "1548.14" {
             description "1548.14 nm/193.646875 THz 3.125GHz spacing";
           }
           enum "1548.11" {
             description "1548.11 nm/193.650000 THz 3.125/6.25/12.5/50/75GHz spacing";
           }
           enum "1548.09" {
             description "1548.09 nm/193.653125 THz 3.125GHz spacing";
           }
           enum "1548.06" {
             description "1548.06 nm/193.656250 THz 3.125/6.25GHz spacing";
           }
           enum "1548.04" {
             description "1548.04 nm/193.659375 THz 3.125GHz spacing";
           }
           enum "1548.02" {
             description "1548.02 nm/193.662500 THz 3.125/6.25/12.5GHz spacing";
           }
           enum "1547.99" {
             description "1547.99 nm/193.665625 THz 3.125GHz spacing";
           }
           enum "1547.97" {
             description "1547.97 nm/193.668750 THz 3.125/6.25GHz spacing";
           }
           enum "1547.94" {
             description "1547.94 nm/193.671875 THz 3.125GHz spacing";
           }
           enum "1547.92" {
             description "1547.92 nm/193.675000 THz 3.125/6.25/12.5GHz spacing";
           }
           enum "1547.89" {
             description "1547.89 nm/193.678125 THz 3.125GHz spacing";
           }
           enum "1547.87" {
             description "1547.87 nm/193.681250 THz 3.125/6.25GHz spacing";
           }
           enum "1547.84" {
             description "1547.84 nm/193.684375 THz 3.125GHz spacing";
           }
           enum "1547.82" {
             description "1547.82 nm/193.687500 THz 3.125/6.25/12.5GHz spacing";
           }
           enum "1547.79" {
             description "1547.79 nm/193.690625 THz 3.125GHz spacing";
           }
           enum "1547.77" {
             description "1547.77 nm/193.693750 THz 3.125/6.25GHz spacing";
           }
           enum "1547.74" {
             description "1547.74 nm/193.696875 THz 3.125GHz spacing";
           }
           enum "1547.72" {
             description "1547.72 nm/193.700000 THz 3.125/6.25/12.5/100GHz spacing";
           }
           enum "1547.69" {
             description "1547.69 nm/193.703125 THz 3.125GHz spacing";
           }
           enum "1547.67" {
             description "1547.67 nm/193.706250 THz 3.125/6.25GHz spacing";
           }
           enum "1547.64" {
             description "1547.64 nm/193.709375 THz 3.125GHz spacing";
           }
           enum "1547.62" {
             description "1547.62 nm/193.712500 THz 3.125/6.25/12.5GHz spacing";
           }
           enum "1547.59" {
             description "1547.59 nm/193.715625 THz 3.125GHz spacing";
           }
           enum "1547.57" {
             description "1547.57 nm/193.718750 THz 3.125/6.25GHz spacing";
           }
           enum "1547.54" {
             description "1547.54 nm/193.721875 THz 3.125GHz spacing";
           }
           enum "1547.52" {
             description "1547.52 nm/193.725000 THz 3.125/6.25/12.5/75GHz spacing";
           }
           enum "1547.49" {
             description "1547.49 nm/193.728125 THz 3.125GHz spacing";
           }
           enum "1547.47" {
             description "1547.47 nm/193.731250 THz 3.125/6.25GHz spacing";
           }
           enum "1547.44" {
             description "1547.44 nm/193.734375 THz 3.125GHz spacing";
           }
           enum "1547.42" {
             description "1547.42 nm/193.737500 THz 3.125/6.25/12.5GHz spacing";
           }
           enum "1547.39" {
             description "1547.39 nm/193.740625 THz 3.125GHz spacing";
           }
           enum "1547.37" {
             description "1547.37 nm/193.743750 THz 3.125/6.25GHz spacing";
           }
           enum "1547.34" {
             description "1547.34 nm/193.746875 THz 3.125GHz spacing";
           }
           enum "1547.32" {
             description "1547.32 nm/193.750000 THz 3.125/6.25/12.5/50GHz spacing";
           }
           enum "1547.29" {
             description "1547.29 nm/193.753125 THz 3.125GHz spacing";
           }
           enum "1547.27" {
             description "1547.27 nm/193.756250 THz 3.125/6.25GHz spacing";
           }
           enum "1547.24" {
             description "1547.24 nm/193.759375 THz 3.125GHz spacing";
           }
           enum "1547.22" {
             description "1547.22 nm/193.762500 THz 3.125/6.25/12.5GHz spacing";
           }
           enum "1547.19" {
             description "1547.19 nm/193.765625 THz 3.125GHz spacing";
           }
           enum "1547.17" {
             description "1547.17 nm/193.768750 THz 3.125/6.25GHz spacing";
           }
           enum "1547.14" {
             description "1547.14 nm/193.771875 THz 3.125GHz spacing";
           }
           enum "1547.12" {
             description "1547.12 nm/193.775000 THz 3.125/6.25/12.5GHz spacing";
           }
           enum "1547.09" {
             description "1547.09 nm/193.778125 THz 3.125GHz spacing";
           }
           enum "1547.07" {
             description "1547.07 nm/193.781250 THz 3.125/6.25GHz spacing";
           }
           enum "1547.04" {
             description "1547.04 nm/193.784375 THz 3.125GHz spacing";
           }
           enum "1547.02" {
             description "1547.02 nm/193.787500 THz 3.125/6.25/12.5GHz spacing";
           }
           enum "1546.99" {
             description "1546.99 nm/193.790625 THz 3.125GHz spacing";
           }
           enum "1546.97" {
             description "1546.97 nm/193.793750 THz 3.125/6.25GHz spacing";
           }
           enum "1546.94" {
             description "1546.94 nm/193.796875 THz 3.125GHz spacing";
           }
           enum "1546.92" {
             description "1546.92 nm/193.800000 THz 3.125/6.25/12.5/50/75/100GHz spacing";
           }
           enum "1546.89" {
             description "1546.89 nm/193.803125 THz 3.125GHz spacing";
           }
           enum "1546.87" {
             description "1546.87 nm/193.806250 THz 3.125/6.25GHz spacing";
           }
           enum "1546.84" {
             description "1546.84 nm/193.809375 THz 3.125GHz spacing";
           }
           enum "1546.82" {
             description "1546.82 nm/193.812500 THz 3.125/6.25/12.5GHz spacing";
           }
           enum "1546.79" {
             description "1546.79 nm/193.815625 THz 3.125GHz spacing";
           }
           enum "1546.77" {
             description "1546.77 nm/193.818750 THz 3.125/6.25GHz spacing";
           }
           enum "1546.74" {
             description "1546.74 nm/193.821875 THz 3.125GHz spacing";
           }
           enum "1546.72" {
             description "1546.72 nm/193.825000 THz 3.125/6.25/12.5GHz spacing";
           }
           enum "1546.69" {
             description "1546.69 nm/193.828125 THz 3.125GHz spacing";
           }
           enum "1546.67" {
             description "1546.67 nm/193.831250 THz 3.125/6.25GHz spacing";
           }
           enum "1546.64" {
             description "1546.64 nm/193.834375 THz 3.125GHz spacing";
           }
           enum "1546.62" {
             description "1546.62 nm/193.837500 THz 3.125/6.25/12.5GHz spacing";
           }
           enum "1546.59" {
             description "1546.59 nm/193.840625 THz 3.125GHz spacing";
           }
           enum "1546.57" {
             description "1546.57 nm/193.843750 THz 3.125/6.25GHz spacing";
           }
           enum "1546.54" {
             description "1546.54 nm/193.846875 THz 3.125GHz spacing";
           }
           enum "1546.52" {
             description "1546.52 nm/193.850000 THz 3.125/6.25/12.5/50GHz spacing";
           }
           enum "1546.49" {
             description "1546.49 nm/193.853125 THz 3.125GHz spacing";
           }
           enum "1546.47" {
             description "1546.47 nm/193.856250 THz 3.125/6.25GHz spacing";
           }
           enum "1546.44" {
             description "1546.44 nm/193.859375 THz 3.125GHz spacing";
           }
           enum "1546.42" {
             description "1546.42 nm/193.862500 THz 3.125/6.25/12.5GHz spacing";
           }
           enum "1546.39" {
             description "1546.39 nm/193.865625 THz 3.125GHz spacing";
           }
           enum "1546.37" {
             description "1546.37 nm/193.868750 THz 3.125/6.25GHz spacing";
           }
           enum "1546.34" {
             description "1546.34 nm/193.871875 THz 3.125GHz spacing";
           }
           enum "1546.32" {
             description "1546.32 nm/193.875000 THz 3.125/6.25/12.5/75GHz spacing";
           }
           enum "1546.29" {
             description "1546.29 nm/193.878125 THz 3.125GHz spacing";
           }
           enum "1546.27" {
             description "1546.27 nm/193.881250 THz 3.125/6.25GHz spacing";
           }
           enum "1546.24" {
             description "1546.24 nm/193.884375 THz 3.125GHz spacing";
           }
           enum "1546.22" {
             description "1546.22 nm/193.887500 THz 3.125/6.25/12.5GHz spacing";
           }
           enum "1546.19" {
             description "1546.19 nm/193.890625 THz 3.125GHz spacing";
           }
           enum "1546.17" {
             description "1546.17 nm/193.893750 THz 3.125/6.25GHz spacing";
           }
           enum "1546.14" {
             description "1546.14 nm/193.896875 THz 3.125GHz spacing";
           }
           enum "1546.12" {
             description "1546.12 nm/193.900000 THz 3.125/6.25/12.5/100GHz spacing";
           }
           enum "1546.09" {
             description "1546.09 nm/193.903125 THz 3.125GHz spacing";
           }
           enum "1546.07" {
             description "1546.07 nm/193.906250 THz 3.125/6.25GHz spacing";
           }
           enum "1546.04" {
             description "1546.04 nm/193.909375 THz 3.125GHz spacing";
           }
           enum "1546.02" {
             description "1546.02 nm/193.912500 THz 3.125/6.25/12.5GHz spacing";
           }
           enum "1545.99" {
             description "1545.99 nm/193.915625 THz 3.125GHz spacing";
           }
           enum "1545.97" {
             description "1545.97 nm/193.918750 THz 3.125/6.25GHz spacing";
           }
           enum "1545.94" {
             description "1545.94 nm/193.921875 THz 3.125GHz spacing";
           }
           enum "1545.92" {
             description "1545.92 nm/193.925000 THz 3.125/6.25/12.5GHz spacing";
           }
           enum "1545.89" {
             description "1545.89 nm/193.928125 THz 3.125GHz spacing";
           }
           enum "1545.87" {
             description "1545.87 nm/193.931250 THz 3.125/6.25GHz spacing";
           }
           enum "1545.84" {
             description "1545.84 nm/193.934375 THz 3.125GHz spacing";
           }
           enum "1545.82" {
             description "1545.82 nm/193.937500 THz 3.125/6.25/12.5GHz spacing";
           }
           enum "1545.80" {
             description "1545.80 nm/193.940625 THz 3.125GHz spacing";
           }
           enum "1545.77" {
             description "1545.77 nm/193.943750 THz 3.125/6.25GHz spacing";
           }
           enum "1545.75" {
             description "1545.75 nm/193.946875 THz 3.125GHz spacing";
           }
           enum "1545.72" {
             description "1545.72 nm/193.950000 THz 3.125/6.25/12.5/50/75GHz spacing";
           }
           enum "1545.70" {
             description "1545.70 nm/193.953125 THz 3.125GHz spacing";
           }
           enum "1545.67" {
             description "1545.67 nm/193.956250 THz 3.125/6.25GHz spacing";
           }
           enum "1545.65" {
             description "1545.65 nm/193.959375 THz 3.125GHz spacing";
           }
           enum "1545.62" {
             description "1545.62 nm/193.962500 THz 3.125/6.25/12.5GHz spacing";
           }
           enum "1545.60" {
             description "1545.60 nm/193.965625 THz 3.125GHz spacing";
           }
           enum "1545.57" {
             description "1545.57 nm/193.968750 THz 3.125/6.25GHz spacing";
           }
           enum "1545.55" {
             description "1545.55 nm/193.971875 THz 3.125GHz spacing";
           }
           enum "1545.52" {
             description "1545.52 nm/193.975000 THz 3.125/6.25/12.5GHz spacing";
           }
           enum "1545.50" {
             description "1545.50 nm/193.978125 THz 3.125GHz spacing";
           }
           enum "1545.47" {
             description "1545.47 nm/193.981250 THz 3.125/6.25GHz spacing";
           }
           enum "1545.45" {
             description "1545.45 nm/193.984375 THz 3.125GHz spacing";
           }
           enum "1545.42" {
             description "1545.42 nm/193.987500 THz 3.125/6.25/12.5GHz spacing";
           }
           enum "1545.40" {
             description "1545.40 nm/193.990625 THz 3.125GHz spacing";
           }
           enum "1545.37" {
             description "1545.37 nm/193.993750 THz 3.125/6.25GHz spacing";
           }
           enum "1545.35" {
             description "1545.35 nm/193.996875 THz 3.125GHz spacing";
           }
           enum "1545.32" {
             description "1545.32 nm/194.000000 THz 3.125/6.25/12.5/100GHz spacing";
           }
           enum "1545.30" {
             description "1545.30 nm/194.003125 THz 3.125GHz spacing";
           }
           enum "1545.27" {
             description "1545.27 nm/194.006250 THz 3.125/6.25GHz spacing";
           }
           enum "1545.25" {
             description "1545.25 nm/194.009375 THz 3.125GHz spacing";
           }
           enum "1545.22" {
             description "1545.22 nm/194.012500 THz 3.125/6.25/12.5GHz spacing";
           }
           enum "1545.20" {
             description "1545.20 nm/194.015625 THz 3.125GHz spacing";
           }
           enum "1545.17" {
             description "1545.17 nm/194.018750 THz 3.125/6.25GHz spacing";
           }
           enum "1545.15" {
             description "1545.15 nm/194.021875 THz 3.125GHz spacing";
           }
           enum "1545.12" {
             description "1545.12 nm/194.025000 THz 3.125/6.25/12.5/75GHz spacing";
           }
           enum "1545.10" {
             description "1545.10 nm/194.028125 THz 3.125GHz spacing";
           }
           enum "1545.07" {
             description "1545.07 nm/194.031250 THz 3.125/6.25GHz spacing";
           }
           enum "1545.05" {
             description "1545.05 nm/194.034375 THz 3.125GHz spacing";
           }
           enum "1545.02" {
             description "1545.02 nm/194.037500 THz 3.125/6.25/12.5GHz spacing";
           }
           enum "1545.00" {
             description "1545.00 nm/194.040625 THz 3.125GHz spacing";
           }
           enum "1544.97" {
             description "1544.97 nm/194.043750 THz 3.125/6.25GHz spacing";
           }
           enum "1544.95" {
             description "1544.95 nm/194.046875 THz 3.125GHz spacing";
           }
           enum "1544.92" {
             description "1544.92 nm/194.050000 THz 3.125/6.25/12.5/50GHz spacing";
           }
           enum "1544.90" {
             description "1544.90 nm/194.053125 THz 3.125GHz spacing";
           }
           enum "1544.87" {
             description "1544.87 nm/194.056250 THz 3.125/6.25GHz spacing";
           }
           enum "1544.85" {
             description "1544.85 nm/194.059375 THz 3.125GHz spacing";
           }
           enum "1544.82" {
             description "1544.82 nm/194.062500 THz 3.125/6.25/12.5GHz spacing";
           }
           enum "1544.80" {
             description "1544.80 nm/194.065625 THz 3.125GHz spacing";
           }
           enum "1544.77" {
             description "1544.77 nm/194.068750 THz 3.125/6.25GHz spacing";
           }
           enum "1544.75" {
             description "1544.75 nm/194.071875 THz 3.125GHz spacing";
           }
           enum "1544.72" {
             description "1544.72 nm/194.075000 THz 3.125/6.25/12.5GHz spacing";
           }
           enum "1544.70" {
             description "1544.70 nm/194.078125 THz 3.125GHz spacing";
           }
           enum "1544.68" {
             description "1544.68 nm/194.081250 THz 3.125/6.25GHz spacing";
           }
           enum "1544.65" {
             description "1544.65 nm/194.084375 THz 3.125GHz spacing";
           }
           enum "1544.63" {
             description "1544.63 nm/194.087500 THz 3.125/6.25/12.5GHz spacing";
           }
           enum "1544.60" {
             description "1544.60 nm/194.090625 THz 3.125GHz spacing";
           }
           enum "1544.58" {
             description "1544.58 nm/194.093750 THz 3.125/6.25GHz spacing";
           }
           enum "1544.55" {
             description "1544.55 nm/194.096875 THz 3.125GHz spacing";
           }
           enum "1544.53" {
             description "1544.53 nm/194.100000 THz 3.125/6.25/12.5/50/75/100GHz spacing";
           }
           enum "1544.50" {
             description "1544.50 nm/194.103125 THz 3.125GHz spacing";
           }
           enum "1544.48" {
             description "1544.48 nm/194.106250 THz 3.125/6.25GHz spacing";
           }
           enum "1544.45" {
             description "1544.45 nm/194.109375 THz 3.125GHz spacing";
           }
           enum "1544.43" {
             description "1544.43 nm/194.112500 THz 3.125/6.25/12.5GHz spacing";
           }
           enum "1544.40" {
             description "1544.40 nm/194.115625 THz 3.125GHz spacing";
           }
           enum "1544.38" {
             description "1544.38 nm/194.118750 THz 3.125/6.25GHz spacing";
           }
           enum "1544.35" {
             description "1544.35 nm/194.121875 THz 3.125GHz spacing";
           }
           enum "1544.33" {
             description "1544.33 nm/194.125000 THz 3.125/6.25/12.5GHz spacing";
           }
           enum "1544.30" {
             description "1544.30 nm/194.128125 THz 3.125GHz spacing";
           }
           enum "1544.28" {
             description "1544.28 nm/194.131250 THz 3.125/6.25GHz spacing";
           }
           enum "1544.25" {
             description "1544.25 nm/194.134375 THz 3.125GHz spacing";
           }
           enum "1544.23" {
             description "1544.23 nm/194.137500 THz 3.125/6.25/12.5GHz spacing";
           }
           enum "1544.20" {
             description "1544.20 nm/194.140625 THz 3.125GHz spacing";
           }
           enum "1544.18" {
             description "1544.18 nm/194.143750 THz 3.125/6.25GHz spacing";
           }
           enum "1544.15" {
             description "1544.15 nm/194.146875 THz 3.125GHz spacing";
           }
           enum "1544.13" {
             description "1544.13 nm/194.150000 THz 3.125/6.25/12.5/50GHz spacing";
           }
           enum "1544.10" {
             description "1544.10 nm/194.153125 THz 3.125GHz spacing";
           }
           enum "1544.08" {
             description "1544.08 nm/194.156250 THz 3.125/6.25GHz spacing";
           }
           enum "1544.05" {
             description "1544.05 nm/194.159375 THz 3.125GHz spacing";
           }
           enum "1544.03" {
             description "1544.03 nm/194.162500 THz 3.125/6.25/12.5GHz spacing";
           }
           enum "1544.00" {
             description "1544.00 nm/194.165625 THz 3.125GHz spacing";
           }
           enum "1543.98" {
             description "1543.98 nm/194.168750 THz 3.125/6.25GHz spacing";
           }
           enum "1543.95" {
             description "1543.95 nm/194.171875 THz 3.125GHz spacing";
           }
           enum "1543.93" {
             description "1543.93 nm/194.175000 THz 3.125/6.25/12.5/75GHz spacing";
           }
           enum "1543.90" {
             description "1543.90 nm/194.178125 THz 3.125GHz spacing";
           }
           enum "1543.88" {
             description "1543.88 nm/194.181250 THz 3.125/6.25GHz spacing";
           }
           enum "1543.85" {
             description "1543.85 nm/194.184375 THz 3.125GHz spacing";
           }
           enum "1543.83" {
             description "1543.83 nm/194.187500 THz 3.125/6.25/12.5GHz spacing";
           }
           enum "1543.81" {
             description "1543.81 nm/194.190625 THz 3.125GHz spacing";
           }
           enum "1543.78" {
             description "1543.78 nm/194.193750 THz 3.125/6.25GHz spacing";
           }
           enum "1543.76" {
             description "1543.76 nm/194.196875 THz 3.125GHz spacing";
           }
           enum "1543.73" {
             description "1543.73 nm/194.200000 THz 3.125/6.25/12.5/100GHz spacing";
           }
           enum "1543.71" {
             description "1543.71 nm/194.203125 THz 3.125GHz spacing";
           }
           enum "1543.68" {
             description "1543.68 nm/194.206250 THz 3.125/6.25GHz spacing";
           }
           enum "1543.66" {
             description "1543.66 nm/194.209375 THz 3.125GHz spacing";
           }
           enum "1543.63" {
             description "1543.63 nm/194.212500 THz 3.125/6.25/12.5GHz spacing";
           }
           enum "1543.61" {
             description "1543.61 nm/194.215625 THz 3.125GHz spacing";
           }
           enum "1543.58" {
             description "1543.58 nm/194.218750 THz 3.125/6.25GHz spacing";
           }
           enum "1543.56" {
             description "1543.56 nm/194.221875 THz 3.125GHz spacing";
           }
           enum "1543.53" {
             description "1543.53 nm/194.225000 THz 3.125/6.25/12.5GHz spacing";
           }
           enum "1543.51" {
             description "1543.51 nm/194.228125 THz 3.125GHz spacing";
           }
           enum "1543.48" {
             description "1543.48 nm/194.231250 THz 3.125/6.25GHz spacing";
           }
           enum "1543.46" {
             description "1543.46 nm/194.234375 THz 3.125GHz spacing";
           }
           enum "1543.43" {
             description "1543.43 nm/194.237500 THz 3.125/6.25/12.5GHz spacing";
           }
           enum "1543.41" {
             description "1543.41 nm/194.240625 THz 3.125GHz spacing";
           }
           enum "1543.38" {
             description "1543.38 nm/194.243750 THz 3.125/6.25GHz spacing";
           }
           enum "1543.36" {
             description "1543.36 nm/194.246875 THz 3.125GHz spacing";
           }
           enum "1543.33" {
             description "1543.33 nm/194.250000 THz 3.125/6.25/12.5/50/75GHz spacing";
           }
           enum "1543.31" {
             description "1543.31 nm/194.253125 THz 3.125GHz spacing";
           }
           enum "1543.28" {
             description "1543.28 nm/194.256250 THz 3.125/6.25GHz spacing";
           }
           enum "1543.26" {
             description "1543.26 nm/194.259375 THz 3.125GHz spacing";
           }
           enum "1543.23" {
             description "1543.23 nm/194.262500 THz 3.125/6.25/12.5GHz spacing";
           }
           enum "1543.21" {
             description "1543.21 nm/194.265625 THz 3.125GHz spacing";
           }
           enum "1543.18" {
             description "1543.18 nm/194.268750 THz 3.125/6.25GHz spacing";
           }
           enum "1543.16" {
             description "1543.16 nm/194.271875 THz 3.125GHz spacing";
           }
           enum "1543.13" {
             description "1543.13 nm/194.275000 THz 3.125/6.25/12.5GHz spacing";
           }
           enum "1543.11" {
             description "1543.11 nm/194.278125 THz 3.125GHz spacing";
           }
           enum "1543.08" {
             description "1543.08 nm/194.281250 THz 3.125/6.25GHz spacing";
           }
           enum "1543.06" {
             description "1543.06 nm/194.284375 THz 3.125GHz spacing";
           }
           enum "1543.04" {
             description "1543.04 nm/194.287500 THz 3.125/6.25/12.5GHz spacing";
           }
           enum "1543.01" {
             description "1543.01 nm/194.290625 THz 3.125GHz spacing";
           }
           enum "1542.99" {
             description "1542.99 nm/194.293750 THz 3.125/6.25GHz spacing";
           }
           enum "1542.96" {
             description "1542.96 nm/194.296875 THz 3.125GHz spacing";
           }
           enum "1542.94" {
             description "1542.94 nm/194.300000 THz 3.125/6.25/12.5/100GHz spacing";
           }
           enum "1542.91" {
             description "1542.91 nm/194.303125 THz 3.125GHz spacing";
           }
           enum "1542.89" {
             description "1542.89 nm/194.306250 THz 3.125/6.25GHz spacing";
           }
           enum "1542.86" {
             description "1542.86 nm/194.309375 THz 3.125GHz spacing";
           }
           enum "1542.84" {
             description "1542.84 nm/194.312500 THz 3.125/6.25/12.5GHz spacing";
           }
           enum "1542.81" {
             description "1542.81 nm/194.315625 THz 3.125GHz spacing";
           }
           enum "1542.79" {
             description "1542.79 nm/194.318750 THz 3.125/6.25GHz spacing";
           }
           enum "1542.76" {
             description "1542.76 nm/194.321875 THz 3.125GHz spacing";
           }
           enum "1542.74" {
             description "1542.74 nm/194.325000 THz 3.125/6.25/12.5/75GHz spacing";
           }
           enum "1542.71" {
             description "1542.71 nm/194.328125 THz 3.125GHz spacing";
           }
           enum "1542.69" {
             description "1542.69 nm/194.331250 THz 3.125/6.25GHz spacing";
           }
           enum "1542.66" {
             description "1542.66 nm/194.334375 THz 3.125GHz spacing";
           }
           enum "1542.64" {
             description "1542.64 nm/194.337500 THz 3.125/6.25/12.5GHz spacing";
           }
           enum "1542.61" {
             description "1542.61 nm/194.340625 THz 3.125GHz spacing";
           }
           enum "1542.59" {
             description "1542.59 nm/194.343750 THz 3.125/6.25GHz spacing";
           }
           enum "1542.56" {
             description "1542.56 nm/194.346875 THz 3.125GHz spacing";
           }
           enum "1542.54" {
             description "1542.54 nm/194.350000 THz 3.125/6.25/12.5/50GHz spacing";
           }
           enum "1542.51" {
             description "1542.51 nm/194.353125 THz 3.125GHz spacing";
           }
           enum "1542.49" {
             description "1542.49 nm/194.356250 THz 3.125/6.25GHz spacing";
           }
           enum "1542.46" {
             description "1542.46 nm/194.359375 THz 3.125GHz spacing";
           }
           enum "1542.44" {
             description "1542.44 nm/194.362500 THz 3.125/6.25/12.5GHz spacing";
           }
           enum "1542.42" {
             description "1542.42 nm/194.365625 THz 3.125GHz spacing";
           }
           enum "1542.39" {
             description "1542.39 nm/194.368750 THz 3.125/6.25GHz spacing";
           }
           enum "1542.37" {
             description "1542.37 nm/194.371875 THz 3.125GHz spacing";
           }
           enum "1542.34" {
             description "1542.34 nm/194.375000 THz 3.125/6.25/12.5GHz spacing";
           }
           enum "1542.32" {
             description "1542.32 nm/194.378125 THz 3.125GHz spacing";
           }
           enum "1542.29" {
             description "1542.29 nm/194.381250 THz 3.125/6.25GHz spacing";
           }
           enum "1542.27" {
             description "1542.27 nm/194.384375 THz 3.125GHz spacing";
           }
           enum "1542.24" {
             description "1542.24 nm/194.387500 THz 3.125/6.25/12.5GHz spacing";
           }
           enum "1542.22" {
             description "1542.22 nm/194.390625 THz 3.125GHz spacing";
           }
           enum "1542.19" {
             description "1542.19 nm/194.393750 THz 3.125/6.25GHz spacing";
           }
           enum "1542.17" {
             description "1542.17 nm/194.396875 THz 3.125GHz spacing";
           }
           enum "1542.14" {
             description "1542.14 nm/194.400000 THz 3.125/6.25/12.5/50/75/100GHz spacing";
           }
           enum "1542.12" {
             description "1542.12 nm/194.403125 THz 3.125GHz spacing";
           }
           enum "1542.09" {
             description "1542.09 nm/194.406250 THz 3.125/6.25GHz spacing";
           }
           enum "1542.07" {
             description "1542.07 nm/194.409375 THz 3.125GHz spacing";
           }
           enum "1542.04" {
             description "1542.04 nm/194.412500 THz 3.125/6.25/12.5GHz spacing";
           }
           enum "1542.02" {
             description "1542.02 nm/194.415625 THz 3.125GHz spacing";
           }
           enum "1541.99" {
             description "1541.99 nm/194.418750 THz 3.125/6.25GHz spacing";
           }
           enum "1541.97" {
             description "1541.97 nm/194.421875 THz 3.125GHz spacing";
           }
           enum "1541.94" {
             description "1541.94 nm/194.425000 THz 3.125/6.25/12.5GHz spacing";
           }
           enum "1541.92" {
             description "1541.92 nm/194.428125 THz 3.125GHz spacing";
           }
           enum "1541.89" {
             description "1541.89 nm/194.431250 THz 3.125/6.25GHz spacing";
           }
           enum "1541.87" {
             description "1541.87 nm/194.434375 THz 3.125GHz spacing";
           }
           enum "1541.84" {
             description "1541.84 nm/194.437500 THz 3.125/6.25/12.5GHz spacing";
           }
           enum "1541.82" {
             description "1541.82 nm/194.440625 THz 3.125GHz spacing";
           }
           enum "1541.80" {
             description "1541.80 nm/194.443750 THz 3.125/6.25GHz spacing";
           }
           enum "1541.77" {
             description "1541.77 nm/194.446875 THz 3.125GHz spacing";
           }
           enum "1541.75" {
             description "1541.75 nm/194.450000 THz 3.125/6.25/12.5/50GHz spacing";
           }
           enum "1541.72" {
             description "1541.72 nm/194.453125 THz 3.125GHz spacing";
           }
           enum "1541.70" {
             description "1541.70 nm/194.456250 THz 3.125/6.25GHz spacing";
           }
           enum "1541.67" {
             description "1541.67 nm/194.459375 THz 3.125GHz spacing";
           }
           enum "1541.65" {
             description "1541.65 nm/194.462500 THz 3.125/6.25/12.5GHz spacing";
           }
           enum "1541.62" {
             description "1541.62 nm/194.465625 THz 3.125GHz spacing";
           }
           enum "1541.60" {
             description "1541.60 nm/194.468750 THz 3.125/6.25GHz spacing";
           }
           enum "1541.57" {
             description "1541.57 nm/194.471875 THz 3.125GHz spacing";
           }
           enum "1541.55" {
             description "1541.55 nm/194.475000 THz 3.125/6.25/12.5/75GHz spacing";
           }
           enum "1541.52" {
             description "1541.52 nm/194.478125 THz 3.125GHz spacing";
           }
           enum "1541.50" {
             description "1541.50 nm/194.481250 THz 3.125/6.25GHz spacing";
           }
           enum "1541.47" {
             description "1541.47 nm/194.484375 THz 3.125GHz spacing";
           }
           enum "1541.45" {
             description "1541.45 nm/194.487500 THz 3.125/6.25/12.5GHz spacing";
           }
           enum "1541.42" {
             description "1541.42 nm/194.490625 THz 3.125GHz spacing";
           }
           enum "1541.40" {
             description "1541.40 nm/194.493750 THz 3.125/6.25GHz spacing";
           }
           enum "1541.37" {
             description "1541.37 nm/194.496875 THz 3.125GHz spacing";
           }
           enum "1541.35" {
             description "1541.35 nm/194.500000 THz 3.125/6.25/12.5/100GHz spacing";
           }
           enum "1541.32" {
             description "1541.32 nm/194.503125 THz 3.125GHz spacing";
           }
           enum "1541.30" {
             description "1541.30 nm/194.506250 THz 3.125/6.25GHz spacing";
           }
           enum "1541.28" {
             description "1541.28 nm/194.509375 THz 3.125GHz spacing";
           }
           enum "1541.25" {
             description "1541.25 nm/194.512500 THz 3.125/6.25/12.5GHz spacing";
           }
           enum "1541.23" {
             description "1541.23 nm/194.515625 THz 3.125GHz spacing";
           }
           enum "1541.20" {
             description "1541.20 nm/194.518750 THz 3.125/6.25GHz spacing";
           }
           enum "1541.18" {
             description "1541.18 nm/194.521875 THz 3.125GHz spacing";
           }
           enum "1541.15" {
             description "1541.15 nm/194.525000 THz 3.125/6.25/12.5GHz spacing";
           }
           enum "1541.13" {
             description "1541.13 nm/194.528125 THz 3.125GHz spacing";
           }
           enum "1541.10" {
             description "1541.10 nm/194.531250 THz 3.125/6.25GHz spacing";
           }
           enum "1541.08" {
             description "1541.08 nm/194.534375 THz 3.125GHz spacing";
           }
           enum "1541.05" {
             description "1541.05 nm/194.537500 THz 3.125/6.25/12.5GHz spacing";
           }
           enum "1541.03" {
             description "1541.03 nm/194.540625 THz 3.125GHz spacing";
           }
           enum "1541.00" {
             description "1541.00 nm/194.543750 THz 3.125/6.25GHz spacing";
           }
           enum "1540.98" {
             description "1540.98 nm/194.546875 THz 3.125GHz spacing";
           }
           enum "1540.95" {
             description "1540.95 nm/194.550000 THz 3.125/6.25/12.5/50/75GHz spacing";
           }
           enum "1540.93" {
             description "1540.93 nm/194.553125 THz 3.125GHz spacing";
           }
           enum "1540.90" {
             description "1540.90 nm/194.556250 THz 3.125/6.25GHz spacing";
           }
           enum "1540.88" {
             description "1540.88 nm/194.559375 THz 3.125GHz spacing";
           }
           enum "1540.85" {
             description "1540.85 nm/194.562500 THz 3.125/6.25/12.5GHz spacing";
           }
           enum "1540.83" {
             description "1540.83 nm/194.565625 THz 3.125GHz spacing";
           }
           enum "1540.80" {
             description "1540.80 nm/194.568750 THz 3.125/6.25GHz spacing";
           }
           enum "1540.78" {
             description "1540.78 nm/194.571875 THz 3.125GHz spacing";
           }
           enum "1540.76" {
             description "1540.76 nm/194.575000 THz 3.125/6.25/12.5GHz spacing";
           }
           enum "1540.73" {
             description "1540.73 nm/194.578125 THz 3.125GHz spacing";
           }
           enum "1540.71" {
             description "1540.71 nm/194.581250 THz 3.125/6.25GHz spacing";
           }
           enum "1540.68" {
             description "1540.68 nm/194.584375 THz 3.125GHz spacing";
           }
           enum "1540.66" {
             description "1540.66 nm/194.587500 THz 3.125/6.25/12.5GHz spacing";
           }
           enum "1540.63" {
             description "1540.63 nm/194.590625 THz 3.125GHz spacing";
           }
           enum "1540.61" {
             description "1540.61 nm/194.593750 THz 3.125/6.25GHz spacing";
           }
           enum "1540.58" {
             description "1540.58 nm/194.596875 THz 3.125GHz spacing";
           }
           enum "1540.56" {
             description "1540.56 nm/194.600000 THz 3.125/6.25/12.5/100GHz spacing";
           }
           enum "1540.53" {
             description "1540.53 nm/194.603125 THz 3.125GHz spacing";
           }
           enum "1540.51" {
             description "1540.51 nm/194.606250 THz 3.125/6.25GHz spacing";
           }
           enum "1540.48" {
             description "1540.48 nm/194.609375 THz 3.125GHz spacing";
           }
           enum "1540.46" {
             description "1540.46 nm/194.612500 THz 3.125/6.25/12.5GHz spacing";
           }
           enum "1540.43" {
             description "1540.43 nm/194.615625 THz 3.125GHz spacing";
           }
           enum "1540.41" {
             description "1540.41 nm/194.618750 THz 3.125/6.25GHz spacing";
           }
           enum "1540.38" {
             description "1540.38 nm/194.621875 THz 3.125GHz spacing";
           }
           enum "1540.36" {
             description "1540.36 nm/194.625000 THz 3.125/6.25/12.5/75GHz spacing";
           }
           enum "1540.33" {
             description "1540.33 nm/194.628125 THz 3.125GHz spacing";
           }
           enum "1540.31" {
             description "1540.31 nm/194.631250 THz 3.125/6.25GHz spacing";
           }
           enum "1540.29" {
             description "1540.29 nm/194.634375 THz 3.125GHz spacing";
           }
           enum "1540.26" {
             description "1540.26 nm/194.637500 THz 3.125/6.25/12.5GHz spacing";
           }
           enum "1540.24" {
             description "1540.24 nm/194.640625 THz 3.125GHz spacing";
           }
           enum "1540.21" {
             description "1540.21 nm/194.643750 THz 3.125/6.25GHz spacing";
           }
           enum "1540.19" {
             description "1540.19 nm/194.646875 THz 3.125GHz spacing";
           }
           enum "1540.16" {
             description "1540.16 nm/194.650000 THz 3.125/6.25/12.5/50GHz spacing";
           }
           enum "1540.14" {
             description "1540.14 nm/194.653125 THz 3.125GHz spacing";
           }
           enum "1540.11" {
             description "1540.11 nm/194.656250 THz 3.125/6.25GHz spacing";
           }
           enum "1540.09" {
             description "1540.09 nm/194.659375 THz 3.125GHz spacing";
           }
           enum "1540.06" {
             description "1540.06 nm/194.662500 THz 3.125/6.25/12.5GHz spacing";
           }
           enum "1540.04" {
             description "1540.04 nm/194.665625 THz 3.125GHz spacing";
           }
           enum "1540.01" {
             description "1540.01 nm/194.668750 THz 3.125/6.25GHz spacing";
           }
           enum "1539.99" {
             description "1539.99 nm/194.671875 THz 3.125GHz spacing";
           }
           enum "1539.96" {
             description "1539.96 nm/194.675000 THz 3.125/6.25/12.5GHz spacing";
           }
           enum "1539.94" {
             description "1539.94 nm/194.678125 THz 3.125GHz spacing";
           }
           enum "1539.91" {
             description "1539.91 nm/194.681250 THz 3.125/6.25GHz spacing";
           }
           enum "1539.89" {
             description "1539.89 nm/194.684375 THz 3.125GHz spacing";
           }
           enum "1539.86" {
             description "1539.86 nm/194.687500 THz 3.125/6.25/12.5GHz spacing";
           }
           enum "1539.84" {
             description "1539.84 nm/194.690625 THz 3.125GHz spacing";
           }
           enum "1539.82" {
             description "1539.82 nm/194.693750 THz 3.125/6.25GHz spacing";
           }
           enum "1539.79" {
             description "1539.79 nm/194.696875 THz 3.125GHz spacing";
           }
           enum "1539.77" {
             description "1539.77 nm/194.700000 THz 3.125/6.25/12.5/50/75/100GHz spacing";
           }
           enum "1539.74" {
             description "1539.74 nm/194.703125 THz 3.125GHz spacing";
           }
           enum "1539.72" {
             description "1539.72 nm/194.706250 THz 3.125/6.25GHz spacing";
           }
           enum "1539.69" {
             description "1539.69 nm/194.709375 THz 3.125GHz spacing";
           }
           enum "1539.67" {
             description "1539.67 nm/194.712500 THz 3.125/6.25/12.5GHz spacing";
           }
           enum "1539.64" {
             description "1539.64 nm/194.715625 THz 3.125GHz spacing";
           }
           enum "1539.62" {
             description "1539.62 nm/194.718750 THz 3.125/6.25GHz spacing";
           }
           enum "1539.59" {
             description "1539.59 nm/194.721875 THz 3.125GHz spacing";
           }
           enum "1539.57" {
             description "1539.57 nm/194.725000 THz 3.125/6.25/12.5GHz spacing";
           }
           enum "1539.54" {
             description "1539.54 nm/194.728125 THz 3.125GHz spacing";
           }
           enum "1539.52" {
             description "1539.52 nm/194.731250 THz 3.125/6.25GHz spacing";
           }
           enum "1539.49" {
             description "1539.49 nm/194.734375 THz 3.125GHz spacing";
           }
           enum "1539.47" {
             description "1539.47 nm/194.737500 THz 3.125/6.25/12.5GHz spacing";
           }
           enum "1539.44" {
             description "1539.44 nm/194.740625 THz 3.125GHz spacing";
           }
           enum "1539.42" {
             description "1539.42 nm/194.743750 THz 3.125/6.25GHz spacing";
           }
           enum "1539.40" {
             description "1539.40 nm/194.746875 THz 3.125GHz spacing";
           }
           enum "1539.37" {
             description "1539.37 nm/194.750000 THz 3.125/6.25/12.5/50GHz spacing";
           }
           enum "1539.35" {
             description "1539.35 nm/194.753125 THz 3.125GHz spacing";
           }
           enum "1539.32" {
             description "1539.32 nm/194.756250 THz 3.125/6.25GHz spacing";
           }
           enum "1539.30" {
             description "1539.30 nm/194.759375 THz 3.125GHz spacing";
           }
           enum "1539.27" {
             description "1539.27 nm/194.762500 THz 3.125/6.25/12.5GHz spacing";
           }
           enum "1539.25" {
             description "1539.25 nm/194.765625 THz 3.125GHz spacing";
           }
           enum "1539.22" {
             description "1539.22 nm/194.768750 THz 3.125/6.25GHz spacing";
           }
           enum "1539.20" {
             description "1539.20 nm/194.771875 THz 3.125GHz spacing";
           }
           enum "1539.17" {
             description "1539.17 nm/194.775000 THz 3.125/6.25/12.5/75GHz spacing";
           }
           enum "1539.15" {
             description "1539.15 nm/194.778125 THz 3.125GHz spacing";
           }
           enum "1539.12" {
             description "1539.12 nm/194.781250 THz 3.125/6.25GHz spacing";
           }
           enum "1539.10" {
             description "1539.10 nm/194.784375 THz 3.125GHz spacing";
           }
           enum "1539.07" {
             description "1539.07 nm/194.787500 THz 3.125/6.25/12.5GHz spacing";
           }
           enum "1539.05" {
             description "1539.05 nm/194.790625 THz 3.125GHz spacing";
           }
           enum "1539.03" {
             description "1539.03 nm/194.793750 THz 3.125/6.25GHz spacing";
           }
           enum "1539.00" {
             description "1539.00 nm/194.796875 THz 3.125GHz spacing";
           }
           enum "1538.98" {
             description "1538.98 nm/194.800000 THz 3.125/6.25/12.5/100GHz spacing";
           }
           enum "1538.95" {
             description "1538.95 nm/194.803125 THz 3.125GHz spacing";
           }
           enum "1538.93" {
             description "1538.93 nm/194.806250 THz 3.125/6.25GHz spacing";
           }
           enum "1538.90" {
             description "1538.90 nm/194.809375 THz 3.125GHz spacing";
           }
           enum "1538.88" {
             description "1538.88 nm/194.812500 THz 3.125/6.25/12.5GHz spacing";
           }
           enum "1538.85" {
             description "1538.85 nm/194.815625 THz 3.125GHz spacing";
           }
           enum "1538.83" {
             description "1538.83 nm/194.818750 THz 3.125/6.25GHz spacing";
           }
           enum "1538.80" {
             description "1538.80 nm/194.821875 THz 3.125GHz spacing";
           }
           enum "1538.78" {
             description "1538.78 nm/194.825000 THz 3.125/6.25/12.5GHz spacing";
           }
           enum "1538.75" {
             description "1538.75 nm/194.828125 THz 3.125GHz spacing";
           }
           enum "1538.73" {
             description "1538.73 nm/194.831250 THz 3.125/6.25GHz spacing";
           }
           enum "1538.70" {
             description "1538.70 nm/194.834375 THz 3.125GHz spacing";
           }
           enum "1538.68" {
             description "1538.68 nm/194.837500 THz 3.125/6.25/12.5GHz spacing";
           }
           enum "1538.65" {
             description "1538.65 nm/194.840625 THz 3.125GHz spacing";
           }
           enum "1538.63" {
             description "1538.63 nm/194.843750 THz 3.125/6.25GHz spacing";
           }
           enum "1538.61" {
             description "1538.61 nm/194.846875 THz 3.125GHz spacing";
           }
           enum "1538.58" {
             description "1538.58 nm/194.850000 THz 3.125/6.25/12.5/50/75GHz spacing";
           }
           enum "1538.56" {
             description "1538.56 nm/194.853125 THz 3.125GHz spacing";
           }
           enum "1538.53" {
             description "1538.53 nm/194.856250 THz 3.125/6.25GHz spacing";
           }
           enum "1538.51" {
             description "1538.51 nm/194.859375 THz 3.125GHz spacing";
           }
           enum "1538.48" {
             description "1538.48 nm/194.862500 THz 3.125/6.25/12.5GHz spacing";
           }
           enum "1538.46" {
             description "1538.46 nm/194.865625 THz 3.125GHz spacing";
           }
           enum "1538.43" {
             description "1538.43 nm/194.868750 THz 3.125/6.25GHz spacing";
           }
           enum "1538.41" {
             description "1538.41 nm/194.871875 THz 3.125GHz spacing";
           }
           enum "1538.38" {
             description "1538.38 nm/194.875000 THz 3.125/6.25/12.5GHz spacing";
           }
           enum "1538.36" {
             description "1538.36 nm/194.878125 THz 3.125GHz spacing";
           }
           enum "1538.33" {
             description "1538.33 nm/194.881250 THz 3.125/6.25GHz spacing";
           }
           enum "1538.31" {
             description "1538.31 nm/194.884375 THz 3.125GHz spacing";
           }
           enum "1538.28" {
             description "1538.28 nm/194.887500 THz 3.125/6.25/12.5GHz spacing";
           }
           enum "1538.26" {
             description "1538.26 nm/194.890625 THz 3.125GHz spacing";
           }
           enum "1538.24" {
             description "1538.24 nm/194.893750 THz 3.125/6.25GHz spacing";
           }
           enum "1538.21" {
             description "1538.21 nm/194.896875 THz 3.125GHz spacing";
           }
           enum "1538.19" {
             description "1538.19 nm/194.900000 THz 3.125/6.25/12.5/100GHz spacing";
           }
           enum "1538.16" {
             description "1538.16 nm/194.903125 THz 3.125GHz spacing";
           }
           enum "1538.14" {
             description "1538.14 nm/194.906250 THz 3.125/6.25GHz spacing";
           }
           enum "1538.11" {
             description "1538.11 nm/194.909375 THz 3.125GHz spacing";
           }
           enum "1538.09" {
             description "1538.09 nm/194.912500 THz 3.125/6.25/12.5GHz spacing";
           }
           enum "1538.06" {
             description "1538.06 nm/194.915625 THz 3.125GHz spacing";
           }
           enum "1538.04" {
             description "1538.04 nm/194.918750 THz 3.125/6.25GHz spacing";
           }
           enum "1538.01" {
             description "1538.01 nm/194.921875 THz 3.125GHz spacing";
           }
           enum "1537.99" {
             description "1537.99 nm/194.925000 THz 3.125/6.25/12.5/75GHz spacing";
           }
           enum "1537.96" {
             description "1537.96 nm/194.928125 THz 3.125GHz spacing";
           }
           enum "1537.94" {
             description "1537.94 nm/194.931250 THz 3.125/6.25GHz spacing";
           }
           enum "1537.91" {
             description "1537.91 nm/194.934375 THz 3.125GHz spacing";
           }
           enum "1537.89" {
             description "1537.89 nm/194.937500 THz 3.125/6.25/12.5GHz spacing";
           }
           enum "1537.87" {
             description "1537.87 nm/194.940625 THz 3.125GHz spacing";
           }
           enum "1537.84" {
             description "1537.84 nm/194.943750 THz 3.125/6.25GHz spacing";
           }
           enum "1537.82" {
             description "1537.82 nm/194.946875 THz 3.125GHz spacing";
           }
           enum "1537.79" {
             description "1537.79 nm/194.950000 THz 3.125/6.25/12.5/50GHz spacing";
           }
           enum "1537.77" {
             description "1537.77 nm/194.953125 THz 3.125GHz spacing";
           }
           enum "1537.74" {
             description "1537.74 nm/194.956250 THz 3.125/6.25GHz spacing";
           }
           enum "1537.72" {
             description "1537.72 nm/194.959375 THz 3.125GHz spacing";
           }
           enum "1537.69" {
             description "1537.69 nm/194.962500 THz 3.125/6.25/12.5GHz spacing";
           }
           enum "1537.67" {
             description "1537.67 nm/194.965625 THz 3.125GHz spacing";
           }
           enum "1537.64" {
             description "1537.64 nm/194.968750 THz 3.125/6.25GHz spacing";
           }
           enum "1537.62" {
             description "1537.62 nm/194.971875 THz 3.125GHz spacing";
           }
           enum "1537.59" {
             description "1537.59 nm/194.975000 THz 3.125/6.25/12.5GHz spacing";
           }
           enum "1537.57" {
             description "1537.57 nm/194.978125 THz 3.125GHz spacing";
           }
           enum "1537.55" {
             description "1537.55 nm/194.981250 THz 3.125/6.25GHz spacing";
           }
           enum "1537.52" {
             description "1537.52 nm/194.984375 THz 3.125GHz spacing";
           }
           enum "1537.50" {
             description "1537.50 nm/194.987500 THz 3.125/6.25/12.5GHz spacing";
           }
           enum "1537.47" {
             description "1537.47 nm/194.990625 THz 3.125GHz spacing";
           }
           enum "1537.45" {
             description "1537.45 nm/194.993750 THz 3.125/6.25GHz spacing";
           }
           enum "1537.42" {
             description "1537.42 nm/194.996875 THz 3.125GHz spacing";
           }
           enum "1537.40" {
             description "1537.40 nm/195.000000 THz 3.125/6.25/12.5/50/75/100GHz spacing";
           }
           enum "1537.37" {
             description "1537.37 nm/195.003125 THz 3.125GHz spacing";
           }
           enum "1537.35" {
             description "1537.35 nm/195.006250 THz 3.125/6.25GHz spacing";
           }
           enum "1537.32" {
             description "1537.32 nm/195.009375 THz 3.125GHz spacing";
           }
           enum "1537.30" {
             description "1537.30 nm/195.012500 THz 3.125/6.25/12.5GHz spacing";
           }
           enum "1537.27" {
             description "1537.27 nm/195.015625 THz 3.125GHz spacing";
           }
           enum "1537.25" {
             description "1537.25 nm/195.018750 THz 3.125/6.25GHz spacing";
           }
           enum "1537.22" {
             description "1537.22 nm/195.021875 THz 3.125GHz spacing";
           }
           enum "1537.20" {
             description "1537.20 nm/195.025000 THz 3.125/6.25/12.5GHz spacing";
           }
           enum "1537.18" {
             description "1537.18 nm/195.028125 THz 3.125GHz spacing";
           }
           enum "1537.15" {
             description "1537.15 nm/195.031250 THz 3.125/6.25GHz spacing";
           }
           enum "1537.13" {
             description "1537.13 nm/195.034375 THz 3.125GHz spacing";
           }
           enum "1537.10" {
             description "1537.10 nm/195.037500 THz 3.125/6.25/12.5GHz spacing";
           }
           enum "1537.08" {
             description "1537.08 nm/195.040625 THz 3.125GHz spacing";
           }
           enum "1537.05" {
             description "1537.05 nm/195.043750 THz 3.125/6.25GHz spacing";
           }
           enum "1537.03" {
             description "1537.03 nm/195.046875 THz 3.125GHz spacing";
           }
           enum "1537.00" {
             description "1537.00 nm/195.050000 THz 3.125/6.25/12.5/50GHz spacing";
           }
           enum "1536.98" {
             description "1536.98 nm/195.053125 THz 3.125GHz spacing";
           }
           enum "1536.95" {
             description "1536.95 nm/195.056250 THz 3.125/6.25GHz spacing";
           }
           enum "1536.93" {
             description "1536.93 nm/195.059375 THz 3.125GHz spacing";
           }
           enum "1536.90" {
             description "1536.90 nm/195.062500 THz 3.125/6.25/12.5GHz spacing";
           }
           enum "1536.88" {
             description "1536.88 nm/195.065625 THz 3.125GHz spacing";
           }
           enum "1536.86" {
             description "1536.86 nm/195.068750 THz 3.125/6.25GHz spacing";
           }
           enum "1536.83" {
             description "1536.83 nm/195.071875 THz 3.125GHz spacing";
           }
           enum "1536.81" {
             description "1536.81 nm/195.075000 THz 3.125/6.25/12.5/75GHz spacing";
           }
           enum "1536.78" {
             description "1536.78 nm/195.078125 THz 3.125GHz spacing";
           }
           enum "1536.76" {
             description "1536.76 nm/195.081250 THz 3.125/6.25GHz spacing";
           }
           enum "1536.73" {
             description "1536.73 nm/195.084375 THz 3.125GHz spacing";
           }
           enum "1536.71" {
             description "1536.71 nm/195.087500 THz 3.125/6.25/12.5GHz spacing";
           }
           enum "1536.68" {
             description "1536.68 nm/195.090625 THz 3.125GHz spacing";
           }
           enum "1536.66" {
             description "1536.66 nm/195.093750 THz 3.125/6.25GHz spacing";
           }
           enum "1536.63" {
             description "1536.63 nm/195.096875 THz 3.125GHz spacing";
           }
           enum "1536.61" {
             description "1536.61 nm/195.100000 THz 3.125/6.25/12.5/100GHz spacing";
           }
           enum "1536.58" {
             description "1536.58 nm/195.103125 THz 3.125GHz spacing";
           }
           enum "1536.56" {
             description "1536.56 nm/195.106250 THz 3.125/6.25GHz spacing";
           }
           enum "1536.54" {
             description "1536.54 nm/195.109375 THz 3.125GHz spacing";
           }
           enum "1536.51" {
             description "1536.51 nm/195.112500 THz 3.125/6.25/12.5GHz spacing";
           }
           enum "1536.49" {
             description "1536.49 nm/195.115625 THz 3.125GHz spacing";
           }
           enum "1536.46" {
             description "1536.46 nm/195.118750 THz 3.125/6.25GHz spacing";
           }
           enum "1536.44" {
             description "1536.44 nm/195.121875 THz 3.125GHz spacing";
           }
           enum "1536.41" {
             description "1536.41 nm/195.125000 THz 3.125/6.25/12.5GHz spacing";
           }
           enum "1536.39" {
             description "1536.39 nm/195.128125 THz 3.125GHz spacing";
           }
           enum "1536.36" {
             description "1536.36 nm/195.131250 THz 3.125/6.25GHz spacing";
           }
           enum "1536.34" {
             description "1536.34 nm/195.134375 THz 3.125GHz spacing";
           }
           enum "1536.31" {
             description "1536.31 nm/195.137500 THz 3.125/6.25/12.5GHz spacing";
           }
           enum "1536.29" {
             description "1536.29 nm/195.140625 THz 3.125GHz spacing";
           }
           enum "1536.26" {
             description "1536.26 nm/195.143750 THz 3.125/6.25GHz spacing";
           }
           enum "1536.24" {
             description "1536.24 nm/195.146875 THz 3.125GHz spacing";
           }
           enum "1536.22" {
             description "1536.22 nm/195.150000 THz 3.125/6.25/12.5/50/75GHz spacing";
           }
           enum "1536.19" {
             description "1536.19 nm/195.153125 THz 3.125GHz spacing";
           }
           enum "1536.17" {
             description "1536.17 nm/195.156250 THz 3.125/6.25GHz spacing";
           }
           enum "1536.14" {
             description "1536.14 nm/195.159375 THz 3.125GHz spacing";
           }
           enum "1536.12" {
             description "1536.12 nm/195.162500 THz 3.125/6.25/12.5GHz spacing";
           }
           enum "1536.09" {
             description "1536.09 nm/195.165625 THz 3.125GHz spacing";
           }
           enum "1536.07" {
             description "1536.07 nm/195.168750 THz 3.125/6.25GHz spacing";
           }
           enum "1536.04" {
             description "1536.04 nm/195.171875 THz 3.125GHz spacing";
           }
           enum "1536.02" {
             description "1536.02 nm/195.175000 THz 3.125/6.25/12.5GHz spacing";
           }
           enum "1535.99" {
             description "1535.99 nm/195.178125 THz 3.125GHz spacing";
           }
           enum "1535.97" {
             description "1535.97 nm/195.181250 THz 3.125/6.25GHz spacing";
           }
           enum "1535.94" {
             description "1535.94 nm/195.184375 THz 3.125GHz spacing";
           }
           enum "1535.92" {
             description "1535.92 nm/195.187500 THz 3.125/6.25/12.5GHz spacing";
           }
           enum "1535.90" {
             description "1535.90 nm/195.190625 THz 3.125GHz spacing";
           }
           enum "1535.87" {
             description "1535.87 nm/195.193750 THz 3.125/6.25GHz spacing";
           }
           enum "1535.85" {
             description "1535.85 nm/195.196875 THz 3.125GHz spacing";
           }
           enum "1535.82" {
             description "1535.82 nm/195.200000 THz 3.125/6.25/12.5/100GHz spacing";
           }
           enum "1535.80" {
             description "1535.80 nm/195.203125 THz 3.125GHz spacing";
           }
           enum "1535.77" {
             description "1535.77 nm/195.206250 THz 3.125/6.25GHz spacing";
           }
           enum "1535.75" {
             description "1535.75 nm/195.209375 THz 3.125GHz spacing";
           }
           enum "1535.72" {
             description "1535.72 nm/195.212500 THz 3.125/6.25/12.5GHz spacing";
           }
           enum "1535.70" {
             description "1535.70 nm/195.215625 THz 3.125GHz spacing";
           }
           enum "1535.67" {
             description "1535.67 nm/195.218750 THz 3.125/6.25GHz spacing";
           }
           enum "1535.65" {
             description "1535.65 nm/195.221875 THz 3.125GHz spacing";
           }
           enum "1535.63" {
             description "1535.63 nm/195.225000 THz 3.125/6.25/12.5/75GHz spacing";
           }
           enum "1535.60" {
             description "1535.60 nm/195.228125 THz 3.125GHz spacing";
           }
           enum "1535.58" {
             description "1535.58 nm/195.231250 THz 3.125/6.25GHz spacing";
           }
           enum "1535.55" {
             description "1535.55 nm/195.234375 THz 3.125GHz spacing";
           }
           enum "1535.53" {
             description "1535.53 nm/195.237500 THz 3.125/6.25/12.5GHz spacing";
           }
           enum "1535.50" {
             description "1535.50 nm/195.240625 THz 3.125GHz spacing";
           }
           enum "1535.48" {
             description "1535.48 nm/195.243750 THz 3.125/6.25GHz spacing";
           }
           enum "1535.45" {
             description "1535.45 nm/195.246875 THz 3.125GHz spacing";
           }
           enum "1535.43" {
             description "1535.43 nm/195.250000 THz 3.125/6.25/12.5/50GHz spacing";
           }
           enum "1535.40" {
             description "1535.40 nm/195.253125 THz 3.125GHz spacing";
           }
           enum "1535.38" {
             description "1535.38 nm/195.256250 THz 3.125/6.25GHz spacing";
           }
           enum "1535.36" {
             description "1535.36 nm/195.259375 THz 3.125GHz spacing";
           }
           enum "1535.33" {
             description "1535.33 nm/195.262500 THz 3.125/6.25/12.5GHz spacing";
           }
           enum "1535.31" {
             description "1535.31 nm/195.265625 THz 3.125GHz spacing";
           }
           enum "1535.28" {
             description "1535.28 nm/195.268750 THz 3.125/6.25GHz spacing";
           }
           enum "1535.26" {
             description "1535.26 nm/195.271875 THz 3.125GHz spacing";
           }
           enum "1535.23" {
             description "1535.23 nm/195.275000 THz 3.125/6.25/12.5GHz spacing";
           }
           enum "1535.21" {
             description "1535.21 nm/195.278125 THz 3.125GHz spacing";
           }
           enum "1535.18" {
             description "1535.18 nm/195.281250 THz 3.125/6.25GHz spacing";
           }
           enum "1535.16" {
             description "1535.16 nm/195.284375 THz 3.125GHz spacing";
           }
           enum "1535.13" {
             description "1535.13 nm/195.287500 THz 3.125/6.25/12.5GHz spacing";
           }
           enum "1535.11" {
             description "1535.11 nm/195.290625 THz 3.125GHz spacing";
           }
           enum "1535.08" {
             description "1535.08 nm/195.293750 THz 3.125/6.25GHz spacing";
           }
           enum "1535.06" {
             description "1535.06 nm/195.296875 THz 3.125GHz spacing";
           }
           enum "1535.04" {
             description "1535.04 nm/195.300000 THz 3.125/6.25/12.5/50/75/100GHz spacing";
           }
           enum "1535.01" {
             description "1535.01 nm/195.303125 THz 3.125GHz spacing";
           }
           enum "1534.99" {
             description "1534.99 nm/195.306250 THz 3.125/6.25GHz spacing";
           }
           enum "1534.96" {
             description "1534.96 nm/195.309375 THz 3.125GHz spacing";
           }
           enum "1534.94" {
             description "1534.94 nm/195.312500 THz 3.125/6.25/12.5GHz spacing";
           }
           enum "1534.91" {
             description "1534.91 nm/195.315625 THz 3.125GHz spacing";
           }
           enum "1534.89" {
             description "1534.89 nm/195.318750 THz 3.125/6.25GHz spacing";
           }
           enum "1534.86" {
             description "1534.86 nm/195.321875 THz 3.125GHz spacing";
           }
           enum "1534.84" {
             description "1534.84 nm/195.325000 THz 3.125/6.25/12.5GHz spacing";
           }
           enum "1534.81" {
             description "1534.81 nm/195.328125 THz 3.125GHz spacing";
           }
           enum "1534.79" {
             description "1534.79 nm/195.331250 THz 3.125/6.25GHz spacing";
           }
           enum "1534.77" {
             description "1534.77 nm/195.334375 THz 3.125GHz spacing";
           }
           enum "1534.74" {
             description "1534.74 nm/195.337500 THz 3.125/6.25/12.5GHz spacing";
           }
           enum "1534.72" {
             description "1534.72 nm/195.340625 THz 3.125GHz spacing";
           }
           enum "1534.69" {
             description "1534.69 nm/195.343750 THz 3.125/6.25GHz spacing";
           }
           enum "1534.67" {
             description "1534.67 nm/195.346875 THz 3.125GHz spacing";
           }
           enum "1534.64" {
             description "1534.64 nm/195.350000 THz 3.125/6.25/12.5/50GHz spacing";
           }
           enum "1534.62" {
             description "1534.62 nm/195.353125 THz 3.125GHz spacing";
           }
           enum "1534.59" {
             description "1534.59 nm/195.356250 THz 3.125/6.25GHz spacing";
           }
           enum "1534.57" {
             description "1534.57 nm/195.359375 THz 3.125GHz spacing";
           }
           enum "1534.54" {
             description "1534.54 nm/195.362500 THz 3.125/6.25/12.5GHz spacing";
           }
           enum "1534.52" {
             description "1534.52 nm/195.365625 THz 3.125GHz spacing";
           }
           enum "1534.50" {
             description "1534.50 nm/195.368750 THz 3.125/6.25GHz spacing";
           }
           enum "1534.47" {
             description "1534.47 nm/195.371875 THz 3.125GHz spacing";
           }
           enum "1534.45" {
             description "1534.45 nm/195.375000 THz 3.125/6.25/12.5/75GHz spacing";
           }
           enum "1534.42" {
             description "1534.42 nm/195.378125 THz 3.125GHz spacing";
           }
           enum "1534.40" {
             description "1534.40 nm/195.381250 THz 3.125/6.25GHz spacing";
           }
           enum "1534.37" {
             description "1534.37 nm/195.384375 THz 3.125GHz spacing";
           }
           enum "1534.35" {
             description "1534.35 nm/195.387500 THz 3.125/6.25/12.5GHz spacing";
           }
           enum "1534.32" {
             description "1534.32 nm/195.390625 THz 3.125GHz spacing";
           }
           enum "1534.30" {
             description "1534.30 nm/195.393750 THz 3.125/6.25GHz spacing";
           }
           enum "1534.27" {
             description "1534.27 nm/195.396875 THz 3.125GHz spacing";
           }
           enum "1534.25" {
             description "1534.25 nm/195.400000 THz 3.125/6.25/12.5/100GHz spacing";
           }
           enum "1534.23" {
             description "1534.23 nm/195.403125 THz 3.125GHz spacing";
           }
           enum "1534.20" {
             description "1534.20 nm/195.406250 THz 3.125/6.25GHz spacing";
           }
           enum "1534.18" {
             description "1534.18 nm/195.409375 THz 3.125GHz spacing";
           }
           enum "1534.15" {
             description "1534.15 nm/195.412500 THz 3.125/6.25/12.5GHz spacing";
           }
           enum "1534.13" {
             description "1534.13 nm/195.415625 THz 3.125GHz spacing";
           }
           enum "1534.10" {
             description "1534.10 nm/195.418750 THz 3.125/6.25GHz spacing";
           }
           enum "1534.08" {
             description "1534.08 nm/195.421875 THz 3.125GHz spacing";
           }
           enum "1534.05" {
             description "1534.05 nm/195.425000 THz 3.125/6.25/12.5GHz spacing";
           }
           enum "1534.03" {
             description "1534.03 nm/195.428125 THz 3.125GHz spacing";
           }
           enum "1534.00" {
             description "1534.00 nm/195.431250 THz 3.125/6.25GHz spacing";
           }
           enum "1533.98" {
             description "1533.98 nm/195.434375 THz 3.125GHz spacing";
           }
           enum "1533.96" {
             description "1533.96 nm/195.437500 THz 3.125/6.25/12.5GHz spacing";
           }
           enum "1533.93" {
             description "1533.93 nm/195.440625 THz 3.125GHz spacing";
           }
           enum "1533.91" {
             description "1533.91 nm/195.443750 THz 3.125/6.25GHz spacing";
           }
           enum "1533.88" {
             description "1533.88 nm/195.446875 THz 3.125GHz spacing";
           }
           enum "1533.86" {
             description "1533.86 nm/195.450000 THz 3.125/6.25/12.5/50/75GHz spacing";
           }
           enum "1533.83" {
             description "1533.83 nm/195.453125 THz 3.125GHz spacing";
           }
           enum "1533.81" {
             description "1533.81 nm/195.456250 THz 3.125/6.25GHz spacing";
           }
           enum "1533.78" {
             description "1533.78 nm/195.459375 THz 3.125GHz spacing";
           }
           enum "1533.76" {
             description "1533.76 nm/195.462500 THz 3.125/6.25/12.5GHz spacing";
           }
           enum "1533.73" {
             description "1533.73 nm/195.465625 THz 3.125GHz spacing";
           }
           enum "1533.71" {
             description "1533.71 nm/195.468750 THz 3.125/6.25GHz spacing";
           }
           enum "1533.69" {
             description "1533.69 nm/195.471875 THz 3.125GHz spacing";
           }
           enum "1533.66" {
             description "1533.66 nm/195.475000 THz 3.125/6.25/12.5GHz spacing";
           }
           enum "1533.64" {
             description "1533.64 nm/195.478125 THz 3.125GHz spacing";
           }
           enum "1533.61" {
             description "1533.61 nm/195.481250 THz 3.125/6.25GHz spacing";
           }
           enum "1533.59" {
             description "1533.59 nm/195.484375 THz 3.125GHz spacing";
           }
           enum "1533.56" {
             description "1533.56 nm/195.487500 THz 3.125/6.25/12.5GHz spacing";
           }
           enum "1533.54" {
             description "1533.54 nm/195.490625 THz 3.125GHz spacing";
           }
           enum "1533.51" {
             description "1533.51 nm/195.493750 THz 3.125/6.25GHz spacing";
           }
           enum "1533.49" {
             description "1533.49 nm/195.496875 THz 3.125GHz spacing";
           }
           enum "1533.47" {
             description "1533.47 nm/195.500000 THz 3.125/6.25/12.5/100GHz spacing";
           }
           enum "1533.44" {
             description "1533.44 nm/195.503125 THz 3.125GHz spacing";
           }
           enum "1533.42" {
             description "1533.42 nm/195.506250 THz 3.125/6.25GHz spacing";
           }
           enum "1533.39" {
             description "1533.39 nm/195.509375 THz 3.125GHz spacing";
           }
           enum "1533.37" {
             description "1533.37 nm/195.512500 THz 3.125/6.25/12.5GHz spacing";
           }
           enum "1533.34" {
             description "1533.34 nm/195.515625 THz 3.125GHz spacing";
           }
           enum "1533.32" {
             description "1533.32 nm/195.518750 THz 3.125/6.25GHz spacing";
           }
           enum "1533.29" {
             description "1533.29 nm/195.521875 THz 3.125GHz spacing";
           }
           enum "1533.27" {
             description "1533.27 nm/195.525000 THz 3.125/6.25/12.5/75GHz spacing";
           }
           enum "1533.24" {
             description "1533.24 nm/195.528125 THz 3.125GHz spacing";
           }
           enum "1533.22" {
             description "1533.22 nm/195.531250 THz 3.125/6.25GHz spacing";
           }
           enum "1533.20" {
             description "1533.20 nm/195.534375 THz 3.125GHz spacing";
           }
           enum "1533.17" {
             description "1533.17 nm/195.537500 THz 3.125/6.25/12.5GHz spacing";
           }
           enum "1533.15" {
             description "1533.15 nm/195.540625 THz 3.125GHz spacing";
           }
           enum "1533.12" {
             description "1533.12 nm/195.543750 THz 3.125/6.25GHz spacing";
           }
           enum "1533.10" {
             description "1533.10 nm/195.546875 THz 3.125GHz spacing";
           }
           enum "1533.07" {
             description "1533.07 nm/195.550000 THz 3.125/6.25/12.5/50GHz spacing";
           }
           enum "1533.05" {
             description "1533.05 nm/195.553125 THz 3.125GHz spacing";
           }
           enum "1533.02" {
             description "1533.02 nm/195.556250 THz 3.125/6.25GHz spacing";
           }
           enum "1533.00" {
             description "1533.00 nm/195.559375 THz 3.125GHz spacing";
           }
           enum "1532.98" {
             description "1532.98 nm/195.562500 THz 3.125/6.25/12.5GHz spacing";
           }
           enum "1532.95" {
             description "1532.95 nm/195.565625 THz 3.125GHz spacing";
           }
           enum "1532.93" {
             description "1532.93 nm/195.568750 THz 3.125/6.25GHz spacing";
           }
           enum "1532.90" {
             description "1532.90 nm/195.571875 THz 3.125GHz spacing";
           }
           enum "1532.88" {
             description "1532.88 nm/195.575000 THz 3.125/6.25/12.5GHz spacing";
           }
           enum "1532.85" {
             description "1532.85 nm/195.578125 THz 3.125GHz spacing";
           }
           enum "1532.83" {
             description "1532.83 nm/195.581250 THz 3.125/6.25GHz spacing";
           }
           enum "1532.80" {
             description "1532.80 nm/195.584375 THz 3.125GHz spacing";
           }
           enum "1532.78" {
             description "1532.78 nm/195.587500 THz 3.125/6.25/12.5GHz spacing";
           }
           enum "1532.75" {
             description "1532.75 nm/195.590625 THz 3.125GHz spacing";
           }
           enum "1532.73" {
             description "1532.73 nm/195.593750 THz 3.125/6.25GHz spacing";
           }
           enum "1532.71" {
             description "1532.71 nm/195.596875 THz 3.125GHz spacing";
           }
           enum "1532.68" {
             description "1532.68 nm/195.600000 THz 3.125/6.25/12.5/50/75/100GHz spacing";
           }
           enum "1532.66" {
             description "1532.66 nm/195.603125 THz 3.125GHz spacing";
           }
           enum "1532.63" {
             description "1532.63 nm/195.606250 THz 3.125/6.25GHz spacing";
           }
           enum "1532.61" {
             description "1532.61 nm/195.609375 THz 3.125GHz spacing";
           }
           enum "1532.58" {
             description "1532.58 nm/195.612500 THz 3.125/6.25/12.5GHz spacing";
           }
           enum "1532.56" {
             description "1532.56 nm/195.615625 THz 3.125GHz spacing";
           }
           enum "1532.53" {
             description "1532.53 nm/195.618750 THz 3.125/6.25GHz spacing";
           }
           enum "1532.51" {
             description "1532.51 nm/195.621875 THz 3.125GHz spacing";
           }
           enum "1532.49" {
             description "1532.49 nm/195.625000 THz 3.125/6.25/12.5GHz spacing";
           }
           enum "1532.46" {
             description "1532.46 nm/195.628125 THz 3.125GHz spacing";
           }
           enum "1532.44" {
             description "1532.44 nm/195.631250 THz 3.125/6.25GHz spacing";
           }
           enum "1532.41" {
             description "1532.41 nm/195.634375 THz 3.125GHz spacing";
           }
           enum "1532.39" {
             description "1532.39 nm/195.637500 THz 3.125/6.25/12.5GHz spacing";
           }
           enum "1532.36" {
             description "1532.36 nm/195.640625 THz 3.125GHz spacing";
           }
           enum "1532.34" {
             description "1532.34 nm/195.643750 THz 3.125/6.25GHz spacing";
           }
           enum "1532.31" {
             description "1532.31 nm/195.646875 THz 3.125GHz spacing";
           }
           enum "1532.29" {
             description "1532.29 nm/195.650000 THz 3.125/6.25/12.5/50GHz spacing";
           }
           enum "1532.27" {
             description "1532.27 nm/195.653125 THz 3.125GHz spacing";
           }
           enum "1532.24" {
             description "1532.24 nm/195.656250 THz 3.125/6.25GHz spacing";
           }
           enum "1532.22" {
             description "1532.22 nm/195.659375 THz 3.125GHz spacing";
           }
           enum "1532.19" {
             description "1532.19 nm/195.662500 THz 3.125/6.25/12.5GHz spacing";
           }
           enum "1532.17" {
             description "1532.17 nm/195.665625 THz 3.125GHz spacing";
           }
           enum "1532.14" {
             description "1532.14 nm/195.668750 THz 3.125/6.25GHz spacing";
           }
           enum "1532.12" {
             description "1532.12 nm/195.671875 THz 3.125GHz spacing";
           }
           enum "1532.09" {
             description "1532.09 nm/195.675000 THz 3.125/6.25/12.5/75GHz spacing";
           }
           enum "1532.07" {
             description "1532.07 nm/195.678125 THz 3.125GHz spacing";
           }
           enum "1532.04" {
             description "1532.04 nm/195.681250 THz 3.125/6.25GHz spacing";
           }
           enum "1532.02" {
             description "1532.02 nm/195.684375 THz 3.125GHz spacing";
           }
           enum "1532.00" {
             description "1532.00 nm/195.687500 THz 3.125/6.25/12.5GHz spacing";
           }
           enum "1531.97" {
             description "1531.97 nm/195.690625 THz 3.125GHz spacing";
           }
           enum "1531.95" {
             description "1531.95 nm/195.693750 THz 3.125/6.25GHz spacing";
           }
           enum "1531.92" {
             description "1531.92 nm/195.696875 THz 3.125GHz spacing";
           }
           enum "1531.90" {
             description "1531.90 nm/195.700000 THz 3.125/6.25/12.5/100GHz spacing";
           }
           enum "1531.87" {
             description "1531.87 nm/195.703125 THz 3.125GHz spacing";
           }
           enum "1531.85" {
             description "1531.85 nm/195.706250 THz 3.125/6.25GHz spacing";
           }
           enum "1531.82" {
             description "1531.82 nm/195.709375 THz 3.125GHz spacing";
           }
           enum "1531.80" {
             description "1531.80 nm/195.712500 THz 3.125/6.25/12.5GHz spacing";
           }
           enum "1531.78" {
             description "1531.78 nm/195.715625 THz 3.125GHz spacing";
           }
           enum "1531.75" {
             description "1531.75 nm/195.718750 THz 3.125/6.25GHz spacing";
           }
           enum "1531.73" {
             description "1531.73 nm/195.721875 THz 3.125GHz spacing";
           }
           enum "1531.70" {
             description "1531.70 nm/195.725000 THz 3.125/6.25/12.5GHz spacing";
           }
           enum "1531.68" {
             description "1531.68 nm/195.728125 THz 3.125GHz spacing";
           }
           enum "1531.65" {
             description "1531.65 nm/195.731250 THz 3.125/6.25GHz spacing";
           }
           enum "1531.63" {
             description "1531.63 nm/195.734375 THz 3.125GHz spacing";
           }
           enum "1531.60" {
             description "1531.60 nm/195.737500 THz 3.125/6.25/12.5GHz spacing";
           }
           enum "1531.58" {
             description "1531.58 nm/195.740625 THz 3.125GHz spacing";
           }
           enum "1531.56" {
             description "1531.56 nm/195.743750 THz 3.125/6.25GHz spacing";
           }
           enum "1531.53" {
             description "1531.53 nm/195.746875 THz 3.125GHz spacing";
           }
           enum "1531.51" {
             description "1531.51 nm/195.750000 THz 3.125/6.25/12.5/50/75GHz spacing";
           }
           enum "1531.48" {
             description "1531.48 nm/195.753125 THz 3.125GHz spacing";
           }
           enum "1531.46" {
             description "1531.46 nm/195.756250 THz 3.125/6.25GHz spacing";
           }
           enum "1531.43" {
             description "1531.43 nm/195.759375 THz 3.125GHz spacing";
           }
           enum "1531.41" {
             description "1531.41 nm/195.762500 THz 3.125/6.25/12.5GHz spacing";
           }
           enum "1531.38" {
             description "1531.38 nm/195.765625 THz 3.125GHz spacing";
           }
           enum "1531.36" {
             description "1531.36 nm/195.768750 THz 3.125/6.25GHz spacing";
           }
           enum "1531.34" {
             description "1531.34 nm/195.771875 THz 3.125GHz spacing";
           }
           enum "1531.31" {
             description "1531.31 nm/195.775000 THz 3.125/6.25/12.5GHz spacing";
           }
           enum "1531.29" {
             description "1531.29 nm/195.778125 THz 3.125GHz spacing";
           }
           enum "1531.26" {
             description "1531.26 nm/195.781250 THz 3.125/6.25GHz spacing";
           }
           enum "1531.24" {
             description "1531.24 nm/195.784375 THz 3.125GHz spacing";
           }
           enum "1531.21" {
             description "1531.21 nm/195.787500 THz 3.125/6.25/12.5GHz spacing";
           }
           enum "1531.19" {
             description "1531.19 nm/195.790625 THz 3.125GHz spacing";
           }
           enum "1531.16" {
             description "1531.16 nm/195.793750 THz 3.125/6.25GHz spacing";
           }
           enum "1531.14" {
             description "1531.14 nm/195.796875 THz 3.125GHz spacing";
           }
           enum "1531.12" {
             description "1531.12 nm/195.800000 THz 3.125/6.25/12.5/100GHz spacing";
           }
           enum "1531.09" {
             description "1531.09 nm/195.803125 THz 3.125GHz spacing";
           }
           enum "1531.07" {
             description "1531.07 nm/195.806250 THz 3.125/6.25GHz spacing";
           }
           enum "1531.04" {
             description "1531.04 nm/195.809375 THz 3.125GHz spacing";
           }
           enum "1531.02" {
             description "1531.02 nm/195.812500 THz 3.125/6.25/12.5GHz spacing";
           }
           enum "1530.99" {
             description "1530.99 nm/195.815625 THz 3.125GHz spacing";
           }
           enum "1530.97" {
             description "1530.97 nm/195.818750 THz 3.125/6.25GHz spacing";
           }
           enum "1530.94" {
             description "1530.94 nm/195.821875 THz 3.125GHz spacing";
           }
           enum "1530.92" {
             description "1530.92 nm/195.825000 THz 3.125/6.25/12.5/75GHz spacing";
           }
           enum "1530.90" {
             description "1530.90 nm/195.828125 THz 3.125GHz spacing";
           }
           enum "1530.87" {
             description "1530.87 nm/195.831250 THz 3.125/6.25GHz spacing";
           }
           enum "1530.85" {
             description "1530.85 nm/195.834375 THz 3.125GHz spacing";
           }
           enum "1530.82" {
             description "1530.82 nm/195.837500 THz 3.125/6.25/12.5GHz spacing";
           }
           enum "1530.80" {
             description "1530.80 nm/195.840625 THz 3.125GHz spacing";
           }
           enum "1530.77" {
             description "1530.77 nm/195.843750 THz 3.125/6.25GHz spacing";
           }
           enum "1530.75" {
             description "1530.75 nm/195.846875 THz 3.125GHz spacing";
           }
           enum "1530.72" {
             description "1530.72 nm/195.850000 THz 3.125/6.25/12.5/50GHz spacing";
           }
           enum "1530.70" {
             description "1530.70 nm/195.853125 THz 3.125GHz spacing";
           }
           enum "1530.68" {
             description "1530.68 nm/195.856250 THz 3.125/6.25GHz spacing";
           }
           enum "1530.65" {
             description "1530.65 nm/195.859375 THz 3.125GHz spacing";
           }
           enum "1530.63" {
             description "1530.63 nm/195.862500 THz 3.125/6.25/12.5GHz spacing";
           }
           enum "1530.60" {
             description "1530.60 nm/195.865625 THz 3.125GHz spacing";
           }
           enum "1530.58" {
             description "1530.58 nm/195.868750 THz 3.125/6.25GHz spacing";
           }
           enum "1530.55" {
             description "1530.55 nm/195.871875 THz 3.125GHz spacing";
           }
           enum "1530.53" {
             description "1530.53 nm/195.875000 THz 3.125/6.25/12.5GHz spacing";
           }
           enum "1530.51" {
             description "1530.51 nm/195.878125 THz 3.125GHz spacing";
           }
           enum "1530.48" {
             description "1530.48 nm/195.881250 THz 3.125/6.25GHz spacing";
           }
           enum "1530.46" {
             description "1530.46 nm/195.884375 THz 3.125GHz spacing";
           }
           enum "1530.43" {
             description "1530.43 nm/195.887500 THz 3.125/6.25/12.5GHz spacing";
           }
           enum "1530.41" {
             description "1530.41 nm/195.890625 THz 3.125GHz spacing";
           }
           enum "1530.38" {
             description "1530.38 nm/195.893750 THz 3.125/6.25GHz spacing";
           }
           enum "1530.36" {
             description "1530.36 nm/195.896875 THz 3.125GHz spacing";
           }
           enum "1530.33" {
             description "1530.33 nm/195.900000 THz 3.125/6.25/12.5/50/75/100GHz spacing";
           }
           enum "1530.31" {
             description "1530.31 nm/195.903125 THz 3.125GHz spacing";
           }
           enum "1530.29" {
             description "1530.29 nm/195.906250 THz 3.125/6.25GHz spacing";
           }
           enum "1530.26" {
             description "1530.26 nm/195.909375 THz 3.125GHz spacing";
           }
           enum "1530.24" {
             description "1530.24 nm/195.912500 THz 3.125/6.25/12.5GHz spacing";
           }
           enum "1530.21" {
             description "1530.21 nm/195.915625 THz 3.125GHz spacing";
           }
           enum "1530.19" {
             description "1530.19 nm/195.918750 THz 3.125/6.25GHz spacing";
           }
           enum "1530.16" {
             description "1530.16 nm/195.921875 THz 3.125GHz spacing";
           }
           enum "1530.14" {
             description "1530.14 nm/195.925000 THz 3.125/6.25/12.5GHz spacing";
           }
           enum "1530.11" {
             description "1530.11 nm/195.928125 THz 3.125GHz spacing";
           }
           enum "1530.09" {
             description "1530.09 nm/195.931250 THz 3.125/6.25GHz spacing";
           }
           enum "1530.07" {
             description "1530.07 nm/195.934375 THz 3.125GHz spacing";
           }
           enum "1530.04" {
             description "1530.04 nm/195.937500 THz 3.125/6.25/12.5GHz spacing";
           }
           enum "1530.02" {
             description "1530.02 nm/195.940625 THz 3.125GHz spacing";
           }
           enum "1529.99" {
             description "1529.99 nm/195.943750 THz 3.125/6.25GHz spacing";
           }
           enum "1529.97" {
             description "1529.97 nm/195.946875 THz 3.125GHz spacing";
           }
           enum "1529.94" {
             description "1529.94 nm/195.950000 THz 3.125/6.25/12.5/50GHz spacing";
           }
           enum "1529.92" {
             description "1529.92 nm/195.953125 THz 3.125GHz spacing";
           }
           enum "1529.89" {
             description "1529.89 nm/195.956250 THz 3.125/6.25GHz spacing";
           }
           enum "1529.87" {
             description "1529.87 nm/195.959375 THz 3.125GHz spacing";
           }
           enum "1529.85" {
             description "1529.85 nm/195.962500 THz 3.125/6.25/12.5GHz spacing";
           }
           enum "1529.82" {
             description "1529.82 nm/195.965625 THz 3.125GHz spacing";
           }
           enum "1529.80" {
             description "1529.80 nm/195.968750 THz 3.125/6.25GHz spacing";
           }
           enum "1529.77" {
             description "1529.77 nm/195.971875 THz 3.125GHz spacing";
           }
           enum "1529.75" {
             description "1529.75 nm/195.975000 THz 3.125/6.25/12.5/75GHz spacing";
           }
           enum "1529.72" {
             description "1529.72 nm/195.978125 THz 3.125GHz spacing";
           }
           enum "1529.70" {
             description "1529.70 nm/195.981250 THz 3.125/6.25GHz spacing";
           }
           enum "1529.68" {
             description "1529.68 nm/195.984375 THz 3.125GHz spacing";
           }
           enum "1529.65" {
             description "1529.65 nm/195.987500 THz 3.125/6.25/12.5GHz spacing";
           }
           enum "1529.63" {
             description "1529.63 nm/195.990625 THz 3.125GHz spacing";
           }
           enum "1529.60" {
             description "1529.60 nm/195.993750 THz 3.125/6.25GHz spacing";
           }
           enum "1529.58" {
             description "1529.58 nm/195.996875 THz 3.125GHz spacing";
           }
           enum "1529.55" {
             description "1529.55 nm/196.000000 THz 3.125/6.25/12.5/100GHz spacing";
           }
           enum "1529.53" {
             description "1529.53 nm/196.003125 THz 3.125GHz spacing";
           }
           enum "1529.50" {
             description "1529.50 nm/196.006250 THz 3.125/6.25GHz spacing";
           }
           enum "1529.48" {
             description "1529.48 nm/196.009375 THz 3.125GHz spacing";
           }
           enum "1529.46" {
             description "1529.46 nm/196.012500 THz 3.125/6.25/12.5GHz spacing";
           }
           enum "1529.43" {
             description "1529.43 nm/196.015625 THz 3.125GHz spacing";
           }
           enum "1529.41" {
             description "1529.41 nm/196.018750 THz 3.125/6.25GHz spacing";
           }
           enum "1529.38" {
             description "1529.38 nm/196.021875 THz 3.125GHz spacing";
           }
           enum "1529.36" {
             description "1529.36 nm/196.025000 THz 3.125/6.25/12.5GHz spacing";
           }
           enum "1529.33" {
             description "1529.33 nm/196.028125 THz 3.125GHz spacing";
           }
           enum "1529.31" {
             description "1529.31 nm/196.031250 THz 3.125/6.25GHz spacing";
           }
           enum "1529.29" {
             description "1529.29 nm/196.034375 THz 3.125GHz spacing";
           }
           enum "1529.26" {
             description "1529.26 nm/196.037500 THz 3.125/6.25/12.5GHz spacing";
           }
           enum "1529.24" {
             description "1529.24 nm/196.040625 THz 3.125GHz spacing";
           }
           enum "1529.21" {
             description "1529.21 nm/196.043750 THz 3.125/6.25GHz spacing";
           }
           enum "1529.19" {
             description "1529.19 nm/196.046875 THz 3.125GHz spacing";
           }
           enum "1529.16" {
             description "1529.16 nm/196.050000 THz 3.125/6.25/12.5/50/75GHz spacing";
           }
           enum "1529.14" {
             description "1529.14 nm/196.053125 THz 3.125GHz spacing";
           }
           enum "1529.11" {
             description "1529.11 nm/196.056250 THz 3.125/6.25GHz spacing";
           }
           enum "1529.09" {
             description "1529.09 nm/196.059375 THz 3.125GHz spacing";
           }
           enum "1529.07" {
             description "1529.07 nm/196.062500 THz 3.125/6.25/12.5GHz spacing";
           }
           enum "1529.04" {
             description "1529.04 nm/196.065625 THz 3.125GHz spacing";
           }
           enum "1529.02" {
             description "1529.02 nm/196.068750 THz 3.125/6.25GHz spacing";
           }
           enum "1528.99" {
             description "1528.99 nm/196.071875 THz 3.125GHz spacing";
           }
           enum "1528.97" {
             description "1528.97 nm/196.075000 THz 3.125/6.25/12.5GHz spacing";
           }
           enum "1528.94" {
             description "1528.94 nm/196.078125 THz 3.125GHz spacing";
           }
           enum "1528.92" {
             description "1528.92 nm/196.081250 THz 3.125/6.25GHz spacing";
           }
           enum "1528.90" {
             description "1528.90 nm/196.084375 THz 3.125GHz spacing";
           }
           enum "1528.87" {
             description "1528.87 nm/196.087500 THz 3.125/6.25/12.5GHz spacing";
           }
           enum "1528.85" {
             description "1528.85 nm/196.090625 THz 3.125GHz spacing";
           }
           enum "1528.82" {
             description "1528.82 nm/196.093750 THz 3.125/6.25GHz spacing";
           }
           enum "1528.80" {
             description "1528.80 nm/196.096875 THz 3.125GHz spacing";
           }
           enum "1528.77" {
             description "1528.77 nm/196.100000 THz 3.125/6.25/12.5/50/75/100GHz spacing";
           }
           enum "1528.75" {
             description "1528.75 nm/196.103125 THz 3.125GHz spacing";
           }
           enum "1528.72" {
             description "1528.72 nm/196.106250 THz 3.125/6.25GHz spacing";
           }
           enum "1528.70" {
             description "1528.70 nm/196.109375 THz 3.125GHz spacing";
           }
           enum "1528.68" {
             description "1528.68 nm/196.112500 THz 3.125/6.25/12.5GHz spacing";
           }
           enum "1528.65" {
             description "1528.65 nm/196.115625 THz 3.125GHz spacing";
           }
           enum "1528.63" {
             description "1528.63 nm/196.118750 THz 3.125/6.25GHz spacing";
           }
           enum "1528.60" {
             description "1528.60 nm/196.121875 THz 3.125GHz spacing";
           }
           enum "1528.58" {
             description "1528.58 nm/196.125000 THz 3.125/6.25/12.5/75GHz spacing";
           }
           enum "1528.55" {
             description "1528.55 nm/196.128125 THz 3.125GHz spacing";
           }
           enum "1528.53" {
             description "1528.53 nm/196.131250 THz 3.125/6.25GHz spacing";
           }
           enum "1528.51" {
             description "1528.51 nm/196.134375 THz 3.125GHz spacing";
           }
           enum "1528.48" {
             description "1528.48 nm/196.137500 THz 3.125/6.25/12.5GHz spacing";
           }
           enum "1528.46" {
             description "1528.46 nm/196.140625 THz 3.125GHz spacing";
           }
           enum "1528.43" {
             description "1528.43 nm/196.143750 THz 3.125/6.25GHz spacing";
           }
           enum "1528.41" {
             description "1528.41 nm/196.146875 THz 3.125GHz spacing";
           }
           enum "1528.38" {
             description "1528.38 nm/196.15040 THz 50Ghz spacing";
           }
         }
       }
       leaf tx-power {
         description "Transmit laser output power";
         units "dBm";
         type string {
           junos:posix-pattern "^[+-]?[0-9]+(\\.[0-9]+)?$";
           junos:pattern-message "numerical value must be specified with optional leading sign and optional decimal point";
         }
       }
       container loopback {
         presence "enable loopback";
         description "Put the optics in loopback mode";
         uses apply-advanced;
       }
       leaf los-warning-threshold {
         description "LOS warning threshold";
         units "dBm";
         type string;
       }
       leaf los-alarm-threshold {
         description "LOS alarm threshold";
         units "dBm";
         type string;
       }
       leaf modulation-format {
         description "Type of Modulation Format";
         type enumeration {
           enum "16qam" {
             description "16-QAM Modulation Format";
           }
           enum "8qam" {
             description "8-QAM MOdulation Format";
           }
           enum "qpsk" {
             description "QPSK Modulation Format";
           }
         }
       }
       choice laser-enable-choice {
         leaf laser-enable {
           description "Enable Laser";
           type empty;
         }
         leaf no-laser-enable {
           description "Don't enable Laser";
           type empty;
         }
       }
       choice is-ma-choice {
         leaf is-ma {
           description "Link is enabled with alarms masked";
           type empty;
         }
         leaf no-is-ma {
           description "Don't link is enabled with alarms masked";
           type empty;
         }
       }
       leaf encoding {
         description "Line encoding";
         type enumeration {
           enum "differential" {
             description "Differential phase line encoding";
           }
           enum "non-differential" {
             description "Non-differential phase line encoding";
           }
         }
       }
       leaf fec {
         description "Forward Error Correction mode";
         type enumeration {
           enum "sdfec" {
             description "Sky-Compatible Soft Decision Forward Error Correction";
           }
           enum "sdfec25" {
             description "Denali-Compatible Soft Decision Forward Error Correction with 25 percent overhead";
           }
           enum "hgfec" {
             description "High Gain Forward Error Correction";
           }
           enum "sdfec15" {
             description "Soft Decision Forward Error Correction with 15 percent overhead";
           }
         }
       }
       leaf high-polarization {
         description "High polarization tracking mode";
         type empty;
       }
       container signal-degrade {
         description "Signal degrade thresholds";
         uses apply-advanced;
         leaf interval {
           description "Time interval";
           default "10";
           units "milliseconds";
           type union {
             type string {
               pattern "<.*>|$.*";
             }
             type uint32 {
               range "1 .. 1000";
             }
           }
         }
         leaf ber-threshold-clear {
           description "Ber threshold for signal degrade clear (format: xe-n, example: 4.5e-3)";
           type string {
             junos:posix-pattern "^[0-9]+(.[0-9]+)?e-[0-9]$";
             junos:pattern-message "Ber threshold value in format: xe-n, x is an integer or decimal number, n = 0..9";
           }
         }
         leaf ber-threshold-signal-degrade {
           description "Ber threshold for signal-degrade (format: xe-n, example: 4.5e-3)";
           type string {
             junos:posix-pattern "^[0-9]+(.[0-9]+)?e-[0-9]$";
             junos:pattern-message "Ber threshold value in format: xe-n, x is an integer or decimal number, n = 0..9";
           }
         }
         leaf q-threshold-signal-degrade-clear {
           description "Q threshold for signal-degrade clear (e.g. 14.26)";
           units "dB";
           type string;
         }
         leaf q-threshold-signal-degrade {
           description "Q threshold for signal-degrade (e.g. 9.26)";
           units "dB";
           type string;
         }
       }
       list alarm {
         key name;
         ordered-by user;
         description "Set optic alarms";
         leaf name {
           junos:cli-feature "nokeyword";
           type enumeration {
             enum "low-light-alarm" {
               description "Enable low light alarm";
             }
           }
         }
         uses apply-advanced;
         choice actiontype {
           case case_1 {
             leaf syslog {
               type empty;
             }
           }
           case case_2 {
             leaf link-down {
               type empty;
             }
           }
         }
       }
       container tca {
         description "Set tca for optic alarms";
         uses apply-advanced;
         container tx-power-high-tca {
           description "Tx power high TCA";
           uses apply-advanced;
           choice enable-tca-choice {
             leaf enable-tca {
               description "Enable tca";
               type empty;
             }
             leaf no-enable-tca {
               description "Don't enable tca";
               type empty;
             }
           }
           leaf threshold {
             description "Threshold for 15 minute tx power high TCA in dBm";
             type string {
               junos:posix-pattern "^[+-]?[0-9]+(\\.[0-9]+)?$";
               junos:pattern-message "numerical value must be specified with optional leading sign and optional decimal point";
             }
           }
           leaf threshold-24hrs {
             description "Threshold for 24 hour tx power high TCA in dBm";
             type string {
               junos:posix-pattern "^[+-]?[0-9]+(\\.[0-9]+)?$";
               junos:pattern-message "numerical value must be specified with optional leading sign and optional decimal point";
             }
           }
         }
         container tx-power-low-tca {
           description "Tx power low TCA";
           uses apply-advanced;
           choice enable-tca-choice {
             leaf enable-tca {
               description "Enable tca";
               type empty;
             }
             leaf no-enable-tca {
               description "Don't enable tca";
               type empty;
             }
           }
           leaf threshold {
             description "Threshold for 15 minute tx power low TCA in dBm";
             type string {
               junos:posix-pattern "^[+-]?[0-9]+(\\.[0-9]+)?$";
               junos:pattern-message "numerical value must be specified with optional leading sign and optional decimal point";
             }
           }
           leaf threshold-24hrs {
             description "Threshold for 24 hour tx power low TCA in dBm";
             type string {
               junos:posix-pattern "^[+-]?[0-9]+(\\.[0-9]+)?$";
               junos:pattern-message "numerical value must be specified with optional leading sign and optional decimal point";
             }
           }
         }
         container rx-power-high-tca {
           description "Rx power high TCA";
           uses apply-advanced;
           choice enable-tca-choice {
             leaf enable-tca {
               description "Enable tca";
               type empty;
             }
             leaf no-enable-tca {
               description "Don't enable tca";
               type empty;
             }
           }
           leaf threshold {
             description "Threshold for 15 minute rx power high TCA in dBm";
             type string {
               junos:posix-pattern "^[+-]?[0-9]+(\\.[0-9]+)?$";
               junos:pattern-message "numerical value must be specified with optional leading sign and optional decimal point";
             }
           }
           leaf threshold-24hrs {
             description "Threshold for 24 hour rx power high TCA in dBm";
             type string {
               junos:posix-pattern "^[+-]?[0-9]+(\\.[0-9]+)?$";
               junos:pattern-message "numerical value must be specified with optional leading sign and optional decimal point";
             }
           }
         }
         container rx-power-low-tca {
           description "Rx power low TCA";
           uses apply-advanced;
           choice enable-tca-choice {
             leaf enable-tca {
               description "Enable tca";
               type empty;
             }
             leaf no-enable-tca {
               description "Don't enable tca";
               type empty;
             }
           }
           leaf threshold {
             description "Threshold for 15 minute rx power low TCA in dBm";
             type string {
               junos:posix-pattern "^[+-]?[0-9]+(\\.[0-9]+)?$";
               junos:pattern-message "numerical value must be specified with optional leading sign and optional decimal point";
             }
           }
           leaf threshold-24hrs {
             description "Threshold for 24 hour rx power low TCA in dBm";
             type string {
               junos:posix-pattern "^[+-]?[0-9]+(\\.[0-9]+)?$";
               junos:pattern-message "numerical value must be specified with optional leading sign and optional decimal point";
             }
           }
         }
         container rx-signal-power-high-tca {
           description "Rx signal power high TCA";
           uses apply-advanced;
           choice enable-tca-choice {
             leaf enable-tca {
               description "Enable tca";
               type empty;
             }
             leaf no-enable-tca {
               description "Don't enable tca";
               type empty;
             }
           }
           leaf threshold {
             description "Threshold for 15 minute rx signal power high TCA in dBm";
             type string {
               junos:posix-pattern "^[+-]?[0-9]+(\\.[0-9]+)?$";
               junos:pattern-message "numerical value must be specified with optional leading sign and optional decimal point";
             }
           }
           leaf threshold-24hrs {
             description "Threshold for 24 hour rx signal power high TCA in dBm";
             type string {
               junos:posix-pattern "^[+-]?[0-9]+(\\.[0-9]+)?$";
               junos:pattern-message "numerical value must be specified with optional leading sign and optional decimal point";
             }
           }
         }
         container rx-signal-power-low-tca {
           description "Rx signal power low TCA";
           uses apply-advanced;
           choice enable-tca-choice {
             leaf enable-tca {
               description "Enable tca";
               type empty;
             }
             leaf no-enable-tca {
               description "Don't enable tca";
               type empty;
             }
           }
           leaf threshold {
             description "Threshold for 15 minute rx signal power low TCA in dBm";
             type string {
               junos:posix-pattern "^[+-]?[0-9]+(\\.[0-9]+)?$";
               junos:pattern-message "numerical value must be specified with optional leading sign and optional decimal point";
             }
           }
           leaf threshold-24hrs {
             description "Threshold for 24 hour rx signal power low TCA in dBm";
             type string {
               junos:posix-pattern "^[+-]?[0-9]+(\\.[0-9]+)?$";
               junos:pattern-message "numerical value must be specified with optional leading sign and optional decimal point";
             }
           }
         }
         container temperature-high-tca {
           description "Temperature high TCA";
           uses apply-advanced;
           choice enable-tca-choice {
             leaf enable-tca {
               description "Enable tca";
               type empty;
             }
             leaf no-enable-tca {
               description "Don't enable tca";
               type empty;
             }
           }
           leaf threshold {
             description "Threshold for 15 minute high temperature TCA in celsius";
             type string {
               junos:posix-pattern "^[+-]?[0-9]+(\\.[0-9]+)?$";
               junos:pattern-message "numerical value must be specified with optional leading sign and optional decimal point";
             }
           }
           leaf threshold-24hrs {
             description "Threshold for 24 hour high temperature TCA in celsius";
             type string {
               junos:posix-pattern "^[+-]?[0-9]+(\\.[0-9]+)?$";
               junos:pattern-message "numerical value must be specified with optional leading sign and optional decimal point";
             }
           }
         }
         container temperature-low-tca {
           description "Temperature low TCA";
           uses apply-advanced;
           choice enable-tca-choice {
             leaf enable-tca {
               description "Enable tca";
               type empty;
             }
             leaf no-enable-tca {
               description "Don't enable tca";
               type empty;
             }
           }
           leaf threshold {
             description "Threshold for 15 minute low temperature TCA in celsius";
             type string {
               junos:posix-pattern "^[+-]?[0-9]+(\\.[0-9]+)?$";
               junos:pattern-message "numerical value must be specified with optional leading sign and optional decimal point";
             }
           }
           leaf threshold-24hrs {
             description "Threshold for 24 hour low temperature TCA in celsius";
             type string {
               junos:posix-pattern "^[+-]?[0-9]+(\\.[0-9]+)?$";
               junos:pattern-message "numerical value must be specified with optional leading sign and optional decimal point";
             }
           }
         }
         container carrier-frequency-offset-high-tca {
           description "Carrier frequency offset high TCA";
           uses apply-advanced;
           choice enable-tca-choice {
             leaf enable-tca {
               description "Enable tca";
               type empty;
             }
             leaf no-enable-tca {
               description "Don't enable tca";
               type empty;
             }
           }
           leaf threshold {
             description "Threshold for 15 minute frequency offset high TCA in MHz";
             type string {
               junos:posix-pattern "^[+-]?[0-9]+(\\.[0-9]+)?$";
               junos:pattern-message "numerical value must be specified with optional leading sign and optional decimal point";
             }
           }
           leaf threshold-24hrs {
             description "Threshold for 24 hour frequency offset high TCA in MHz";
             type string {
               junos:posix-pattern "^[+-]?[0-9]+(\\.[0-9]+)?$";
               junos:pattern-message "numerical value must be specified with optional leading sign and optional decimal point";
             }
           }
         }
         container carrier-frequency-offset-low-tca {
           description "Carrier frequency offset low TCA";
           uses apply-advanced;
           choice enable-tca-choice {
             leaf enable-tca {
               description "Enable tca";
               type empty;
             }
             leaf no-enable-tca {
               description "Don't enable tca";
               type empty;
             }
           }
           leaf threshold {
             description "Threshold for 15 minute frequency offset low TCA in MHz";
             type string {
               junos:posix-pattern "^[+-]?[0-9]+(\\.[0-9]+)?$";
               junos:pattern-message "numerical value must be specified with optional leading sign and optional decimal point";
             }
           }
           leaf threshold-24hrs {
             description "Threshold for 24 hour frequency offset low TCA in MHz";
             type string {
               junos:posix-pattern "^[+-]?[0-9]+(\\.[0-9]+)?$";
               junos:pattern-message "numerical value must be specified with optional leading sign and optional decimal point";
             }
           }
         }
         container fec-ber {
           junos:cli-feature "oneliner";
           description "Optics Errored Seconds Threshold crossing defect trigger";
           choice enable-tca-choice {
             leaf enable-tca {
               description "Enable the Optics errored seconds threshold crossing alert";
               type empty;
             }
             leaf no-enable-tca {
               description "Don't enable the Optics errored seconds threshold crossing alert";
               type empty;
             }
           }
           leaf threshold {
             description "TCA threshold for BER value in format: xe-n, x is an integer or decimal number, n = 0..9";
             default "10e-3";
             type string {
               junos:posix-pattern "^[0-9]+(\\.[0-9]+)?e-[0-9]$";
               junos:pattern-message "FEC BER threshold value in format: xe-n, x is an integer or decimal number, n = 0..9";
             }
           }
           leaf threshold-24hrs {
             description "TCA threshold for BER value in format: xe-n, x is an integer or decimal number, n = 0..9";
             default "10e-3";
             type string {
               junos:posix-pattern "^[0-9]+(\\.[0-9]+)?e-[0-9]$";
               junos:pattern-message "FEC BER threshold value in format: xe-n, x is an integer or decimal number, n = 0..9";
             }
           }
         }
         container tec-current-high-tca {
           description "TEC Current high TCA";
           uses apply-advanced;
           choice enable-tca-choice {
             leaf enable-tca {
               description "Enable tca";
               type empty;
             }
             leaf no-enable-tca {
               description "Don't enable tca";
               type empty;
             }
           }
           leaf threshold {
             description "Threshold for 15 minute TEC Current high TCA in mA";
             type string {
               junos:posix-pattern "^[+-]?[0-9]+(\\.[0-9]+)?$";
               junos:pattern-message "numerical value must be specified with optional leading sign and optional decimal point";
             }
           }
           leaf threshold-24hrs {
             description "Threshold for 24 hour TEC Current high TCA in mA";
             type string {
               junos:posix-pattern "^[+-]?[0-9]+(\\.[0-9]+)?$";
               junos:pattern-message "numerical value must be specified with optional leading sign and optional decimal point";
             }
           }
         }
         container tec-current-low-tca {
           description "TEC Current low TCA";
           uses apply-advanced;
           choice enable-tca-choice {
             leaf enable-tca {
               description "Enable tca";
               type empty;
             }
             leaf no-enable-tca {
               description "Don't enable tca";
               type empty;
             }
           }
           leaf threshold {
             description "Threshold for 15 minute TEC Current low TCA in mA";
             type string {
               junos:posix-pattern "^[+-]?[0-9]+(\\.[0-9]+)?$";
               junos:pattern-message "numerical value must be specified with optional leading sign and optional decimal point";
             }
           }
           leaf threshold-24hrs {
             description "Threshold for 24 hour TEC Current low TCA in mA";
             type string {
               junos:posix-pattern "^[+-]?[0-9]+(\\.[0-9]+)?$";
               junos:pattern-message "numerical value must be specified with optional leading sign and optional decimal point";
             }
           }
         }
         container residual-isi-high-tca {
           description "Residual ISI high TCA";
           uses apply-advanced;
           choice enable-tca-choice {
             leaf enable-tca {
               description "Enable tca";
               type empty;
             }
             leaf no-enable-tca {
               description "Don't enable tca";
               type empty;
             }
           }
           leaf threshold {
             description "Threshold for 15 minute Residual ISI high TCA in ps/nm";
             type string {
               junos:posix-pattern "^[+-]?[0-9]+(\\.[0-9]+)?$";
               junos:pattern-message "numerical value must be specified with optional leading sign and optional decimal point";
             }
           }
           leaf threshold-24hrs {
             description "Threshold for 24 hour Residual ISI high TCA in ps/nm";
             type string {
               junos:posix-pattern "^[+-]?[0-9]+(\\.[0-9]+)?$";
               junos:pattern-message "numerical value must be specified with optional leading sign and optional decimal point";
             }
           }
         }
         container residual-isi-low-tca {
           description "Residual ISI low TCA";
           uses apply-advanced;
           choice enable-tca-choice {
             leaf enable-tca {
               description "Enable tca";
               type empty;
             }
             leaf no-enable-tca {
               description "Don't enable tca";
               type empty;
             }
           }
           leaf threshold {
             description "Threshold for 15 minute Residual ISI low TCA in ps/nm";
             type string {
               junos:posix-pattern "^[+-]?[0-9]+(\\.[0-9]+)?$";
               junos:pattern-message "numerical value must be specified with optional leading sign and optional decimal point";
             }
           }
           leaf threshold-24hrs {
             description "Threshold for 24 hour Residual ISI low TCA in ps/nm";
             type string {
               junos:posix-pattern "^[+-]?[0-9]+(\\.[0-9]+)?$";
               junos:pattern-message "numerical value must be specified with optional leading sign and optional decimal point";
             }
           }
         }
         container pam-histogram-high-tca {
           description "PAM Histogram high TCA";
           uses apply-advanced;
           choice enable-tca-choice {
             leaf enable-tca {
               description "Enable tca";
               type empty;
             }
             leaf no-enable-tca {
               description "Don't enable tca";
               type empty;
             }
           }
           leaf threshold {
             description "Threshold for 15 minute PAM Histogram high TCA";
             type string {
               junos:posix-pattern "^[0-9]+$";
               junos:pattern-message "must be an unsigned integer";
             }
           }
           leaf threshold-24hrs {
             description "Threshold for 24 hour PAM Histogram high TCA";
             type string {
               junos:posix-pattern "^[0-9]+$";
               junos:pattern-message "must be an unsigned integer";
             }
           }
         }
         container snr-low-tca {
           description "SNR low TCA";
           uses apply-advanced;
           choice enable-tca-choice {
             leaf enable-tca {
               description "Enable tca";
               type empty;
             }
             leaf no-enable-tca {
               description "Don't enable tca";
               type empty;
             }
           }
           leaf threshold {
             description "Threshold for 15 minute SNR low TCA in dBm ";
             type string {
               junos:posix-pattern "^[+-]?[0-9]+(\\.[0-9]+)?$";
               junos:pattern-message "numerical value must be specified with optional leading sign and optional decimal point";
             }
           }
           leaf threshold-24hrs {
             description "Threshold for 24 hour SNR low TCA in dBm";
             type string {
               junos:posix-pattern "^[+-]?[0-9]+(\\.[0-9]+)?$";
               junos:pattern-message "numerical value must be specified with optional leading sign and optional decimal point";
             }
           }
         }
         container fec-corrected-errors-high-tca {
           description "FEC Corrected Error High Threshold crossing defect trigger";
           uses apply-advanced;
           choice enable-tca-choice {
             leaf enable-tca {
               description "Enable the FEC Corrected Errors threshold crossing alert";
               type empty;
             }
             leaf no-enable-tca {
               description "Don't enable the FEC Corrected Errors threshold crossing alert";
               type empty;
             }
           }
           leaf threshold {
             description "FEC Corrected-Errs value in format: xe-n, x is an integer or decimal number, n = 0..9";
             default "10e-3";
             type string {
               junos:posix-pattern "^[0-9]+(\\.[0-9]+)?e-[0-9]$";
               junos:pattern-message "FEC Corrected-Errs threshold value in format: xe-n, x is an integer or decimal number, n = 0..9";
             }
           }
           leaf threshold-24hrs {
             description "FEC Corrected-Errs value in format: xe-n, x is an integer or decimal number, n = 0..9";
             default "10e-3";
             type string {
               junos:posix-pattern "^[0-9]+(\\.[0-9]+)?e-[0-9]$";
               junos:pattern-message "FEC Corrected-Errs threshold value in format: xe-n, x is an integer or decimal number, n = 0..9";
             }
           }
         }
         container fec-ucorrected-words-high-tca {
           description "FEC UCorrected Words High Threshold crossing defect trigger";
           uses apply-advanced;
           choice enable-tca-choice {
             leaf enable-tca {
               description "Enable the FEC UCorrected Words threshold crossing alert";
               type empty;
             }
             leaf no-enable-tca {
               description "Don't enable the FEC UCorrected Words threshold crossing alert";
               type empty;
             }
           }
           leaf threshold {
             description "FEC UCorrected-Words value in format: xe-n, x is an integer or decimal number, n = 0..9";
             default "10e-3";
             type string {
               junos:posix-pattern "^[0-9]+(\\.[0-9]+)?e-[0-9]$";
               junos:pattern-message "FEC UCorrected-Words threshold value in format: xe-n, x is an integer or decimal number, n = 0..9";
             }
           }
           leaf threshold-24hrs {
             description "FEC UCorrected-Words value in format: xe-n, x is an integer or decimal number, n = 0..9";
             default "10e-3";
             type string {
               junos:posix-pattern "^[0-9]+(\\.[0-9]+)?e-[0-9]$";
               junos:pattern-message "FEC UCorrected-Words threshold value in format: xe-n, x is an integer or decimal number, n = 0..9";
             }
           }
         }
         container laser-frequency-error-high-tca {
           description "Laser frequency error high TCA";
           uses apply-advanced;
           choice enable-tca-choice {
             leaf enable-tca {
               description "Enable tca";
               type empty;
             }
             leaf no-enable-tca {
               description "Don't enable tca";
               type empty;
             }
           }
           leaf threshold {
             description "Threshold for 15 minute frequency error high TCA in MHz";
             type string {
               junos:posix-pattern "^[+-]?[0-9]+(\\.[0-9]+)?$";
               junos:pattern-message "numerical value must be specified with optional leading sign and optional decimal point";
             }
           }
           leaf threshold-24hrs {
             description "Threshold for 24 hour frequency error high TCA in MHz";
             type string {
               junos:posix-pattern "^[+-]?[0-9]+(\\.[0-9]+)?$";
               junos:pattern-message "numerical value must be specified with optional leading sign and optional decimal point";
             }
           }
         }
         container laser-frequency-error-low-tca {
           description "Laser frequency error low TCA";
           uses apply-advanced;
           choice enable-tca-choice {
             leaf enable-tca {
               description "Enable tca";
               type empty;
             }
             leaf no-enable-tca {
               description "Don't enable tca";
               type empty;
             }
           }
           leaf threshold {
             description "Threshold for 15 minute frequency error low TCA in MHz";
             type string {
               junos:posix-pattern "^[+-]?[0-9]+(\\.[0-9]+)?$";
               junos:pattern-message "numerical value must be specified with optional leading sign and optional decimal point";
             }
           }
           leaf threshold-24hrs {
             description "Threshold for 24 hour frequency error low TCA in MHz";
             type string {
               junos:posix-pattern "^[+-]?[0-9]+(\\.[0-9]+)?$";
               junos:pattern-message "numerical value must be specified with optional leading sign and optional decimal point";
             }
           }
         }
       }
       list warning {
         key name;
         ordered-by user;
         description "Set optic warnings";
         leaf name {
           junos:cli-feature "nokeyword";
           type enumeration {
             enum "low-light-warning" {
               description "Enable low light warning";
             }
           }
         }
         uses apply-advanced;
         choice actiontype {
           case case_1 {
             leaf syslog {
               description "Set action as syslog";
               type empty;
             }
           }
           case case_2 {
             leaf link-down {
               description "Set action as link-down";
               type empty;
             }
           }
         }
       }
       choice lane-info {
         case case_1 {
         }
         case case_2 {
         }
       }
     }
     container otn-options {
       description "Optical Transmission Network interface-specific options";
       uses otn_options_type;
     }
     container och-options {
       description "Optical channel configuration options";
       uses och-attributes;
     }
     container otu-options {
       description "Optical transmission unit configuration options";
       uses otu-attributes;
     }
     container odu-options {
       description "Optical data unit configuration options";
       uses odu-attributes;
     }
     container ett-options {
       description "Transport ethernet client configuration options";
       uses ett-attributes;
     }
     container fastether-options {
       description "Fast Ethernet interface-specific options";
       uses apply-advanced;
       choice loopback-choice {
         leaf loopback {
           description "Enable loopback";
           type empty;
         }
         leaf no-loopback {
           description "Don't enable loopback";
           type empty;
         }
       }
       choice flow-control-choice {
         leaf flow-control {
           description "Enable flow control";
           type empty;
         }
         leaf no-flow-control {
           description "Don't enable flow control";
           type empty;
         }
       }
       choice source-filtering-choice {
         leaf source-filtering {
           description "Enable source address filtering";
           type empty;
         }
         leaf no-source-filtering {
           description "Don't enable source address filtering";
           type empty;
         }
       }
       choice auto-negotiation-choice {
         leaf auto-negotiation {
           description "Enable auto-negotiation";
           type empty;
         }
         leaf no-auto-negotiation {
           description "Don't enable auto-negotiation";
           type empty;
         }
       }
       leaf ingress-rate-limit {
         description "Ingress rate at port";
         units "megabits per second";
         type union {
           type string {
             pattern "<.*>|$.*";
           }
           type uint32 {
             range "1 .. 100";
           }
         }
       }
       list source-address-filter {
         key name;
         ordered-by user;
         junos:cli-feature "homogeneous";
         junos:cli-feature "oneliner";
         description "Source address filters";
         junos:must "(!(any \".. .. unit <*> family ethernet-switching\"))";
         junos:must-message "source mac filters not allowed on ethernet switched port";
         leaf name {
           description "Remote MAC address";
           junos:cli-feature "nokeyword";
           type jt:mac-addr;
         }
       }
       container redundant-parent {
         junos:cli-feature "oneliner-plus";
         description " Parent of this interface";
         uses apply-advanced;
         leaf parent {
           description "Join a redundant ethernet interface";
           junos:cli-feature "nokeyword";
           junos:must "(!(any \"interfaces <*> ether-options redundant-parent $$\"))";
           junos:must-message "All children must be of the same ethernet type";
           junos:must "(!(any \"interfaces <*> gigether-options redundant-parent $$\"))";
           junos:must-message "All the children must be of same ethernet type";
           type union {
             type jt:interface-device;
             type string {
               pattern "<.*>|$.*";
             }
           }
         }
       }
       container ieee-802.3ad {
         junos:must "(!(\"system autoinstallation\"))";
         junos:must-message "incompatible with 'system autoinstallation'";
         junos:cli-feature "oneliner-plus";
         description "IEEE 802.3ad";
         uses apply-advanced;
         container lacp {
           description "Link Aggregation Control Protocol configuration";
           uses apply-advanced;
           leaf port-priority {
             description "Priority of the port (0 ... 65535)";
             type union {
               type uint16;
               type string {
                 pattern "<.*>|$.*";
               }
             }
           }
         }
         leaf bundle {
           description "Join an aggregated Ethernet interface";
           junos:cli-feature "nokeyword";
           junos:must "(!(any \"class-of-service interfaces ${interface} unit <*> rewrite-rules\"))";
           junos:must-message "rewrite config can not be applied on ae child";
           junos:must "(!(any \"class-of-service interfaces ${interface} unit <*> classifiers\"))";
           junos:must-message "classifier config can not be applied on ae child";
           junos:must "(!(any \"class-of-service interfaces ${interface} unit <*> output-traffic-control-profile\"))";
           junos:must-message "output-traffic-control-profile config can not be applied on ae child";
           junos:must "(!(\"class-of-service interfaces ${interface} output-traffic-control-profile\"))";
           junos:must-message "output-traffic-control-profile config can not be applied on ae child";
           junos:must "(!(\"class-of-service interfaces ${interface} shaping-rate\"))";
           junos:must-message "shaping-rate config can not be applied on ae child";
           junos:must "(!(\"class-of-service interfaces ${interface} scheduler-map\"))";
           junos:must-message "scheduler-map config can not be applied on ae child";
           junos:must "(!(\".. .. .. vlan-offload\"))";
           junos:must-message "ae child device vlan-offload is not allowed";
           junos:must "(!(\".. .. .. flow-control\"))";
           junos:must-message "Setting flow-control on ae child device is not allowed";
           junos:must "(!(\".. .. .. mtu\"))";
           junos:must-message "Setting mtu on ae child device is not allowed";
           junos:must "(!(\".. .. .. vlan-vci-tagging\"))";
           junos:must-message "ae child device vlan-vci-tagging is not allowed";
           junos:must "(!(\".. .. .. stacked-vlan-tagging\"))";
           junos:must-message "ae child device stacked-vlan-tagging is not allowed";
           junos:must "(!(\".. .. .. flexible-vlan-tagging\"))";
           junos:must-message "ae child device flexible-vlan-tagging is not allowed";
           junos:must "(!(\".. .. .. vlan-tagging\"))";
           junos:must-message "ae child device vlan-tagging is not allowed";
           type union {
             type jt:interface-device;
             type string {
               pattern "<.*>|$.*";
             }
           }
         }
         choice type {
           case case_1 {
             leaf primary {
               description "Primary interface for link-protection mode";
               type empty;
             }
           }
           case case_2 {
             leaf backup {
               description "Backup interface for link-protection mode";
               type empty;
             }
           }
         }
       }
       container mpls {
         description "MPLS options";
         uses mpls_ifd_options;
       }
       leaf ignore-l3-incompletes {
         description "Ignore L3 incomplete errors";
         type empty;
       }
     }
     container redundant-ether-options {
       description "Ethernet redundancy options";
       uses apply-advanced;
       leaf redundancy-group {
         description "Redundancy group of this interface";
         junos:must "(\"chassis cluster redundancy-group $$\")";
         junos:must-message "A redundancy group should be defined";
         type union {
           type string {
             pattern "<.*>|$.*";
           }
           type uint16 {
             range "1 .. 128";
           }
         }
       }
       choice loopback-choice {
         leaf loopback {
           description "Enable loopback";
           type empty;
         }
         leaf no-loopback {
           description "Don't enable loopback";
           type empty;
         }
       }
       choice flow-control-choice {
         leaf flow-control {
           description "Enable flow control";
           type empty;
         }
         leaf no-flow-control {
           description "Don't enable flow control";
           type empty;
         }
       }
       choice source-filtering-choice {
         leaf source-filtering {
           description "Enable source address filtering";
           type empty;
         }
         leaf no-source-filtering {
           description "Don't enable source address filtering";
           type empty;
         }
       }
       list source-address-filter {
         key name;
         ordered-by user;
         junos:cli-feature "homogeneous";
         junos:cli-feature "oneliner";
         description "Source address filters";
         leaf name {
           description "Remote MAC address";
           junos:cli-feature "nokeyword";
           type jt:mac-addr;
         }
       }
       leaf mru {
         description "Maximum receive packet size";
         type union {
           type string {
             pattern "<.*>|$.*";
           }
           type uint32;
         }
       }
       leaf link-speed {
         description "Link speed of individual interface that joins the RETH";
         type enumeration {
           enum "10m" {
             description "Links are 10M";
           }
           enum "100m" {
             description "Links are 100M";
           }
           enum "1g" {
             description "Links are 1G";
           }
           enum "10g" {
             description "Links are 10G";
           }
           enum "25g" {
             description "Links are 25G";
           }
           enum "40g" {
             description "Links are 40G";
           }
           enum "50g" {
             description "Links are 50G";
           }
           enum "100g" {
             description "Links are 100G";
           }
           enum "400g" {
             description "Links are 400G";
           }
         }
       }
       leaf minimum-links {
         description "Minimum number of active links";
         default "1";
         type union {
           type string {
             pattern "<.*>|$.*";
           }
           type uint16 {
             range "1 .. 8";
           }
         }
       }
       container lacp {
         description "Link Aggregation Control Protocol configuration";
         uses apply-advanced;
         choice mode {
           case case_1 {
             leaf active {
               description "Initiate transmission of LACP packets";
               type empty;
             }
           }
           case case_2 {
             leaf passive {
               description "Respond to LACP packets";
               type empty;
             }
           }
         }
         leaf periodic {
           description "Timer interval for periodic transmission of LACP packets";
           type enumeration {
             enum "fast" {
               description "Receive packets every second";
             }
             enum "slow" {
               description "Receive packets every 30 seconds";
             }
           }
         }
       }
     }
     container aggregated-ether-options {
       description "Aggregated Ethernet interface-specific options";
       uses apply-advanced;
       choice loopback-choice {
         leaf loopback {
           description "Enable loopback";
           type empty;
         }
         leaf no-loopback {
           description "Don't enable loopback";
           type empty;
         }
       }
       choice flow-control-choice {
         leaf flow-control {
           description "Enable flow control";
           type empty;
         }
         leaf no-flow-control {
           description "Don't enable flow control";
           type empty;
         }
       }
       choice source-filtering-choice {
         leaf source-filtering {
           description "Enable source address filtering";
           type empty;
         }
         leaf no-source-filtering {
           description "Don't enable source address filtering";
           type empty;
         }
       }
       leaf autostate-exclude {
         description "Interface will not contribute to IRB state";
         type empty;
       }
       container link-protection {
         presence "enable link-protection";
         description "Enable link protection mode";
         uses apply-advanced;
         leaf revertive {
           description "Revert back from active backup link to primary, if primary is UP";
           junos:must "(!(\"interfaces ${interface} aggregated-ether-options link-protection non-revertive\"))";
           junos:must-message "link-protection revertive and non-revertive are mutually exclusive";
           junos:must "(!(\"chassis aggregated-devices ethernet lacp\"))";
           junos:must-message "link-protection revertive and LACP are mutually exclusive";
           junos:must "(!(\"interfaces ${interface} aggregated-ether-options lacp\"))";
           junos:must-message "link-protection revertive and LACP are mutually exclusive";
           type empty;
         }
         leaf non-revertive {
           description "Do not revert back (default mode) from active backup link to primary, if primary is UP";
           junos:must "(!(\"interfaces ${interface} aggregated-ether-options link-protection revertive\"))";
           junos:must-message "link-protection revertive and non-revertive are mutually exclusive";
           junos:must "(!(\"chassis aggregated-devices ethernet lacp\"))";
           junos:must-message "link-protection revertive and LACP are mutually exclusive";
           junos:must "(!(\"interfaces ${interface} aggregated-ether-options lacp\"))";
           junos:must-message "link-protection revertive and LACP are mutually exclusive";
           type empty;
         }
         leaf backup-state {
           description "Link protection backup link state";
           default "accept-data";
           type enumeration {
             enum "accept-data" {
               description "Accept data on receive channel of backup link";
             }
             enum "discard-data" {
               description "Discard data on receive channel of backup link";
             }
             enum "down" {
               description "Backup link is marked down";
               junos:must "(!(\"chassis aggregated-devices ethernet lacp\"))";
               junos:must-message "backup-state down and LACP are mutually exclusive";
               junos:must "(!(\"interfaces ${interface} aggregated-ether-options lacp\"))";
               junos:must-message "backup-state down and LACP are mutually exclusive";
             }
           }
         }
         container rtg-config {
           presence "enable rtg-config";
           description "RTG enable on AE";
           uses apply-advanced;
           leaf preempt-cutover-timer {
             description "RTG preempt-cutover-timer in seconds";
             default "1";
             type union {
               type string {
                 pattern "<.*>|$.*";
               }
               type uint32 {
                 range "0 .. 255";
               }
             }
           }
         }
       }
       choice fcoe-lag-choice {
         leaf fcoe-lag {
           description "Enable FIP/FCoE LAG";
           type empty;
         }
         leaf no-fcoe-lag {
           description "Don't enable FIP/FCoE LAG";
           type empty;
         }
       }
       list source-address-filter {
         key name;
         ordered-by user;
         junos:cli-feature "homogeneous";
         junos:cli-feature "oneliner";
         description "Source address filters";
         leaf name {
           description "Remote MAC address";
           junos:cli-feature "nokeyword";
           type jt:mac-addr;
         }
       }
       container load-balance {
         uses aggregate-load-balance;
       }
       container bfd-liveness-detection {
         junos:must "(!(\".. lacp fast-failover\"))";
         junos:must-message "BFD not supported with lacp with fast-failover mode";
         junos:must "(!(\".. lacp link-protection\"))";
         junos:must-message "BFD not supported with lacp link protection";
         junos:must "(!(\".. link-protection\"))";
         junos:must-message "BFD not supported with link protection";
         description "Bidirectional Forwarding Detection (BFD) options";
         uses apply-advanced;
         leaf version {
           description "BFD protocol version number";
           default "automatic";
           type enumeration {
             enum "0" {
               description "BFD version 0 (deprecated)";
             }
             enum "1" {
               description "BFD version 1";
             }
             enum "automatic" {
               description "Choose BFD version automatically";
             }
           }
         }
         leaf minimum-interval {
           description "Minimum transmit and receive interval";
           units "milliseconds";
           type union {
             type string {
               pattern "<.*>|$.*";
             }
             type uint32 {
               range "1 .. 255000";
             }
           }
         }
         leaf minimum-transmit-interval {
           description "Minimum transmit interval";
           status deprecated;
           units "milliseconds";
           type union {
             type string {
               pattern "<.*>|$.*";
             }
             type uint32 {
               range "1 .. 255000";
             }
           }
         }
         leaf minimum-receive-interval {
           description "Minimum receive interval";
           units "milliseconds";
           type union {
             type string {
               pattern "<.*>|$.*";
             }
             type uint32 {
               range "1 .. 255000";
             }
           }
         }
         leaf multiplier {
           description "Detection time multiplier";
           default "3";
           type union {
             type string {
               pattern "<.*>|$.*";
             }
             type uint32 {
               range "1 .. 255";
             }
           }
         }
         leaf inline-disable {
           description "Disable inline mode for this BFD session";
           type empty;
         }
         leaf pdu-size {
           description "BFD transport protocol payload size";
           default "24";
           type union {
             type string {
               pattern "<.*>|$.*";
             }
             type uint32 {
               range "24 .. 16000";
             }
           }
         }
         choice adaptation-choice {
           case case_1 {
             leaf no-adaptation {
               description "Disable adaptation";
               type empty;
             }
           }
         }
         container transmit-interval {
           description "Transmit-interval options";
           uses apply-advanced;
           leaf minimum-interval {
             description "Minimum transmit interval";
             units "milliseconds";
             type union {
               type string {
                 pattern "<.*>|$.*";
               }
               type uint32 {
                 range "1 .. 255000";
               }
             }
           }
           leaf threshold {
             description "High transmit interval triggering a trap";
             units "milliseconds";
             type union {
               type uint32;
               type string {
                 pattern "<.*>|$.*";
               }
             }
           }
         }
         container detection-time {
           description "Detection-time options";
           uses apply-advanced;
           leaf threshold {
             description "High detection-time triggering a trap";
             units "milliseconds";
             type union {
               type uint32;
               type string {
                 pattern "<.*>|$.*";
               }
             }
           }
         }
         container authentication {
           description "Authentication options";
           uses apply-advanced;
           leaf key-chain {
             description "Key chain name";
             junos:must "(\".. algorithm\")";
             junos:must-message "May not be configured without algorithm";
             junos:must "(\"security authentication-key-chains key-chain $$\")";
             junos:must-message "Referenced key-chain must be defined";
             type string;
           }
           leaf algorithm {
             description "Algorithm name";
             junos:must "(\".. key-chain\")";
             junos:must-message "May not be configured without key-chain";
             type enumeration {
               enum "simple-password" {
                 description "Simple password";
               }
               enum "keyed-md5" {
                 description "Keyed message Digest 5";
               }
               enum "meticulous-keyed-md5" {
                 description "Meticulous keyed message Digest 5";
               }
               enum "keyed-sha-1" {
                 description "Keyed secure hash algorithm (SHA1) ";
               }
               enum "meticulous-keyed-sha-1" {
                 description "Meticulous keyed secure hash algorithm (SHA1) ";
               }
             }
           }
           leaf loose-check {
             description "Verify authentication only if authentication is negotiated";
             type empty;
           }
         }
         container damping {
           description "BFD flap damping parameters";
           uses apply-advanced;
           leaf suppress {
             description "Suppress threshold for figure-of-merit value";
             default "5000";
             type union {
               type string {
                 pattern "<.*>|$.*";
               }
               type uint32 {
                 range "1000 .. 200000";
               }
             }
           }
           leaf reuse {
             description "Reuse threshold for figure-of-merit value";
             default "1000";
             type union {
               type string {
                 pattern "<.*>|$.*";
               }
               type uint32 {
                 range "1000 .. 200000";
               }
             }
           }
           leaf max-suppress-time {
             description "Maximum hold-down time";
             default "600";
             units "seconds";
             type union {
               type string {
                 pattern "<.*>|$.*";
               }
               type uint32 {
                 range "1 .. 20000";
               }
             }
           }
           leaf half-life-interval {
             description "Decay half life interval";
             default "30";
             units "seconds";
             type union {
               type string {
                 pattern "<.*>|$.*";
               }
               type uint32 {
                 range "1 .. 600";
               }
             }
           }
           leaf increment {
             description "Increments applied to figure-of-merit value for every flap";
             default "1000";
             type union {
               type string {
                 pattern "<.*>|$.*";
               }
               type uint32 {
                 range "1000 .. 20000";
               }
             }
           }
         }
         leaf neighbor {
           description "BFD neighbor address";
           type jt:ipaddr;
         }
         leaf local-address {
           description "BFD local address";
           type jt:ipaddr;
         }
         leaf holddown-interval {
           description "Time to hold the session-UP notification to the client";
           units "milliseconds";
           type union {
             type string {
               pattern "<.*>|$.*";
             }
             type uint32 {
               range "0 .. 255000";
             }
           }
         }
       }
       leaf minimum-links {
         description "Minimum number of aggregated links";
         junos:must "(!(\"interfaces ${interface} aggregated-ether-options link-speed mixed\"))";
         junos:must-message "Minimum-links option is not compatible with link-speed mixed";
         type union {
           type string {
             pattern "<.*>|$.*";
           }
           type uint16;
         }
       }
       container minimum-bandwidth {
         presence "enable minimum-bandwidth";
         junos:must "(!(\"interfaces ${interface}  aggregated-ether-options optimize-aggregate-frr\"))";
         junos:must-message "Minimum-bandwidth and optimize-aggregate-frr are mutually exclusive";
         junos:must "(!(\"interfaces ${interface}  aggregated-ether-options minimum-links\"))";
         junos:must-message "Minimum-bandwidth and minimum-links are mutually exclusive";
         description "Minimum bandwidth configured for aggregated bundle";
         uses apply-advanced;
         leaf bw-value {
           description "Bandwidth value";
           default "1";
           type union {
             type uint64;
             type string {
               pattern "<.*>|$.*";
             }
           }
         }
         leaf bw-unit {
           description "Bandwidth unit";
           type enumeration {
             enum "bps" {
               description "Links are in bits per sec";
             }
             enum "kbps" {
               description "Links are in kilo bits per sec";
             }
             enum "mbps" {
               description "Links are in mega bits per sec";
             }
             enum "gbps" {
               description "Links are in giga bits per sec ";
             }
           }
         }
       }
       choice redundancy_choice {
         case case_1 {
         }
         case case_2 {
         }
       }
       container rebalance-periodic {
         uses apply-advanced;
       }
       leaf link-speed {
         description "Link speed of individual interface that joins the AE";
         type enumeration {
           enum "10m" {
             description "Links are 10M";
           }
           enum "100m" {
             description "Links are 100M";
           }
           enum "1g" {
             description "Links are 1G";
           }
           enum "2.5g" {
             description "Links are 2.5G";
           }
           enum "5g" {
             description "Links are 5G";
           }
           enum "8g" {
             description "Links are 8G";
           }
           enum "10g" {
             description "Links are 10G";
           }
           enum "25g" {
             description "Links are 25G";
           }
           enum "40g" {
             description "Links are 40G";
           }
           enum "50g" {
             description "Links are 50G";
           }
           enum "80g" {
             description "Links are 80G";
           }
           enum "100g" {
             description "Links are 100G";
           }
           enum "200g" {
             description "Links are 200G";
           }
           enum "400g" {
             description "Links are 400G";
           }
           enum "800g" {
             description "Links are 800G";
           }
           enum "oc192" {
             description "Links are OC-192";
           }
           enum "mixed" {
             description "Links are various speeds";
             junos:must "(!(\"interfaces ${interface} per-unit-scheduler\"))";
             junos:must-message "per-unit-scheduler is incompatible with link-speed mixed";
             junos:must "(!(\".. resilient-hash\"))";
             junos:must-message "Mixed-rate AE is not supported along with Resilient Hashing  mode";
             junos:must "(!(\".. load-balance adaptive\"))";
             junos:must-message "Mixed-rate AE is not supported along with Adaptive Load balance mode";
           }
         }
       }
       container lacp {
         description "Link Aggregation Control Protocol configuration";
         uses apply-advanced;
         choice mode {
           case case_1 {
             leaf active {
               description "Initiate transmission of LACP packets";
               type empty;
             }
           }
           case case_2 {
             leaf passive {
               description "Respond to LACP packets";
               type empty;
             }
           }
         }
         leaf periodic {
           description "Timer interval for periodic transmission of LACP packets";
           type enumeration {
             enum "fast" {
               description "Receive packets every second";
             }
             enum "slow" {
               description "Receive packets every 30 seconds";
             }
           }
         }
         leaf multiplier {
           description "LACP timeout detection multiplier";
           type union {
             type string {
               pattern "<.*>|$.*";
             }
             type uint32 {
               range "3 .. 30";
             }
           }
         }
         container link-protection {
           presence "enable link-protection";
           junos:must "(!(\".. .. link-protection\"))";
           junos:must-message "LACP and non LACP based link-protection not allowed together";
           uses apply-advanced;
           leaf disable {
             description "To turn off LACP link-protection";
             type empty;
           }
           choice mode {
             case case_1 {
               leaf revertive {
                 description "Switch links when better priority link comes up";
                 type empty;
               }
             }
             case case_2 {
               leaf non-revertive {
                 description "Do not switch links when better priority link comes up";
                 type empty;
               }
             }
           }
           container rtg-config {
             presence "enable rtg-config";
             description "RTG Feature enable on AE";
             uses apply-advanced;
             leaf preempt-cutover-timer {
               description "RTG preempt-cutover-timer in seconds";
               default "1";
               type union {
                 type string {
                   pattern "<.*>|$.*";
                 }
                 type uint32 {
                   range "0 .. 255";
                 }
               }
             }
           }
         }
         leaf sync-reset {
           description "On minimum-link failure notify out of sync to peer";
           type enumeration {
             enum "disable" {
               description "To disable minimum-link failure handling at LACP level";
             }
             enum "enable" {
               description "To enable minimum-link failure handling at LACP level";
             }
           }
         }
         leaf system-priority {
           description "Priority of the system (0 ... 65535)";
           type string;
         }
         leaf system-id {
           description "Node's System ID, encoded as a MAC address";
           type jt:mac-addr;
         }
         leaf admin-key {
           description "Node's administrative key";
           type union {
             type uint16;
             type string {
               pattern "<.*>|$.*";
             }
           }
         }
       }
       container ethernet-switch-profile {
         description "Ethernet virtual LAN/media access control-level options";
         uses apply-advanced;
         leaf-list tag-protocol-id {
           ordered-by user;
           description "IEEE 802.1q Tag Protocol Identifier values for VLAN-tagged frames";
           type string;
           max-elements 1;
         }
         leaf mac-learn-enable {
           description "Learn MAC addresses dynamically";
           type empty;
         }
       }
     }
     container es-options {
       description "ES PIC interface-specific options";
       uses apply-advanced;
       leaf backup-interface {
         description "Name of backup interface";
         type union {
           type jt:interface-device;
           type string {
             pattern "<.*>|$.*";
           }
         }
       }
     }
     container dsl-options {
       junos:must "(!(\".. shdsl-options\"))";
       junos:must-message "SHDSL or VDSL options cannot co-exist with DSL options on the same ATM interface";
       description "DSL interface-specific options";
       uses apply-advanced;
       leaf operating-mode {
         description "DSL operating mode";
         type enumeration {
           enum "auto" {
             description "Autonegotiate mode";
           }
           enum "ansi-dmt" {
             description "ANSI T1.413 Issue II mode";
           }
           enum "itu-dmt" {
             description "ITU G.992.1 mode";
           }
           enum "etsi" {
             description "ETSI TS 101 388 V1.3.1 mode";
           }
           enum "itu-annexb-ur2" {
             description "ITU G.992.1 UR-2 mode";
           }
           enum "itu-annexb-non-ur2" {
             description "ITU G.992.1 Non UR-2 mode";
           }
           enum "itu-dmt-bis" {
             description "ITU G.992.3 mode";
           }
           enum "adsl2plus" {
             description "ITU G.992.5 mode";
           }
           enum "annexm-itu-dmt-bis" {
             description "AnnexM ITU G.992.3 mode";
           }
           enum "annexm-adsl2plus" {
             description "AnnexM ITU G.992.5 mode";
           }
         }
       }
     }
     container vdsl-options {
       description "VDSL interface-specific options";
       uses apply-advanced;
       leaf vdsl-profile {
         description "VDSL profile";
         type enumeration {
           enum "auto" {
             description "Auto";
           }
           enum "8a" {
             description "Profile 8a";
           }
           enum "8b" {
             description "Profile 8b";
           }
           enum "8c" {
             description "Profile 8c";
           }
           enum "8d" {
             description "Profile 8d";
           }
           enum "12a" {
             description "Profile 12a";
           }
           enum "12b" {
             description "Profile 12b";
           }
           enum "17a" {
             description "Profile 17a";
           }
         }
       }
       leaf sra {
         description "DSL SRA";
         default "disable";
         type enumeration {
           enum "enable" {
             description "Enable SRA";
           }
           enum "disable" {
             description "Disable SRA";
           }
         }
       }
       leaf v43 {
         description "DSL V43 tones";
         default "enable";
         type enumeration {
           enum "enable" {
             description "Enable V43";
           }
           enum "disable" {
             description "Disable V43";
           }
         }
       }
       leaf sos {
         description "Enable SOS";
         type empty;
       }
     }
     container dsl-sfp-options {
       description "DSL SFP options";
       uses apply-advanced;
       container adsl-options {
         description "ADSL options";
         uses apply-advanced;
         leaf vpi {
           description "Virtual path identifier";
           junos:must "(\".. vci\")";
           junos:must-message "vci must be specified";
           type union {
             type string {
               pattern "<.*>|$.*";
             }
             type uint32 {
               range "0 .. 255";
             }
           }
         }
         leaf vci {
           description "Virtual circuit identifier";
           junos:must "(\".. vpi\")";
           junos:must-message "vpi must be specified";
           type union {
             type string {
               pattern "<.*>|$.*";
             }
             type uint32 {
               range "32 .. 65535";
             }
           }
         }
         leaf encap {
           description "Encapsulation";
           junos:must "((\".. vci\" && \".. vpi\"))";
           junos:must-message "vci and vpi must be specified";
           type enumeration {
             enum "bypass" {
               description "Bypass";
             }
             enum "llcsnap-bridged-802dot1q" {
               description "LLCSNAP bridged 802.1q";
             }
             enum "llcsnap-routed-ip" {
               description "LLCSNAP routed ip";
             }
             enum "vc-mux-bridged" {
               description "VC MUX bridged";
             }
             enum "vc-mux-routed-ip" {
               description "VC MUX routed ip";
             }
             enum "generic" {
               description "Generic";
             }
           }
         }
         leaf annex {
           description "Annex type";
           junos:must "((\".. vci\" && \".. vpi\"))";
           junos:must-message "vci and vpi must be specified";
           type enumeration {
             enum "auto" {
               description "Annex type auto";
             }
             enum "annexj-off" {
               description "Annex type annexj turn off";
             }
           }
         }
       }
       container vdsl-options {
         description "VDSL options";
         uses apply-advanced;
         leaf profile {
           description "VDSL profile";
           type enumeration {
             enum "auto" {
               description "Automatic";
             }
             enum "8a" {
               description "Profile 8a";
             }
             enum "8b" {
               description "Profile 8b";
             }
             enum "8c" {
               description "Profile 8c";
             }
             enum "8d" {
               description "Profile 8d";
             }
             enum "12a" {
               description "Profile 12a";
             }
             enum "12b" {
               description "Profile 12b";
             }
             enum "17a" {
               description "Profile 17a";
             }
             enum "30a" {
               description "Profile 30a";
             }
           }
         }
         leaf carrier {
           description "Carrier setting";
           type enumeration {
             enum "auto" {
               description "Automatic";
             }
             enum "a43" {
               description "Carrier A43";
             }
             enum "b43" {
               description "Carrier B43";
             }
           }
         }
       }
       container gfast-options {
         description "G.fast options";
         uses apply-advanced;
         leaf carrier {
           description "Carrier setting";
           type enumeration {
             enum "a43" {
               description "Carrier A43";
             }
             enum "a43c" {
               description "Carrier A43C";
             }
             enum "b43" {
               description "Carrier B43";
             }
             enum "b43c" {
               description "Carrier B43C";
             }
           }
         }
       }
     }
     container shdsl-options {
       junos:must "(!(\"interfaces ${interface} vdsl-options\"))";
       junos:must-message "VDSL options cannot co-exist with SHDSL options on the same interface";
       junos:must "(!(\"interfaces ${interface} dsl-options\"))";
       junos:must-message "DSL options cannot co-exist with SHDSL options on the same interface";
       description "SHDSL interface-specific options";
       uses apply-advanced;
       leaf annex {
         description "Type of SHDSL annex";
         default "annex-b";
         type enumeration {
           enum "annex-a" {
             description "Annex-a PIC";
           }
           enum "annex-b" {
             description "Annex-b PIC";
           }
           enum "annex-f" {
             description "Annex-f PIC";
           }
           enum "annex-g" {
             description "Annex-g PIC";
           }
           enum "annex-auto" {
             description "Annex-auto PIC";
           }
         }
       }
       leaf line-rate {
         description "SHDSL line rate";
         type string;
       }
       leaf loopback {
         description "Loopback mode";
         type enumeration {
           enum "local" {
             description "Local loopback";
           }
           enum "remote" {
             description "Remote loopback";
           }
         }
       }
       container snr-margin {
         presence "enable snr-margin";
         description "Signal to noise ratio margin";
         uses apply-advanced;
         leaf current {
           description "Current signal to noise ratio margin";
           units "dB";
           type string;
         }
         leaf snext {
           description "SNEXT signal to noise ratio margin";
           units "dB";
           type string;
         }
       }
     }
     container data-input {
       description "Configuration for drop-insert data input";
       uses apply-advanced;
       choice input-choice {
         case case_1 {
           leaf system {
             description "Data sourced from system";
             type empty;
           }
         }
         case case_2 {
           leaf interface {
             description "Interface that acts as data source";
             junos:must "(!(\"interfaces $$ data-input\"))";
             junos:must-message "Interface should not have data-input configured";
             type union {
               type jt:interface-device;
               type string {
                 pattern "<.*>|$.*";
               }
             }
           }
         }
       }
     }
     container switch-options {
       description "Front end ports configuration";
       uses apply-advanced;
       list switch-port {
         key name;
         leaf name {
           description "Front end port number";
           junos:cli-feature "nokeyword";
           type union {
             type string {
               pattern "<.*>|$.*";
             }
             type uint32 {
               range "0 .. 15";
             }
           }
         }
         uses apply-advanced;
         choice auto-negotiation-choice {
           leaf auto-negotiation {
             description "Enable auto-negotiation";
             type empty;
           }
           leaf no-auto-negotiation {
             description "Don't enable auto-negotiation";
             type empty;
           }
         }
         leaf link-mode {
           description "Link operational mode";
           junos:must "(\".. speed\")";
           junos:must-message "speed must be configured with link-mode";
           type enumeration {
             enum "half-duplex" {
               description "Half-duplex operation";
             }
             enum "full-duplex" {
               description "Full-duplex operation";
             }
           }
         }
         leaf speed {
           description "Link speed";
           junos:must "(\".. link-mode\")";
           junos:must-message "link-mode must be configured with speed";
           type enumeration {
             enum "10m" {
             }
             enum "100m" {
             }
             enum "1g" {
             }
           }
         }
         leaf vlan-id {
           description "VLAN ID for this port";
           junos:must "(\".. .. .. vlan-tagging\")";
           junos:must-message "vlan-tagging needs to be enabled to support vlan-id";
           type union {
             type string {
               pattern "<.*>|$.*";
             }
             type uint32 {
               range "0 .. 4094";
             }
           }
         }
         leaf cascade-port {
           description "Port externally connected to another cascade port";
           junos:must "(!(\".. vlan-id\"))";
           junos:must-message "Cascade port cannot have VLAN id";
           junos:must "(\".. .. .. vlan-tagging\")";
           junos:must-message "vlan-tagging needs to be enabled to support cascade-port";
           type empty;
         }
       }
     }
     container container-options {
       description "Container interface specific options";
       uses apply-advanced;
       container container-type {
         presence "enable container-type";
         description "Protocol type of the container interface";
         uses apply-advanced;
         choice container-type-choice {
           case case_1 {
             container aps {
               description "APS options on the container";
               presence "enable aps";
               junos:must "((\".. .. member-interface-type sonet\" || (\".. .. member-interface-type atm\" || (\".. .. member-interface-type channelized-sonet\" || \".. .. member-interface-type channelized-sdh\"))))";
               junos:must-message "APS can be enabled on Sonet, Channelized-Sonet, Channelized-SDH  or ATM interfaces only";
               uses aps_type;
             }
           }
         }
       }
       container member-interface-type {
         description "Link type of members of container";
         uses apply-advanced;
         choice member_interface_type_choice {
           case case_1 {
             container sonet {
               uses apply-advanced;
               leaf member-interface-speed {
                 description "Link speed of members of container";
                 type enumeration {
                   enum "oc3" {
                     description "Links are OC-3";
                   }
                   enum "oc12" {
                     description "Links are OC-12";
                   }
                   enum "oc48" {
                     description "Links are OC-48";
                   }
                   enum "oc192" {
                     description "Links are OC-192";
                   }
                   enum "oc768" {
                     description "Links are OC-768";
                   }
                   enum "mixed" {
                     description "Links are of different speeds";
                   }
                 }
               }
             }
           }
           case case_2 {
             container atm {
               uses apply-advanced;
               leaf member-interface-speed {
                 description "Link speed of members of container";
                 type enumeration {
                   enum "oc3" {
                     description "Links are OC-3";
                   }
                   enum "oc12" {
                     description "Links are OC-12";
                   }
                   enum "oc48" {
                     description "Links are OC-48";
                   }
                 }
               }
             }
           }
           case case_3 {
             container channelized-sonet {
               uses apply-advanced;
               leaf member-interface-speed {
                 description "Link speed of members of container";
                 type enumeration {
                   enum "coc3" {
                     description "Links are COC-3";
                   }
                   enum "coc12" {
                     description "Links are COC-12";
                   }
                   enum "coc48" {
                     description "Links are COC-48";
                   }
                   enum "coc192" {
                     description "Links are COC-192";
                   }
                   enum "coc768" {
                     description "Links are COC-768";
                   }
                 }
               }
             }
           }
           case case_4 {
             container channelized-sdh {
               uses apply-advanced;
               leaf member-interface-speed {
                 description "Link speed of members of container";
                 type enumeration {
                   enum "cstm1" {
                     description "Links are cstm-1";
                   }
                   enum "cstm4" {
                     description "Links are cstm-4";
                   }
                   enum "cstm16" {
                     description "Links are cstm-16";
                   }
                   enum "coc64" {
                     description "Links are cstm-64";
                   }
                   enum "cstm256" {
                     description "Links are cstm256";
                   }
                 }
               }
             }
           }
         }
       }
       container redundancy {
         description "Container interface redundancy options";
         uses apply-advanced;
         container hold-time {
           junos:cli-feature "oneliner";
           description "Hold time for link up and link down";
           leaf up {
             description "Link up hold time";
             units "milliseconds";
             type union {
               type string {
                 pattern "<.*>|$.*";
               }
               type uint32 {
                 range "0 .. 65534";
               }
             }
           }
           leaf down {
             description "Link down hold time";
             units "milliseconds";
             type union {
               type string {
                 pattern "<.*>|$.*";
               }
               type uint32 {
                 range "0 .. 65534";
               }
             }
           }
         }
       }
       leaf-list container-list {
         ordered-by user;
         description "List of container interfaces this member link is associated to";
         type union {
           type jt:interface-device;
           type string {
             pattern "<.*>|$.*";
           }
         }
       }
       choice redundancy-type {
         case case_1 {
           choice aps-redundancy {
             case case_1 {
               leaf primary {
                 description "This member link is primary interface of the container";
                 type empty;
               }
             }
             case case_2 {
               leaf standby {
                 description "This member link is standby interface of the container";
                 type empty;
               }
             }
           }
         }
       }
       leaf fast-aps {
         description "Fast APS switch";
         type empty;
       }
       leaf allow-configuration-override {
         description "Allow physical configuration of member link to override container configuration";
         type empty;
       }
     }
     list unit {
       key name;
       description "Logical interface";
       leaf name {
         junos:cli-feature "nokeyword";
         type string;
       }
       uses apply-advanced;
       leaf interface-tag {
         description "Interface tag name";
         type string {
           length "1 .. 64";
           junos:posix-pattern "^[A-Za-z0-9][_0-9A-Za-z-]*$";
           junos:pattern-message "Must be a non-reserved string of 64 characters or less";
         }
       }
       container policer-overhead {
         description "Policer overhead adjustment for this unit";
         uses apply-advanced;
         leaf policer-overhead-value {
           description "Policer overhead bytes to be accounted in ingress and egress";
           junos:cli-feature "nokeyword";
           units "bytes";
           junos:must "((!(\".. ingress\") && !(\".. egress\")))";
           junos:must-message "Do not use the options ingress or egress when adjust values are specified";
           type union {
             type string {
               pattern "<.*>|$.*";
             }
             type int32;
           }
         }
         leaf ingress {
           description "Ingress value in bytes";
           units "bytes";
           type union {
             type string {
               pattern "<.*>|$.*";
             }
             type int32 {
               range "-64 .. 64";
             }
           }
         }
         leaf egress {
           description "Egress value in bytes";
           units "bytes";
           type union {
             type string {
               pattern "<.*>|$.*";
             }
             type int32 {
               range "-64 .. 64";
             }
           }
         }
       }
       leaf alias {
         description "Interface alias";
         junos:must "(!(\"interfaces interface-range $$\"))";
         junos:must-message "Interface alias cannot be an existing interface range name";
         type string;
       }
       leaf proxy-macip-advertisement {
         description "Proxy advertisement of type 2 MAC+IP route for EVPN";
         type empty;
       }
       leaf virtual-gateway-accept-data {
         description "Accept packets destined for virtual gateway address";
         type empty;
       }
       container peer-psd {
         presence "enable peer-psd";
         junos:cli-feature "oneliner";
         description "Peer psd";
         leaf psd-name {
           description "Peer psd name";
           junos:cli-feature "nokeyword";
           junos:must "(\".. .. peer-interface\")";
           junos:must-message "peer-interface must be configured on this interface";
           type string;
         }
       }
       container peer-interface {
         presence "enable peer-interface";
         junos:cli-feature "oneliner-plus";
         description "Peer interface";
         uses apply-advanced;
         leaf interface-name {
           description "Peer interface name";
           junos:cli-feature "nokeyword";
           junos:must "((\".. .. peer-psd\" || \"interfaces $$-IFL peer-interface\"))";
           junos:must-message "Peer interface or peer psd must be configured";
           type union {
             type jt:interface-unit;
             type string {
               pattern "<.*>|$.*";
             }
           }
         }
       }
       container interface-shared-with {
         presence "enable interface-shared-with";
         junos:must "(\"chassis system-domains\")";
         junos:must-message "Chassis system-domains must be configured";
         junos:cli-feature "oneliner-plus";
         description "Specify which PSD owns this logical interface";
         uses apply-advanced;
         leaf psd-name {
           description "Name of protected system domain (psd[1-31], ex. psd2)";
           junos:cli-feature "nokeyword";
           type string {
             junos:posix-pattern "^psd([1-9]|[1-2][0-9]|[3][0-1])$";
             junos:pattern-message "Protected system domain name is a string consisting of \'psd\' follows by the PSD ID (1-31), ex. psd2";
           }
         }
       }
       choice enable-disable {
         case case_1 {
           leaf disable {
             description "Disable this logical interface";
             type empty;
           }
         }
       }
       leaf passive-monitor-mode {
         description "Use interface to tap packets from another router";
         type empty;
       }
       leaf clear-dont-fragment-bit {
         description "Clear DF bit in packet (AS PIC and J-series only as well as MIF)";
         type empty;
       }
       leaf description {
         description "Text description of interface";
         type string;
       }
       leaf encapsulation {
         description "Logical link-layer encapsulation";
         type enumeration {
           enum "atm-nlpid" {
             description "ATM NLPID encapsulation";
           }
           enum "atm-cisco-nlpid" {
             description "Cisco-compatible ATM NLPID encapsulation";
           }
           enum "atm-snap" {
             description "ATM LLC/SNAP encapsulation";
           }
           enum "atm-vc-mux" {
             description "ATM VC multiplexing";
           }
           enum "atm-ccc-vc-mux" {
             description "ATM VC for CCC";
           }
           enum "atm-tcc-vc-mux" {
             description "ATM VC for translational cross-connect";
           }
           enum "atm-tcc-snap" {
             description "ATM LLC/SNAP for translational cross-connect";
           }
           enum "atm-ccc-cell-relay" {
             description "ATM cell relay for CCC";
           }
           enum "vlan-vci-ccc" {
             description "CCC for VLAN Q-in-Q and ATM VPI/VCI interworking";
           }
           enum "ether-over-atm-llc" {
             description "Ethernet over ATM (LLC/SNAP) encapsulation";
           }
           enum "ether-vpls-over-atm-llc" {
             description "Ethernet VPLS over ATM (bridging) encapsulation";
           }
           enum "ppp-over-ether-over-atm-llc" {
             description "PPPoE over ATM (LLC/SNAP) encapsulation";
             junos:must "(!(\".. family\"))";
             junos:must-message "Can't configure protocol family with encapsulation ppp-over-ether-over-atm-llc";
             junos:must "(\".. .. encapsulation ethernet-over-atm\")";
             junos:must-message "Physical link-layer encapsulation must be ethernet-over-atm";
           }
           enum "ppp-over-ether" {
             description "PPPoE encapsulation";
             junos:must "(!(\"forwarding-options hyper-mode\"))";
             junos:must-message "To configure encapsulation ppp-over-ether, 'forwarding-options hyper-mode' should not be configured";
             junos:must "(!(\".. family\"))";
             junos:must-message "Can't configure protocol family with encapsulation ppp-over-ether";
           }
           enum "atm-ppp-vc-mux" {
             description "ATM PPP over raw AAL5";
           }
           enum "atm-ppp-llc" {
             description "ATM PPP over AAL5/LLC";
           }
           enum "atm-mlppp-llc" {
             description "ATM MLPPP over AAL5/LLC";
           }
           enum "frame-relay-ppp" {
             description "PPP over Frame Relay";
             junos:must "(!(\".. family inet6\"))";
             junos:must-message "family inet6 is not supported on encapsulation frame-relay-ppp";
             junos:must "(!(\".. family inet\"))";
             junos:must-message "family inet is not supported on encapsulation frame-relay-ppp";
             junos:must "(\".. .. encapsulation frame-relay\")";
             junos:must-message "Physical link-layer encapsulation must be frame-relay";
           }
           enum "frame-relay-ccc" {
             description "Frame Relay DLCI for CCC";
           }
           enum "frame-relay" {
             description "Frame Relay DLCI";
           }
           enum "frame-relay-tcc" {
             description "Frame Relay DLCI for translational cross-connect";
           }
           enum "frame-relay-ether-type" {
             description "Cisco-compatible Frame Relay Encapsulation DLCI";
             junos:must "((\".. .. encapsulation flexible-frame-relay\" || (\".. .. encapsulation frame-relay-ether-type\" || \".. .. encapsulation frame-relay-ether-type-tcc\")))";
             junos:must-message "Interface encapsulation must be cisco-compatible or flexible frame relay";
           }
           enum "frame-relay-ether-type-tcc" {
             description "Cisco-compatible Frame Relay Encapsulation DLCI for TCC";
           }
           enum "ether-vpls-fr" {
             description "Ethernet VPLS over Frame Relay (bridging) encapsulation";
           }
           enum "vlan-ccc" {
             description "802.1q tagging for a cross-connect";
           }
           enum "ethernet-ccc" {
             description "Ethernet for a cross-connect";
           }
           enum "vlan-vpls" {
             description "VLAN virtual private LAN service";
           }
           enum "vlan-bridge" {
             description "VLAN layer-2 bridging";
           }
           enum "ethernet-tcc" {
             description "Ethernet translational cross-connect";
           }
           enum "dix" {
             description "Ethernet DIXv2 (RFC 894)";
           }
           enum "ethernet" {
             description "Ethernet II (RFC 894)";
           }
           enum "ethernet-vpls" {
             description "Ethernet II virtual private LAN service";
           }
           enum "ethernet-bridge" {
             description "Ethernet II bridging";
           }
           enum "vlan" {
             description "802.1q-tagged Ethernet";
           }
           enum "vlan-tcc" {
             description "802.1q tagging for a translational cross-connect";
           }
           enum "multilink-ppp" {
             description "Multilink PPP";
           }
           enum "multilink-frame-relay-end-to-end" {
             description "Multilink Frame Relay end-to-end (FRF.15)";
           }
           enum "ppp-ccc" {
             description "Serial PPP device for a cross-connect";
           }
         }
       }
       leaf mtu {
         description "Maximum transmission unit packet size";
         type union {
           type string {
             pattern "<.*>|$.*";
           }
           type uint32;
         }
       }
       choice pointedness {
         case case_1 {
           leaf point-to-point {
             description "Point-to-point connection";
             type empty;
           }
         }
         case case_2 {
           leaf multipoint {
             description "Multipoint connection";
             type empty;
           }
         }
       }
       leaf bandwidth {
         description "Logical unit bandwidth (informational only)";
         type string;
       }
       container radio-router {
         description "Parameters for dynamic link cost management";
         presence "enable radio-router";
         junos:cli-feature "oneliner-plus";
         uses dynamic_ifbw_parms_type;
       }
       choice traps-choice {
         leaf traps {
           description "Enable SNMP notifications on state changes";
           type empty;
         }
         leaf no-traps {
           description "Don't enable SNMP notifications on state changes";
           type empty;
         }
       }
       choice routing-services-choice {
         leaf routing-services {
           description "Enable routing services";
           status deprecated;
           type empty;
         }
         leaf no-routing-services {
           description "Don't enable routing services";
           status deprecated;
           type empty;
         }
       }
       container routing-service {
         description "Routing Services on this interface";
         uses apply-advanced;
         choice enable-disable {
           case case_1 {
             leaf enable {
               description "Enable Routing Service";
               type empty;
             }
           }
           case case_2 {
             leaf disable {
               description "Disable Routing Service";
               type empty;
             }
           }
         }
       }
       container arp-resp {
         presence "enable arp-resp";
         junos:cli-feature "oneliner";
         description "Knob to control ARP response on the interface, default is restricted";
         choice arp-response-options {
           case case_1 {
             leaf unrestricted {
               description "Enable unrestricted ARP respone on the interface";
               type empty;
             }
           }
           case case_2 {
             leaf restricted {
               description "Enable restricted proxy ARP response on the interface";
               type empty;
             }
           }
         }
       }
       container proxy-arp {
         presence "enable proxy-arp";
         junos:must "(!(\"switch-options no-arp-trap \"))";
         junos:must-message "Cannot enable proxy ARP with no-arp-trap";
         junos:cli-feature "oneliner";
         description "Enable proxy ARP on the interface, default is unrestricted";
         choice proxyarp-options {
           case case_1 {
             leaf unrestricted {
               description "Enable unrestricted proxy ARP on the interface";
               type empty;
             }
           }
           case case_2 {
             leaf restricted {
               description "Enable restricted proxy ARP on the interface";
               type empty;
             }
           }
         }
       }
       choice vlan_choice {
         case case_1 {
           leaf vlan-id {
             description "Virtual LAN identifier value for 802.1q VLAN tags";
             junos:must "(!(\"interfaces ${interface} stacked-vlan-tagging\"))";
             junos:must-message "vlan-id is not supported on stacked-vlan-tagging mode";
             junos:must "((unique \"interfaces ${interface} unit <*> vlan-id $$\" || !(\"interfaces ${interface} flexible-vlan-tagging\")))";
             junos:must-message "duplicate vlan-id";
             type string;
           }
         }
         case case_2 {
           leaf vlan-id-range {
             description "Virtual LAN identifier range of form vid1-vid2";
             junos:must "((\"interfaces ${interface} vlan-tagging\" || \"interfaces ${interface} flexible-vlan-tagging\"))";
             junos:must-message "valid only with vlan-tagging or flexible-vlan-tagging mode";
             type jt:vlan-range;
           }
         }
         case case_3 {
           leaf-list inner-vlan-id-swap-ranges {
             description "Inner vlan-id swap range(s) of form vid1-vid2 for dynamic L2 VLANs";
             type jt:vlan-range;
           }
         }
         case case_4 {
           leaf-list vlan-id-list {
             description "List of VLAN identifiers";
             junos:must "((\" .. encapsulation vlan-ccc\" || (\"interfaces ${interface} encapsulation extended-vlan-ccc\" || (\" .. encapsulation vlan-vpls\" || (\"interfaces ${interface} encapsulation extended-vlan-vpls\" || (\" .. encapsulation vlan-bridge\" || \"interfaces ${interface} encapsulation extended-vlan-bridge\"))))))";
             junos:must-message "valid only with ccc/vpls/bridge encapsulation";
             junos:must "((\"interfaces ${interface} vlan-tagging\" || \"interfaces ${interface} flexible-vlan-tagging\"))";
             junos:must-message "valid only with vlan-tagging or flexible-vlan-tagging mode";
             junos:must "(\".. input-vlan-map push\")";
             junos:must-message "interface with vlan-id-list is supported only with input-vlan-map push";
             type jt:vlan-range;
           }
         }
         case case_5 {
           leaf-list vlan-tag {
             ordered-by user;
             description "IEEE 802.1q tag list for VLAN tagged frames";
             status deprecated;
             type string;
           }
         }
         case case_6 {
           container vlan-tags {
             presence "enable vlan-tags";
             junos:must "((!(\"interfaces ${interface} vlan-tagging\") || !((\". inner\" || (\". inner-range\" || \". inner-list\")))))";
             junos:must-message "inner/inner-range/inner-list is valid only on stacked-vlan-tagging and flexible-vlan-tagging mode";
             junos:must "((!(\"interfaces ${interface} stacked-vlan-tagging\") || (\". inner\" || (\". inner-range\" || \". inner-list\"))))";
             junos:must-message "inner/inner-range/inner-list must be defined for stacked-vlan-tagging mode";
             junos:must "((\".. demux-options\" || (\"interfaces ${interface} vlan-tagging\" || (\"interfaces ${interface} stacked-vlan-tagging\" || \"interfaces ${interface} flexible-vlan-tagging\"))))";
             junos:must-message "valid only with vlan-tagging, stacked-vlan-tagging or flexible-vlan-tagging mode";
             junos:cli-feature "oneliner";
             description "IEEE 802.1q tags";
             leaf outer {
               description "[tpid.]vlan-id, tpid format is 0xNNNN and is optional";
               type string;
             }
             choice inner_choice {
               case case_1 {
                 leaf inner {
                   description "[tpid.]vlan-id, tpid format is 0xNNNN and is optional";
                   type string;
                 }
               }
               case case_2 {
                 leaf inner-range {
                   description "[tpid.]vid1-vid2, tpid format is 0xNNNN and is optional";
                   type string {
                     junos:posix-pattern "^((0[Xx][0-9A-Fa-f]{4}.){0,1}([1-9][0-9]{0,2}|[1-3][0-9]{3}|40[0-8][0-9]|409[0-4])-([1-9][0-9]{0,2}|[1-3][0-9]{3}|40[0-8][0-9]|409[0-4]))$";
                     junos:pattern-message "vid in vlan-tag ([0xNNNN.]vid1-vid2) must be 1 to 4094";
                   }
                 }
               }
               case case_3 {
                 leaf-list inner-list {
                   description "List of VLAN identifiers";
                   junos:must "((\" .. .. encapsulation vlan-ccc\" || (\"interfaces ${interface} encapsulation extended-vlan-ccc\" || (\" .. .. encapsulation vlan-vpls\" || (\"interfaces ${interface} encapsulation extended-vlan-vpls\" || (\" .. .. encapsulation vlan-bridge\" || \"interfaces ${interface} encapsulation extended-vlan-bridge\"))))))";
                   junos:must-message "valid only with ccc/vpls/bridge encapsulation";
                   type jt:vlan-range;
                 }
               }
             }
           }
         }
       }
       leaf deep-vlan-qualified-learning {
         description "Enable qualified MAC-address learning on the specified vlan tag";
         junos:must "((\".. vlan-tags outer\" && \".. vlan-tags inner\"))";
         junos:must-message "deep-vlan-qualified-learning can be specified only with one outer and one inner vlan tags";
         type union {
           type string {
             pattern "<.*>|$.*";
           }
           type uint32 {
             range 3;
           }
         }
       }
       leaf native-inner-vlan-id {
         description "Native virtual LAN identifier for singly tagged frames";
         junos:must "((\".. vlan-tags\" || \".. family bridge inner-vlan-id-list\"))";
         junos:must-message "native-inner-vlan-id can be specified only on a dual vlan tagged unit";
         junos:must "(\"interfaces ${interface} flexible-vlan-tagging\")";
         junos:must-message "native-inner-vlan-id can be specified only with flexible-vlan-tagging mode";
         type union {
           type string {
             pattern "<.*>|$.*";
           }
           type uint32 {
             range "0 .. 4094";
           }
         }
       }
       container accept-source-mac {
         junos:must "(!(\".. family ethernet-switching\"))";
         junos:must-message "source mac filters not allowed on ethernet switched port";
         description "Remote media access control address to/from which to accept traffic";
         uses apply-advanced;
         list mac-address {
           key name;
           description "Remote MAC address";
           uses mac_list;
         }
       }
       container input-vlan-map {
         description "VLAN map operation on input";
         junos:cli-feature "oneliner-plus";
         uses vlan_map;
       }
       container output-vlan-map {
         description "VLAN map operation on output";
         junos:cli-feature "oneliner-plus";
         uses vlan_map;
       }
       leaf swap-by-poppush {
         description "Pop original vlan tag and then push a new vlan tag";
         type empty;
       }
       leaf receive-lsp {
         description "Name of incoming label-switched path";
         type string;
       }
       leaf transmit-lsp {
         description "Name of outgoing label-switched path";
         type string;
       }
       leaf dlci {
         description "Frame Relay data-link control identifier";
         type union {
           type string {
             pattern "<.*>|$.*";
           }
           type uint32 {
             range "1 .. 1022";
           }
         }
       }
       leaf multicast-dlci {
         description "Frame Relay data-link control identifier for multicast packets";
         type union {
           type string {
             pattern "<.*>|$.*";
           }
           type uint32 {
             range "1 .. 1022";
           }
         }
       }
       choice vci_type {
         case case_1 {
           leaf vci {
             description "ATM point-to-point virtual circuit identifier ([vpi.]vci)";
             junos:must "(!(\".. encapsulation vlan-vci-ccc\"))";
             junos:must-message "'vci-range' must be used with encapsulation vlan-vci-ccc";
             type jt:atm-vci;
           }
         }
         case case_2 {
           leaf allow-any-vci {
             description "Allow all VCIs to open in atm-ccc-cell-relay mode";
             type empty;
           }
         }
         case case_3 {
           leaf vpi {
             description "ATM point-to-point virtual path identifier (vpi)";
             type union {
               type string {
                 pattern "<.*>|$.*";
               }
               type uint32 {
                 range "0 .. 255";
               }
             }
           }
         }
         case case_4 {
           leaf trunk-id {
             description "ATM trunk identifier";
             type union {
               type string {
                 pattern "<.*>|$.*";
               }
               type uint32 {
                 range "0 .. 31";
               }
             }
           }
         }
       }
       choice psn_vci_type {
         case case_1 {
         }
         case case_2 {
         }
       }
       container atm-l2circuit-mode {
         junos:cli-feature "oneliner";
         description "Select ATM Layer 2 circuit transport mode";
         choice mode_choice {
           case case_1 {
             leaf cell {
               description "ATM Layer 2 circuit cell mode";
               type empty;
             }
           }
           case case_2 {
             leaf aal5 {
               description "ATM Layer 2 circuit AAL5 mode";
               type empty;
             }
           }
         }
       }
       container vci-range {
         junos:must "(!(\".. vci\"))";
         junos:must-message "'vci-range' and 'vci' statements cannot co-exist";
         junos:cli-feature "oneliner";
         description "ATM VCI range start <start-vci> end <end-vci>";
         leaf start {
           description "ATM VCI range's start value";
           type union {
             type string {
               pattern "<.*>|$.*";
             }
             type uint16 {
               range "32 .. 4094";
             }
           }
         }
         leaf end {
           description "ATM VCI range's end value";
           type union {
             type string {
               pattern "<.*>|$.*";
             }
             type uint16 {
               range "32 .. 4094";
             }
           }
         }
       }
       leaf trunk-bandwidth {
         description "ATM trunk bandwidth";
         units "bits per second";
         type string;
       }
       leaf multicast-vci {
         description "ATM virtual circuit identifier for multicast packets";
         type jt:atm-vci;
       }
       container shaping {
         description "Virtual circuit traffic-shaping options";
         uses dcd_shaping_config;
       }
       container oam-period {
         junos:cli-feature "oneliner";
         description "OAM cell period";
         choice oam_period_choices {
           case case_1 {
             leaf oam-period {
               description "OAM cell period";
               junos:cli-feature "nokeyword";
               units "seconds";
               type union {
                 type string {
                   pattern "<.*>|$.*";
                 }
                 type uint32 {
                   range "1 .. 900";
                 }
               }
             }
           }
           case case_2 {
             container disable {
               presence "enable disable";
               junos:cli-feature "oneliner";
               description "Disable F5 OAM loopback";
             }
           }
         }
       }
       container oam-liveness {
         description "OAM virtual circuit liveness parameters";
         uses apply-advanced;
         leaf up-count {
           description "Number of OAM cells to consider VC up";
           type union {
             type string {
               pattern "<.*>|$.*";
             }
             type uint32 {
               range "1 .. 255";
             }
           }
         }
         leaf down-count {
           description "Number of OAM cells to consider VC down";
           type union {
             type string {
               pattern "<.*>|$.*";
             }
             type uint32 {
               range "1 .. 255";
             }
           }
         }
       }
       container ppp-options {
         description "Point-to-Point Protocol interface-specific options";
         uses ppp_options_type;
       }
       container pppoe-options {
         description "PPP over Ethernet interface-specific options";
         uses pppoe_options_type;
       }
       choice keepalive_choices {
         case case_1 {
           container keepalives {
             description "Send or demand keepalive messages";
             presence "enable keepalives";
             junos:cli-feature "oneliner";
             uses keepalives_type;
           }
         }
         case case_2 {
           leaf no-keepalives {
             description "Do not send or demand keepalive messages";
             type empty;
           }
         }
       }
       leaf inverse-arp {
         description "Enable inverse ARP";
         type empty;
       }
       leaf transmit-weight {
         description "ATM2 transmit weight for VC under VP tunnel";
         type union {
           type string {
             pattern "<.*>|$.*";
           }
           type uint16 {
             range "1 .. 32767";
           }
         }
       }
       container epd-threshold {
         description "Early packet discard threshold for ATM2";
         junos:cli-feature "oneliner";
         uses epd_threshold_config;
       }
       leaf cell-bundle-size {
         description "L2 circuit cell bundle size";
         units "cells";
         type union {
           type string {
             pattern "<.*>|$.*";
           }
           type uint32 {
             range "1 .. 176";
           }
         }
       }
       leaf cell-bundle-timeout {
         description "L2 circuit cell bundle timeout";
         units "microseconds";
         type union {
           type string {
             pattern "<.*>|$.*";
           }
           type uint32 {
             range "1 .. 512";
           }
         }
       }
       leaf plp-to-clp {
         description "Enable ATM2 PLP to CLP copy";
         type empty;
       }
       leaf atm-scheduler-map {
         description "Assign ATM2 CoS scheduling map";
         type union {
           type string {
             pattern "default";
           }
           type string;
         }
       }
       leaf mrru {
         description "Maximum received reconstructed unit";
         units "bytes";
         type union {
           type string {
             pattern "<.*>|$.*";
           }
           type uint16 {
             range "1500 .. 4500";
           }
         }
       }
       leaf short-sequence {
         description "Short sequence number header format (MLPPP only)";
         type empty;
       }
       leaf fragment-threshold {
         description "Fragmentation threshold";
         units "bytes";
         type union {
           type string {
             pattern "<.*>|$.*";
           }
           type uint32 {
             range "64 .. 4500";
           }
         }
       }
       leaf drop-timeout {
         description "Drop timeout";
         units "milliseconds";
         type union {
           type string {
             pattern "<.*>|$.*";
           }
           type uint16 {
             range "0 .. 2000";
           }
         }
       }
       leaf disable-mlppp-inner-ppp-pfc {
         description "Disable compression for inner PPP header in MLPPP payload";
         type empty;
       }
       leaf minimum-links {
         description "Minimum number of links to sustain the bundle";
         type union {
           type string {
             pattern "<.*>|$.*";
           }
           type uint16;
         }
       }
       leaf multilink-max-classes {
         description "Number of multilink classes";
         type union {
           type string {
             pattern "<.*>|$.*";
           }
           type uint16;
         }
       }
       container compression {
         presence "enable compression";
         junos:must "(!(\".. encapsulation multilink-frame-relay-end-to-end\"))";
         junos:must-message "CRTP is not supported for multilink-frame-relay-end-to-end encapsulation";
         description "Various packet header compressions";
         uses apply-advanced;
         container rtp {
           presence "enable rtp";
           description "Compress and decompress RTP";
           uses apply-advanced;
           leaf f-max-period {
             description "Maximum number of compressed packets between transmission of full headers";
             type union {
               type string {
                 pattern "<.*>|$.*";
               }
               type uint32 {
                 range "1 .. 65535";
               }
             }
           }
           leaf-list queues {
             ordered-by user;
             description "Queue holding RTP packets. Default is queue 1";
             type enumeration {
               enum "q0" {
                 description "RTP packets assigned to queue 0";
               }
               enum "q1" {
                 description "RTP packets assigned to queue 1";
               }
               enum "q2" {
                 description "RTP packets assigned to queue 2";
               }
               enum "q3" {
                 description "RTP packets assigned to queue 3";
               }
             }
           }
           container port {
             presence "enable port";
             junos:cli-feature "oneliner";
             description "UDP destination ports reserved for RTP packets";
             leaf minimum {
               type union {
                 type string {
                   pattern "<.*>|$.*";
                 }
                 type uint32 {
                   range "0 .. 65535";
                 }
               }
             }
             leaf maximum {
               type union {
                 type string {
                   pattern "<.*>|$.*";
                 }
                 type uint32 {
                   range "0 .. 65535";
                 }
               }
             }
           }
           container maximum-contexts {
             junos:cli-feature "oneliner";
             description "Maximum number of simultaneous RTP contexts";
             leaf number {
               description "Maximum number of simultaneous RTP contexts";
               junos:cli-feature "nokeyword";
               type union {
                 type string {
                   pattern "<.*>|$.*";
                 }
                 type uint32 {
                   range "16 .. 2048";
                 }
               }
             }
           }
         }
       }
       leaf interleave-fragments {
         description "Interleave long packets with high priority ones";
         type empty;
       }
       leaf link-layer-overhead {
         description "Link layer bit stuffing overhead (0.0 .. 50.0 percent)";
         type jt:unsigned-float;
       }
       leaf accounting-profile {
         description "Accounting profile name";
         junos:must "((\"accounting-options interface-profile $$\" || \"accounting-options flat-file-profile $$\"))";
         junos:must-message "referenced accounting profile must be defined";
         type string;
       }
       leaf peer-unit {
         description "Peer unit number";
         type union {
           type string {
             pattern "<.*>|$.*";
           }
           type uint32 {
             range "0 .. 40960";
           }
         }
       }
       container tunnel {
         description "Tunnel parameters";
         uses apply-advanced;
         container encapsulation {
           presence "enable encapsulation";
           junos:cli-feature "homogeneous";
           description "Encapsulation over tunnel";
           container vxlan-gpe {
             presence "enable vxlan-gpe";
             junos:must "((!(\".. udp\") && !(\".. ipip\")))";
             junos:must-message "Only one encapsulation can  be set per IFL";
             uses apply-advanced;
             container source {
               uses apply-advanced;
               leaf address {
                 description "Interface address prefix";
                 junos:must "(!(\".. interface\"))";
                 junos:must-message "To configure address interface must be not set";
                 type jt:ipv4addr;
               }
               leaf mac-address {
                 description "Interface source mac address";
                 junos:must "((\".. interface\" || \".. address\"))";
                 junos:must-message "Either address or interface must be set";
                 type jt:mac-addr;
               }
               leaf interface {
                 description "Name of the interface";
                 type union {
                   type jt:interface-name;
                   type string {
                     pattern "<.*>|$.*";
                   }
                 }
               }
             }
             container destination {
               uses apply-advanced;
               leaf address {
                 description "Interface address prefix";
                 type jt:ipv4addr;
               }
               leaf mac-address {
                 description "Interface destination mac address";
                 junos:must "(\".. address\")";
                 junos:must-message "destination address must be set";
                 type jt:mac-addr;
               }
             }
             leaf tunnel-endpoint {
               description "Tunnel end point type";
               type enumeration {
                 enum "vxlan" {
                   description "To configure vxlan tunnel-end-point";
                 }
               }
             }
             container source-udp-port-range {
               junos:cli-feature "oneliner";
               description "Value range for source-udp-port";
               leaf min {
                 description "Minimum range value";
                 type union {
                   type string {
                     pattern "<.*>|$.*";
                   }
                   type uint32 {
                     range "1 .. 65535";
                   }
                 }
               }
               leaf max {
                 description "Maximum range value";
                 type union {
                   type string {
                     pattern "<.*>|$.*";
                   }
                   type uint32 {
                     range "1 .. 65535";
                   }
                 }
               }
             }
             leaf destination-udp-port {
               description "Value to write to the destination-udp-port field";
               type union {
                 type string {
                   pattern "<.*>|$.*";
                 }
                 type uint32 {
                   range "1 .. 65535";
                 }
               }
             }
             leaf vni {
               description "Value to write to the vni field";
               type union {
                 type string {
                   pattern "<.*>|$.*";
                 }
                 type uint32 {
                   range "0 .. 16777214";
                 }
               }
             }
           }
         }
         leaf encap-type {
           description "Tunnel encapsulation type";
           type enumeration {
             enum "ipv4" {
               description "Tunnel IPv4 encapsulation";
             }
             enum "ipv6" {
               description "Tunnel IPv6 encapsulation";
             }
           }
         }
         choice source_type {
           case case_1 {
             leaf source {
               description "Tunnel source address";
               type jt:ipaddr;
             }
           }
           case case_2 {
             leaf source-hostname {
               description "Tunnel source hostname";
               junos:must "(\".. encap-type\")";
               junos:must-message "encap-type must be specified for the tunnel with source-hostname";
               type string;
             }
           }
           case case_3 {
             leaf source-interface {
               description "Tunnel source interface";
               junos:must "(\".. encap-type\")";
               junos:must-message "encap-type must be specified for the tunnel with source-interface";
               type union {
                 type jt:interface-name;
                 type string {
                   pattern "<.*>|$.*";
                 }
               }
             }
           }
         }
         choice destination_type {
           case case_1 {
             leaf destination {
               description "Tunnel destination address";
               type jt:ipaddr;
             }
           }
           case case_2 {
             leaf destination-hostname {
               description "Tunnel destination hostname";
               junos:must "(\".. encap-type\")";
               junos:must-message "encap-type must be specified for the tunnel with destination-hostname";
               type string;
             }
           }
         }
         leaf backup-destination {
           description "Backup tunnel destination";
           junos:must "(!(\".. destination $$\"))";
           junos:must-message "Backup and primary tunnel destinations must be different";
           type jt:ipaddr;
         }
         choice fragmentation {
           case case_1 {
             leaf allow-fragmentation {
               description "Do not set DF bit on packets";
               type empty;
             }
           }
           case case_2 {
             leaf do-not-fragment {
               description "Set DF bit on packets";
               type empty;
             }
           }
         }
         leaf ttl {
           description "Time to live";
           type union {
             type string {
               pattern "<.*>|$.*";
             }
             type uint32 {
               range "1 .. 255";
             }
           }
         }
         leaf traffic-class {
           description "TOS/Traffic class field of IP-header";
           type union {
             type string {
               pattern "<.*>|$.*";
             }
             type uint32 {
               range "0 .. 255";
             }
           }
         }
         leaf flow-label {
           description "Flow label field of IP6-header";
           type union {
             type string {
               pattern "<.*>|$.*";
             }
             type uint32 {
               range "0 .. 1048575";
             }
           }
         }
         choice path-mtu-discovery-choice {
           leaf path-mtu-discovery {
             description "Enable path MTU discovery for tunnels";
             type empty;
           }
           leaf no-path-mtu-discovery {
             description "Don't enable path MTU discovery for tunnels";
             type empty;
           }
         }
         container routing-instance {
           description "Routing instance to which tunnel ends belong";
           uses apply-advanced;
           leaf destination {
             description "Routing instance of tunnel destination";
             junos:must "((\"routing-instances $$\" || any \"tenants <*> routing-instances $$\"))";
             junos:must-message "referenced routing-instance must be defined";
             type string {
               junos:posix-pattern "!^((__.*__)|(all)|(.*[ ].*)|(\"\")|(.{129,}))$";
               junos:pattern-message "Must be a non-reserved string of 128 characters or less with no spaces.";
             }
           }
         }
       }
       leaf compression-device {
         description "Logical interface used for compression";
         type union {
           type jt:interface-unit;
           type string {
             pattern "<.*>|$.*";
           }
         }
       }
       container layer2-policer {
         junos:must "(\".. family\")";
         junos:must-message "Family must be defined for a unit with layer2-policer";
         description "Layer2 policing for logical interface";
         uses apply-advanced;
         choice layer2-input-policer-choice {
           case case_1 {
             leaf input-policer {
               description "Two-color policer for received packets";
               type string;
             }
           }
           case case_2 {
           }
           case case_3 {
             leaf input-three-color {
               description "Color-blind three-color policer for received packets";
               type string;
             }
           }
         }
         choice layer2-output-policer-choice {
           case case_1 {
             leaf output-policer {
               description "Two-color policer for transmitted packets";
               type string;
             }
           }
           case case_2 {
             leaf output-three-color {
               description "Three-color policer for transmitted packets";
               type string;
             }
           }
         }
       }
       choice virtual-gateway {
         case case_1 {
           leaf no-auto-virtual-gateway-esi {
             description "Disable auto ESI generation for virtual gateway address";
             junos:must "((any \".. family inet address <*> virtual-gateway-address\" || any \".. family inet6 address <*> virtual-gateway-address\"))";
             junos:must-message "Only when virtual gateway address is configured";
             type empty;
           }
         }
         case case_2 {
           container virtual-gateway-esi {
             description "ESI configuration of virtual gateway";
             uses apply-advanced;
             leaf identifier {
               description "ESI value for the interface";
               junos:cli-feature "nokeyword";
               junos:must "(unique \"interfaces <*> unit <*> virtual-gateway-esi $$\")";
               junos:must-message "virtual-gateway-esi value must be unique under all IFDs and IFLs";
               junos:must "(unique \"interfaces <*> esi $$\")";
               junos:must-message "ESI value must be unique under all IFDs and IFLs";
               type jt:esi;
             }
             choice mode {
               case case_1 {
                 leaf single-active {
                   description "Single-active mode";
                   type empty;
                 }
               }
               case case_2 {
                 leaf all-active {
                   description "All-active mode";
                   type empty;
                 }
               }
             }
           }
         }
       }
       container service {
         description "Service operations";
         uses apply-advanced;
         list pcef {
           key name;
           ordered-by user;
           description "PCEF configuration";
           leaf name {
             description "PCEF Profile name";
             junos:cli-feature "nokeyword";
             junos:must "((\".. family inet service\" || \".. family inet6 service\"))";
             junos:must-message "Must be configured along with a family inet/inet6 service.";
             type string;
           }
           uses apply-advanced;
           leaf activate-all {
             description "Activate all rules and rulebases in the pcef profile";
             junos:must "(!(\"activate\"))";
             junos:must-message "Can't be configured with activate-rule or activate- rulebase.";
             type empty;
           }
           list activate {
             key name;
             ordered-by user;
             description "Name of pcef profile rule or rulebase to activate";
             leaf name {
               description "Name of pcef profile rule or rulebase to activate";
               junos:cli-feature "nokeyword";
               type string;
             }
             uses apply-advanced;
           }
         }
       }
       choice generate-eui64-choice {
         leaf generate-eui64 {
           description "To generate Link Local EUI-64 addresses";
           junos:must "(\".. family inet6 unnumbered-address\")";
           junos:must-message "generate-eui64 attribute must be set when unnumbered-address is configured under family inet6";
           type empty;
         }
         leaf no-generate-eui64 {
           description "Don't to generate Link Local EUI-64 addresses";
           junos:must "(\".. family inet6 unnumbered-address\")";
           junos:must-message "generate-eui64 attribute must be set when unnumbered-address is configured under family inet6";
           type empty;
         }
       }
       container family {
         junos:must "(!(\".. encapsulation ppp-over-ether\"))";
         junos:must-message "Can't configure protocol family with encapsulation ppp-over-ether";
         junos:cli-feature "homogeneous";
         description "Protocol family";
         container inet {
           presence "enable inet";
           junos:must "(!(\".. .. .. encapsulation vlan-vpls\"))";
           junos:must-message "Can't configure protocol family inet with encapsulation vpls";
           description "IPv4 parameters";
           uses apply-advanced;
           container class-based-filtering {
             description "Enable class based filter on interface";
             uses apply-advanced;
           }
           container dhcp {
             description "Dynamic Host Configuration Protocol client configuration";
             presence "enable dhcp";
             junos:must "(!(any \"forwarding-options dhcp-relay group <*> interface ${interface}.${unit}\"))";
             junos:must-message "Incompatible with the interface configured under 'forwarding-options dhcp-relay group'";
             junos:must "(!(\"system services dhcp\"))";
             junos:must-message "Incompatible with the dhcp server configured under 'system services dhcp'";
             junos:must "(!(\"system autoinstallation interfaces\"))";
             junos:must-message "Incompatible with 'system autoinstallation interfaces'";
             junos:must "(!(\".. address\"))";
             junos:must-message "Incompatible with interface assigned with address";
             uses dhcp-client-type;
           }
           container targeted-broadcast {
             presence "enable targeted-broadcast";
             junos:must "(!((\"interfaces $$={irb} unit ${unit} family $$={inet} targeted-broadcast\" && \"protocols l2-learning global-mode transparent-bridge\")))";
             junos:must-message "targeted-broadcast do not be supported on irb interface in transparent mode";
             description "Directed broadcast";
             uses apply-advanced;
             choice targeted-bcast-choice {
               case case_1 {
                 leaf forward-and-send-to-re {
                   description "Allow packets to be forwarded and sent to re";
                   type empty;
                 }
               }
               case case_2 {
                 leaf forward-only {
                   description "Allow packets only to be forwarded";
                   type empty;
                 }
               }
             }
           }
           leaf destination-class-usage {
             description "Enable destination class usage on this interface";
             status deprecated;
             type empty;
           }
           leaf transit-options-packets {
             description "Transit IP options packets (don't send to Routing Engine)";
             status deprecated;
             type empty;
           }
           leaf transit-ttl-exceeded {
             description "Transit IP TTL-exceeded packets (don't send to Routing Engine)";
             status deprecated;
             type empty;
           }
           leaf receive-options-packets {
             description "Receive IP options packets (don't send to Routing Engine)";
             type empty;
           }
           leaf receive-ttl-exceeded {
             description "Receive IP TTL-exceeded packets (don't send to Routing Engine)";
             type empty;
           }
           container accounting {
             description "Configure interface-based accounting options";
             uses apply-advanced;
             container source-class-usage {
               junos:must "(!(\".. .. class-based-filtering source-class-usage\"))";
               junos:must-message "source-class-usage is not allowed with class-based-filtering source-class-usage";
               junos:must "(!(\".. .. source-lookup\"))";
               junos:must-message " source-class-usage is not allowed with source-lookup";
               description "Enable source class usage on this interface";
               uses apply-advanced;
               leaf input {
                 description "Specify this interface for source-class-usage input";
                 type empty;
               }
               leaf output {
                 description "Specify this interface for source-class-usage output";
                 type empty;
               }
             }
             leaf destination-class-usage {
               description "Enable destination class usage on this interface";
               junos:must "(!(\".. .. class-based-filtering destination-class-usage\"))";
               junos:must-message "destination-class-usage is not allowed with class-based-filtering destination-class-usage";
               type empty;
             }
           }
           container rpf-check {
             presence "enable rpf-check";
             junos:cli-feature "oneliner-plus";
             description "Enable reverse-path-forwarding checks on this interface";
             uses apply-advanced;
             leaf fail-filter {
               description "Name of filter applied to packets failing RPF check";
               type string;
             }
             container mode {
               junos:cli-feature "oneliner";
               description "Mode for reverse path forwarding";
               leaf loose {
                 description "Reverse-path-forwarding loose mode";
                 type empty;
               }
             }
           }
           leaf mtu {
             description "Protocol family maximum transmission unit";
             type union {
               type uint32;
               type string {
                 pattern "<.*>|$.*";
               }
             }
           }
           leaf arp-max-cache {
             description "Max interface ARP nexthop cache size";
             type union {
               type string {
                 pattern "<.*>|$.*";
               }
               type uint32 {
                 range "1 .. 2000000";
               }
             }
           }
           leaf arp-new-hold-limit {
             description "Max no. of new unresolved nexthops";
             junos:must "(\".. arp-max-cache\")";
             junos:must-message "Interface max ARP cache size must be configured";
             type union {
               type string {
                 pattern "<.*>|$.*";
               }
               type uint32 {
                 range "1 .. 2000000";
               }
             }
           }
           leaf no-redirects {
             description "Do not redirect traffic";
             type empty;
           }
           leaf nat-outside-interface {
             description "Public interface used for NAT";
             junos:must "(!(\"interfaces ${interface} unit ${unit} family inet6\"))";
             junos:must-message "family inet6 is not supported with nat-outside-interface";
             type empty;
           }
           leaf no-neighbor-learn {
             description "Disable neighbor address learning on interface";
             type empty;
           }
           leaf unconditional-src-learn {
             description "Glean from arp packets even when source cannot be validated";
             type empty;
           }
           leaf multicast-only {
             description "Allow only multicast traffic (tunnels only)";
             type empty;
           }
           leaf primary {
             description "Candidate for primary interface in system";
             type empty;
           }
           leaf ipsec-sa {
             description "Name of security association";
             type string {
               length "1 .. 32";
             }
           }
           container filter {
             description "Packet filtering";
             uses apply-advanced;
             choice input_choice {
               case case_1 {
                 container input {
                   junos:cli-feature "oneliner";
                   description "Filter to be applied to received packets";
                   leaf filter-name {
                     description "Name of the filter";
                     junos:cli-feature "nokeyword";
                     junos:must "((!(\".. .. .. rpf-check\") || (!(any \"firewall family inet filter $$ term <*> from first-byte-of-payload\") && !(any \"firewall family inet filter $$ term <*> from first-byte-of-payload-except\"))))";
                     junos:must-message "filter with first-byte-of-payload match cannot be bound on URPF";
                     type string;
                   }
                   leaf shared-name {
                     description "Filter shared-name of instances of interface-shared filter";
                     type string;
                   }
                   leaf precedence {
                     description "Precedence of the filter";
                     type union {
                       type string {
                         pattern "<.*>|$.*";
                       }
                       type uint32 {
                         range "0 .. 255";
                       }
                     }
                   }
                 }
               }
               case case_2 {
                 leaf-list input-list {
                   ordered-by user;
                   description "List of filter modules applied to received packets ";
                   type string;
                 }
               }
             }
             choice output_choice {
               case case_1 {
                 container output {
                   junos:cli-feature "oneliner";
                   description "Filter to be applied to transmitted packets";
                   leaf filter-name {
                     description "Name of the filter";
                     junos:cli-feature "nokeyword";
                     junos:must "((!(\".. .. .. rpf-check\") || (!(any \"firewall family inet filter $$ term <*> from first-byte-of-payload\") && !(any \"firewall family inet filter $$ term <*> from first-byte-of-payload-except\"))))";
                     junos:must-message "filter with first-byte-of-payload match cannot be bound on URPF";
                     type string;
                   }
                   leaf shared-name {
                     description "Filter shared-name of instances of interface-shared filter";
                     type string;
                   }
                   leaf precedence {
                     description "Precedence of the filter";
                     type union {
                       type string {
                         pattern "<.*>|$.*";
                       }
                       type uint32 {
                         range "0 .. 255";
                       }
                     }
                   }
                 }
               }
               case case_2 {
                 leaf-list output-list {
                   ordered-by user;
                   description "List of filter modules applied to transmitted packets ";
                   type string;
                 }
               }
             }
             container adf {
               description "Ascend Data Filter definition";
               uses apply-advanced;
               list rule {
                 key name;
                 ordered-by user;
                 description "Set of ADF rules";
                 leaf name {
                   description "Value for a single rule";
                   junos:cli-feature "nokeyword";
                   type string;
                 }
                 uses apply-advanced;
               }
               leaf counter {
                 description "Add a counter to each rule";
                 type empty;
               }
               leaf input-precedence {
                 description "Precedence of the input rules";
                 type union {
                   type string {
                     pattern "<.*>|$.*";
                   }
                   type uint32 {
                     range "0 .. 255";
                   }
                 }
               }
               leaf not-mandatory {
                 description "No errors will be reported if no rules are present";
                 type empty;
               }
               leaf output-precedence {
                 description "Precedence of the output rules";
                 type union {
                   type string {
                     pattern "<.*>|$.*";
                   }
                   type uint32 {
                     range "0 .. 255";
                   }
                 }
               }
             }
             leaf group {
               description "Group to which interface belongs";
               type union {
                 type string {
                   pattern "<.*>|$.*";
                 }
                 type uint32;
               }
             }
             leaf dialer {
               description "Name of filter applied on dialer";
               junos:must "(\".. .. .. .. dialer-options dial-string\")";
               junos:must-message "Dial string is mandatory for dialer filter";
               junos:must "(!(\".. .. .. .. dialer-options watch-list\"))";
               junos:must-message "A dialer interface cannot have watch-list as well as dialer filter";
               type string;
             }
           }
           container simple-filter {
             description "Filter for doing multifield classification";
             uses apply-advanced;
             leaf input {
               description "Name of simple filter applied to received packets";
               type string;
             }
           }
           container policer {
             description "Interface policing";
             uses apply-advanced;
             leaf arp {
               description "Name of policer applied to received ARP packets";
               junos:must "(!(\".. disable-arp-policer\"))";
               junos:must-message "Interface configuration can have either disable-arp-policer or arp policer configured";
               junos:must "((!(\".. .. .. .. peer-unit\") || (\".. .. .. .. encapsulation ethernet\" || \".. .. .. .. encapsulation vlan\")))";
               junos:must-message "Interface encapsulation must be ethernet or vlan";
               type string;
             }
             leaf input {
               description "Name of policer applied to received packets";
               junos:must "(!(\".. .. input-hierarchical-policer\"))";
               junos:must-message "Both input policer and input hierarchical policer can not be applied on the same family";
               type string;
             }
             leaf output {
               description "Name of policer applied to transmitted packets";
               type string;
             }
           }
           container sampling {
             junos:must "((\"forwarding-options sampling family inet\" || (\"forwarding-options packet-capture\" || any \"forwarding-options sampling instance <*> family inet\")))";
             junos:must-message "Requires forwarding-options sampling or packet-capture config";
             description "Interface sampling";
             uses apply-advanced;
             leaf input {
               description "Sample all packets input on this interface";
               type empty;
             }
             leaf output {
               description "Sample all packets output on this interface";
               type empty;
             }
           }
           container service {
             junos:must "((!(\".. rpf-check\") || \"chassis network-services enhanced-ip\"))";
             junos:must-message "rpf-check can not be enabled with interface services";
             description "Service operations";
             uses apply-advanced;
             container input {
               junos:cli-feature "oneliner-plus";
               description "Service sets to consider for received packets";
               uses apply-advanced;
               list service-set {
                 key name;
                 ordered-by user;
                 junos:cli-feature "oneliner-plus";
                 description "Service set to consider for received packets";
                 leaf name {
                   description "Name of service set";
                   junos:cli-feature "nokeyword";
                   junos:must "((!(\".. .. .. .. .. .. demux-source\") && !(\".. .. .. .. .. .. demux-destination\")))";
                   junos:must-message "Service set cannot be configured on interfaces with demux-source or demux-destination";
                   junos:must "(\"services service-set $$ interface-service\")";
                   junos:must-message "this service set must be an interface service";
                   type string {
                     junos:posix-pattern "^[[:alnum:]][[:alnum:]/.:_-]*$";
                     junos:pattern-message "Must be a string beginning with a number or letter and consisting of letters, numbers, dashes, underscores, forward slashes, colons and dots.";
                   }
                 }
                 uses apply-advanced;
                 leaf service-filter {
                   description "Name of service filter";
                   type string;
                 }
               }
               leaf post-service-filter {
                 description "Post-service filter to apply to received packets";
                 type string;
               }
             }
             container output {
               junos:cli-feature "oneliner-plus";
               description "Service sets to consider for transmitted packets";
               uses apply-advanced;
               list service-set {
                 key name;
                 ordered-by user;
                 junos:cli-feature "oneliner-plus";
                 description "Service set to consider for transmitted packets";
                 leaf name {
                   description "Name of service set";
                   junos:cli-feature "nokeyword";
                   type string {
                     junos:posix-pattern "^[[:alnum:]][[:alnum:]/.:_-]*$";
                     junos:pattern-message "Must be a string beginning with a number or letter and consisting of letters, numbers, dashes, underscores, forward slashes, colons and dots.";
                   }
                 }
                 uses apply-advanced;
                 leaf service-filter {
                   description "Name of service filter";
                   type string;
                 }
               }
             }
           }
           list next-hop-tunnel {
             key name;
             ordered-by user;
             junos:cli-feature "oneliner-plus";
             description "One or more next-hop tunnel tables";
             leaf name {
               description "Next-hop tunnel gateway address";
               junos:cli-feature "nokeyword";
               type string;
             }
             uses apply-advanced;
             leaf ipsec-vpn {
               description "Name of IPSec VPN";
               junos:must "(\"security ipsec vpn $$\")";
               junos:must-message "Referenced IPSec vpn must be defined under [edit security ipsec vpn] hierarchy level";
               junos:must "(unique \"interfaces st0 unit <*> family inet next-hop-tunnel <*> ipsec-vpn $$\")";
               junos:must-message "Referenced IPSec vpn must be unique";
               type string;
             }
           }
           choice tunnel-termination-status {
             case case_1 {
               leaf tunnel-termination {
                 description "Tunnel termination";
                 type empty;
               }
             }
             case case_2 {
               leaf no-tunnel-termination {
                 description "No Tunnel termination";
                 type empty;
               }
             }
           }
           list address {
             key name;
             ordered-by user;
             description "Interface address/destination prefix";
             junos:must "((!(\".. unnumbered-address\") && !(\".. location-pool-address\")))";
             junos:must-message "address cannot be defined with unnumbered-address or location-pool-address simultaneously";
             leaf name {
               description "Interface address/destination prefix";
               junos:cli-feature "nokeyword";
               type jt:ipv4prefix;
             }
             uses apply-advanced;
             leaf destination {
               description "Destination address";
               type jt:ipv4addr;
             }
             leaf destination-profile {
               description "Profile to use for destination address";
               junos:must "(\"access group-profile $$ ppp\")";
               junos:must-message "referenced group-profile must be defined and must contain ppp statement";
               type string;
             }
             leaf broadcast {
               description "Broadcast address";
               type jt:ipv4addr;
             }
             leaf primary {
               description "Candidate for primary address in system";
               type empty;
             }
             leaf preferred {
               description "Preferred address on interface";
               type empty;
             }
             leaf master-only {
               description "Master management IP address for router";
               type empty;
             }
             container tag {
               description "Tag used for route/local";
               uses apply-advanced;
               leaf tag-value {
                 description "The tag value on the address";
                 junos:cli-feature "nokeyword";
                 type union {
                   type string {
                     pattern "<.*>|$.*";
                   }
                   type uint32 {
                     range "1 .. 4294967295";
                   }
                 }
               }
               leaf type {
                 description "Tag type must be [1-16]";
                 type union {
                   type string {
                     pattern "<.*>|$.*";
                   }
                   type uint32 {
                     range "1 .. 16";
                   }
                 }
               }
             }
             container tag2 {
               description "Tag2 used for route/local";
               uses apply-advanced;
               leaf tag2-value {
                 description "The tag value on the address";
                 junos:cli-feature "nokeyword";
                 type union {
                   type string {
                     pattern "<.*>|$.*";
                   }
                   type uint32 {
                     range "1 .. 4294967295";
                   }
                 }
               }
               leaf type {
                 description "Tag type must be [1-16]";
                 type union {
                   type string {
                     pattern "<.*>|$.*";
                   }
                   type uint32 {
                     range "1 .. 16";
                   }
                 }
               }
             }
             list multipoint-destination {
               key name;
               ordered-by user;
               junos:cli-feature "oneliner-plus";
               description "Multipoint NBMA destination";
               leaf name {
                 description "Destination address";
                 junos:cli-feature "nokeyword";
                 type jt:ipv4addr;
               }
               uses apply-advanced;
               choice link-address {
                 case case_1 {
                   leaf dlci {
                     description "Frame Relay data-link control identifier";
                     type union {
                       type string {
                         pattern "<.*>|$.*";
                       }
                       type uint32 {
                         range "1 .. 1022";
                       }
                     }
                   }
                 }
                 case case_2 {
                   leaf vci {
                     description "ATM virtual circuit identifier ([vpi.]vci)";
                     type jt:atm-vci;
                   }
                 }
               }
               container shaping {
                 description "Virtual circuit traffic-shaping options";
                 uses dcd_shaping_config;
               }
               container oam-period {
                 junos:cli-feature "oneliner";
                 description "OAM cell period";
                 choice oam_period_choices {
                   case case_1 {
                     leaf oam_period {
                       description "OAM cell period";
                       junos:cli-feature "nokeyword";
                       units "seconds";
                       type union {
                         type string {
                           pattern "<.*>|$.*";
                         }
                         type uint32 {
                           range "1 .. 900";
                         }
                       }
                     }
                   }
                   case case_2 {
                     container disable {
                       presence "enable disable";
                       junos:cli-feature "oneliner";
                       description "Disable OAM loopback";
                     }
                   }
                 }
               }
               container oam-liveness {
                 description "OAM virtual circuit liveness parameters";
                 uses apply-advanced;
                 leaf up-count {
                   description "Number of OAM cells to consider VC up";
                   type union {
                     type string {
                       pattern "<.*>|$.*";
                     }
                     type uint32 {
                       range "1 .. 255";
                     }
                   }
                 }
                 leaf down-count {
                   description "Number of OAM cells to consider VC down";
                   type union {
                     type string {
                       pattern "<.*>|$.*";
                     }
                     type uint32 {
                       range "1 .. 255";
                     }
                   }
                 }
               }
               leaf inverse-arp {
                 description "Enable inverse ARP reply messages";
                 type empty;
               }
               leaf transmit-weight {
                 description "ATM2 transmit weight for VC under VP tunnel";
                 type union {
                   type string {
                     pattern "<.*>|$.*";
                   }
                   type uint16 {
                     range "1 .. 32767";
                   }
                 }
               }
               container epd-threshold {
                 description "Early packet discard threshold for ATM2";
                 junos:cli-feature "oneliner";
                 uses epd_threshold_config;
               }
             }
             list arp {
               key name;
               ordered-by user;
               junos:cli-feature "oneliner";
               description "Static Address Resolution Protocol entries";
               leaf name {
                 description "Destination IP address";
                 junos:cli-feature "nokeyword";
                 type jt:ipv4addr;
               }
               leaf l2-interface {
                 description "Layer 2 interface name for ARP entry";
                 type union {
                   type jt:interface-name;
                   type string {
                     pattern "<.*>|$.*";
                   }
                 }
               }
               choice mac_address_type {
                 case case_1 {
                   leaf mac {
                     description "MAC address";
                     type jt:mac-unicast;
                   }
                 }
                 case case_2 {
                   leaf multicast-mac {
                     description "Multicast MAC address";
                     type jt:mac-multicast;
                   }
                 }
               }
               leaf publish {
                 description "Reply to ARP requests for this entry";
                 junos:must "((\".. mac\" || \".. multicast-mac\"))";
                 junos:must-message "mac or multicast-mac must be configured to publish";
                 type empty;
               }
               leaf flood-as-unknown-unicast {
                 description "Broadcast the packet with unicast MAC";
                 junos:must "(!(\".. l2-interface\"))";
                 junos:must-message "l2-interface cannot be configured with flood-as-unknown-unicast";
                 junos:must "(\".. mac\")";
                 junos:must-message "mac must be configured to flood-as-unknown-unicast";
                 type empty;
               }
             }
             container web-authentication {
               junos:cli-feature "oneliner-plus";
               description "Parameters for web-based firewall-user authentication";
               uses apply-advanced;
               leaf http {
                 description "Enable authentication via HTTP";
                 type empty;
               }
               leaf https {
                 description "Enable authentication via HTTPS";
                 junos:must "(\"system services web-management https\")";
                 junos:must-message "web-management should be configured for enabling web-authentication";
                 type empty;
               }
               leaf redirect-to-https {
                 description "Web authentication redirect to HTTPS";
                 junos:must "(\".. https\")";
                 junos:must-message "https must be enabled";
                 type empty;
               }
             }
             list vrrp-group {
               key name;
               ordered-by user;
               description "VRRP group";
               uses vrrp-group;
             }
             leaf virtual-gateway-address {
               description "Virtual Gateway IP address";
               junos:must "(!(\".. vrrp-group\"))";
               junos:must-message "vrrp configuration incompatible with virtual gateway address";
               type jt:ipv4addr;
             }
           }
           container unnumbered-address {
             junos:cli-feature "oneliner";
             description "Unnumbered interface address/destination prefix";
             leaf source {
               description "Interface from which to take local address";
               junos:cli-feature "nokeyword";
               junos:must "(\"interfaces $$-IFL family inet address\")";
               junos:must-message "referred interface must have address configured under family inet";
               type union {
                 type jt:interface-unit;
                 type string {
                   pattern "<.*>|$.*";
                 }
               }
             }
             leaf preferred-source-address {
               description "Preferred address on the donor interface";
               type string;
             }
             leaf destination {
               description "Destination address";
               type jt:ipv4addr;
             }
             leaf destination-profile {
               description "Profile to use for destination address";
               junos:must "(\"access group-profile $$ ppp\")";
               junos:must-message "referenced group-profile must be defined and must contain ppp statement";
               type string;
             }
           }
           container location-pool-address {
             presence "enable location-pool-address";
             junos:must "((!(\".. address\") && !(\".. unnumbered-address\")))";
             junos:must-message "location-pool-address cannot be defined with address or unnumbered-address simultaneously";
             description "Location-based IP address pool";
             uses apply-advanced;
             leaf pool-name {
               description "Pool name";
               junos:cli-feature "nokeyword";
               junos:must "(\"access address-assignment location-pool $$\")";
               junos:must-message "referenced IP address location pool must be defined";
               type string {
                 length "1 .. 64";
               }
             }
           }
           leaf negotiate-address {
             description "Negotiate address with remote";
             junos:must "(!(\".. .. .. .. encapsulation multilink-frame-relay-uni-nni\"))";
             junos:must-message "negotiate-address is not supported with family mlfr-uni-nni ";
             junos:must "(!(\".. .. .. encapsulation multilink-frame-relay-end-to-end\"))";
             junos:must-message "negotiate-address is not supported with family mlfr-end-to-end ";
             junos:must "(!(\".. location-pool-address\"))";
             junos:must-message "negotiate-address and location-pool-address must not be defined simultaneously";
             junos:must "(!(\".. unnumbered-address\"))";
             junos:must-message "negotiate-address and unnumbered-address must not be defined simultaneously";
             junos:must "(!(\".. address\"))";
             junos:must-message "negotiate-address and address must not be defined simultaneously";
             type empty;
           }
           leaf destination-udp-port {
             description "Choose destination UDP port number";
             junos:must "(\".. .. .. tunnel encapsulation udp\")";
             junos:must-message "destination-udp-port can be configured only for encapsulation udp on fti interface";
             type union {
               type string {
                 pattern "<.*>|$.*";
               }
               type uint32 {
                 range "10000 .. 10009";
               }
             }
           }
           container auto-configure {
             description "Auto configuration";
             uses dynamic_ipv4_type;
           }
         }
         container iso {
           presence "enable iso";
           junos:must "(!(\".. .. encapsulation frame-relay-ppp\"))";
           junos:must-message "family iso is not supported on encapsulation frame-relay-ppp";
           description "OSI ISO protocol parameters";
           uses apply-advanced;
           list address {
             key name;
             ordered-by user;
             description "Interface address";
             leaf name {
               description "Interface address";
               junos:cli-feature "nokeyword";
               type jt:isoaddr;
             }
             uses apply-advanced;
           }
           leaf mtu {
             description "Protocol family maximum transmission unit";
             type union {
               type uint32;
               type string {
                 pattern "<.*>|$.*";
               }
             }
           }
           leaf destination-udp-port {
             description "Choose destination UDP port number";
             junos:must "(\".. .. .. tunnel encapsulation udp\")";
             junos:must-message "destination-udp-port can be configured only for encapsulation udp on fti interface";
             type union {
               type string {
                 pattern "<.*>|$.*";
               }
               type uint32 {
                 range "10030 .. 10039";
               }
             }
           }
         }
         container inet6 {
           presence "enable inet6";
           description "IPv6 protocol parameters";
           uses apply-advanced;
           container class-based-filtering {
             description "Enable class based filter on interface";
             uses apply-advanced;
           }
           container dhcpv6-client {
             junos:must "(!(\"system services dhcp\"))";
             junos:must-message "Incompatible with the dhcp server configured under 'system services dhcp'";
             junos:must "(!(\"system autoinstallation\"))";
             junos:must-message "Incompatible with 'system autoinstallation'";
             junos:must "(!(\".. address\"))";
             junos:must-message "Incompatible with interface assigned with address";
             junos:must "(!(any \"forwarding-options dhcp-relay dhcpv6  group <*> interface ${interface}.${unit}\"))";
             junos:must-message "DHCPv6 client and relay cannot be configured on the same interface ";
             junos:must "(!(any \"system services dhcp-local-server dhcpv6 group <*> interface ${interface}.${unit}\"))";
             junos:must-message "DHCPv6 client and server cannot be configured on the same interface ";
             description "Dynamic Host Configuration Protocol DHCPv6 client configuration";
             uses apply-advanced;
             leaf client-type {
               description "DHCPv6 client type";
               type enumeration {
                 enum "stateful" {
                   description "Stateful client type for address assignment.";
                 }
                 enum "autoconfig" {
                   description "Autoconfig  client type for router-advertisement";
                   junos:must "(\"protocols router-advertisement interface ${interface}.${unit}\")";
                   junos:must-message "Interface for ra messages is must for auto mode";
                   junos:must "(!(\"interfaces ${interface} unit ${unit} family inet6 dhcpv6-client update-router-advertisement\"))";
                   junos:must-message "Incompatible with 'dhcpv6-client update-router-advertisement'";
                   junos:must "(!(\"interfaces ${interface} unit ${unit} family inet6 dhcpv6-client client-ia-type ia-pd\"))";
                   junos:must-message "Incompatible with 'client-ia-type ia-pd'";
                 }
               }
             }
             list client-ia-type {
               key name;
               ordered-by user;
               description "DHCPv6 client identity association type";
               leaf name {
                 junos:cli-feature "nokeyword";
                 type enumeration {
                   enum "ia-na" {
                     description "Identity Association-Non-temporary Address";
                   }
                   enum "ia-pd" {
                     description "Identity Association-Prefix Address";
                   }
                 }
               }
               uses apply-advanced;
             }
             container rapid-commit {
               presence "enable rapid-commit";
               description "Option is used to signal the use of the two message exchange for address assignment";
             }
             leaf interface-identifier {
               description "Identifier for this interface";
               type jt:ipv6addr;
             }
             leaf use-ra-prefix {
               description "Assign interface IP from RA prefix when ia-na address not received";
               junos:must "(\"interfaces ${interface} unit ${unit} family inet6 dhcpv6-client client-ia-type ia-na\")";
               junos:must-message "Incompatible with out 'client-ia-type ia-na'";
               junos:must "(\"interfaces ${interface} unit ${unit} family inet6 dhcpv6-client client-type stateful\")";
               junos:must-message "Incompatible with out 'client-type stateful'";
               type empty;
             }
             container prefix-delegating {
               junos:must "(\"interfaces ${interface} unit ${unit} family inet6 dhcpv6-client client-ia-type ia-pd\")";
               junos:must-message "Incompatible with out 'client-ia-type ia-pd'";
               description "Prefix delegating parameters";
               uses apply-advanced;
               leaf preferred-prefix-length {
                 description "Client preferred prefix length";
                 type union {
                   type string {
                     pattern "<.*>|$.*";
                   }
                   type uint32 {
                     range "0 .. 64";
                   }
                 }
               }
               leaf sub-prefix-length {
                 description "The sub prefix length for LAN interfaces";
                 type union {
                   type string {
                     pattern "<.*>|$.*";
                   }
                   type uint32 {
                     range "1 .. 127";
                   }
                 }
               }
             }
             container client-identifier {
               junos:cli-feature "oneliner";
               description "DHCP Server identifies a client by client-identifier value ";
               leaf duid-type {
                 description "DUID identifying a client";
                 type enumeration {
                   enum "duid-llt" {
                     description "Link-layer address plus time";
                   }
                   enum "vendor" {
                     description "Vendor-assigned unique ID based on Enterprise Number";
                   }
                   enum "duid-ll" {
                     description "Link-layer address";
                   }
                 }
               }
             }
             leaf vendor-id {
               description "Vendor class id for the dhcpv6 client";
               type string {
                 length "1 .. 60";
               }
             }
             list req-option {
               key name;
               ordered-by user;
               description "DHCPV6 client requested option configuration";
               leaf name {
                 junos:cli-feature "nokeyword";
                 type enumeration {
                   enum "dns-server" {
                     description "Dns-server option";
                   }
                   enum "domain" {
                     description "Dns-server option";
                   }
                   enum "ntp-server" {
                     description "Ntp-server option";
                   }
                   enum "time-zone" {
                     description "Time-zone option";
                   }
                   enum "sip-server" {
                     description "Sip-server option";
                   }
                   enum "sip-domain" {
                     description "Sip-domain option";
                   }
                   enum "nis-server" {
                     description "Nis-server option";
                   }
                   enum "nis-domain" {
                     description "Nis-domain option";
                   }
                   enum "fqdn" {
                     description "Fully-qualified-domain option";
                   }
                   enum "vendor-spec" {
                     description "Vendor-spec option";
                   }
                   enum "zero-touch-redirect" {
                     description "Zero-touch-redirect";
                   }
                   enum "bootfile-url" {
                     description "Bootfile url";
                   }
                   enum "bootfile-param" {
                     description "Bootfile param";
                   }
                 }
               }
               uses apply-advanced;
             }
             container options {
               description "DHCP options";
               uses apply-advanced;
               list number {
                 key name;
                 junos:cli-feature "oneliner";
                 description "DHCP option code";
                 leaf name {
                   description "DHCP option identifier code";
                   junos:cli-feature "nokeyword";
                   type union {
                     type string {
                       pattern "<.*>|$.*";
                     }
                     type uint32 {
                       range "1 .. 254";
                     }
                   }
                 }
                 choice option-type-choice {
                   case case_1 {
                     leaf hex-string {
                       description "Hexadecimal string";
                       type string {
                         length "1 .. 510";
                         junos:posix-pattern "^[[:xdigit:]]+$";
                         junos:pattern-message "Must be hexadecimal digits (0-9, a-f, A-F)";
                       }
                     }
                   }
                 }
               }
             }
             leaf retransmission-attempt {
               description "Number of attempts to retransmit the DHCPV6 client protocol packet";
               default "9";
               type union {
                 type string {
                   pattern "<.*>|$.*";
                 }
                 type uint32 {
                   range "0 .. 50000";
                 }
               }
             }
             container no-dns-install {
               presence "enable no-dns-install";
               description "Not propagate DNS to kernel";
             }
             container update-router-advertisement {
               junos:must "(\"interfaces ${interface} unit ${unit} family inet6 dhcpv6-client client-ia-type $$={2}\")";
               junos:must-message "Incompatible without 'client-ia-type ia-pd'";
               description "Dhcpv6 client update rpd for prefix delegation";
               uses apply-advanced;
               list interface {
                 key name;
                 ordered-by user;
                 description "Interfaces on which to delegate prefix";
                 max-elements 3;
                 leaf name {
                   description "Interfaces-name on which to delegate prefix";
                   junos:cli-feature "nokeyword";
                   junos:must "(unique \"interfaces <*> unit 0 family inet6 dhcpv6-client update-router-advertisement interface $$\")";
                   junos:must-message "This interface is already updated by a dhcpv6-client";
                   junos:must "(!(\"protocols router-advertisement interface $$\"))";
                   junos:must-message "Incompatible with the interface configured under 'protocols router-advertisement interface'";
                   type union {
                     type jt:interface-name;
                     type string {
                       pattern "<.*>|$.*";
                     }
                   }
                 }
                 uses apply-advanced;
                 leaf interface-identifier {
                   description "Identifier for this interface";
                   type jt:ipv6addr;
                 }
                 leaf prefix-identifier {
                   description "Prefix identifier for prefix used in this interface";
                   type jt:ipv6addr;
                 }
                 choice managed-configuration-choice {
                   leaf managed-configuration {
                     description "Set managed address configuration";
                     type empty;
                   }
                   leaf no-managed-configuration {
                     description "Don't set managed address configuration";
                     type empty;
                   }
                 }
                 choice other-stateful-configuration-choice {
                   leaf other-stateful-configuration {
                     description "Set other stateful configuration";
                     type empty;
                   }
                   leaf no-other-stateful-configuration {
                     description "Don't set other stateful configuration";
                     type empty;
                   }
                 }
                 leaf max-advertisement-interval {
                   description "Maximum advertisement interval";
                   units "seconds";
                   type union {
                     type string {
                       pattern "<.*>|$.*";
                     }
                     type uint32 {
                       range "4 .. 1800";
                     }
                   }
                 }
                 leaf min-advertisement-interval {
                   description "Minimum advertisement interval";
                   units "seconds";
                   type union {
                     type string {
                       pattern "<.*>|$.*";
                     }
                     type uint32 {
                       range "3 .. 1350";
                     }
                   }
                 }
                 choice enable-recursive-dns-server-option-choice {
                   leaf enable-recursive-dns-server-option {
                     description "Enables the recursive DNS server option";
                     type empty;
                   }
                   leaf no-enable-recursive-dns-server-option {
                     description "Don't enables the recursive DNS server option";
                     type empty;
                   }
                 }
               }
             }
             leaf update-server {
               description "Propagate TCP/IP settings to DHCP server";
               type empty;
             }
           }
           container rpf-check {
             presence "enable rpf-check";
             junos:cli-feature "oneliner-plus";
             description "Enable reverse-path-forwarding checks on this interface";
             uses apply-advanced;
             leaf fail-filter {
               description "Name of filter applied to packets failing RPF check";
               type string;
             }
             container mode {
               junos:cli-feature "oneliner";
               description "Mode for reverse path forwarding";
               leaf loose {
                 description "Reverse-path-forwarding loose mode";
                 type empty;
               }
             }
           }
           container accounting {
             description "Interface-based accounting options";
             uses apply-advanced;
             container source-class-usage {
               junos:must "(!(\".. .. class-based-filtering source-class-usage\"))";
               junos:must-message "source-class-usage is not allowed with class-based-filtering source-class-usage";
               junos:must "(!(\".. .. source-lookup\"))";
               junos:must-message " source-class-usage is not allowed with source-lookup";
               uses apply-advanced;
               leaf input {
                 description "Interface for source-class-usage input";
                 type empty;
               }
               leaf output {
                 description "Interface for source-class-usage output";
                 type empty;
               }
             }
             leaf destination-class-usage {
               description "Enable destination class usage on this interface";
               junos:must "(!(\".. .. class-based-filtering destination-class-usage\"))";
               junos:must-message "destination-class-usage is not allowed with class-based-filtering destination-class-usage";
               type empty;
             }
           }
           leaf mtu {
             description "Protocol family maximum transmission unit";
             type union {
               type uint32;
               type string {
                 pattern "<.*>|$.*";
               }
             }
           }
           leaf nd6-stale-time {
             description "Stale time to reconfirm reachability with inet6 neighbour";
             units "seconds";
             type union {
               type string {
                 pattern "<.*>|$.*";
               }
               type uint32 {
                 range "1 .. 18000";
               }
             }
           }
           leaf no-neighbor-learn {
             description "Disable neighbor address learning on interface";
             type empty;
           }
           container ndp-proxy {
             description "Enable ndp proxy on interface";
             uses apply-advanced;
             leaf interface-restricted {
               description "Enable ndp interface proxy restricted to interface";
               junos:must "(!(\".. interface-unrestricted\"))";
               junos:must-message "interface-restricted and interface-unrestricted are not allowed together";
               type empty;
             }
             leaf interface-unrestricted {
               description "Enable ndp interface proxy unrestricted to interface";
               junos:must "(!(\".. interface-restricted\"))";
               junos:must-message "interface-restricted and interface-unrestricted are not allowed together";
               type empty;
             }
           }
           container dad-proxy {
             junos:must "(\".. ndp-proxy\")";
             junos:must-message "ndp-proxy must be configured";
             description "DAD proxy on interface";
             uses apply-advanced;
             leaf interface-restricted {
               description "Enable DAD interface proxy restricted to interface";
               junos:must "(!(\".. interface-unrestricted\"))";
               junos:must-message "interface-restricted and interface-unrestricted are not allowed together";
               junos:must "(\".. .. ndp-proxy interface-restricted\")";
               junos:must-message "ndp-proxy interface-restricted must be configured to set this";
               type empty;
             }
             leaf interface-unrestricted {
               description "Enable DAD interface proxy unrestricted to interface";
               junos:must "(!(\".. interface-restricted\"))";
               junos:must-message "interface-restricted and interface-unrestricted are not allowed together";
               junos:must "(\".. .. ndp-proxy interface-unrestricted\")";
               junos:must-message "ndp-proxy interface-unrestricted must be configured to set this";
               type empty;
             }
           }
           leaf nd6-max-cache {
             description "Max interface ND nexthop cache size";
             type union {
               type string {
                 pattern "<.*>|$.*";
               }
               type uint32 {
                 range "1 .. 2000000";
               }
             }
           }
           leaf nd6-new-hold-limit {
             description "Max no. of new unresolved nexthops";
             junos:must "(\".. nd6-max-cache\")";
             junos:must-message "Interface max ND cache size must be configured";
             type union {
               type string {
                 pattern "<.*>|$.*";
               }
               type uint32 {
                 range "1 .. 2000000";
               }
             }
           }
           leaf no-redirects {
             description "Do not redirect traffic";
             type empty;
           }
           container filter {
             description "Packet filtering";
             uses apply-advanced;
             choice input_choice {
               case case_1 {
                 container input {
                   junos:cli-feature "oneliner";
                   description "Filter to be applied to received packets";
                   leaf filter-name {
                     description "Name of the filter";
                     junos:cli-feature "nokeyword";
                     junos:must "((!(\".. .. .. rpf-check\") || (!(any \"firewall family inet6 filter $$ term <*> from first-byte-of-payload\") && !(any \"firewall family inet6 filter $$ term <*> from first-byte-of-payload-except\"))))";
                     junos:must-message "filter with first-byte-of-payload match cannot be bound on URPF";
                     type string;
                   }
                   leaf shared-name {
                     description "Filter shared-name of instances of interface-shared filter";
                     type string;
                   }
                   leaf precedence {
                     description "Precedence of the filter";
                     type union {
                       type string {
                         pattern "<.*>|$.*";
                       }
                       type uint32 {
                         range "0 .. 255";
                       }
                     }
                   }
                 }
               }
               case case_2 {
                 leaf-list input-list {
                   ordered-by user;
                   description "List of filter modules applied to received packets ";
                   type string;
                 }
               }
             }
             choice output_choice {
               case case_1 {
                 container output {
                   junos:cli-feature "oneliner";
                   description "Filter to be applied to transmitted packets";
                   leaf filter-name {
                     description "Name of the filter";
                     junos:cli-feature "nokeyword";
                     type string;
                   }
                   leaf shared-name {
                     description "Filter shared-name of instances of interface-shared filter";
                     type string;
                   }
                   leaf precedence {
                     description "Precedence of the filter";
                     type union {
                       type string {
                         pattern "<.*>|$.*";
                       }
                       type uint32 {
                         range "0 .. 255";
                       }
                     }
                   }
                 }
               }
               case case_2 {
                 leaf-list output-list {
                   ordered-by user;
                   description "List of filter modules applied to transmitted packets ";
                   type string;
                 }
               }
             }
             container adf {
               description "Ascend Data Filter definition";
               uses apply-advanced;
               list rule {
                 key name;
                 ordered-by user;
                 description "Set of ADF rules";
                 leaf name {
                   description "Value for a single rule";
                   junos:cli-feature "nokeyword";
                   type string;
                 }
                 uses apply-advanced;
               }
               leaf counter {
                 description "Add a counter to each rule";
                 type empty;
               }
               leaf input-precedence {
                 description "Precedence of the input rules";
                 type union {
                   type string {
                     pattern "<.*>|$.*";
                   }
                   type uint32 {
                     range "0 .. 255";
                   }
                 }
               }
               leaf not-mandatory {
                 description "No errors will be reported if no rules are present";
                 type empty;
               }
               leaf output-precedence {
                 description "Precedence of the output rules";
                 type union {
                   type string {
                     pattern "<.*>|$.*";
                   }
                   type uint32 {
                     range "0 .. 255";
                   }
                 }
               }
             }
             leaf group {
               description "Group to which interface belongs";
               type union {
                 type string {
                   pattern "<.*>|$.*";
                 }
                 type uint32;
               }
             }
             leaf dialer {
               description "Name of filter applied on dialer";
               junos:must "(\".. .. .. .. dialer-options dial-string\")";
               junos:must-message "Dial string is mandatory for dialer filter";
               junos:must "(!(\".. .. .. .. dialer-options watch-list\"))";
               junos:must-message "A dialer interface cannot have watch-list as well as dialer filter";
               type string;
             }
           }
           container policer {
             description "Interface policing";
             uses apply-advanced;
             leaf input {
               description "Name of policer applied to received packets";
               type string;
             }
             leaf output {
               description "Name of policer applied to transmitted packets";
               type string;
             }
           }
           container sampling {
             junos:must "((\"forwarding-options sampling family inet6\" || (\"forwarding-options packet-capture\" || any \"forwarding-options sampling instance <*> family inet6\")))";
             junos:must-message "Requires forwarding-options sampling or packet-capture config";
             description "Interface sampling";
             uses apply-advanced;
             leaf input {
               description "Sample all packets input on this interface";
               type empty;
             }
             leaf output {
               description "Sample all packets output on this interface";
               type empty;
             }
           }
           container service {
             description "Service operations";
             uses apply-advanced;
             container input {
               junos:cli-feature "oneliner-plus";
               description "Service sets to consider for received packets";
               uses apply-advanced;
               list service-set {
                 key name;
                 ordered-by user;
                 junos:cli-feature "oneliner-plus";
                 description "Service set to consider for received packets";
                 leaf name {
                   description "Name of service set";
                   junos:cli-feature "nokeyword";
                   junos:must "((!(\".. .. .. .. .. .. demux-source\") && !(\".. .. .. .. .. .. demux-destination\")))";
                   junos:must-message "Service set cannot be configured on interfaces with demux-source or demux-destination";
                   junos:must "(\"services service-set $$ interface-service\")";
                   junos:must-message "this service set must be an interface service";
                   type string {
                     junos:posix-pattern "^[[:alnum:]][[:alnum:]/.:_-]*$";
                     junos:pattern-message "Must be a string beginning with a number or letter and consisting of letters, numbers, dashes, underscores, forward slashes, colons and dots.";
                   }
                 }
                 uses apply-advanced;
                 leaf service-filter {
                   description "Name of service filter";
                   type string;
                 }
               }
               leaf post-service-filter {
                 description "Post-service filter to apply to received packets";
                 type string;
               }
             }
             container output {
               junos:cli-feature "oneliner-plus";
               description "Service sets to consider for transmitted packets";
               uses apply-advanced;
               list service-set {
                 key name;
                 ordered-by user;
                 junos:cli-feature "oneliner-plus";
                 description "Service set to consider for transmitted packets";
                 leaf name {
                   description "Name of service set";
                   junos:cli-feature "nokeyword";
                   type string {
                     junos:posix-pattern "^[[:alnum:]][[:alnum:]/.:_-]*$";
                     junos:pattern-message "Must be a string beginning with a number or letter and consisting of letters, numbers, dashes, underscores, forward slashes, colons and dots.";
                   }
                 }
                 uses apply-advanced;
                 leaf service-filter {
                   description "Name of service filter";
                   type string;
                 }
               }
             }
           }
           choice tunnel-termination-status {
             case case_1 {
               leaf tunnel-termination {
                 description "Tunnel termination";
                 type empty;
               }
             }
             case case_2 {
               leaf no-tunnel-termination {
                 description "No Tunnel termination";
                 type empty;
               }
             }
           }
           list address {
             key name;
             ordered-by user;
             description "Interface address or destination prefix";
             junos:must "(!(\".. unnumbered-address\"))";
             junos:must-message "ipv6 unnumbered-address and ipv6 address must not be defined simultaneously";
             leaf name {
               description "Interface address or destination prefix";
               junos:cli-feature "nokeyword";
               type jt:ipv6prefix;
             }
             uses apply-advanced;
             leaf destination {
               description "Destination address";
               type jt:ipv6addr;
             }
             leaf eui-64 {
               description "Generate EUI-64 interface ID";
               type empty;
             }
             leaf primary {
               description "Candidate for primary address in system";
               type empty;
             }
             leaf preferred {
               description "Preferred address on interface";
               type empty;
             }
             leaf master-only {
               description "Master management IP address for router";
               type empty;
             }
             container tag {
               description "Tag used for route/local";
               uses apply-advanced;
               leaf tag-value {
                 description "The tag value on the address";
                 junos:cli-feature "nokeyword";
                 type union {
                   type string {
                     pattern "<.*>|$.*";
                   }
                   type uint32 {
                     range "1 .. 4294967295";
                   }
                 }
               }
               leaf type {
                 description "Tag type must be [1-16]";
                 type union {
                   type string {
                     pattern "<.*>|$.*";
                   }
                   type uint32 {
                     range "1 .. 16";
                   }
                 }
               }
             }
             container tag2 {
               description "Tag2 used for route/local";
               uses apply-advanced;
               leaf tag2-value {
                 description "The tag value on the address";
                 junos:cli-feature "nokeyword";
                 type union {
                   type string {
                     pattern "<.*>|$.*";
                   }
                   type uint32 {
                     range "1 .. 4294967295";
                   }
                 }
               }
               leaf type {
                 description "Tag type must be [1-16]";
                 type union {
                   type string {
                     pattern "<.*>|$.*";
                   }
                   type uint32 {
                     range "1 .. 16";
                   }
                 }
               }
             }
             list ndp {
               key name;
               ordered-by user;
               junos:cli-feature "oneliner";
               description "Static Neighbor Discovery Protocol  entries";
               leaf name {
                 description "Destination IP address";
                 junos:cli-feature "nokeyword";
                 type jt:ipv6addr;
               }
               leaf l2-interface {
                 description "Layer 2 interface name for NDP entry";
                 type union {
                   type jt:interface-name;
                   type string {
                     pattern "<.*>|$.*";
                   }
                 }
               }
               choice mac_address_type {
                 case case_1 {
                   leaf mac {
                     description "MAC address";
                     type jt:mac-unicast;
                   }
                 }
                 case case_2 {
                   leaf multicast-mac {
                     description "Multicast MAC address";
                     type jt:mac-multicast;
                   }
                 }
               }
               leaf publish {
                 description "Reply to NDP requests for this entry";
                 junos:must "((\".. mac\" || \".. multicast-mac\"))";
                 junos:must-message "either 'mac' or 'multicast-mac' must be configured along with 'publish' statment";
                 type empty;
               }
             }
             list vrrp-inet6-group {
               key name;
               ordered-by user;
               description "VRRP group";
               junos:must "(!(\".. eui-64\"))";
               junos:must-message "'vrrp-inet6-group' is not supported when 'eui-64' is configured";
               uses vrrp-group;
             }
             container web-authentication {
               junos:cli-feature "oneliner-plus";
               description "Parameters for web-based firewall-user authentication";
               uses apply-advanced;
               leaf http {
                 description "Enable authentication via HTTP";
                 type empty;
               }
               leaf https {
                 description "Enable authentication via HTTPS";
                 junos:must "(\"system services web-management https\")";
                 junos:must-message "web-management should be configured for enabling web-authentication";
                 type empty;
               }
               leaf redirect-to-https {
                 description "Web authentication redirect to HTTPS";
                 junos:must "(\".. https\")";
                 junos:must-message "https must be enabled";
                 type empty;
               }
             }
             leaf virtual-gateway-address {
               description "Virtual Gateway IP address";
               junos:must "(!(\".. vrrp-inet6-group\"))";
               junos:must-message "vrrp configuration incompatible with virtual gateway address";
               type jt:ipv6addr;
             }
             leaf subnet-router-anycast {
               description "Create a subnet roter anycast address for this address.";
               type empty;
             }
           }
           container unnumbered-address {
             junos:cli-feature "oneliner";
             description "Unnumbered interface address/destination prefix";
             leaf source {
               description "Interface from which to take local address";
               junos:cli-feature "nokeyword";
               junos:must "(\"interfaces $$-IFL family inet6 address\")";
               junos:must-message "referred interface must have address configured under family inet6";
               type union {
                 type jt:interface-unit;
                 type string {
                   pattern "<.*>|$.*";
                 }
               }
             }
             leaf preferred-source-address {
               description "Preferred address on the donor interface";
               type string;
             }
           }
           choice dad-disable-choice {
             leaf dad-disable {
               description "Disable duplicate-address-detection";
               type empty;
             }
             leaf no-dad-disable {
               description "Don't disable duplicate-address-detection";
               type empty;
             }
           }
           leaf destination-udp-port {
             description "Choose destination UDP port number";
             junos:must "(\".. .. .. tunnel encapsulation udp\")";
             junos:must-message "destination-udp-port can be configured only for encapsulation udp on fti interface";
             type union {
               type string {
                 pattern "<.*>|$.*";
               }
               type uint32 {
                 range "10010 .. 10019";
               }
             }
           }
           leaf enhanced-dad-disable {
             description "Disable Enhanced DAD while send NS with Nonce option";
             type empty;
           }
           container auto-configure {
             description "Auto configuration";
             uses dynamic_ipv6_type;
           }
           leaf negotiate-address {
             description "Negotiate address with remote";
             junos:must "(!(\".. unnumbered-address\"))";
             junos:must-message "negotiate-address and unnumbered-address must not be defined simultaneously";
             junos:must "(!(\".. address\"))";
             junos:must-message "negotiate-address and address must not be defined simultaneously";
             type empty;
           }
         }
         container mpls {
           presence "enable mpls";
           junos:must "(!(\".. .. encapsulation frame-relay-ppp\"))";
           junos:must-message "family mpls is not supported on encapsulation frame-relay-ppp";
           description "MPLS protocol parameters";
           uses apply-advanced;
           leaf mtu {
             description "Protocol family maximum transmission unit";
             type union {
               type uint32;
               type string {
                 pattern "<.*>|$.*";
               }
             }
           }
           container filter {
             description "Packet filtering";
             uses apply-advanced;
             choice input_choice {
               case case_1 {
                 leaf input {
                   description "Name of filter applied to received packets";
                   type string;
                 }
               }
               case case_2 {
                 leaf-list input-list {
                   ordered-by user;
                   description "List of filter modules applied to received packets ";
                   type string;
                 }
               }
             }
             leaf-list input-chain {
               ordered-by user;
               description "List of filter modules applied to received packets ";
               type string;
             }
             choice output_choice {
               case case_1 {
                 leaf output {
                   description "Name of filter applied to transmitted packets";
                   type string;
                 }
               }
               case case_2 {
                 leaf-list output-list {
                   ordered-by user;
                   description "List of filter modules applied to transmitted packets ";
                   type string;
                 }
               }
             }
             leaf-list output-chain {
               ordered-by user;
               description "List of filter modules applied to transmitted packets ";
               type string;
             }
             leaf group {
               description "Interface group to which interface belongs";
               type union {
                 type string {
                   pattern "<.*>|$.*";
                 }
                 type uint32 {
                   range "1 .. 255";
                 }
               }
             }
             leaf dialer {
               description "Name of filter applied on dialer";
               junos:must "(\".. .. .. .. dialer-options dial-string\")";
               junos:must-message "Dial string is mandatory for dialer filter";
               junos:must "(!(\".. .. .. .. dialer-options watch-list\"))";
               junos:must-message "A dialer interface cannot have watch-list as well as dialer filter";
               type string;
             }
           }
           container policer {
             description "Interface policing";
             uses apply-advanced;
             leaf input {
               description "Name of policer applied to received packets";
               type string;
             }
             leaf output {
               description "Name of policer applied to transmitted packets";
               type string;
             }
           }
           leaf destination-udp-port {
             description "Choose destination UDP port number";
             junos:must "(\".. .. .. tunnel encapsulation udp\")";
             junos:must-message "destination-udp-port can be configured only for encapsulation udp on fti interface";
             type union {
               type string {
                 pattern "<.*>|$.*";
               }
               type uint32 {
                 range "10020 .. 10029";
               }
             }
           }
         }
         container mlppp {
           junos:must "(!(\"interfaces ${interface} container-options\"))";
           junos:must-message "mlppp is not supported for container interfaces";
           description "Multilink PPP protocol parameters";
           uses apply-advanced;
           leaf bundle {
             description "Logical interface name this link will join";
             junos:must "((!(\".. .. .. dial-options\") || \"interfaces $$-IFL encapsulation multilink-ppp\"))";
             junos:must-message "Bundle interface must be configured";
             junos:must "((!(\".. .. .. pppoe-options\") || \"interfaces $$-IFL encapsulation multilink-ppp\"))";
             junos:must-message "Bundle interface must be configured";
             type string;
           }
           choice anchor-points {
             case case_1 {
             }
             case case_2 {
             }
           }
           leaf dynamic-profile {
             description " dynamic profile for interface to use";
             junos:must "(\"dynamic-profiles $$\")";
             junos:must-message "referenced dynamic-profile must be defined";
             type string {
               length "1 .. 80";
             }
           }
         }
         container mlfr-end-to-end {
           presence "enable mlfr-end-to-end";
           junos:must "(!(\".. .. encapsulation frame-relay-ppp\"))";
           junos:must-message "family mlfr-end-to-end is not supported on encapsulation frame-relay-ppp";
           description "Multilink Frame Relay end-to-end protocol parameters";
           uses apply-advanced;
           leaf bundle {
             description "Logical interface name this link will join";
             type union {
               type jt:interface-unit;
               type string {
                 pattern "<.*>|$.*";
               }
             }
           }
         }
         container mlfr-uni-nni {
           presence "enable mlfr-uni-nni";
           junos:must "(!(\".. .. encapsulation frame-relay-ppp\"))";
           junos:must-message "family mlfr-uni-uni is not supported on encapsulation frame-relay-ppp";
           description "Multilink Frame Relay UNI NNI protocol parameters";
           uses apply-advanced;
           leaf bundle {
             description "Logical interface name this link will join";
             type union {
               type jt:interface-unit;
               type string {
                 pattern "<.*>|$.*";
               }
             }
           }
         }
         container ccc {
           presence "enable ccc";
           junos:must "(!(\".. .. encapsulation frame-relay-ppp\"))";
           junos:must-message "family ccc is not supported on encapsulation frame-relay-ppp";
           description "Circuit cross-connect parameters";
           uses apply-advanced;
           container filter {
             description "Packet filtering";
             uses apply-advanced;
             choice input_choice {
               case case_1 {
                 leaf input {
                   description "Name of filter applied to received packets";
                   type string;
                 }
               }
               case case_2 {
                 leaf-list input-list {
                   ordered-by user;
                   description "List of filter modules applied to received packets ";
                   type string;
                 }
               }
             }
             leaf-list input-chain {
               ordered-by user;
               description "List of filter modules applied to received packets ";
               type string;
             }
             choice output_choice {
               case case_1 {
                 leaf output {
                   description "Name of filter applied to transmitted packets";
                   type string;
                 }
               }
               case case_2 {
                 leaf-list output-list {
                   ordered-by user;
                   description "List of filter modules applied to transmitted packets ";
                   type string;
                 }
               }
             }
             leaf-list output-chain {
               ordered-by user;
               description "List of filter modules applied to transmitted packets ";
               type string;
             }
             leaf group {
               description "Interface group to which interface belongs";
               type union {
                 type string {
                   pattern "<.*>|$.*";
                 }
                 type uint32 {
                   range "1 .. 255";
                 }
               }
             }
           }
           container policer {
             description "Interface policing";
             uses apply-advanced;
             leaf input {
               description "Name of policer applied to received packets";
               type string;
             }
             leaf output {
               description "Name of policer applied to transmitted packets";
               type string;
             }
           }
           leaf translate-fecn-and-becn {
             description "Translate FECN and BECN bits";
             type empty;
           }
           choice de-or-plp {
             case case_1 {
               leaf translate-discard-eligible {
                 description "Translate DE bit";
                 type empty;
               }
             }
             case case_2 {
             }
           }
           leaf keep-address-and-control {
             description "Don't strip PPP address and control bytes";
             type empty;
           }
         }
         container tcc {
           presence "enable tcc";
           junos:must "(!(\".. .. encapsulation frame-relay-ppp\"))";
           junos:must-message "family tcc is not supported on encapsulation frame-relay-ppp";
           description "Translational cross-connect parameters";
           uses apply-advanced;
           container policer {
             description "Interface policing";
             uses apply-advanced;
             leaf input {
               description "Name of policer applied to received packets";
               type string;
             }
             leaf output {
               description "Name of policer applied to transmitted packets";
               type string;
             }
           }
           container proxy {
             presence "enable proxy";
             uses apply-advanced;
             leaf inet-address {
               description "Remote host address on non-Ethernet side of Ethernet TCC";
               type jt:ipv4addr;
             }
           }
           container remote {
             presence "enable remote";
             uses apply-advanced;
             leaf inet-address {
               description "Remote host address on Ethernet side of Ethernet TCC";
               type jt:ipv4addr;
             }
             leaf mac-address {
               description "Remote host MAC address on Ethernet side of Ethernet TCC";
               type jt:mac-addr;
             }
           }
         }
         container vpls {
           presence "enable vpls";
           description "Virtual private LAN service parameters";
           uses apply-advanced;
           leaf core-facing {
             description "Interface is core facing";
             type empty;
           }
           container filter {
             description "Packet filtering";
             uses apply-advanced;
             choice input_choice {
               case case_1 {
                 container input {
                   junos:cli-feature "oneliner";
                   description "Filter to be applied to received packets";
                   leaf filter-name {
                     description "Name of the filter";
                     junos:cli-feature "nokeyword";
                     junos:must "((!(\".. .. .. rpf-check\") || (!(any \"firewall family inet filter $$ term <*> from first-byte-of-payload\") && !(any \"firewall family inet filter $$ term <*> from first-byte-of-payload-except\"))))";
                     junos:must-message "filter with first-byte-of-payload match cannot be bound on URPF";
                     type string;
                   }
                   leaf shared-name {
                     description "Filter shared-name of instances of interface-shared filter";
                     type string;
                   }
                   leaf precedence {
                     description "Precedence of the filter";
                     type union {
                       type string {
                         pattern "<.*>|$.*";
                       }
                       type uint32 {
                         range "0 .. 255";
                       }
                     }
                   }
                 }
               }
               case case_2 {
                 leaf-list input-list {
                   ordered-by user;
                   description "List of filter modules applied to received packets ";
                   type string;
                 }
               }
             }
             choice output_choice {
               case case_1 {
                 container output {
                   junos:cli-feature "oneliner";
                   description "Filter to be applied to transmitted packets";
                   leaf filter-name {
                     description "Name of the filter";
                     junos:cli-feature "nokeyword";
                     junos:must "((!(\".. .. .. rpf-check\") || (!(any \"firewall family inet filter $$ term <*> from first-byte-of-payload\") && !(any \"firewall family inet filter $$ term <*> from first-byte-of-payload-except\"))))";
                     junos:must-message "filter with first-byte-of-payload match cannot be bound on URPF";
                     type string;
                   }
                   leaf shared-name {
                     description "Filter shared-name of instances of interface-shared filter";
                     type string;
                   }
                   leaf precedence {
                     description "Precedence of the filter";
                     type union {
                       type string {
                         pattern "<.*>|$.*";
                       }
                       type uint32 {
                         range "0 .. 255";
                       }
                     }
                   }
                 }
               }
               case case_2 {
                 leaf-list output-list {
                   ordered-by user;
                   description "List of filter modules applied to transmitted packets ";
                   type string;
                 }
               }
             }
             container adf {
               description "Ascend Data Filter definition";
               uses apply-advanced;
               list rule {
                 key name;
                 ordered-by user;
                 description "Set of ADF rules";
                 leaf name {
                   description "Value for a single rule";
                   junos:cli-feature "nokeyword";
                   type string;
                 }
                 uses apply-advanced;
               }
               leaf counter {
                 description "Add a counter to each rule";
                 type empty;
               }
               leaf input-precedence {
                 description "Precedence of the input rules";
                 type union {
                   type string {
                     pattern "<.*>|$.*";
                   }
                   type uint32 {
                     range "0 .. 255";
                   }
                 }
               }
               leaf not-mandatory {
                 description "No errors will be reported if no rules are present";
                 type empty;
               }
               leaf output-precedence {
                 description "Precedence of the output rules";
                 type union {
                   type string {
                     pattern "<.*>|$.*";
                   }
                   type uint32 {
                     range "0 .. 255";
                   }
                 }
               }
             }
             leaf group {
               description "Group to which interface belongs";
               type union {
                 type string {
                   pattern "<.*>|$.*";
                 }
                 type uint32 {
                   range "1 .. 255";
                 }
               }
             }
           }
           container policer {
             description "Interface policing";
             uses apply-advanced;
             leaf input {
               description "Name of policer applied to received packets";
               type string;
             }
             leaf output {
               description "Name of policer applied to transmitted packets";
               type string;
             }
           }
         }
         container bridge {
           presence "enable bridge";
           junos:must "((!(\".. vpls\") && (!(\".. inet\") && (!(\".. inet6\") && (!(\".. ccc\") && (!(\".. ethernet-switching\") && (!(\".. iso\") && (!(\".. llc2\") && (!(\".. mpls\") && (!(\".. tcc\") && (!(\".. pppoe\") && !(\".. gre\"))))))))))))";
           junos:must-message "family bridge and rest of the families are mutually exclusive";
           description "Layer-2 bridging parameters";
           uses apply-advanced;
           leaf core-facing {
             description "Interface is core facing";
             type empty;
           }
           container filter {
             description "Packet filtering";
             uses apply-advanced;
             choice input_choice {
               case case_1 {
                 container input {
                   junos:cli-feature "oneliner";
                   description "Filter to be applied to received packets";
                   leaf filter-name {
                     description "Name of the filter";
                     junos:cli-feature "nokeyword";
                     junos:must "((!(\".. .. .. rpf-check\") || (!(any \"firewall family inet filter $$ term <*> from first-byte-of-payload\") && !(any \"firewall family inet filter $$ term <*> from first-byte-of-payload-except\"))))";
                     junos:must-message "filter with first-byte-of-payload match cannot be bound on URPF";
                     type string;
                   }
                   leaf shared-name {
                     description "Filter shared-name of instances of interface-shared filter";
                     type string;
                   }
                   leaf precedence {
                     description "Precedence of the filter";
                     type union {
                       type string {
                         pattern "<.*>|$.*";
                       }
                       type uint32 {
                         range "0 .. 255";
                       }
                     }
                   }
                 }
               }
               case case_2 {
                 leaf-list input-list {
                   ordered-by user;
                   description "List of filter modules applied to received packets ";
                   type string;
                 }
               }
             }
             choice output_choice {
               case case_1 {
                 container output {
                   junos:cli-feature "oneliner";
                   description "Filter to be applied to transmitted packets";
                   leaf filter-name {
                     description "Name of the filter";
                     junos:cli-feature "nokeyword";
                     junos:must "((!(\".. .. .. rpf-check\") || (!(any \"firewall family inet filter $$ term <*> from first-byte-of-payload\") && !(any \"firewall family inet filter $$ term <*> from first-byte-of-payload-except\"))))";
                     junos:must-message "filter with first-byte-of-payload match cannot be bound on URPF";
                     type string;
                   }
                   leaf shared-name {
                     description "Filter shared-name of instances of interface-shared filter";
                     type string;
                   }
                   leaf precedence {
                     description "Precedence of the filter";
                     type union {
                       type string {
                         pattern "<.*>|$.*";
                       }
                       type uint32 {
                         range "0 .. 255";
                       }
                     }
                   }
                 }
               }
               case case_2 {
                 leaf-list output-list {
                   ordered-by user;
                   description "List of filter modules applied to transmitted packets ";
                   type string;
                 }
               }
             }
             container adf {
               description "Ascend Data Filter definition";
               uses apply-advanced;
               list rule {
                 key name;
                 ordered-by user;
                 description "Set of ADF rules";
                 leaf name {
                   description "Value for a single rule";
                   junos:cli-feature "nokeyword";
                   type string;
                 }
                 uses apply-advanced;
               }
               leaf counter {
                 description "Add a counter to each rule";
                 type empty;
               }
               leaf input-precedence {
                 description "Precedence of the input rules";
                 type union {
                   type string {
                     pattern "<.*>|$.*";
                   }
                   type uint32 {
                     range "0 .. 255";
                   }
                 }
               }
               leaf not-mandatory {
                 description "No errors will be reported if no rules are present";
                 type empty;
               }
               leaf output-precedence {
                 description "Precedence of the output rules";
                 type union {
                   type string {
                     pattern "<.*>|$.*";
                   }
                   type uint32 {
                     range "0 .. 255";
                   }
                 }
               }
             }
             leaf group {
               description "Group to which interface belongs";
               type union {
                 type string {
                   pattern "<.*>|$.*";
                 }
                 type uint32 {
                   range "1 .. 255";
                 }
               }
             }
           }
           container policer {
             description "Interface policing";
             uses apply-advanced;
             leaf input {
               description "Name of policer applied to received packets";
               type string;
             }
             leaf output {
               description "Name of policer applied to transmitted packets";
               type string;
             }
           }
           leaf interface-mode {
             description "Interface mode (access or trunk)";
             type enumeration {
               enum "access" {
                 description "Interface mode is access";
                 junos:must "((!(\"interfaces ${interface} vlan-tagging\") && (!(\"interfaces ${interface} flexible-vlan-tagging\") && !(\"interfaces ${interface} stacked-vlan-tagging\"))))";
                 junos:must-message "interface-mode access is allowed only for untagged interfaces";
               }
               enum "trunk" {
                 description "Interface mode is trunk";
                 junos:must "(!(\"interfaces ${interface} no-native-vlan-insert\"))";
                 junos:must-message "'interface-mode trunk' must not be configured with 'no-native-vlan-insert'";
                 junos:must "(((\"protocols mvrp interface ${interface}\" || any \"routing-instances <*> protocols mvrp interface ${interface}\") || (\".. vlan-id-list\" || (\".. isid-list\" || (\".. inner-vlan-id-list\" || (\".. vlan members\" || (\"..inner-vlan members\" || (\".. vlan-id\" || \".. vlan-auto-sense\"))))))))";
                 junos:must-message "'interface-mode trunk' must be defined with either 'vlan-id-list','isid-list', 'inner-vlan-id-list' or the interface must be configured for 'protocols mvrp' or 'vlan-auto-sense'";
               }
             }
           }
           leaf vlan-auto-sense {
             description "Enable VLAN auto sense on this interface";
             junos:must "(\".. interface-mode trunk\")";
             junos:must-message "vlan-auto-sense can be enabled only on trunk interfaces";
             type empty;
           }
           leaf bridge-domain-type {
             description "Bridge domain type (svlan or bvlan)";
             type enumeration {
               enum "svlan" {
                 description "Bridge domain type svlan";
                 junos:must "(\".. isid-list all-service-groups\")";
                 junos:must-message "bridge-domain-type svlan is allowed only for isid tagged interfaces";
                 junos:must "(\".. interface-mode trunk\")";
                 junos:must-message "bridge-domain-type svlan is allowed only for trunk interfaces";
               }
               enum "bvlan" {
                 description "Bridge domain type bvlan";
                 junos:must "(\".. isid-list all\")";
                 junos:must-message "bridge-domain-type bvlan is allowed only for isid tagged interfaces";
                 junos:must "(\".. interface-mode trunk\")";
                 junos:must-message "bridge-domain-type bvlan is allowed only for trunk interfaces";
               }
             }
           }
           leaf inter-switch-link {
             description "PVLAN inter switch link";
             junos:must "(\".. interface-mode trunk\")";
             junos:must-message "'Inter switch link' is supported only under trunk interface mode";
             type empty;
           }
           choice vlan_list {
             case case_1 {
               leaf vlan-id {
                 description "Access mode and trunk mode VLAN membership";
                 type union {
                   type string {
                     pattern "<.*>|$.*";
                   }
                   type uint32 {
                     range "1 .. 4094";
                   }
                 }
               }
             }
             case case_2 {
               leaf-list vlan-id-list {
                 description "Trunk mode VLAN membership for this interface";
                 junos:must "((!(\".. .. .. vlan-id\") && !(\".. .. .. vlan-tags\")))";
                 junos:must-message "'vlan-id-list' cannot be used on interface with vlan-id/vlan-tags";
                 junos:must "(!(\"interfaces ${interface} stacked-vlan-tagging\"))";
                 junos:must-message "'vlan-id-list' is not supported on stacked-vlan-tagging mode";
                 junos:must "(\".. interface-mode trunk\")";
                 junos:must-message "'vlan-id-list' statement supported only under trunk interface mode";
                 type jt:vlan-range;
               }
             }
             case case_3 {
               leaf-list inner-vlan-id-list {
                 description "Trunk mode VLAN membership for this interface based on inner VLAN tag";
                 junos:must "((!(\".. .. .. vlan-tags inner\") && !(\".. .. .. vlan-tags inner-range\")))";
                 junos:must-message "'inner-vlan-id-list' cannot be used on interface with vlan-tags inner/inner-range";
                 junos:must "((\".. .. .. vlan-id\" || \".. .. .. vlan-tags\"))";
                 junos:must-message "'inner-vlan-id-list' can be used only on interface with vlan-id/vlan-tags";
                 junos:must "(\"interfaces ${interface} flexible-vlan-tagging\")";
                 junos:must-message "'inner-vlan-id-list' is supported only on flexible-vlan-tagging mode";
                 junos:must "(\".. interface-mode trunk\")";
                 junos:must-message "'inner-vlan-id-list' statement supported only under trunk interface mode";
                 type jt:vlan-range;
               }
             }
           }
           container vlan-rewrite {
             junos:must "((\".. inner-vlan-id-list\" || \".. vlan-id-list\"))";
             junos:must-message "'vlan-rewrite' statement can be used only with 'vlan-id-list' or inner-vlan-id-list configured";
             junos:must "(\".. interface-mode trunk\")";
             junos:must-message "'vlan-rewrite' statement supported only under trunk interface mode";
             junos:cli-feature "oneliner-plus";
             description "Specify vlan translation";
             uses apply-advanced;
             list translate {
               key name;
               ordered-by user;
               junos:cli-feature "oneliner";
               description "Translate incoming VLAN tag";
               leaf name {
                 description "Specify the incoming VLAN tag";
                 junos:cli-feature "nokeyword";
                 type union {
                   type string {
                     pattern "<.*>|$.*";
                   }
                   type uint32 {
                     range "1 .. 4094";
                   }
                 }
               }
               leaf to-vlan-id {
                 description "Specify the bridge-domain VLAN-ID";
                 junos:cli-feature "nokeyword";
                 type union {
                   type string {
                     pattern "<.*>|$.*";
                   }
                   type uint32 {
                     range "1 .. 4094";
                   }
                 }
               }
             }
           }
           choice isid_list {
             case case_1 {
               leaf isid-list {
                 description "Specify the ISID list";
                 type enumeration {
                   enum "all-service-groups" {
                     description "Map all ISIDs specified under the service-groups";
                     junos:must "(\".. interface-mode trunk\")";
                     junos:must-message "'all-service-groups' statement supported only under trunk interface mode";
                   }
                   enum "all" {
                     description "Map all ISIDs";
                     junos:must "(\".. interface-mode trunk\")";
                     junos:must-message "'all' statement supported only under trunk interface mode";
                   }
                 }
               }
             }
           }
           container recovery-timeout {
             junos:must "(\".. storm-control\")";
             junos:must-message "Recovery timeout should be configured only with storm-control";
             junos:cli-feature "oneliner";
             description "Recovery timeout for this interface";
             leaf time-in-seconds {
               junos:cli-feature "nokeyword";
               units "seconds";
               type union {
                 type string {
                   pattern "<.*>|$.*";
                 }
                 type uint32 {
                   range "10 .. 3600";
                 }
               }
             }
           }
         }
         container ethernet-switching {
           description "Ethernet switching parameters";
           presence "enable ethernet-switching";
           junos:must "((!(\".. vpls\") && (!(\".. inet\") && (!(\".. inet6\") && (!(\".. bridge\") && (!(\".. ccc\") && (!(\".. iso\") && (!(\".. llc2\") && (!(\".. mpls\") && (!(\".. tcc\") && (!(\".. pppoe\") && !(\".. gre\"))))))))))))";
           junos:must-message "Family ethernet-switching and rest of the families are mutually exclusive";
           junos:must "(!((\"protocols l2-learning global-mode switching\" && any \"security zones security-zone <*> interfaces ${interface}\")))";
           junos:must-message "In switching mode, ethernet-switching interface must not be in security zone.";
           junos:must "(!((\"interfaces ${interface} vlan-tagging\" && !(\"protocols l2-learning global-mode transparent-bridge\"))))";
           junos:must-message "An interface cannot have both family ethernet-switching and vlan-tagging configured";
           junos:must "(!((\"interfaces ${interface} vlan-tagging\" && \"protocols l2-learning global-mode switching\")))";
           junos:must-message "An interface cannot have both family ethernet-switching and vlan-tagging configured";
           junos:must "(!((!(\"protocols l2-learning global-mode transparent-bridge\") && any \"security zones security-zone <*> interfaces ${interface}\")))";
           junos:must-message "In switching mode, ethernet-switching interface must not be in security zone.";
           uses ethernet-switching-type;
         }
         container pppoe {
           description "PPP over Ethernet underlying interface-specific options";
           presence "enable pppoe";
           junos:must "(!(\"forwarding-options hyper-mode\"))";
           junos:must-message "To configure family pppoe, 'forwarding-options hyper-mode' should not be configured";
           junos:must "((!(\".. vpls\") && (!(\".. ccc\") && (!(\".. ethernet-switching\") && (!(\".. iso\") && (!(\".. llc2\") && (!(\".. mpls\") && (!(\".. tcc\") && (!(\".. bridge\") && !(\".. gre\"))))))))))";
           junos:must-message "Invalid family type configured with family pppoe";
           junos:must "(!(\".. .. pppoe-underlying-options\"))";
           junos:must-message "family pppoe is mutually exclusive with pppoe-underlying-options";
           uses pppoe_underlying_options_type;
         }
         container any {
           presence "enable any";
           description "Parameters for 'any' family";
           uses apply-advanced;
           container filter {
             description "Layer 2 packet filtering";
             uses apply-advanced;
             leaf input {
               description "Name of filter applied to received packets";
               junos:must "((\"firewall family any filter $$\" || (!(\"firewall\") && \".. .. .. .. .. .. firewall family any filter $$\")))";
               junos:must-message "referenced filter must be defined under firewall family any";
               type string {
                 junos:posix-pattern "!^((__.*)|(.{65,}))$";
                 junos:pattern-message "Must be a non-reserved string of 64 characters or less";
               }
             }
             leaf group {
               description "Group to which interface belongs";
               type union {
                 type string {
                   pattern "<.*>|$.*";
                 }
                 type uint32 {
                   range "1 .. 255";
                 }
               }
             }
           }
         }
         uses apply-advanced;
       }
       leaf service-domain {
         description "Service domain to which interface belongs";
         type enumeration {
           enum "inside" {
             description "Inside network";
           }
           enum "outside" {
             description "Outside network";
           }
         }
       }
       leaf copy-tos-to-outer-ip-header {
         description "Copy IP payload header's ToS field to GRE delivery header";
         type empty;
       }
       container load-balancing-options {
         junos:must "(!(\".. .. load-balancing-options high-availability-options one-to-one\"))";
         junos:must-message "load-balancing-options are used when number of active members is more than one";
         description "AMS subunit load balancing options";
         uses apply-advanced;
         leaf preferred-active {
           description "Preferred active Interface name";
           junos:must "((\".. .. .. load-balancing-options member-interface $$\" && !(\".. .. .. load-balancing-options high-availability-options many-to-one preferred-backup $$\")))";
           junos:must-message "Active should be one of member-interfaces excluding preferred-backup";
           type union {
             type jt:interface-device;
             type string {
               pattern "<.*>|$.*";
             }
           }
         }
         leaf disable-hash {
           description "Hash based distribution is not needed for this subunit";
           junos:must "(\".. .. service-domain\")";
           junos:must-message "service-domain must be configured if disable-hash is enabled";
           junos:must "(!(\".. hash-keys\"))";
           junos:must-message "hash-keys must not be configured if disable-hash is enabled";
           type empty;
         }
         leaf modulo-key {
           description "Modulo based distribution";
           junos:must "(!(\".. .. .. load-balancing-options member-failure-options redistribute-all-traffic\"))";
           junos:must-message "redistribute-all-traffic can not be configured with modulo-key";
           junos:must "(!(\".. disable-hash\"))";
           junos:must-message "disable-hash can not be configured with modulo-key";
           junos:must "(\".. .. service-domain\")";
           junos:must-message "service-domain must be configured with modulo-key";
           junos:must "(!(\".. hash-keys\"))";
           junos:must-message "hash-keys can not be configured with modulo-key";
           type enumeration {
             enum "source-ip" {
               description "Source Ip Address";
             }
             enum "destination-ip" {
               description "Destination Ip Address";
             }
           }
         }
         container hash-keys {
           uses apply-advanced;
           leaf-list ingress-key {
             ordered-by user;
             description "Hash Key for the ingress direction";
             type enumeration {
               enum "source-ip" {
                 description "Source Ip Address";
               }
               enum "destination-ip" {
                 description "Destination Ip Address";
               }
               enum "protocol" {
                 description "Protocol";
               }
               enum "iif" {
                 description "Incoming Interface";
               }
             }
           }
           leaf-list egress-key {
             ordered-by user;
             description "Hash Key for the egress direction";
             status deprecated;
             type enumeration {
               enum "source-ip" {
                 description "Source Ip Address";
                 status deprecated;
               }
               enum "destination-ip" {
                 description "Destination Ip Address";
                 status deprecated;
               }
               enum "protocol" {
                 description "Protocol";
                 status deprecated;
               }
               enum "oif" {
                 description "Outgoing Interface";
                 status deprecated;
               }
             }
           }
           leaf ipv6-source-prefix-length {
             description "IPv6 source prefix length for hash computation";
             type enumeration {
               enum "56" {
                 description "56 bit IPv6 address prefix";
               }
               enum "64" {
                 description "64 bit IPv6 address prefix";
               }
               enum "96" {
                 description "96 bit IPv6 address prefix";
               }
               enum "128" {
                 description "Complete 128 bit IPv6 address";
               }
             }
           }
         }
       }
       container interface-state {
         description "IRB interface state computation";
         uses apply-advanced;
         choice state {
           case case_1 {
             leaf local {
               description "IRB State computation based on local interface state";
               type empty;
             }
           }
           case case_2 {
             leaf remote {
               description "IRB State computation based on remote reachability";
               type empty;
             }
           }
           case case_3 {
             leaf local-remote {
               description "IRB State computation based on local or remote reachability";
               type empty;
             }
           }
           case case_4 {
             leaf local-interface {
               description "IRB State computation based on loopback AE port state";
               type union {
                 type jt:interface-name;
                 type string {
                   pattern "<.*>|$.*";
                 }
               }
             }
           }
         }
         leaf local-count {
           description "Minimum number of local layer2 link in up state to consider IRB up";
           junos:must "(!(\".. remote\"))";
           junos:must-message "Must configure local, local-remote or keep default";
           type union {
             type uint16;
             type string {
               pattern "<.*>|$.*";
             }
           }
         }
         leaf vtep-count {
           description "Minimum number of VTEP link in up state to consider IRB up";
           junos:must "(!(\".. local\"))";
           junos:must-message "Must configure remote,local-remote or keep default";
           type union {
             type uint16;
             type string {
               pattern "<.*>|$.*";
             }
           }
         }
         container hold-time {
           description "Delay before marking interface up or down for defect";
           uses apply-advanced;
           leaf up {
             description "Delay in seconds before marking IRB interface up";
             units "seconds";
             type union {
               type uint32;
               type string {
                 pattern "<.*>|$.*";
               }
             }
           }
           leaf down {
             description "Delay in seconds before marking IRB interface down";
             units "seconds";
             type union {
               type uint32;
               type string {
                 pattern "<.*>|$.*";
               }
             }
           }
         }
       }
       leaf mac {
         description "Configure logical interface MAC address";
         type jt:mac-unicast;
       }
       leaf virtual-gateway-v4-mac {
         description "Configure virtual gateway IPV4 virtual MAC address";
         type jt:mac-unicast;
       }
       leaf virtual-gateway-v6-mac {
         description "Configure virtual gateway IPV6 virtual MAC address";
         type jt:mac-unicast;
       }
       leaf no-dhcp-flood {
         description "Disable dhcp flooding";
         type empty;
       }
       leaf etree-ac-role {
         description "ETREE attachment circuit role";
         type enumeration {
           enum "root" {
             description "ETREE root interface";
           }
           enum "leaf" {
             description "ETREE leaf interface";
           }
         }
       }
       container dialer-options {
         presence "enable dialer-options";
         description "Dialer options";
         uses apply-advanced;
         leaf pool {
           description "Dialer pool";
           junos:must "((!(\"interfaces umd0 dialer-options pool $$\") || !(\".. callback\")))";
           junos:must-message "callback is not supported if the subordinate interface is umd0";
           junos:must "(any \"interfaces <*> dialer-options pool $$\")";
           junos:must-message "Pool not configured in any subordinate interface";
           junos:must "(unique \"interfaces <dl*>\")";
           junos:must-message "Only one dl interface can be configured";
           type string {
             length "1 .. 64";
           }
         }
         leaf-list dial-string {
           ordered-by user;
           description "String to dial out";
           type string {
             length "1 .. 63";
           }
           max-elements 15;
         }
         container incoming-map {
           description "Map incoming call to dialer";
           uses apply-advanced;
           choice caller-type {
             case case_1 {
               list caller {
                 key name;
                 ordered-by user;
                 junos:cli-feature "oneliner";
                 description "Caller Id to be screened";
                 max-elements 300;
                 leaf name {
                   description "Caller ID (upto 15 digits)";
                   junos:cli-feature "nokeyword";
                   type string {
                     junos:posix-pattern "^([0-9]{1,15})$";
                     junos:pattern-message "Can contain up to 15 digits";
                   }
                 }
               }
             }
             case case_2 {
               leaf accept-all {
                 description "Accept all incoming calls";
                 type empty;
               }
             }
           }
         }
         leaf callback {
           description "Call back on any incoming call to the dialer";
           junos:must "(!(\".. watch-list \"))";
           junos:must-message "A dialer interface cannot have callback enabled and watch-list at the same time";
           junos:must "(\".. dial-string\")";
           junos:must-message "Dial string is mandatory for callback";
           junos:must "(\".. incoming-map\")";
           junos:must-message "incoming-map is mandatory for callback";
           type empty;
         }
         leaf callback-wait-period {
           description "Time to wait before calling back";
           units "seconds";
           junos:must "(\".. callback\")";
           junos:must-message "Callback needs to be configured";
           type union {
             type string {
               pattern "<.*>|$.*";
             }
             type uint32 {
               range "2 .. 255";
             }
           }
         }
         leaf redial-delay {
           description "Time to wait before redialing";
           units "seconds";
           type union {
             type string {
               pattern "<.*>|$.*";
             }
             type uint32 {
               range "2 .. 255";
             }
           }
         }
         leaf idle-timeout {
           description "Delay before taking down the interface";
           default "120";
           units "seconds";
           junos:must "((\".. .. family inet  filter dialer\" || (\".. .. family inet6 filter dialer\" || \".. .. family mpls  filter dialer\")))";
           junos:must-message "Dialer filter must be configured";
           type union {
             type string {
               pattern "<.*>|$.*";
             }
             type uint32 {
               range "0 .. 4294967295";
             }
           }
         }
         list watch-list {
           key name;
           junos:cli-feature "homogeneous";
           description "Dialer watch list";
           junos:must "(\".. dial-string\")";
           junos:must-message "dial-string is mandatory for watch-list";
           leaf name {
             description "Address prefix";
             junos:cli-feature "nokeyword";
             type jt:ipprefix-only;
           }
           uses apply-advanced;
         }
         leaf load-threshold {
           description "Load threshold for adding interfaces";
           junos:must "(\".. .. .. encapsulation multilink-ppp\")";
           junos:must-message "Encapsulation must be multilink-ppp";
           type union {
             type string {
               pattern "<.*>|$.*";
             }
             type uint32 {
               range "0 .. 100";
             }
           }
         }
         leaf load-interval {
           description "Interval used to calculate average load";
           units "seconds";
           junos:must "(\".. .. .. encapsulation multilink-ppp\")";
           junos:must-message "Encapsulation must be multilink-ppp";
           type union {
             type string {
               pattern "<.*>|$.*";
             }
             type uint32 {
               range "20 .. 180";
             }
           }
         }
         leaf activation-delay {
           description "Activation delay";
           units "seconds";
           junos:must "(!((\".. .. family inet  filter dialer\" || (\".. .. family inet6 filter dialer\" || \".. .. family mpls  filter dialer\"))))";
           junos:must-message "Activation delay cannot be configured for dialer filter";
           type union {
             type string {
               pattern "<.*>|$.*";
             }
             type uint32 {
               range "1 .. 4294967295";
             }
           }
         }
         leaf deactivation-delay {
           description "Deactivation delay";
           units "seconds";
           junos:must "(!((\".. .. family inet  filter dialer\" || (\".. .. family inet6 filter dialer\" || \".. .. family mpls  filter dialer\"))))";
           junos:must-message "Deactivation delay cannot be configured for dialer filter";
           type union {
             type string {
               pattern "<.*>|$.*";
             }
             type uint32 {
               range "1 .. 4294967295";
             }
           }
         }
         leaf initial-route-check {
           description "Delay to check primary after the router is up";
           default "120";
           units "seconds";
           junos:must "(\".. watch-list\")";
           junos:must-message "No watch list specified under dialer options";
           type union {
             type string {
               pattern "<.*>|$.*";
             }
             type uint16 {
               range "1 .. 300";
             }
           }
         }
         leaf-list route {
           ordered-by user;
           description "Route on dialer";
           type jt:ipprefix;
         }
         leaf always-on {
           description "Always keep on-line";
           junos:must "(!((\".. .. family inet  filter dialer\" || (\".. .. family inet6 filter dialer\" || \".. .. family mpls  filter dialer\"))))";
           junos:must-message "A dialer interface cannot have always-on enabled and filter at the same time";
           type empty;
         }
         leaf self-recover-time {
           description "Sub-interface self-recover time";
           units "seconds";
           type union {
             type string {
               pattern "<.*>|$.*";
             }
             type uint32 {
               range "2 .. 120";
             }
           }
         }
       }
       container backup-options {
         description "Backup interface configuration options";
         uses apply-advanced;
         leaf interface {
           description "Backup interface";
           junos:must "(\"interfaces $$-IFL dialer-options dial-string\")";
           junos:must-message "No dial-string configured in backup dialer interface";
           junos:must "(!(\"interfaces $$-IFL dialer-options callback \"))";
           junos:must-message "A dialer interface cannot be backup as well as have callback";
           junos:must "(!((\"interfaces $$-IFL family inet  filter dialer\" || (\"interfaces $$-IFL family inet6 filter dialer\" || \"interfaces $$-IFL family mpls  filter dialer\"))))";
           junos:must-message "A dialer interface cannot be backup as well as have dialer filter";
           junos:must "(!(\"interfaces $$-IFL dialer-options watch-list \"))";
           junos:must-message "A dialer interface cannot be backup as well as have watch list";
           junos:must "(\"interfaces $$-IFL dialer-options\")";
           junos:must-message "No dialer options configured in backup dialer interface";
           junos:must "(!(\"interfaces $$-IFL dialer-options always-on\"))";
           junos:must-message "A dialer interface cannot be backup as well as always-on";
           type union {
             type jt:interface-name;
             type string {
               pattern "<.*>|$.*";
             }
           }
         }
       }
       container dynamic-call-admission-control {
         description "Dynamic call admission control configuration";
         uses apply-advanced;
         leaf bearer-bandwidth-limit {
           description "Bearer bandwidth limit";
           units "kilobits per second";
           type union {
             type string {
               pattern "<.*>|$.*";
             }
             type uint16 {
               range "0 .. 9999";
             }
           }
         }
         leaf activation-priority {
           description "Priority assigned to bearer bandwidth limit";
           default "50";
           type union {
             type string {
               pattern "<.*>|$.*";
             }
             type uint8 {
               range "0 .. 255";
             }
           }
         }
       }
       container explicit-proxy {
         presence "enable explicit-proxy";
         description "Attach explicit proxy profiles";
         uses apply-advanced;
         leaf-list profile {
           description "Explicit proxy profile name";
           type string {
             length "1 .. 63";
           }
         }
       }
     }
     container no-partition {
       junos:cli-feature "oneliner";
       description "Use channelizable interface as clear channel";
       leaf interface-type {
         description "Interface type";
         type enumeration {
           enum "e1" {
             description "E1 interface";
           }
           enum "t1" {
             description "T1 interface";
           }
           enum "at" {
             description "ATM interface";
           }
           enum "t3" {
             description "T3 interface";
           }
           enum "e3" {
             description "E3 interface";
           }
           enum "ct3" {
             description "Channelized T3 interface";
           }
           enum "so" {
             description "SONET interface";
           }
           enum "cau4" {
             description "CAU4 interface";
           }
         }
       }
     }
     list partition {
       key name;
       ordered-by user;
       junos:cli-feature "oneliner";
       description "Channelized interface partition";
       junos:must "(!(\".. no-partition\"))";
       junos:must-message "cannot set partitions with no-partition attribute turned on";
       leaf name {
         description "Sublevel interface partition index (for example, 1, 3-4)";
         junos:cli-feature "nokeyword";
         type string;
       }
       leaf oc-slice {
         description "Range of SONET/SDH slices (for example, 1, 7-9)";
         type string;
       }
       leaf timeslots {
         description "Timeslots [(1..24) for T1, (1..31) for E1]; for example, 1-3,4,9,22-24 (no spaces)";
         type string;
       }
       leaf interface-type {
         description "Sublevel interface type";
         type enumeration {
           enum "ds" {
             description "DS0 interface";
           }
           enum "e1" {
             description "E1 interface";
           }
           enum "t1" {
             description "T1 interface";
           }
           enum "at" {
             description "ATM interface";
           }
           enum "ct1" {
             description "Channelized T1 interface";
           }
           enum "ce1" {
             description "Channelized E1 interface";
           }
           enum "t3" {
             description "T3 interface";
           }
           enum "ct3" {
             description "Channelized T3 interface";
           }
           enum "e3" {
             description "E3 interface";
           }
           enum "so" {
             description "SONET interface";
           }
           enum "coc1" {
             description "Channelized OC1 interface";
           }
           enum "cau4" {
             description "Channelized AU4 interface";
           }
           enum "dc" {
             description "D channel interface";
             junos:must "(any \".. .. partition <*> interface-type bc\")";
             junos:must-message "BC partition must be defined for PRI";
           }
           enum "bc" {
             description "B channel interface";
             junos:must "(any \".. .. partition <*> interface-type dc\")";
             junos:must-message "DC partition must be defined for PRI";
           }
         }
       }
     }
     container modem-options {
       description "MODEM interface-specific options";
       uses apply-advanced;
       leaf init-command-string {
         description "AT command string to initialize modem";
         type string {
           length "1 .. 127";
         }
       }
       leaf dialin {
         default "console";
         type enumeration {
           enum "console" {
             description "Management console access";
           }
           enum "routable" {
             description "Routable access";
           }
         }
       }
     }
     container isdn-options {
       description "ISDN interface-specific options";
       uses apply-advanced;
       leaf switch-type {
         description "ISDN switch type";
         type enumeration {
           enum "ni1" {
             description "NI1 BRI variant";
           }
           enum "etsi" {
             description "ETSI variant";
           }
           enum "att5e" {
             description "ATT5E variant";
           }
           enum "ntdms100" {
             description "NTDMS100 variant";
           }
           enum "ntt" {
             description "INS NET (NTT) PRI/BRI variant";
           }
           enum "ni2" {
             description "NI2 PRI variant";
           }
         }
       }
       leaf media-type {
         description "IDSN media type - voice, data or both";
         default "data";
         type enumeration {
           enum "data" {
             description "Data";
           }
           enum "voice" {
             description "Voice";
           }
           enum "combined" {
             description "Combined";
           }
         }
       }
       leaf spid1 {
         description "Service profile identifier";
         type string {
           length "1 .. 20";
         }
       }
       leaf spid2 {
         description "Additional service profile identifier";
         type string {
           length "1 .. 20";
         }
       }
       leaf calling-number {
         description "Calling number included in outgoing calls";
         type string {
           junos:posix-pattern "^([0-9A-DLPTWS*#!,@;^$/]{1,15})$|^([0-9A-DLPTWS*#!,@;^$/]{1,15}:[0-9A-DLPTWS*#!,@;^$/]{1,40})$";
           junos:pattern-message "Can contain up to 15 digits, alphanumeric or special characters; optional subaddress can contain up to 40 alphanumeric and special characters with the colon (:) used as the separator";
         }
       }
       list incoming-called-number {
         key name;
         ordered-by user;
         junos:cli-feature "oneliner";
         description "Incoming called number to be screened";
         max-elements 30;
         leaf name {
           description "Number called (upto 15 digits)";
           junos:cli-feature "nokeyword";
           type string {
             junos:posix-pattern "^([0-9]{1,15})$";
             junos:pattern-message "Can contain up to 15 digits";
           }
         }
         leaf reject {
           description "Reject the called number";
           type empty;
         }
       }
       leaf tei-option {
         description "ISDN terminal endpoint identifier negotiation options";
         type enumeration {
           enum "first-call" {
             description "Terminal endpoint identifier negotiation during first call";
           }
           enum "power-up" {
             description "Terminal endpoint identifier negotiation during power-up";
           }
         }
       }
       leaf static-tei-val {
         description "Static TEI value";
         type union {
           type string {
             pattern "<.*>|$.*";
           }
           type uint32 {
             range "0 .. 63";
           }
         }
       }
       leaf t310 {
         description "Timer T310 value";
         units "seconds";
         type union {
           type string {
             pattern "<.*>|$.*";
           }
           type uint32 {
             range "1 .. 65536";
           }
         }
       }
       leaf bchannel-allocation {
         description "Allocate PRI dialout b-channel in ascending/descending order";
         default "descending";
         type enumeration {
           enum "ascending" {
             description "Allocate b-channel in ascending order";
           }
           enum "descending" {
             description "Allocate b-channel in descending order";
           }
         }
       }
     }
     container dialer-options {
       presence "enable dialer-options";
       description "Dialer options";
       uses apply-advanced;
       list pool {
         key name;
         junos:cli-feature "oneliner";
         description "Dialer pool";
         max-elements 30;
         leaf name {
           description "Dialer pool identifier";
           junos:cli-feature "nokeyword";
           type string {
             length "1 .. 64";
           }
         }
         leaf priority {
           description "Dialer pool priority";
           type union {
             type string {
               pattern "<.*>|$.*";
             }
             type uint32 {
               range "1 .. 255";
             }
           }
         }
       }
     }
     leaf act-sim {
       description "Default SIM slot to connect LTE network";
       type union {
         type string {
           pattern "<.*>|$.*";
         }
         type uint32;
       }
     }
     container cellular-options {
       presence "enable cellular-options";
       description "Cellular interface specific options";
       uses apply-advanced;
       list sim {
         key name;
         description "SIM slot to connect LTE network";
         leaf name {
           description "SIM slot number";
           junos:cli-feature "nokeyword";
           type union {
             type string {
               pattern "<.*>|$.*";
             }
             type uint32;
           }
         }
         uses apply-advanced;
         container select-profile {
           junos:cli-feature "oneliner";
           description "Profile to be applied";
           leaf profile-id {
             description "Profile to be used for data calls";
             type union {
               type string {
                 pattern "<.*>|$.*";
               }
               type uint32 {
                 range "1 .. 16";
               }
             }
           }
         }
         container radio-access {
           junos:cli-feature "oneliner";
           description "Select radio access technology";
           choice rat-value {
             case case_1 {
               leaf automatic {
                 description "Automatically selects radio access type";
                 type empty;
               }
             }
             case case_2 {
               leaf umts-3g-only {
                 description "3G only";
                 type empty;
               }
             }
             case case_3 {
               leaf umts-3g-preferred {
                 description "UMTS 3G Preferred";
                 type empty;
               }
             }
             case case_4 {
               leaf lte-only {
                 description "Only LTE";
                 type empty;
               }
             }
             case case_5 {
               leaf lte-preferred {
                 description "LTE Preferred";
                 type empty;
               }
             }
           }
         }
         leaf encrypted-sim-unlock-code {
           description "Encrypted PIN";
           type jt:unreadable;
         }
         leaf gateway {
           description "Set customer gateway for LTE network";
           type jt:ipprefix;
         }
       }
     }
     container redundant-pseudo-interface-options {
       description "Pseudo interface redundancy options";
       uses apply-advanced;
       leaf redundancy-group {
         description "Redundancy group of this interface";
         junos:must "(\"chassis cluster redundancy-group $$\")";
         junos:must-message "A redundancy group should be defined";
         type union {
           type string {
             pattern "<.*>|$.*";
           }
           type uint16 {
             range "0 .. 255";
           }
         }
       }
     }
   }
   grouping keepalives_type {
     junos:cli-feature "oneliner";
     uses apply-advanced;
     leaf interval {
       description "Keepalive period";
       units "seconds";
       type union {
         type string {
           pattern "<.*>|$.*";
         }
         type uint16 {
           range "1 .. 32767";
         }
       }
     }
     leaf up-count {
       description "Keepalive received to bring link up";
       type union {
         type string {
           pattern "<.*>|$.*";
         }
         type uint16 {
           range "1 .. 255";
         }
       }
     }
     leaf down-count {
       description "Keepalive missed to bring link down";
       type union {
         type string {
           pattern "<.*>|$.*";
         }
         type uint16 {
           range "1 .. 255";
         }
       }
     }
   }
   grouping log-object {
     description "Configure security log";
     uses apply-advanced;
     list exclude {
       key name;
       ordered-by user;
       junos:cli-feature "homogeneous";
       description "List of security log criteria to exclude from the audit log";
       status deprecated;
       leaf name {
         description "Exclude criteria name";
         junos:cli-feature "nokeyword";
         type string;
       }
       uses apply-advanced;
       leaf destination-address {
         description "Destination address";
         type jt:ipaddr;
       }
       leaf destination-port {
         description "Destination port";
         type union {
           type uint32;
           type string {
             pattern "<.*>|$.*";
           }
         }
       }
       leaf event-id {
         description "Event ID filter";
         type string;
       }
       leaf failure {
         description "Event was a failure";
         type empty;
       }
       leaf interface-name {
         description "Name of interface";
         type string;
       }
       leaf policy-name {
         description "Policy name filter";
         type string;
       }
       leaf process {
         description "Process that generated the event";
         type string;
       }
       leaf protocol {
         description "Protocol filter";
         type string;
       }
       leaf source-address {
         description "Source address";
         type jt:ipaddr;
       }
       leaf source-port {
         description "Source port";
         type union {
           type uint32;
           type string {
             pattern "<.*>|$.*";
           }
         }
       }
       leaf success {
         description "Event was successful";
         type empty;
       }
       leaf username {
         description "Username filter";
         type string;
       }
     }
     leaf limit {
       description "Limit number of security log entries to keep in memory";
       status deprecated;
       default "10000";
       type union {
         type uint32;
         type string {
           pattern "<.*>|$.*";
         }
       }
     }
     container cache {
       presence "enable cache";
       description "Cache security log events in the audit log buffer";
       uses apply-advanced;
       list exclude {
         key name;
         ordered-by user;
         junos:cli-feature "homogeneous";
         description "List of security log criteria to exclude from the audit log";
         junos:must "(!(\".. .. exclude\"))";
         junos:must-message "'security log cache exclude' and 'security log exclude' are mutually exclusive";
         leaf name {
           description "Exclude criteria name";
           junos:cli-feature "nokeyword";
           type string;
         }
         uses apply-advanced;
         leaf destination-address {
           description "Destination address";
           type jt:ipaddr;
         }
         leaf destination-port {
           description "Destination port";
           type union {
             type uint32;
             type string {
               pattern "<.*>|$.*";
             }
           }
         }
         leaf event-id {
           description "Event ID filter";
           type string;
         }
         leaf failure {
           description "Event was a failure";
           type empty;
         }
         leaf interface-name {
           description "Name of interface";
           type string;
         }
         leaf policy-name {
           description "Policy name filter";
           type string;
         }
         leaf process {
           description "Process that generated the event";
           type string;
         }
         leaf protocol {
           description "Protocol filter";
           type string;
         }
         leaf source-address {
           description "Source address";
           type jt:ipaddr;
         }
         leaf source-port {
           description "Source port";
           type union {
             type uint32;
             type string {
               pattern "<.*>|$.*";
             }
           }
         }
         leaf success {
           description "Event was successful";
           type empty;
         }
         leaf username {
           description "Username filter";
           type string;
         }
       }
       leaf limit {
         description "Limit number of security log entries to keep in memory";
         default "10000";
         junos:must "(!(\".. .. limit\"))";
         junos:must-message "'security log cache limit' and 'security log limit' are mutually exclusive";
         type union {
           type uint32;
           type string {
             pattern "<.*>|$.*";
           }
         }
       }
     }
     leaf disable {
       description "Disable security logging for the device";
       type empty;
     }
     leaf utc-timestamp {
       description "Use UTC time for security log timestamps";
       type empty;
     }
     leaf mode {
       description "Controls how security logs are processed and exported";
       type enumeration {
         enum "stream" {
           description "Process security logs directly in the forwarding plane";
         }
         enum "event" {
           description "Process security logs in the control plane";
         }
         enum "stream-event" {
           description "Process security logs in both forwarding plane and control plane";
         }
       }
     }
     leaf event-rate {
       description "Control plane event rate";
       units "logs per second";
       junos:must "((\"security log mode event\" || (\"services service-set ${service-set} syslog mode event\" || (\"security log mode stream-event\" || \"services service-set ${service-set} syslog mode stream-event\"))))";
       junos:must-message "To configure event-rate, security log must be in event or stream-event mode";
       type union {
         type string {
           pattern "<.*>|$.*";
         }
         type uint32 {
           range "0 .. 1500";
         }
       }
     }
     leaf format {
       description "Set security log format for the device";
       type enumeration {
         enum "syslog" {
           description "Traditional syslog";
         }
         enum "sd-syslog" {
           description "Structured syslog";
         }
         enum "binary" {
           description "Binary log";
         }
         enum "protobuf" {
           description "Protobuf log";
         }
       }
     }
     leaf escape {
       description "Enable escape defined by RFC5424 for the sd and binary format logs";
       type empty;
     }
     container time-format {
       description "Configure year or millisecond for syslog";
       uses time-format-object;
     }
     leaf rate-cap {
       description "Data plane event rate";
       units "logs per second";
       type union {
         type string {
           pattern "<.*>|$.*";
         }
         type uint32 {
           range "0 .. 5000";
         }
       }
     }
     leaf max-database-record {
       description "Maximum records in database";
       default "0";
       type union {
         type string {
           pattern "<.*>|$.*";
         }
         type uint32;
       }
     }
     leaf retry-count {
       description "Set number of times client should retry to send message";
       default "5";
       type union {
         type string {
           pattern "<.*>|$.*";
         }
         type uint32 {
           range "1 .. 5";
         }
       }
     }
     container report {
       presence "enable report";
       description "Set security log report settings";
       uses apply-advanced;
       leaf database-capacity {
         description "Total capacity of all the tables in database";
         type enumeration {
           enum "max-db-size" {
             description "Increases database size to 216M entries";
           }
         }
       }
       container logs-per-table {
         presence "enable logs-per-table";
         description "Log number per table in database (Warning:This will clear all the logs from the table)";
         uses apply-advanced;
         leaf session-all {
           description "Log number of session";
           type union {
             type string {
               pattern "<.*>|$.*";
             }
             type uint32;
           }
         }
         leaf screen {
           description "Log number of screen";
           type union {
             type string {
               pattern "<.*>|$.*";
             }
             type uint32;
           }
         }
         leaf idp {
           description "Log number of idp";
           type union {
             type string {
               pattern "<.*>|$.*";
             }
             type uint32;
           }
         }
         leaf utm {
           description "Log number of utm";
           type union {
             type string {
               pattern "<.*>|$.*";
             }
             type uint32;
           }
         }
         leaf ipsec-vpn {
           description "Log number of ipsec-vpn";
           type union {
             type string {
               pattern "<.*>|$.*";
             }
             type uint32;
           }
         }
         leaf sky {
           description "Log number of sky";
           type union {
             type string {
               pattern "<.*>|$.*";
             }
             type uint32;
           }
         }
       }
       container log-share-per-table {
         presence "enable log-share-per-table";
         description "Log share(%) per table in database";
         uses apply-advanced;
         leaf session-all {
           description "Percentage share for session table (%) (default=22)";
           type union {
             type string {
               pattern "<.*>|$.*";
             }
             type uint32 {
               range "0 .. 100";
             }
           }
         }
         leaf screen {
           description "Percentage share for screen table (%) (default=13)";
           type union {
             type string {
               pattern "<.*>|$.*";
             }
             type uint32 {
               range "0 .. 100";
             }
           }
         }
         leaf idp {
           description "Percentage share for idp table (%) (default=13)";
           type union {
             type string {
               pattern "<.*>|$.*";
             }
             type uint32 {
               range "0 .. 100";
             }
           }
         }
         leaf utm {
           description "Percentage share for utm table (%) (default=13)";
           type union {
             type string {
               pattern "<.*>|$.*";
             }
             type uint32 {
               range "0 .. 100";
             }
           }
         }
         leaf ipsec-vpn {
           description "Percentage share for ipsec-vpn table (%) (default=13)";
           type union {
             type string {
               pattern "<.*>|$.*";
             }
             type uint32 {
               range "0 .. 100";
             }
           }
         }
         leaf atp {
           description "Percentage share for atp table (%) (default=13)";
           type union {
             type string {
               pattern "<.*>|$.*";
             }
             type uint32 {
               range "0 .. 100";
             }
           }
         }
         leaf dns {
           description "Percentage share for dns table (%) (default=13)";
           type union {
             type string {
               pattern "<.*>|$.*";
             }
             type uint32 {
               range "0 .. 100";
             }
           }
         }
       }
       leaf table-lifetime {
         description "Table lifetime day(s)";
         default "90";
         type union {
           type string {
             pattern "<.*>|$.*";
           }
           type uint32 {
             range "0 .. 365";
           }
         }
       }
       leaf table-mode {
         description "Report table mode";
         type enumeration {
           enum "dense" {
             description "Enable dense mode(B-Tree)";
           }
           enum "disabl-dense" {
             description "Disable dense mode(Moving to R-Tree)";
           }
         }
       }
       container database-filter {
         presence "enable database-filter";
         description "Check the logs whether should be inserted into database";
         uses apply-advanced;
         list event-category {
           key name;
           ordered-by user;
           description "Filter by event-category";
           leaf name {
             description "Name";
             junos:cli-feature "nokeyword";
             type enumeration {
               enum "session" {
                 description "Session log";
               }
               enum "screen" {
                 description "Screen log";
               }
               enum "idp" {
                 description "IDP log";
               }
               enum "webfilter" {
                 description "Webfilter log";
               }
               enum "content-filter" {
                 description "Content-filter log";
               }
               enum "anti-virus" {
                 description "Antivirus log";
               }
               enum "anti-spam" {
                 description "Anti-spam log";
               }
               enum "ipsec" {
                 description "IPsec VPN log";
               }
               enum "sky" {
                 description "Sky ATP log";
               }
               enum "secintel" {
                 description "Secintel log";
               }
               enum "icap" {
                 description "ICAP log";
               }
               enum "ssl-proxy" {
                 description "SSL proxy log";
               }
               enum "dnsf" {
                 description "DNSF log";
               }
               enum "dns" {
                 description "Dns log";
               }
               enum "session-create" {
                 description "Session create log";
               }
               enum "session-close" {
                 description "Session close log";
               }
               enum "session-deny" {
                 description "Session deny log";
               }
             }
           }
           uses apply-advanced;
         }
         leaf exclude {
           description "Exclude the logs";
           type empty;
         }
       }
     }
     choice source {
       case case_1 {
         leaf source-address {
           description "Source ip address used when exporting security logs";
           junos:must "(!(\"services service-set ${service-set} syslog mode event\"))";
           junos:must-message "To configure source address, mode must be stream or stream-event";
           type jt:ipaddr;
         }
       }
       case case_2 {
         leaf source-interface {
           description "Source interface used when exporting security logs";
           junos:must "(!(\"services service-set ${service-set} syslog mode event\"))";
           junos:must-message "To configure source interface, mode must be stream or stream-event";
           type union {
             type jt:interface-name;
             type string {
               pattern "<.*>|$.*";
             }
           }
         }
       }
     }
     container transport {
       presence "enable transport";
       junos:must "(!(\"services service-set ${service-set} syslog mode event\"))";
       junos:must-message "To configure transport info, mode must be stream or stream-event";
       description "Set security log transport settings";
       uses apply-advanced;
       leaf tcp-connections {
         description "Set tcp connection number per-stream";
         type union {
           type string {
             pattern "<.*>|$.*";
           }
           type uint32 {
             range "1 .. 5";
           }
         }
       }
       leaf protocol {
         description "Set security log transport protocol for the device";
         type enumeration {
           enum "udp" {
             description "UDP transfer for log";
           }
           enum "tcp" {
             description "TCP transfer for log";
           }
           enum "tls" {
             description "TLS transfer for log";
           }
         }
       }
       leaf tls-profile {
         description "TLS profile";
         junos:must "(\"services ssl initiation profile $$\")";
         junos:must-message "SSl profile must be defined under [services ssl initiation profile]";
         type string;
       }
     }
     leaf facility-override {
       description "Alternate facility for logging to remote host";
       type enumeration {
         enum "authorization" {
           description "Authorization system";
         }
         enum "daemon" {
           description "Various system processes";
         }
         enum "ftp" {
           description "FTP process";
         }
         enum "kernel" {
           description "Kernel";
         }
         enum "user" {
           description "User processes";
         }
         enum "local0" {
           description "Local logging option number 0";
         }
         enum "local1" {
           description "Local logging option number 1";
         }
         enum "local2" {
           description "Local logging option number 2";
         }
         enum "local3" {
           description "Local logging option number 3";
         }
         enum "local4" {
           description "Local logging option number 4";
         }
         enum "local5" {
           description "Local logging option number 5";
         }
         enum "local6" {
           description "Local logging option number 6";
         }
         enum "local7" {
           description "Local logging option number 7";
         }
       }
     }
     leaf local-log-tag {
       description "Tag included in logs";
       junos:must "(!(\"services service-set ${service-set} syslog mode stream\"))";
       junos:must-message "To configure local-log-tag, mode must be event or stream-event";
       type string {
         junos:posix-pattern "![ =:]{1,15}";
         junos:pattern-message "Must be a string of 15 characters or less";
       }
     }
     list local-category {
       key name;
       ordered-by user;
       description "Selects the type of events that may be logged locally";
       junos:must "(!(\"services service-set ${service-set} syslog mode stream\"))";
       junos:must-message "To configure local-category, mode must be event or stream-event";
       leaf name {
         junos:cli-feature "nokeyword";
         type enumeration {
           enum "all" {
             description "All events are logged";
           }
           enum "content-security" {
             description "Content security events are logged";
           }
           enum "fw-auth" {
             description "Fw-auth events are logged";
           }
           enum "screen" {
             description "Screen events are logged";
           }
           enum "alg" {
             description "Alg events are logged";
           }
           enum "nat" {
             description "Nat events are logged";
           }
           enum "flow" {
             description "Flow events are logged";
           }
           enum "sctp" {
             description "Sctp events are logged";
           }
           enum "gtp" {
             description "Gtp events are logged";
           }
           enum "ipsec" {
             description "Ipsec events are logged";
           }
           enum "idp" {
             description "Idp events are logged";
           }
           enum "rtlog" {
             description "Rtlog events are logged";
           }
           enum "pst-ds-lite" {
             description "Pst-ds-lite events are logged";
           }
           enum "appqos" {
             description "Appqos events are logged";
           }
           enum "secintel" {
             description "Secintel events are logged";
           }
           enum "aamw" {
             description "AAMW events are logged";
           }
           enum "sfw" {
             description "Stateful Firewall events are logged";
           }
           enum "session" {
             description "Session open and close events are logged";
           }
           enum "session-open" {
             description "Session open events are logged";
           }
           enum "session-close" {
             description "Session close events are logged";
           }
           enum "urlf" {
             description "URLF events are logged";
           }
           enum "ha" {
             description "Stateful High-Availability open and close events are logged";
           }
           enum "ha-open" {
             description "Stateful High-Availability open events are logged";
           }
           enum "ha-close" {
             description "Stateful High-Availability close events are logged";
           }
           enum "pcp" {
             description "PCP logs";
           }
           enum "dnsf" {
             description "DNSF";
           }
           enum "dns" {
             description "DNS";
           }
         }
       }
       uses apply-advanced;
     }
     leaf root-streaming {
       description "Logs will be streamed from the Root LSYS";
       type empty;
     }
     list stream {
       key name;
       ordered-by user;
       description "Set security log stream settings";
       junos:must "(!(\"services service-set ${service-set} syslog mode event\"))";
       junos:must-message "To configure stream, mode must be stream or stream-event";
       max-elements 12;
       leaf name {
         description "Name of security log stream";
         junos:cli-feature "nokeyword";
         type string {
           length "1 .. 63";
           junos:posix-pattern "^[[:alnum:]._-]+$";
           junos:pattern-message "Must be a string consisting of letters, numbers, dashes and underscores";
         }
       }
       uses apply-advanced;
       leaf severity {
         description "Severity threshold for security logs";
         type enumeration {
           enum "emergency" {
             description "Conditions that cause security functions to stop";
           }
           enum "alert" {
             description "Conditions that require immediate attention";
           }
           enum "critical" {
             description "Critical conditions";
           }
           enum "error" {
             description "General error conditions";
           }
           enum "warning" {
             description "General warning conditions";
           }
           enum "notice" {
             description "Non-error conditions that are of interest";
           }
           enum "info" {
             description "Information about normal security operations";
           }
           enum "debug" {
             description "Information normally used in debugging";
           }
         }
       }
       leaf format {
         description "Specify the log stream format";
         type enumeration {
           enum "syslog" {
             description "Traditional syslog";
           }
           enum "sd-syslog" {
             description "Structured syslog";
           }
           enum "welf" {
             description "Web Trends Extended Log Format";
           }
           enum "binary" {
             description "Binary log";
           }
           enum "protobuf" {
             description "Protobuf log";
           }
         }
       }
       list category {
         key name;
         ordered-by user;
         description "Selects the type of events that may be logged";
         junos:must "(!(\"security log stream ${stream} filter\"))";
         junos:must-message "Category is exclusive with filter";
         leaf name {
           junos:cli-feature "nokeyword";
           type enumeration {
             enum "all" {
               description "All events are logged";
             }
             enum "content-security" {
               description "Content security events are logged";
             }
             enum "fw-auth" {
               description "Fw-auth events are logged";
             }
             enum "screen" {
               description "Screen events are logged";
             }
             enum "alg" {
               description "Alg events are logged";
             }
             enum "nat" {
               description "Nat events are logged";
             }
             enum "flow" {
               description "Flow events are logged";
             }
             enum "sctp" {
               description "Sctp events are logged";
             }
             enum "gtp" {
               description "Gtp events are logged";
             }
             enum "ipsec" {
               description "Ipsec events are logged";
             }
             enum "idp" {
               description "Idp events are logged";
             }
             enum "rtlog" {
               description "Rtlog events are logged";
             }
             enum "pst-ds-lite" {
               description "Pst-ds-lite events are logged";
             }
             enum "appqos" {
               description "Appqos events are logged";
             }
             enum "secintel" {
               description "Secintel events are logged";
             }
             enum "aamw" {
               description "AAMW events are logged";
             }
             enum "sfw" {
               description "Stateful Firewall events are logged";
             }
             enum "session" {
               description "Session open and close events are logged";
             }
             enum "session-open" {
               description "Session open events are logged";
             }
             enum "session-close" {
               description "Session close events are logged";
             }
             enum "urlf" {
               description "URLF events are logged";
             }
             enum "ha" {
               description "Stateful High-Availability open and close events are logged";
             }
             enum "ha-open" {
               description "Stateful High-Availability open events are logged";
             }
             enum "ha-close" {
               description "Stateful High-Availability close events are logged";
             }
             enum "pcp" {
               description "PCP logs";
             }
             enum "dnsf" {
               description "DNSF";
             }
             enum "dns" {
               description "DNS";
             }
           }
         }
         uses apply-advanced;
       }
       list filter {
         key name;
         ordered-by user;
         description "Selects the filter to filter the logs to be logged";
         junos:must "(!(\"security log stream ${stream} category\"))";
         junos:must-message "filter is exclusive with category";
         leaf name {
           junos:cli-feature "nokeyword";
           type enumeration {
             enum "threat-attack" {
               description "Threat-attack security events are logged";
             }
           }
         }
         uses apply-advanced;
       }
       container host {
         description "Destination to send security logs to";
         junos:must "(!(\"security log stream ${stream} file\"))";
         junos:must-message "host is exclusive with file";
         junos:must "((\"security log source-address\" || (\"security log source-interface\" || (\"security log stream ${stream} source-address\" || (\"services service-set ${service-set} syslog source-interface\" || (\"services service-set ${service-set} syslog source-address\" || \"services service-set ${service-set} syslog stream ${stream} source-address\"))))))";
         junos:must-message "To configure host stream, security log source-address/source-interface must be configured";
         uses host-object;
       }
       container rate-limit {
         description "Rate-limit for security logs";
         uses apply-advanced;
         leaf rate {
           description "Log rate";
           junos:cli-feature "nokeyword";
           units "logs per second";
           type union {
             type string {
               pattern "<.*>|$.*";
             }
             type uint32 {
               range "1 .. 65535";
             }
           }
         }
       }
       container radius {
         description "Radius configuration";
         uses apply-advanced;
         container ipaddr {
           junos:must "((\"security log source-address\" || (\"security log source-interface\" || (\"security log stream ${stream} source-address\" || (\"services service-set ${service-set} syslog source-interface\" || (\"services service-set ${service-set} syslog source-address\" || \"services service-set ${service-set} syslog stream ${stream} source-address\"))))))";
           junos:must-message "source-address/source-interface is must for radius";
           description "IP address for primary and backup (backup is optional)";
           uses apply-advanced;
           leaf primary {
             description "Primary radius server IP";
             junos:must "(\"security log stream ${stream} radius secret\")";
             junos:must-message "secret must be configured for the radius stream";
             type jt:ipaddr;
           }
           leaf backup {
             description "Backup radius server IP";
             junos:must "(\"security log stream ${stream} radius ipaddr primary\")";
             junos:must-message "primary radius server must be defined";
             type jt:ipaddr;
           }
         }
         leaf port {
           description "Radius server port number (default port 1813)";
           junos:must "(\"security log stream ${stream} radius ipaddr primary\")";
           junos:must-message "primary radius server must be defined to make it as radius stream";
           type union {
             type uint16;
             type string {
               pattern "<.*>|$.*";
             }
           }
         }
         leaf secret {
           description "Radius secret";
           junos:must "(\"security log stream ${stream} radius ipaddr primary\")";
           junos:must-message "primary radius server must be defined to make it as radius stream";
           type string {
             length "0 .. 256";
           }
         }
       }
       container file {
         junos:must "(!(\"security log stream ${stream} host\"))";
         junos:must-message "file is exclusive with host";
         description "Security log file options for logs in local file";
         uses apply-advanced;
         leaf localfilename {
           description "Name of local log file";
           type string {
             length "1 .. 256";
             junos:posix-pattern "![/ %]";
             junos:pattern-message "Must not contain \'/\', % or a space";
           }
         }
         leaf size {
           description "Maximum size of local log file in megabytes";
           type union {
             type string {
               pattern "<.*>|$.*";
             }
             type uint32;
           }
         }
         leaf rotation {
           description "Maximum number of rotate files";
           default "10";
           type union {
             type string {
               pattern "<.*>|$.*";
             }
             type uint32;
           }
         }
         leaf allow-duplicates {
           description "To disable log consolidation";
           type empty;
         }
       }
       container transport {
         presence "enable transport";
         description "Set security log transport settings";
         uses apply-advanced;
         leaf tcp-connections {
           description "Set tcp connection number per-stream";
           type union {
             type string {
               pattern "<.*>|$.*";
             }
             type uint32 {
               range "1 .. 5";
             }
           }
         }
         leaf protocol {
           description "Set security log transport protocol for the device";
           type enumeration {
             enum "udp" {
               description "UDP transfer for log";
             }
             enum "tcp" {
               description "TCP transfer for log";
             }
             enum "tls" {
               description "TLS transfer for log";
             }
           }
         }
         leaf tls-profile {
           description "TLS profile";
           junos:must "(\"services ssl initiation profile $$\")";
           junos:must-message "SSL profile must be defined under [services ssl initiation profile]";
           type string;
         }
       }
       container time-format {
         description "Configure year or millisecond for syslog";
         uses time-format-object;
       }
       leaf source-address {
         description "Source ip address used when exporting security logs";
         type jt:ipaddr;
       }
     }
     container file {
       description "Security log file options for logs in binary/protobuf format";
       uses apply-advanced;
       leaf filename {
         description "Name of log file";
         type string {
           length "1 .. 256";
         }
       }
       leaf size {
         description "Maximum size of log file in megabytes";
         type union {
           type string {
             pattern "<.*>|$.*";
           }
           type uint32 {
             range "1 .. 10";
           }
         }
       }
       leaf path {
         description "Path to log files";
         type string {
           length "1 .. 256";
         }
       }
       leaf files {
         description "Maximum number of log files";
         type union {
           type string {
             pattern "<.*>|$.*";
           }
           type uint32 {
             range "2 .. 10";
           }
         }
       }
     }
     container apply {
       description "Apply settings from other features";
       uses apply-advanced;
       leaf dscp-code-point {
         description "Apply setting class-of-service host-outbound-traffic dscp-code-point";
         junos:must "(\"class-of-service host-outbound-traffic dscp-code-point\")";
         junos:must-message "class-of-service host-outbound-traffic dscp-code-point must be defined";
         type empty;
       }
     }
     container traceoptions {
       description "Security log daemon trace options";
       uses apply-advanced;
       leaf no-remote-trace {
         description "Disable remote tracing";
         junos:must "(\"system tracing\")";
         junos:must-message "'no-remote-trace' is valid only when [system tracing] is configured";
         type empty;
       }
       container file {
         junos:cli-feature "oneliner";
         description "Trace file information";
         leaf filename {
           description "Name of file in which to write trace information";
           junos:cli-feature "nokeyword";
           type string {
             length "1 .. 1024";
             junos:posix-pattern "![/ %]";
             junos:pattern-message "Must not contain \'/\', % or a space";
           }
         }
         leaf size {
           description "Maximum trace file size";
           units "bytes";
           type string;
         }
         leaf files {
           description "Maximum number of trace files";
           default "3";
           type union {
             type string {
               pattern "<.*>|$.*";
             }
             type uint32 {
               range "2 .. 1000";
             }
           }
         }
         choice world-readable-choice {
           leaf world-readable {
             description "Allow any user to read the log file";
             type empty;
           }
           leaf no-world-readable {
             description "Don't allow any user to read the log file";
             type empty;
           }
         }
         leaf match {
           description "Regular expression for lines to be logged";
           type jt:regular-expression;
         }
       }
       list flag {
         key name;
         ordered-by user;
         junos:cli-feature "oneliner";
         description "List of things to include in trace";
         leaf name {
           junos:cli-feature "nokeyword";
           type enumeration {
             enum "source" {
               description "Communication with security log forwarder";
             }
             enum "configuration" {
               description "Reading of configuration";
             }
             enum "all" {
               description "Everything";
             }
             enum "report" {
               description "Trace report";
             }
             enum "hpl" {
               description "Trace HPL logging";
             }
           }
         }
       }
     }
     list profile {
       key name;
       ordered-by user;
       description "Security log profile setting";
       max-elements 10;
       leaf name {
         description "Name of security log profile";
         junos:cli-feature "nokeyword";
         type string {
           length "1 .. 63";
           junos:posix-pattern "^[[:alnum:].-]+$";
           junos:pattern-message "Must be a string consisting of letters, numbers, dashes";
         }
       }
       uses apply-advanced;
       list stream-name {
         key name;
         ordered-by user;
         description "Use which stream ";
         junos:must "((\".. category\" || \".. template\"))";
         junos:must-message "To send logs must define category or template";
         max-elements 4;
         leaf name {
           description "Name of the stream";
           junos:cli-feature "nokeyword";
           junos:must "((\"security log stream $$\" || \"services service-set ${service-set} syslog stream $$\"))";
           junos:must-message "stream must be defined under [security log stream] for SRX or under [services service-set <> syslog stream]";
           type string;
         }
         uses apply-advanced;
       }
       container category {
         presence "enable category";
         junos:must "(!(\" .. template\"))";
         junos:must-message "Cannot configure category and template for the same profile";
         description "Selects the category of events for the profile";
         uses apply-advanced;
         container session {
           presence "enable session";
           description "Select session category";
           uses apply-advanced;
           list field-extra-name {
             key name;
             description "Select the extra Fields, only apply to sd-syslog and syslog formt";
             leaf name {
               description "The name of the extra field";
               junos:cli-feature "nokeyword";
               type enumeration {
                 enum "sd-id" {
                   description "Add SD-ID field, only apply to sd-syslog and syslog formt";
                 }
                 enum "hostname" {
                   description "Add hostname field, only apply to sd-syslog and syslog formt";
                 }
                 enum "timestamp" {
                   description "Add timestamp field, only apply to sd-syslog and syslog formt";
                 }
               }
             }
             uses apply-advanced;
           }
           list field-name {
             key name;
             ordered-by user;
             description "Select the fields by order";
             leaf name {
               description "The name of the field";
               junos:cli-feature "nokeyword";
               type string;
             }
             uses apply-advanced;
           }
         }
         container webfilter {
           presence "enable webfilter";
           description "Select webfilter category";
           uses apply-advanced;
           list field-extra-name {
             key name;
             description "Select the extra Fields, only apply to sd-syslog and syslog formt";
             leaf name {
               description "The name of the extra field";
               junos:cli-feature "nokeyword";
               type enumeration {
                 enum "sd-id" {
                   description "Add SD-ID field, only apply to sd-syslog and syslog formt";
                 }
                 enum "hostname" {
                   description "Add hostname field, only apply to sd-syslog and syslog formt";
                 }
                 enum "timestamp" {
                   description "Add timestamp field, only apply to sd-syslog and syslog formt";
                 }
               }
             }
             uses apply-advanced;
           }
           list field-name {
             key name;
             ordered-by user;
             description "Select the fields by order";
             leaf name {
               description "The name of the field";
               junos:cli-feature "nokeyword";
               type string;
             }
             uses apply-advanced;
           }
         }
         container antivirus {
           presence "enable antivirus";
           description "Select antivirus category";
           uses apply-advanced;
           list field-extra-name {
             key name;
             description "Select the extra Fields, only apply to sd-syslog and syslog formt";
             leaf name {
               description "The name of the extra field";
               junos:cli-feature "nokeyword";
               type enumeration {
                 enum "sd-id" {
                   description "Add SD-ID field, only apply to sd-syslog and syslog formt";
                 }
                 enum "hostname" {
                   description "Add hostname field, only apply to sd-syslog and syslog formt";
                 }
                 enum "timestamp" {
                   description "Add timestamp field, only apply to sd-syslog and syslog formt";
                 }
               }
             }
             uses apply-advanced;
           }
           list field-name {
             key name;
             ordered-by user;
             description "Select the fields by order";
             leaf name {
               description "The name of the field";
               junos:cli-feature "nokeyword";
               type string;
             }
             uses apply-advanced;
           }
         }
         container content-filter {
           presence "enable content-filter";
           description "Select content-filter category";
           uses apply-advanced;
           list field-extra-name {
             key name;
             description "Select the extra Fields, only apply to sd-syslog and syslog formt";
             leaf name {
               description "The name of the extra field";
               junos:cli-feature "nokeyword";
               type enumeration {
                 enum "sd-id" {
                   description "Add SD-ID field, only apply to sd-syslog and syslog formt";
                 }
                 enum "hostname" {
                   description "Add hostname field, only apply to sd-syslog and syslog formt";
                 }
                 enum "timestamp" {
                   description "Add timestamp field, only apply to sd-syslog and syslog formt";
                 }
               }
             }
             uses apply-advanced;
           }
           list field-name {
             key name;
             ordered-by user;
             description "Select the fields by order";
             leaf name {
               description "The name of the field";
               junos:cli-feature "nokeyword";
               type string;
             }
             uses apply-advanced;
           }
         }
         container antispam {
           presence "enable antispam";
           description "Select antispam category";
           uses apply-advanced;
           list field-extra-name {
             key name;
             description "Select the extra Fields, only apply to sd-syslog and syslog formt";
             leaf name {
               description "The name of the extra field";
               junos:cli-feature "nokeyword";
               type enumeration {
                 enum "sd-id" {
                   description "Add SD-ID field, only apply to sd-syslog and syslog formt";
                 }
                 enum "hostname" {
                   description "Add hostname field, only apply to sd-syslog and syslog formt";
                 }
                 enum "timestamp" {
                   description "Add timestamp field, only apply to sd-syslog and syslog formt";
                 }
               }
             }
             uses apply-advanced;
           }
           list field-name {
             key name;
             ordered-by user;
             description "Select the fields by order";
             leaf name {
               description "The name of the field";
               junos:cli-feature "nokeyword";
               type string;
             }
             uses apply-advanced;
           }
         }
         container idp {
           presence "enable idp";
           description "Select idp category";
           uses apply-advanced;
           list field-extra-name {
             key name;
             description "Select the extra Fields, only apply to sd-syslog and syslog formt";
             leaf name {
               description "The name of the extra field";
               junos:cli-feature "nokeyword";
               type enumeration {
                 enum "sd-id" {
                   description "Add SD-ID field, only apply to sd-syslog and syslog formt";
                 }
                 enum "hostname" {
                   description "Add hostname field, only apply to sd-syslog and syslog formt";
                 }
                 enum "timestamp" {
                   description "Add timestamp field, only apply to sd-syslog and syslog formt";
                 }
               }
             }
             uses apply-advanced;
           }
           list field-name {
             key name;
             ordered-by user;
             description "Select the fields by order";
             leaf name {
               description "The name of the field";
               junos:cli-feature "nokeyword";
               type string;
             }
             uses apply-advanced;
           }
         }
         container secintel {
           presence "enable secintel";
           description "Select secintel category";
           uses apply-advanced;
           list field-extra-name {
             key name;
             description "Select the extra Fields, only apply to sd-syslog and syslog formt";
             leaf name {
               description "The name of the extra field";
               junos:cli-feature "nokeyword";
               type enumeration {
                 enum "sd-id" {
                   description "Add SD-ID field, only apply to sd-syslog and syslog formt";
                 }
                 enum "hostname" {
                   description "Add hostname field, only apply to sd-syslog and syslog formt";
                 }
                 enum "timestamp" {
                   description "Add timestamp field, only apply to sd-syslog and syslog formt";
                 }
               }
             }
             uses apply-advanced;
           }
           list field-name {
             key name;
             ordered-by user;
             description "Select the fields by order";
             leaf name {
               description "The name of the field";
               junos:cli-feature "nokeyword";
               type string;
             }
             uses apply-advanced;
           }
         }
         container aamw {
           presence "enable aamw";
           description "Select aamw category";
           uses apply-advanced;
           list field-extra-name {
             key name;
             description "Select the extra Fields, only apply to sd-syslog and syslog formt";
             leaf name {
               description "The name of the extra field";
               junos:cli-feature "nokeyword";
               type enumeration {
                 enum "sd-id" {
                   description "Add SD-ID field, only apply to sd-syslog and syslog formt";
                 }
                 enum "hostname" {
                   description "Add hostname field, only apply to sd-syslog and syslog formt";
                 }
                 enum "timestamp" {
                   description "Add timestamp field, only apply to sd-syslog and syslog formt";
                 }
               }
             }
             uses apply-advanced;
           }
           list field-name {
             key name;
             ordered-by user;
             description "Select the fields by order";
             leaf name {
               description "The name of the field";
               junos:cli-feature "nokeyword";
               type string;
             }
             uses apply-advanced;
           }
         }
         container ssl-proxy {
           presence "enable ssl-proxy";
           description "Select ssl-proxy category";
           uses apply-advanced;
           list field-extra-name {
             key name;
             description "Select the extra Fields, only apply to sd-syslog and syslog formt";
             leaf name {
               description "The name of the extra field";
               junos:cli-feature "nokeyword";
               type enumeration {
                 enum "sd-id" {
                   description "Add SD-ID field, only apply to sd-syslog and syslog formt";
                 }
                 enum "hostname" {
                   description "Add hostname field, only apply to sd-syslog and syslog formt";
                 }
                 enum "timestamp" {
                   description "Add timestamp field, only apply to sd-syslog and syslog formt";
                 }
               }
             }
             uses apply-advanced;
           }
           list field-name {
             key name;
             ordered-by user;
             description "Select the fields by order";
             leaf name {
               description "The name of the field";
               junos:cli-feature "nokeyword";
               type string;
             }
             uses apply-advanced;
           }
         }
         container apptrack {
           presence "enable apptrack";
           description "Select apptrack category";
           uses apply-advanced;
           list field-extra-name {
             key name;
             description "Select the extra Fields, only apply to sd-syslog and syslog formt";
             leaf name {
               description "The name of the extra field";
               junos:cli-feature "nokeyword";
               type enumeration {
                 enum "sd-id" {
                   description "Add SD-ID field, only apply to sd-syslog and syslog formt";
                 }
                 enum "hostname" {
                   description "Add hostname field, only apply to sd-syslog and syslog formt";
                 }
                 enum "timestamp" {
                   description "Add timestamp field, only apply to sd-syslog and syslog formt";
                 }
               }
             }
             uses apply-advanced;
           }
           list field-name {
             key name;
             ordered-by user;
             description "Select the fields by order";
             leaf name {
               description "The name of the field";
               junos:cli-feature "nokeyword";
               type string;
             }
             uses apply-advanced;
           }
         }
       }
       container default-profile {
         presence "enable default-profile";
         uses apply-advanced;
         leaf activate {
           description "Set this profile as default profile";
           type empty;
         }
       }
       container template {
         presence "enable template";
         junos:must "(!(\" .. category\"))";
         junos:must-message "Cannot configure category and template for the same profile";
         description "Select the template for the profile";
         uses apply-advanced;
         choice template-id {
           case case_1 {
             leaf traditional-firewall {
               description "Traditional-firewall";
               type empty;
             }
           }
           case case_2 {
             leaf unified-ngfw {
               description "Unified-ngfw";
               type empty;
             }
           }
           case case_3 {
             leaf sd-wan {
               description "Sd-wan";
               type empty;
             }
           }
         }
       }
     }
   }
   grouping host-object {
     uses apply-advanced;
     leaf ipaddr {
       description "IP address/Host name";
       junos:cli-feature "nokeyword";
       type string {
         length "1 .. 256";
         junos:posix-pattern "^[[:alnum:]._:-]+$|^\\\\*$";
         junos:pattern-message "Must be a valid DNS name";
       }
     }
     leaf port {
       description "Host port number";
       type union {
         type uint16;
         type string {
           pattern "<.*>|$.*";
         }
       }
     }
     leaf routing-instance {
       description "Routing-instance name";
       junos:must "(((\"security\" && \"routing-instances $$ instance-type virtual-router\") || \"services\"))";
       junos:must-message "Virtual router must be defined under [routing-instances]";
       junos:must "(\"routing-instances $$\")";
       junos:must-message "Routing-instance must be defined";
       type string;
     }
     leaf log-tag {
       description "Tag included in logs to this host";
       junos:must "(!(\"services service-set ${service-set} syslog local-log-tag\"))";
       junos:must-message "The local-log-tag and host log-tag cannot co-exist in a service-set.";
       type string {
         junos:posix-pattern "![ =:]{1,15}";
         junos:pattern-message "Must be a string of 15 characters or less";
       }
     }
     leaf prefer-ipv6-dns {
       description "Use IPv6 from DNS when available instead of IPv4";
       type empty;
     }
   }
   grouping mac_list {
     description "MAC address";
     leaf name {
       junos:cli-feature "nokeyword";
       type jt:mac-addr;
     }
     uses apply-advanced;
     container policer {
       description "MAC policing";
       uses apply-advanced;
       leaf input {
         description "Name of policer applied to received packets";
         type string;
       }
       leaf output {
         description "Name of policer applied to transmitted packets";
         type string;
       }
     }
   }
   grouping macro-data-type {
     junos:cli-feature "nokeyword";
     junos:cli-feature "homogeneous";
     junos:cli-feature "oneliner";
     leaf name {
       description "Keyword part of the keyword-value pair";
       junos:cli-feature "nokeyword";
       type string;
     }
     leaf value {
       description "Value part of the keyword-value pair";
       junos:cli-feature "nokeyword";
       type string;
     }
   }
   grouping mpls_ifd_options {
     uses apply-advanced;
     container pop-all-labels {
       presence "enable pop-all-labels";
       junos:cli-feature "oneliner-plus";
       description "Pop all MPLS labels off incoming packets";
       uses apply-advanced;
       leaf-list required-depth {
         ordered-by user;
         description "Required label depth of packet to pop all labels";
         type enumeration {
           enum "all" {
             description "Takes effect only in Stoli based FPCs, in all other FPCs equivalent to '[1 2]'";
           }
           enum "1" {
             description "Required label depth of packet to pop labels";
           }
           enum "2" {
             description "Required label depth of packet to pop labels";
           }
         }
       }
     }
   }
   grouping och-attributes {
     description "Optical channel configuration attributes";
     uses apply-advanced;
     leaf rate {
       description "Data rate of the OCH payload";
       type enumeration {
         enum "100g" {
           description "100Gbit OCH data rate";
         }
       }
     }
     leaf modulation {
       description "Optical modulation format";
       type enumeration {
         enum "qpsk" {
           description "QPSK Modulation Format";
         }
       }
     }
     leaf encoding {
       description "Optical encoding";
       type enumeration {
         enum "differential" {
           description "Differential encoding";
         }
       }
     }
     choice channel-number {
       case case_1 {
         leaf wavelength {
           description "Optical channel wavelength in nanometers";
           type enumeration {
             enum "1568.77" {
               description "1568.77 nm/191.1003 THz 50/100Ghz spacing";
             }
             enum "1568.36" {
               description "1568.36 nm/191.150000 THz 3.125/6.25/12.5/50GHz spacing";
             }
             enum "1568.34" {
               description "1568.34 nm/191.153125 THz 3.125GHz spacing";
             }
             enum "1568.31" {
               description "1568.31 nm/191.156250 THz 3.125/6.25GHz spacing";
             }
             enum "1568.29" {
               description "1568.29 nm/191.159375 THz 3.125GHz spacing";
             }
             enum "1568.26" {
               description "1568.26 nm/191.162500 THz 3.125/6.25/12.5GHz spacing";
             }
             enum "1568.23" {
               description "1568.23 nm/191.165625 THz 3.125GHz spacing";
             }
             enum "1568.21" {
               description "1568.21 nm/191.168750 THz 3.125/6.25GHz spacing";
             }
             enum "1568.18" {
               description "1568.18 nm/191.171875 THz 3.125GHz spacing";
             }
             enum "1568.16" {
               description "1568.16 nm/191.175000 THz 3.125/6.25/12.5/75GHz spacing";
             }
             enum "1568.13" {
               description "1568.13 nm/191.178125 THz 3.125GHz spacing";
             }
             enum "1568.11" {
               description "1568.11 nm/191.181250 THz 3.125/6.25GHz spacing";
             }
             enum "1568.08" {
               description "1568.08 nm/191.184375 THz 3.125GHz spacing";
             }
             enum "1568.05" {
               description "1568.05 nm/191.187500 THz 3.125/6.25/12.5GHz spacing";
             }
             enum "1568.03" {
               description "1568.03 nm/191.190625 THz 3.125GHz spacing";
             }
             enum "1568.00" {
               description "1568.00 nm/191.193750 THz 3.125/6.25GHz spacing";
             }
             enum "1567.98" {
               description "1567.98 nm/191.196875 THz 3.125GHz spacing";
             }
             enum "1567.95" {
               description "1567.95 nm/191.200000 THz 3.125/6.25/12.5/100GHz spacing";
             }
             enum "1567.93" {
               description "1567.93 nm/191.203125 THz 3.125GHz spacing";
             }
             enum "1567.90" {
               description "1567.90 nm/191.206250 THz 3.125/6.25GHz spacing";
             }
             enum "1567.88" {
               description "1567.88 nm/191.209375 THz 3.125GHz spacing";
             }
             enum "1567.85" {
               description "1567.85 nm/191.212500 THz 3.125/6.25/12.5GHz spacing";
             }
             enum "1567.82" {
               description "1567.82 nm/191.215625 THz 3.125GHz spacing";
             }
             enum "1567.80" {
               description "1567.80 nm/191.218750 THz 3.125/6.25GHz spacing";
             }
             enum "1567.77" {
               description "1567.77 nm/191.221875 THz 3.125GHz spacing";
             }
             enum "1567.75" {
               description "1567.75 nm/191.225000 THz 3.125/6.25/12.5GHz spacing";
             }
             enum "1567.72" {
               description "1567.72 nm/191.228125 THz 3.125GHz spacing";
             }
             enum "1567.70" {
               description "1567.70 nm/191.231250 THz 3.125/6.25GHz spacing";
             }
             enum "1567.67" {
               description "1567.67 nm/191.234375 THz 3.125GHz spacing";
             }
             enum "1567.64" {
               description "1567.64 nm/191.237500 THz 3.125/6.25/12.5GHz spacing";
             }
             enum "1567.62" {
               description "1567.62 nm/191.240625 THz 3.125GHz spacing";
             }
             enum "1567.59" {
               description "1567.59 nm/191.243750 THz 3.125/6.25GHz spacing";
             }
             enum "1567.57" {
               description "1567.57 nm/191.246875 THz 3.125GHz spacing";
             }
             enum "1567.54" {
               description "1567.54 nm/191.250000 THz 3.125/6.25/12.5/50/75GHz spacing";
             }
             enum "1567.52" {
               description "1567.52 nm/191.253125 THz 3.125GHz spacing";
             }
             enum "1567.49" {
               description "1567.49 nm/191.256250 THz 3.125/6.25GHz spacing";
             }
             enum "1567.47" {
               description "1567.47 nm/191.259375 THz 3.125GHz spacing";
             }
             enum "1567.44" {
               description "1567.44 nm/191.262500 THz 3.125/6.25/12.5GHz spacing";
             }
             enum "1567.41" {
               description "1567.41 nm/191.265625 THz 3.125GHz spacing";
             }
             enum "1567.39" {
               description "1567.39 nm/191.268750 THz 3.125/6.25GHz spacing";
             }
             enum "1567.36" {
               description "1567.36 nm/191.271875 THz 3.125GHz spacing";
             }
             enum "1567.34" {
               description "1567.34 nm/191.275000 THz 3.125/6.25/12.5GHz spacing";
             }
             enum "1567.31" {
               description "1567.31 nm/191.278125 THz 3.125GHz spacing";
             }
             enum "1567.29" {
               description "1567.29 nm/191.281250 THz 3.125/6.25GHz spacing";
             }
             enum "1567.26" {
               description "1567.26 nm/191.284375 THz 3.125GHz spacing";
             }
             enum "1567.23" {
               description "1567.23 nm/191.287500 THz 3.125/6.25/12.5GHz spacing";
             }
             enum "1567.21" {
               description "1567.21 nm/191.290625 THz 3.125GHz spacing";
             }
             enum "1567.18" {
               description "1567.18 nm/191.293750 THz 3.125/6.25GHz spacing";
             }
             enum "1567.16" {
               description "1567.16 nm/191.296875 THz 3.125GHz spacing";
             }
             enum "1567.13" {
               description "1567.13 nm/191.300000 THz 3.125/6.25/12.5/100GHz spacing";
             }
             enum "1567.11" {
               description "1567.11 nm/191.303125 THz 3.125GHz spacing";
             }
             enum "1567.08" {
               description "1567.08 nm/191.306250 THz 3.125/6.25GHz spacing";
             }
             enum "1567.06" {
               description "1567.06 nm/191.309375 THz 3.125GHz spacing";
             }
             enum "1567.03" {
               description "1567.03 nm/191.312500 THz 3.125/6.25/12.5GHz spacing";
             }
             enum "1567.00" {
               description "1567.00 nm/191.315625 THz 3.125GHz spacing";
             }
             enum "1566.98" {
               description "1566.98 nm/191.318750 THz 3.125/6.25GHz spacing";
             }
             enum "1566.95" {
               description "1566.95 nm/191.321875 THz 3.125GHz spacing";
             }
             enum "1566.93" {
               description "1566.93 nm/191.325000 THz 3.125/6.25/12.5/75GHz spacing";
             }
             enum "1566.90" {
               description "1566.90 nm/191.328125 THz 3.125GHz spacing";
             }
             enum "1566.88" {
               description "1566.88 nm/191.331250 THz 3.125/6.25GHz spacing";
             }
             enum "1566.85" {
               description "1566.85 nm/191.334375 THz 3.125GHz spacing";
             }
             enum "1566.83" {
               description "1566.83 nm/191.337500 THz 3.125/6.25/12.5GHz spacing";
             }
             enum "1566.80" {
               description "1566.80 nm/191.340625 THz 3.125GHz spacing";
             }
             enum "1566.77" {
               description "1566.77 nm/191.343750 THz 3.125/6.25GHz spacing";
             }
             enum "1566.75" {
               description "1566.75 nm/191.346875 THz 3.125GHz spacing";
             }
             enum "1566.72" {
               description "1566.72 nm/191.350000 THz 3.125/6.25/12.5/50GHz spacing";
             }
             enum "1566.70" {
               description "1566.70 nm/191.353125 THz 3.125GHz spacing";
             }
             enum "1566.67" {
               description "1566.67 nm/191.356250 THz 3.125/6.25GHz spacing";
             }
             enum "1566.65" {
               description "1566.65 nm/191.359375 THz 3.125GHz spacing";
             }
             enum "1566.62" {
               description "1566.62 nm/191.362500 THz 3.125/6.25/12.5GHz spacing";
             }
             enum "1566.60" {
               description "1566.60 nm/191.365625 THz 3.125GHz spacing";
             }
             enum "1566.57" {
               description "1566.57 nm/191.368750 THz 3.125/6.25GHz spacing";
             }
             enum "1566.54" {
               description "1566.54 nm/191.371875 THz 3.125GHz spacing";
             }
             enum "1566.52" {
               description "1566.52 nm/191.375000 THz 3.125/6.25/12.5GHz spacing";
             }
             enum "1566.49" {
               description "1566.49 nm/191.378125 THz 3.125GHz spacing";
             }
             enum "1566.47" {
               description "1566.47 nm/191.381250 THz 3.125/6.25GHz spacing";
             }
             enum "1566.44" {
               description "1566.44 nm/191.384375 THz 3.125GHz spacing";
             }
             enum "1566.42" {
               description "1566.42 nm/191.387500 THz 3.125/6.25/12.5GHz spacing";
             }
             enum "1566.39" {
               description "1566.39 nm/191.390625 THz 3.125GHz spacing";
             }
             enum "1566.36" {
               description "1566.36 nm/191.393750 THz 3.125/6.25GHz spacing";
             }
             enum "1566.34" {
               description "1566.34 nm/191.396875 THz 3.125GHz spacing";
             }
             enum "1566.31" {
               description "1566.31 nm/191.400000 THz 3.125/6.25/12.5/50/75/100GHz spacing";
             }
             enum "1566.29" {
               description "1566.29 nm/191.403125 THz 3.125GHz spacing";
             }
             enum "1566.26" {
               description "1566.26 nm/191.406250 THz 3.125/6.25GHz spacing";
             }
             enum "1566.24" {
               description "1566.24 nm/191.409375 THz 3.125GHz spacing";
             }
             enum "1566.21" {
               description "1566.21 nm/191.412500 THz 3.125/6.25/12.5GHz spacing";
             }
             enum "1566.19" {
               description "1566.19 nm/191.415625 THz 3.125GHz spacing";
             }
             enum "1566.16" {
               description "1566.16 nm/191.418750 THz 3.125/6.25GHz spacing";
             }
             enum "1566.13" {
               description "1566.13 nm/191.421875 THz 3.125GHz spacing";
             }
             enum "1566.11" {
               description "1566.11 nm/191.425000 THz 3.125/6.25/12.5GHz spacing";
             }
             enum "1566.08" {
               description "1566.08 nm/191.428125 THz 3.125GHz spacing";
             }
             enum "1566.06" {
               description "1566.06 nm/191.431250 THz 3.125/6.25GHz spacing";
             }
             enum "1566.03" {
               description "1566.03 nm/191.434375 THz 3.125GHz spacing";
             }
             enum "1566.01" {
               description "1566.01 nm/191.437500 THz 3.125/6.25/12.5GHz spacing";
             }
             enum "1565.98" {
               description "1565.98 nm/191.440625 THz 3.125GHz spacing";
             }
             enum "1565.96" {
               description "1565.96 nm/191.443750 THz 3.125/6.25GHz spacing";
             }
             enum "1565.93" {
               description "1565.93 nm/191.446875 THz 3.125GHz spacing";
             }
             enum "1565.90" {
               description "1565.90 nm/191.450000 THz 3.125/6.25/12.5/50GHz spacing";
             }
             enum "1565.88" {
               description "1565.88 nm/191.453125 THz 3.125GHz spacing";
             }
             enum "1565.85" {
               description "1565.85 nm/191.456250 THz 3.125/6.25GHz spacing";
             }
             enum "1565.83" {
               description "1565.83 nm/191.459375 THz 3.125GHz spacing";
             }
             enum "1565.80" {
               description "1565.80 nm/191.462500 THz 3.125/6.25/12.5GHz spacing";
             }
             enum "1565.78" {
               description "1565.78 nm/191.465625 THz 3.125GHz spacing";
             }
             enum "1565.75" {
               description "1565.75 nm/191.468750 THz 3.125/6.25GHz spacing";
             }
             enum "1565.73" {
               description "1565.73 nm/191.471875 THz 3.125GHz spacing";
             }
             enum "1565.70" {
               description "1565.70 nm/191.475000 THz 3.125/6.25/12.5/75GHz spacing";
             }
             enum "1565.67" {
               description "1565.67 nm/191.478125 THz 3.125GHz spacing";
             }
             enum "1565.65" {
               description "1565.65 nm/191.481250 THz 3.125/6.25GHz spacing";
             }
             enum "1565.62" {
               description "1565.62 nm/191.484375 THz 3.125GHz spacing";
             }
             enum "1565.60" {
               description "1565.60 nm/191.487500 THz 3.125/6.25/12.5GHz spacing";
             }
             enum "1565.57" {
               description "1565.57 nm/191.490625 THz 3.125GHz spacing";
             }
             enum "1565.55" {
               description "1565.55 nm/191.493750 THz 3.125/6.25GHz spacing";
             }
             enum "1565.52" {
               description "1565.52 nm/191.496875 THz 3.125GHz spacing";
             }
             enum "1565.50" {
               description "1565.50 nm/191.500000 THz 3.125/6.25/12.5/100GHz spacing";
             }
             enum "1565.47" {
               description "1565.47 nm/191.503125 THz 3.125GHz spacing";
             }
             enum "1565.44" {
               description "1565.44 nm/191.506250 THz 3.125/6.25GHz spacing";
             }
             enum "1565.42" {
               description "1565.42 nm/191.509375 THz 3.125GHz spacing";
             }
             enum "1565.39" {
               description "1565.39 nm/191.512500 THz 3.125/6.25/12.5GHz spacing";
             }
             enum "1565.37" {
               description "1565.37 nm/191.515625 THz 3.125GHz spacing";
             }
             enum "1565.34" {
               description "1565.34 nm/191.518750 THz 3.125/6.25GHz spacing";
             }
             enum "1565.32" {
               description "1565.32 nm/191.521875 THz 3.125GHz spacing";
             }
             enum "1565.29" {
               description "1565.29 nm/191.525000 THz 3.125/6.25/12.5GHz spacing";
             }
             enum "1565.27" {
               description "1565.27 nm/191.528125 THz 3.125GHz spacing";
             }
             enum "1565.24" {
               description "1565.24 nm/191.531250 THz 3.125/6.25GHz spacing";
             }
             enum "1565.21" {
               description "1565.21 nm/191.534375 THz 3.125GHz spacing";
             }
             enum "1565.19" {
               description "1565.19 nm/191.537500 THz 3.125/6.25/12.5GHz spacing";
             }
             enum "1565.16" {
               description "1565.16 nm/191.540625 THz 3.125GHz spacing";
             }
             enum "1565.14" {
               description "1565.14 nm/191.543750 THz 3.125/6.25GHz spacing";
             }
             enum "1565.11" {
               description "1565.11 nm/191.546875 THz 3.125GHz spacing";
             }
             enum "1565.09" {
               description "1565.09 nm/191.550000 THz 3.125/6.25/12.5/50/75GHz spacing";
             }
             enum "1565.06" {
               description "1565.06 nm/191.553125 THz 3.125GHz spacing";
             }
             enum "1565.04" {
               description "1565.04 nm/191.556250 THz 3.125/6.25GHz spacing";
             }
             enum "1565.01" {
               description "1565.01 nm/191.559375 THz 3.125GHz spacing";
             }
             enum "1564.99" {
               description "1564.99 nm/191.562500 THz 3.125/6.25/12.5GHz spacing";
             }
             enum "1564.96" {
               description "1564.96 nm/191.565625 THz 3.125GHz spacing";
             }
             enum "1564.93" {
               description "1564.93 nm/191.568750 THz 3.125/6.25GHz spacing";
             }
             enum "1564.91" {
               description "1564.91 nm/191.571875 THz 3.125GHz spacing";
             }
             enum "1564.88" {
               description "1564.88 nm/191.575000 THz 3.125/6.25/12.5GHz spacing";
             }
             enum "1564.86" {
               description "1564.86 nm/191.578125 THz 3.125GHz spacing";
             }
             enum "1564.83" {
               description "1564.83 nm/191.581250 THz 3.125/6.25GHz spacing";
             }
             enum "1564.81" {
               description "1564.81 nm/191.584375 THz 3.125GHz spacing";
             }
             enum "1564.78" {
               description "1564.78 nm/191.587500 THz 3.125/6.25/12.5GHz spacing";
             }
             enum "1564.76" {
               description "1564.76 nm/191.590625 THz 3.125GHz spacing";
             }
             enum "1564.73" {
               description "1564.73 nm/191.593750 THz 3.125/6.25GHz spacing";
             }
             enum "1564.70" {
               description "1564.70 nm/191.596875 THz 3.125GHz spacing";
             }
             enum "1564.68" {
               description "1564.68 nm/191.600000 THz 3.125/6.25/12.5/100GHz spacing";
             }
             enum "1564.65" {
               description "1564.65 nm/191.603125 THz 3.125GHz spacing";
             }
             enum "1564.63" {
               description "1564.63 nm/191.606250 THz 3.125/6.25GHz spacing";
             }
             enum "1564.60" {
               description "1564.60 nm/191.609375 THz 3.125GHz spacing";
             }
             enum "1564.58" {
               description "1564.58 nm/191.612500 THz 3.125/6.25/12.5GHz spacing";
             }
             enum "1564.55" {
               description "1564.55 nm/191.615625 THz 3.125GHz spacing";
             }
             enum "1564.53" {
               description "1564.53 nm/191.618750 THz 3.125/6.25GHz spacing";
             }
             enum "1564.50" {
               description "1564.50 nm/191.621875 THz 3.125GHz spacing";
             }
             enum "1564.47" {
               description "1564.47 nm/191.625000 THz 3.125/6.25/12.5/75GHz spacing";
             }
             enum "1564.45" {
               description "1564.45 nm/191.628125 THz 3.125GHz spacing";
             }
             enum "1564.42" {
               description "1564.42 nm/191.631250 THz 3.125/6.25GHz spacing";
             }
             enum "1564.40" {
               description "1564.40 nm/191.634375 THz 3.125GHz spacing";
             }
             enum "1564.37" {
               description "1564.37 nm/191.637500 THz 3.125/6.25/12.5GHz spacing";
             }
             enum "1564.35" {
               description "1564.35 nm/191.640625 THz 3.125GHz spacing";
             }
             enum "1564.32" {
               description "1564.32 nm/191.643750 THz 3.125/6.25GHz spacing";
             }
             enum "1564.30" {
               description "1564.30 nm/191.646875 THz 3.125GHz spacing";
             }
             enum "1564.27" {
               description "1564.27 nm/191.650000 THz 3.125/6.25/12.5/50GHz spacing";
             }
             enum "1564.25" {
               description "1564.25 nm/191.653125 THz 3.125GHz spacing";
             }
             enum "1564.22" {
               description "1564.22 nm/191.656250 THz 3.125/6.25GHz spacing";
             }
             enum "1564.19" {
               description "1564.19 nm/191.659375 THz 3.125GHz spacing";
             }
             enum "1564.17" {
               description "1564.17 nm/191.662500 THz 3.125/6.25/12.5GHz spacing";
             }
             enum "1564.14" {
               description "1564.14 nm/191.665625 THz 3.125GHz spacing";
             }
             enum "1564.12" {
               description "1564.12 nm/191.668750 THz 3.125/6.25GHz spacing";
             }
             enum "1564.09" {
               description "1564.09 nm/191.671875 THz 3.125GHz spacing";
             }
             enum "1564.07" {
               description "1564.07 nm/191.675000 THz 3.125/6.25/12.5GHz spacing";
             }
             enum "1564.04" {
               description "1564.04 nm/191.678125 THz 3.125GHz spacing";
             }
             enum "1564.02" {
               description "1564.02 nm/191.681250 THz 3.125/6.25GHz spacing";
             }
             enum "1563.99" {
               description "1563.99 nm/191.684375 THz 3.125GHz spacing";
             }
             enum "1563.96" {
               description "1563.96 nm/191.687500 THz 3.125/6.25/12.5GHz spacing";
             }
             enum "1563.94" {
               description "1563.94 nm/191.690625 THz 3.125GHz spacing";
             }
             enum "1563.91" {
               description "1563.91 nm/191.693750 THz 3.125/6.25GHz spacing";
             }
             enum "1563.89" {
               description "1563.89 nm/191.696875 THz 3.125GHz spacing";
             }
             enum "1563.86" {
               description "1563.86 nm/191.700000 THz 3.125/6.25/12.5/50/75/100GHz spacing";
             }
             enum "1563.84" {
               description "1563.84 nm/191.703125 THz 3.125GHz spacing";
             }
             enum "1563.81" {
               description "1563.81 nm/191.706250 THz 3.125/6.25GHz spacing";
             }
             enum "1563.79" {
               description "1563.79 nm/191.709375 THz 3.125GHz spacing";
             }
             enum "1563.76" {
               description "1563.76 nm/191.712500 THz 3.125/6.25/12.5GHz spacing";
             }
             enum "1563.74" {
               description "1563.74 nm/191.715625 THz 3.125GHz spacing";
             }
             enum "1563.71" {
               description "1563.71 nm/191.718750 THz 3.125/6.25GHz spacing";
             }
             enum "1563.68" {
               description "1563.68 nm/191.721875 THz 3.125GHz spacing";
             }
             enum "1563.66" {
               description "1563.66 nm/191.725000 THz 3.125/6.25/12.5GHz spacing";
             }
             enum "1563.63" {
               description "1563.63 nm/191.728125 THz 3.125GHz spacing";
             }
             enum "1563.61" {
               description "1563.61 nm/191.731250 THz 3.125/6.25GHz spacing";
             }
             enum "1563.58" {
               description "1563.58 nm/191.734375 THz 3.125GHz spacing";
             }
             enum "1563.56" {
               description "1563.56 nm/191.737500 THz 3.125/6.25/12.5GHz spacing";
             }
             enum "1563.53" {
               description "1563.53 nm/191.740625 THz 3.125GHz spacing";
             }
             enum "1563.51" {
               description "1563.51 nm/191.743750 THz 3.125/6.25GHz spacing";
             }
             enum "1563.48" {
               description "1563.48 nm/191.746875 THz 3.125GHz spacing";
             }
             enum "1563.45" {
               description "1563.45 nm/191.750000 THz 3.125/6.25/12.5/50GHz spacing";
             }
             enum "1563.43" {
               description "1563.43 nm/191.753125 THz 3.125GHz spacing";
             }
             enum "1563.40" {
               description "1563.40 nm/191.756250 THz 3.125/6.25GHz spacing";
             }
             enum "1563.38" {
               description "1563.38 nm/191.759375 THz 3.125GHz spacing";
             }
             enum "1563.35" {
               description "1563.35 nm/191.762500 THz 3.125/6.25/12.5GHz spacing";
             }
             enum "1563.33" {
               description "1563.33 nm/191.765625 THz 3.125GHz spacing";
             }
             enum "1563.30" {
               description "1563.30 nm/191.768750 THz 3.125/6.25GHz spacing";
             }
             enum "1563.28" {
               description "1563.28 nm/191.771875 THz 3.125GHz spacing";
             }
             enum "1563.25" {
               description "1563.25 nm/191.775000 THz 3.125/6.25/12.5/75GHz spacing";
             }
             enum "1563.23" {
               description "1563.23 nm/191.778125 THz 3.125GHz spacing";
             }
             enum "1563.20" {
               description "1563.20 nm/191.781250 THz 3.125/6.25GHz spacing";
             }
             enum "1563.17" {
               description "1563.17 nm/191.784375 THz 3.125GHz spacing";
             }
             enum "1563.15" {
               description "1563.15 nm/191.787500 THz 3.125/6.25/12.5GHz spacing";
             }
             enum "1563.12" {
               description "1563.12 nm/191.790625 THz 3.125GHz spacing";
             }
             enum "1563.10" {
               description "1563.10 nm/191.793750 THz 3.125/6.25GHz spacing";
             }
             enum "1563.07" {
               description "1563.07 nm/191.796875 THz 3.125GHz spacing";
             }
             enum "1563.05" {
               description "1563.05 nm/191.800000 THz 3.125/6.25/12.5/100GHz spacing";
             }
             enum "1563.02" {
               description "1563.02 nm/191.803125 THz 3.125GHz spacing";
             }
             enum "1563.00" {
               description "1563.00 nm/191.806250 THz 3.125/6.25GHz spacing";
             }
             enum "1562.97" {
               description "1562.97 nm/191.809375 THz 3.125GHz spacing";
             }
             enum "1562.95" {
               description "1562.95 nm/191.812500 THz 3.125/6.25/12.5GHz spacing";
             }
             enum "1562.92" {
               description "1562.92 nm/191.815625 THz 3.125GHz spacing";
             }
             enum "1562.89" {
               description "1562.89 nm/191.818750 THz 3.125/6.25GHz spacing";
             }
             enum "1562.87" {
               description "1562.87 nm/191.821875 THz 3.125GHz spacing";
             }
             enum "1562.84" {
               description "1562.84 nm/191.825000 THz 3.125/6.25/12.5GHz spacing";
             }
             enum "1562.82" {
               description "1562.82 nm/191.828125 THz 3.125GHz spacing";
             }
             enum "1562.79" {
               description "1562.79 nm/191.831250 THz 3.125/6.25GHz spacing";
             }
             enum "1562.77" {
               description "1562.77 nm/191.834375 THz 3.125GHz spacing";
             }
             enum "1562.74" {
               description "1562.74 nm/191.837500 THz 3.125/6.25/12.5GHz spacing";
             }
             enum "1562.72" {
               description "1562.72 nm/191.840625 THz 3.125GHz spacing";
             }
             enum "1562.69" {
               description "1562.69 nm/191.843750 THz 3.125/6.25GHz spacing";
             }
             enum "1562.67" {
               description "1562.67 nm/191.846875 THz 3.125GHz spacing";
             }
             enum "1562.64" {
               description "1562.64 nm/191.850000 THz 3.125/6.25/12.5/50/75GHz spacing";
             }
             enum "1562.61" {
               description "1562.61 nm/191.853125 THz 3.125GHz spacing";
             }
             enum "1562.59" {
               description "1562.59 nm/191.856250 THz 3.125/6.25GHz spacing";
             }
             enum "1562.56" {
               description "1562.56 nm/191.859375 THz 3.125GHz spacing";
             }
             enum "1562.54" {
               description "1562.54 nm/191.862500 THz 3.125/6.25/12.5GHz spacing";
             }
             enum "1562.51" {
               description "1562.51 nm/191.865625 THz 3.125GHz spacing";
             }
             enum "1562.49" {
               description "1562.49 nm/191.868750 THz 3.125/6.25GHz spacing";
             }
             enum "1562.46" {
               description "1562.46 nm/191.871875 THz 3.125GHz spacing";
             }
             enum "1562.44" {
               description "1562.44 nm/191.875000 THz 3.125/6.25/12.5GHz spacing";
             }
             enum "1562.41" {
               description "1562.41 nm/191.878125 THz 3.125GHz spacing";
             }
             enum "1562.39" {
               description "1562.39 nm/191.881250 THz 3.125/6.25GHz spacing";
             }
             enum "1562.36" {
               description "1562.36 nm/191.884375 THz 3.125GHz spacing";
             }
             enum "1562.33" {
               description "1562.33 nm/191.887500 THz 3.125/6.25/12.5GHz spacing";
             }
             enum "1562.31" {
               description "1562.31 nm/191.890625 THz 3.125GHz spacing";
             }
             enum "1562.28" {
               description "1562.28 nm/191.893750 THz 3.125/6.25GHz spacing";
             }
             enum "1562.26" {
               description "1562.26 nm/191.896875 THz 3.125GHz spacing";
             }
             enum "1562.23" {
               description "1562.23 nm/191.900000 THz 3.125/6.25/12.5/100GHz spacing";
             }
             enum "1562.21" {
               description "1562.21 nm/191.903125 THz 3.125GHz spacing";
             }
             enum "1562.18" {
               description "1562.18 nm/191.906250 THz 3.125/6.25GHz spacing";
             }
             enum "1562.16" {
               description "1562.16 nm/191.909375 THz 3.125GHz spacing";
             }
             enum "1562.13" {
               description "1562.13 nm/191.912500 THz 3.125/6.25/12.5GHz spacing";
             }
             enum "1562.11" {
               description "1562.11 nm/191.915625 THz 3.125GHz spacing";
             }
             enum "1562.08" {
               description "1562.08 nm/191.918750 THz 3.125/6.25GHz spacing";
             }
             enum "1562.05" {
               description "1562.05 nm/191.921875 THz 3.125GHz spacing";
             }
             enum "1562.03" {
               description "1562.03 nm/191.925000 THz 3.125/6.25/12.5/75GHz spacing";
             }
             enum "1562.00" {
               description "1562.00 nm/191.928125 THz 3.125GHz spacing";
             }
             enum "1561.98" {
               description "1561.98 nm/191.931250 THz 3.125/6.25GHz spacing";
             }
             enum "1561.95" {
               description "1561.95 nm/191.934375 THz 3.125GHz spacing";
             }
             enum "1561.93" {
               description "1561.93 nm/191.937500 THz 3.125/6.25/12.5GHz spacing";
             }
             enum "1561.90" {
               description "1561.90 nm/191.940625 THz 3.125GHz spacing";
             }
             enum "1561.88" {
               description "1561.88 nm/191.943750 THz 3.125/6.25GHz spacing";
             }
             enum "1561.85" {
               description "1561.85 nm/191.946875 THz 3.125GHz spacing";
             }
             enum "1561.83" {
               description "1561.83 nm/191.950000 THz 3.125/6.25/12.5/50GHz spacing";
             }
             enum "1561.80" {
               description "1561.80 nm/191.953125 THz 3.125GHz spacing";
             }
             enum "1561.77" {
               description "1561.77 nm/191.956250 THz 3.125/6.25GHz spacing";
             }
             enum "1561.75" {
               description "1561.75 nm/191.959375 THz 3.125GHz spacing";
             }
             enum "1561.72" {
               description "1561.72 nm/191.962500 THz 3.125/6.25/12.5GHz spacing";
             }
             enum "1561.70" {
               description "1561.70 nm/191.965625 THz 3.125GHz spacing";
             }
             enum "1561.67" {
               description "1561.67 nm/191.968750 THz 3.125/6.25GHz spacing";
             }
             enum "1561.65" {
               description "1561.65 nm/191.971875 THz 3.125GHz spacing";
             }
             enum "1561.62" {
               description "1561.62 nm/191.975000 THz 3.125/6.25/12.5GHz spacing";
             }
             enum "1561.60" {
               description "1561.60 nm/191.978125 THz 3.125GHz spacing";
             }
             enum "1561.57" {
               description "1561.57 nm/191.981250 THz 3.125/6.25GHz spacing";
             }
             enum "1561.55" {
               description "1561.55 nm/191.984375 THz 3.125GHz spacing";
             }
             enum "1561.52" {
               description "1561.52 nm/191.987500 THz 3.125/6.25/12.5GHz spacing";
             }
             enum "1561.50" {
               description "1561.50 nm/191.990625 THz 3.125GHz spacing";
             }
             enum "1561.47" {
               description "1561.47 nm/191.993750 THz 3.125/6.25GHz spacing";
             }
             enum "1561.44" {
               description "1561.44 nm/191.996875 THz 3.125GHz spacing";
             }
             enum "1561.42" {
               description "1561.42 nm/192.000000 THz 3.125/6.25/12.5/50/75/100GHz spacing";
             }
             enum "1561.39" {
               description "1561.39 nm/192.003125 THz 3.125GHz spacing";
             }
             enum "1561.37" {
               description "1561.37 nm/192.006250 THz 3.125/6.25GHz spacing";
             }
             enum "1561.34" {
               description "1561.34 nm/192.009375 THz 3.125GHz spacing";
             }
             enum "1561.32" {
               description "1561.32 nm/192.012500 THz 3.125/6.25/12.5GHz spacing";
             }
             enum "1561.29" {
               description "1561.29 nm/192.015625 THz 3.125GHz spacing";
             }
             enum "1561.27" {
               description "1561.27 nm/192.018750 THz 3.125/6.25GHz spacing";
             }
             enum "1561.24" {
               description "1561.24 nm/192.021875 THz 3.125GHz spacing";
             }
             enum "1561.22" {
               description "1561.22 nm/192.025000 THz 3.125/6.25/12.5GHz spacing";
             }
             enum "1561.19" {
               description "1561.19 nm/192.028125 THz 3.125GHz spacing";
             }
             enum "1561.16" {
               description "1561.16 nm/192.031250 THz 3.125/6.25GHz spacing";
             }
             enum "1561.14" {
               description "1561.14 nm/192.034375 THz 3.125GHz spacing";
             }
             enum "1561.11" {
               description "1561.11 nm/192.037500 THz 3.125/6.25/12.5GHz spacing";
             }
             enum "1561.09" {
               description "1561.09 nm/192.040625 THz 3.125GHz spacing";
             }
             enum "1561.06" {
               description "1561.06 nm/192.043750 THz 3.125/6.25GHz spacing";
             }
             enum "1561.04" {
               description "1561.04 nm/192.046875 THz 3.125GHz spacing";
             }
             enum "1561.01" {
               description "1561.01 nm/192.050000 THz 3.125/6.25/12.5/50GHz spacing";
             }
             enum "1560.99" {
               description "1560.99 nm/192.053125 THz 3.125GHz spacing";
             }
             enum "1560.96" {
               description "1560.96 nm/192.056250 THz 3.125/6.25GHz spacing";
             }
             enum "1560.94" {
               description "1560.94 nm/192.059375 THz 3.125GHz spacing";
             }
             enum "1560.91" {
               description "1560.91 nm/192.062500 THz 3.125/6.25/12.5GHz spacing";
             }
             enum "1560.89" {
               description "1560.89 nm/192.065625 THz 3.125GHz spacing";
             }
             enum "1560.86" {
               description "1560.86 nm/192.068750 THz 3.125/6.25GHz spacing";
             }
             enum "1560.83" {
               description "1560.83 nm/192.071875 THz 3.125GHz spacing";
             }
             enum "1560.81" {
               description "1560.81 nm/192.075000 THz 3.125/6.25/12.5/75GHz spacing";
             }
             enum "1560.78" {
               description "1560.78 nm/192.078125 THz 3.125GHz spacing";
             }
             enum "1560.76" {
               description "1560.76 nm/192.081250 THz 3.125/6.25GHz spacing";
             }
             enum "1560.73" {
               description "1560.73 nm/192.084375 THz 3.125GHz spacing";
             }
             enum "1560.71" {
               description "1560.71 nm/192.087500 THz 3.125/6.25/12.5GHz spacing";
             }
             enum "1560.68" {
               description "1560.68 nm/192.090625 THz 3.125GHz spacing";
             }
             enum "1560.66" {
               description "1560.66 nm/192.093750 THz 3.125/6.25GHz spacing";
             }
             enum "1560.63" {
               description "1560.63 nm/192.096875 THz 3.125GHz spacing";
             }
             enum "1560.61" {
               description "1560.61 nm/192.100000 THz 3.125/6.25/12.5/100GHz spacing";
             }
             enum "1560.58" {
               description "1560.58 nm/192.103125 THz 3.125GHz spacing";
             }
             enum "1560.56" {
               description "1560.56 nm/192.106250 THz 3.125/6.25GHz spacing";
             }
             enum "1560.53" {
               description "1560.53 nm/192.109375 THz 3.125GHz spacing";
             }
             enum "1560.50" {
               description "1560.50 nm/192.112500 THz 3.125/6.25/12.5GHz spacing";
             }
             enum "1560.48" {
               description "1560.48 nm/192.115625 THz 3.125GHz spacing";
             }
             enum "1560.45" {
               description "1560.45 nm/192.118750 THz 3.125/6.25GHz spacing";
             }
             enum "1560.43" {
               description "1560.43 nm/192.121875 THz 3.125GHz spacing";
             }
             enum "1560.40" {
               description "1560.40 nm/192.125000 THz 3.125/6.25/12.5GHz spacing";
             }
             enum "1560.38" {
               description "1560.38 nm/192.128125 THz 3.125GHz spacing";
             }
             enum "1560.35" {
               description "1560.35 nm/192.131250 THz 3.125/6.25GHz spacing";
             }
             enum "1560.33" {
               description "1560.33 nm/192.134375 THz 3.125GHz spacing";
             }
             enum "1560.30" {
               description "1560.30 nm/192.137500 THz 3.125/6.25/12.5GHz spacing";
             }
             enum "1560.28" {
               description "1560.28 nm/192.140625 THz 3.125GHz spacing";
             }
             enum "1560.25" {
               description "1560.25 nm/192.143750 THz 3.125/6.25GHz spacing";
             }
             enum "1560.23" {
               description "1560.23 nm/192.146875 THz 3.125GHz spacing";
             }
             enum "1560.20" {
               description "1560.20 nm/192.150000 THz 3.125/6.25/12.5/50/75GHz spacing";
             }
             enum "1560.17" {
               description "1560.17 nm/192.153125 THz 3.125GHz spacing";
             }
             enum "1560.15" {
               description "1560.15 nm/192.156250 THz 3.125/6.25GHz spacing";
             }
             enum "1560.12" {
               description "1560.12 nm/192.159375 THz 3.125GHz spacing";
             }
             enum "1560.10" {
               description "1560.10 nm/192.162500 THz 3.125/6.25/12.5GHz spacing";
             }
             enum "1560.07" {
               description "1560.07 nm/192.165625 THz 3.125GHz spacing";
             }
             enum "1560.05" {
               description "1560.05 nm/192.168750 THz 3.125/6.25GHz spacing";
             }
             enum "1560.02" {
               description "1560.02 nm/192.171875 THz 3.125GHz spacing";
             }
             enum "1560.00" {
               description "1560.00 nm/192.175000 THz 3.125/6.25/12.5GHz spacing";
             }
             enum "1559.97" {
               description "1559.97 nm/192.178125 THz 3.125GHz spacing";
             }
             enum "1559.95" {
               description "1559.95 nm/192.181250 THz 3.125/6.25GHz spacing";
             }
             enum "1559.92" {
               description "1559.92 nm/192.184375 THz 3.125GHz spacing";
             }
             enum "1559.90" {
               description "1559.90 nm/192.187500 THz 3.125/6.25/12.5GHz spacing";
             }
             enum "1559.87" {
               description "1559.87 nm/192.190625 THz 3.125GHz spacing";
             }
             enum "1559.84" {
               description "1559.84 nm/192.193750 THz 3.125/6.25GHz spacing";
             }
             enum "1559.82" {
               description "1559.82 nm/192.196875 THz 3.125GHz spacing";
             }
             enum "1559.79" {
               description "1559.79 nm/192.200000 THz 3.125/6.25/12.5/100GHz spacing";
             }
             enum "1559.77" {
               description "1559.77 nm/192.203125 THz 3.125GHz spacing";
             }
             enum "1559.74" {
               description "1559.74 nm/192.206250 THz 3.125/6.25GHz spacing";
             }
             enum "1559.72" {
               description "1559.72 nm/192.209375 THz 3.125GHz spacing";
             }
             enum "1559.69" {
               description "1559.69 nm/192.212500 THz 3.125/6.25/12.5GHz spacing";
             }
             enum "1559.67" {
               description "1559.67 nm/192.215625 THz 3.125GHz spacing";
             }
             enum "1559.64" {
               description "1559.64 nm/192.218750 THz 3.125/6.25GHz spacing";
             }
             enum "1559.62" {
               description "1559.62 nm/192.221875 THz 3.125GHz spacing";
             }
             enum "1559.59" {
               description "1559.59 nm/192.225000 THz 3.125/6.25/12.5/75GHz spacing";
             }
             enum "1559.57" {
               description "1559.57 nm/192.228125 THz 3.125GHz spacing";
             }
             enum "1559.54" {
               description "1559.54 nm/192.231250 THz 3.125/6.25GHz spacing";
             }
             enum "1559.52" {
               description "1559.52 nm/192.234375 THz 3.125GHz spacing";
             }
             enum "1559.49" {
               description "1559.49 nm/192.237500 THz 3.125/6.25/12.5GHz spacing";
             }
             enum "1559.46" {
               description "1559.46 nm/192.240625 THz 3.125GHz spacing";
             }
             enum "1559.44" {
               description "1559.44 nm/192.243750 THz 3.125/6.25GHz spacing";
             }
             enum "1559.41" {
               description "1559.41 nm/192.246875 THz 3.125GHz spacing";
             }
             enum "1559.39" {
               description "1559.39 nm/192.250000 THz 3.125/6.25/12.5/50GHz spacing";
             }
             enum "1559.36" {
               description "1559.36 nm/192.253125 THz 3.125GHz spacing";
             }
             enum "1559.34" {
               description "1559.34 nm/192.256250 THz 3.125/6.25GHz spacing";
             }
             enum "1559.31" {
               description "1559.31 nm/192.259375 THz 3.125GHz spacing";
             }
             enum "1559.29" {
               description "1559.29 nm/192.262500 THz 3.125/6.25/12.5GHz spacing";
             }
             enum "1559.26" {
               description "1559.26 nm/192.265625 THz 3.125GHz spacing";
             }
             enum "1559.24" {
               description "1559.24 nm/192.268750 THz 3.125/6.25GHz spacing";
             }
             enum "1559.21" {
               description "1559.21 nm/192.271875 THz 3.125GHz spacing";
             }
             enum "1559.19" {
               description "1559.19 nm/192.275000 THz 3.125/6.25/12.5GHz spacing";
             }
             enum "1559.16" {
               description "1559.16 nm/192.278125 THz 3.125GHz spacing";
             }
             enum "1559.14" {
               description "1559.14 nm/192.281250 THz 3.125/6.25GHz spacing";
             }
             enum "1559.11" {
               description "1559.11 nm/192.284375 THz 3.125GHz spacing";
             }
             enum "1559.08" {
               description "1559.08 nm/192.287500 THz 3.125/6.25/12.5GHz spacing";
             }
             enum "1559.06" {
               description "1559.06 nm/192.290625 THz 3.125GHz spacing";
             }
             enum "1559.03" {
               description "1559.03 nm/192.293750 THz 3.125/6.25GHz spacing";
             }
             enum "1559.01" {
               description "1559.01 nm/192.296875 THz 3.125GHz spacing";
             }
             enum "1558.98" {
               description "1558.98 nm/192.300000 THz 3.125/6.25/12.5/50/75/100GHz spacing";
             }
             enum "1558.96" {
               description "1558.96 nm/192.303125 THz 3.125GHz spacing";
             }
             enum "1558.93" {
               description "1558.93 nm/192.306250 THz 3.125/6.25GHz spacing";
             }
             enum "1558.91" {
               description "1558.91 nm/192.309375 THz 3.125GHz spacing";
             }
             enum "1558.88" {
               description "1558.88 nm/192.312500 THz 3.125/6.25/12.5GHz spacing";
             }
             enum "1558.86" {
               description "1558.86 nm/192.315625 THz 3.125GHz spacing";
             }
             enum "1558.83" {
               description "1558.83 nm/192.318750 THz 3.125/6.25GHz spacing";
             }
             enum "1558.81" {
               description "1558.81 nm/192.321875 THz 3.125GHz spacing";
             }
             enum "1558.78" {
               description "1558.78 nm/192.325000 THz 3.125/6.25/12.5GHz spacing";
             }
             enum "1558.76" {
               description "1558.76 nm/192.328125 THz 3.125GHz spacing";
             }
             enum "1558.73" {
               description "1558.73 nm/192.331250 THz 3.125/6.25GHz spacing";
             }
             enum "1558.70" {
               description "1558.70 nm/192.334375 THz 3.125GHz spacing";
             }
             enum "1558.68" {
               description "1558.68 nm/192.337500 THz 3.125/6.25/12.5GHz spacing";
             }
             enum "1558.65" {
               description "1558.65 nm/192.340625 THz 3.125GHz spacing";
             }
             enum "1558.63" {
               description "1558.63 nm/192.343750 THz 3.125/6.25GHz spacing";
             }
             enum "1558.60" {
               description "1558.60 nm/192.346875 THz 3.125GHz spacing";
             }
             enum "1558.58" {
               description "1558.58 nm/192.350000 THz 3.125/6.25/12.5/50GHz spacing";
             }
             enum "1558.55" {
               description "1558.55 nm/192.353125 THz 3.125GHz spacing";
             }
             enum "1558.53" {
               description "1558.53 nm/192.356250 THz 3.125/6.25GHz spacing";
             }
             enum "1558.50" {
               description "1558.50 nm/192.359375 THz 3.125GHz spacing";
             }
             enum "1558.48" {
               description "1558.48 nm/192.362500 THz 3.125/6.25/12.5GHz spacing";
             }
             enum "1558.45" {
               description "1558.45 nm/192.365625 THz 3.125GHz spacing";
             }
             enum "1558.43" {
               description "1558.43 nm/192.368750 THz 3.125/6.25GHz spacing";
             }
             enum "1558.40" {
               description "1558.40 nm/192.371875 THz 3.125GHz spacing";
             }
             enum "1558.38" {
               description "1558.38 nm/192.375000 THz 3.125/6.25/12.5/75GHz spacing";
             }
             enum "1558.35" {
               description "1558.35 nm/192.378125 THz 3.125GHz spacing";
             }
             enum "1558.32" {
               description "1558.32 nm/192.381250 THz 3.125/6.25GHz spacing";
             }
             enum "1558.30" {
               description "1558.30 nm/192.384375 THz 3.125GHz spacing";
             }
             enum "1558.27" {
               description "1558.27 nm/192.387500 THz 3.125/6.25/12.5GHz spacing";
             }
             enum "1558.25" {
               description "1558.25 nm/192.390625 THz 3.125GHz spacing";
             }
             enum "1558.22" {
               description "1558.22 nm/192.393750 THz 3.125/6.25GHz spacing";
             }
             enum "1558.20" {
               description "1558.20 nm/192.396875 THz 3.125GHz spacing";
             }
             enum "1558.17" {
               description "1558.17 nm/192.400000 THz 3.125/6.25/12.5/100GHz spacing";
             }
             enum "1558.15" {
               description "1558.15 nm/192.403125 THz 3.125GHz spacing";
             }
             enum "1558.12" {
               description "1558.12 nm/192.406250 THz 3.125/6.25GHz spacing";
             }
             enum "1558.10" {
               description "1558.10 nm/192.409375 THz 3.125GHz spacing";
             }
             enum "1558.07" {
               description "1558.07 nm/192.412500 THz 3.125/6.25/12.5GHz spacing";
             }
             enum "1558.05" {
               description "1558.05 nm/192.415625 THz 3.125GHz spacing";
             }
             enum "1558.02" {
               description "1558.02 nm/192.418750 THz 3.125/6.25GHz spacing";
             }
             enum "1558.00" {
               description "1558.00 nm/192.421875 THz 3.125GHz spacing";
             }
             enum "1557.97" {
               description "1557.97 nm/192.425000 THz 3.125/6.25/12.5GHz spacing";
             }
             enum "1557.95" {
               description "1557.95 nm/192.428125 THz 3.125GHz spacing";
             }
             enum "1557.92" {
               description "1557.92 nm/192.431250 THz 3.125/6.25GHz spacing";
             }
             enum "1557.89" {
               description "1557.89 nm/192.434375 THz 3.125GHz spacing";
             }
             enum "1557.87" {
               description "1557.87 nm/192.437500 THz 3.125/6.25/12.5GHz spacing";
             }
             enum "1557.84" {
               description "1557.84 nm/192.440625 THz 3.125GHz spacing";
             }
             enum "1557.82" {
               description "1557.82 nm/192.443750 THz 3.125/6.25GHz spacing";
             }
             enum "1557.79" {
               description "1557.79 nm/192.446875 THz 3.125GHz spacing";
             }
             enum "1557.77" {
               description "1557.77 nm/192.450000 THz 3.125/6.25/12.5/50/75GHz spacing";
             }
             enum "1557.74" {
               description "1557.74 nm/192.453125 THz 3.125GHz spacing";
             }
             enum "1557.72" {
               description "1557.72 nm/192.456250 THz 3.125/6.25GHz spacing";
             }
             enum "1557.69" {
               description "1557.69 nm/192.459375 THz 3.125GHz spacing";
             }
             enum "1557.67" {
               description "1557.67 nm/192.462500 THz 3.125/6.25/12.5GHz spacing";
             }
             enum "1557.64" {
               description "1557.64 nm/192.465625 THz 3.125GHz spacing";
             }
             enum "1557.62" {
               description "1557.62 nm/192.468750 THz 3.125/6.25GHz spacing";
             }
             enum "1557.59" {
               description "1557.59 nm/192.471875 THz 3.125GHz spacing";
             }
             enum "1557.57" {
               description "1557.57 nm/192.475000 THz 3.125/6.25/12.5GHz spacing";
             }
             enum "1557.54" {
               description "1557.54 nm/192.478125 THz 3.125GHz spacing";
             }
             enum "1557.52" {
               description "1557.52 nm/192.481250 THz 3.125/6.25GHz spacing";
             }
             enum "1557.49" {
               description "1557.49 nm/192.484375 THz 3.125GHz spacing";
             }
             enum "1557.46" {
               description "1557.46 nm/192.487500 THz 3.125/6.25/12.5GHz spacing";
             }
             enum "1557.44" {
               description "1557.44 nm/192.490625 THz 3.125GHz spacing";
             }
             enum "1557.41" {
               description "1557.41 nm/192.493750 THz 3.125/6.25GHz spacing";
             }
             enum "1557.39" {
               description "1557.39 nm/192.496875 THz 3.125GHz spacing";
             }
             enum "1557.36" {
               description "1557.36 nm/192.500000 THz 3.125/6.25/12.5/100GHz spacing";
             }
             enum "1557.34" {
               description "1557.34 nm/192.503125 THz 3.125GHz spacing";
             }
             enum "1557.31" {
               description "1557.31 nm/192.506250 THz 3.125/6.25GHz spacing";
             }
             enum "1557.29" {
               description "1557.29 nm/192.509375 THz 3.125GHz spacing";
             }
             enum "1557.26" {
               description "1557.26 nm/192.512500 THz 3.125/6.25/12.5GHz spacing";
             }
             enum "1557.24" {
               description "1557.24 nm/192.515625 THz 3.125GHz spacing";
             }
             enum "1557.21" {
               description "1557.21 nm/192.518750 THz 3.125/6.25GHz spacing";
             }
             enum "1557.19" {
               description "1557.19 nm/192.521875 THz 3.125GHz spacing";
             }
             enum "1557.16" {
               description "1557.16 nm/192.525000 THz 3.125/6.25/12.5/75GHz spacing";
             }
             enum "1557.14" {
               description "1557.14 nm/192.528125 THz 3.125GHz spacing";
             }
             enum "1557.11" {
               description "1557.11 nm/192.531250 THz 3.125/6.25GHz spacing";
             }
             enum "1557.09" {
               description "1557.09 nm/192.534375 THz 3.125GHz spacing";
             }
             enum "1557.06" {
               description "1557.06 nm/192.537500 THz 3.125/6.25/12.5GHz spacing";
             }
             enum "1557.03" {
               description "1557.03 nm/192.540625 THz 3.125GHz spacing";
             }
             enum "1557.01" {
               description "1557.01 nm/192.543750 THz 3.125/6.25GHz spacing";
             }
             enum "1556.98" {
               description "1556.98 nm/192.546875 THz 3.125GHz spacing";
             }
             enum "1556.96" {
               description "1556.96 nm/192.550000 THz 3.125/6.25/12.5/50GHz spacing";
             }
             enum "1556.93" {
               description "1556.93 nm/192.553125 THz 3.125GHz spacing";
             }
             enum "1556.91" {
               description "1556.91 nm/192.556250 THz 3.125/6.25GHz spacing";
             }
             enum "1556.88" {
               description "1556.88 nm/192.559375 THz 3.125GHz spacing";
             }
             enum "1556.86" {
               description "1556.86 nm/192.562500 THz 3.125/6.25/12.5GHz spacing";
             }
             enum "1556.83" {
               description "1556.83 nm/192.565625 THz 3.125GHz spacing";
             }
             enum "1556.81" {
               description "1556.81 nm/192.568750 THz 3.125/6.25GHz spacing";
             }
             enum "1556.78" {
               description "1556.78 nm/192.571875 THz 3.125GHz spacing";
             }
             enum "1556.76" {
               description "1556.76 nm/192.575000 THz 3.125/6.25/12.5GHz spacing";
             }
             enum "1556.73" {
               description "1556.73 nm/192.578125 THz 3.125GHz spacing";
             }
             enum "1556.71" {
               description "1556.71 nm/192.581250 THz 3.125/6.25GHz spacing";
             }
             enum "1556.68" {
               description "1556.68 nm/192.584375 THz 3.125GHz spacing";
             }
             enum "1556.66" {
               description "1556.66 nm/192.587500 THz 3.125/6.25/12.5GHz spacing";
             }
             enum "1556.63" {
               description "1556.63 nm/192.590625 THz 3.125GHz spacing";
             }
             enum "1556.61" {
               description "1556.61 nm/192.593750 THz 3.125/6.25GHz spacing";
             }
             enum "1556.58" {
               description "1556.58 nm/192.596875 THz 3.125GHz spacing";
             }
             enum "1556.55" {
               description "1556.55 nm/192.600000 THz 3.125/6.25/12.5/50/75/100GHz spacing";
             }
             enum "1556.53" {
               description "1556.53 nm/192.603125 THz 3.125GHz spacing";
             }
             enum "1556.50" {
               description "1556.50 nm/192.606250 THz 3.125/6.25GHz spacing";
             }
             enum "1556.48" {
               description "1556.48 nm/192.609375 THz 3.125GHz spacing";
             }
             enum "1556.45" {
               description "1556.45 nm/192.612500 THz 3.125/6.25/12.5GHz spacing";
             }
             enum "1556.43" {
               description "1556.43 nm/192.615625 THz 3.125GHz spacing";
             }
             enum "1556.40" {
               description "1556.40 nm/192.618750 THz 3.125/6.25GHz spacing";
             }
             enum "1556.38" {
               description "1556.38 nm/192.621875 THz 3.125GHz spacing";
             }
             enum "1556.35" {
               description "1556.35 nm/192.625000 THz 3.125/6.25/12.5GHz spacing";
             }
             enum "1556.33" {
               description "1556.33 nm/192.628125 THz 3.125GHz spacing";
             }
             enum "1556.30" {
               description "1556.30 nm/192.631250 THz 3.125/6.25GHz spacing";
             }
             enum "1556.28" {
               description "1556.28 nm/192.634375 THz 3.125GHz spacing";
             }
             enum "1556.25" {
               description "1556.25 nm/192.637500 THz 3.125/6.25/12.5GHz spacing";
             }
             enum "1556.23" {
               description "1556.23 nm/192.640625 THz 3.125GHz spacing";
             }
             enum "1556.20" {
               description "1556.20 nm/192.643750 THz 3.125/6.25GHz spacing";
             }
             enum "1556.18" {
               description "1556.18 nm/192.646875 THz 3.125GHz spacing";
             }
             enum "1556.15" {
               description "1556.15 nm/192.650000 THz 3.125/6.25/12.5/50GHz spacing";
             }
             enum "1556.13" {
               description "1556.13 nm/192.653125 THz 3.125GHz spacing";
             }
             enum "1556.10" {
               description "1556.10 nm/192.656250 THz 3.125/6.25GHz spacing";
             }
             enum "1556.08" {
               description "1556.08 nm/192.659375 THz 3.125GHz spacing";
             }
             enum "1556.05" {
               description "1556.05 nm/192.662500 THz 3.125/6.25/12.5GHz spacing";
             }
             enum "1556.02" {
               description "1556.02 nm/192.665625 THz 3.125GHz spacing";
             }
             enum "1556.00" {
               description "1556.00 nm/192.668750 THz 3.125/6.25GHz spacing";
             }
             enum "1555.97" {
               description "1555.97 nm/192.671875 THz 3.125GHz spacing";
             }
             enum "1555.95" {
               description "1555.95 nm/192.675000 THz 3.125/6.25/12.5/75GHz spacing";
             }
             enum "1555.92" {
               description "1555.92 nm/192.678125 THz 3.125GHz spacing";
             }
             enum "1555.90" {
               description "1555.90 nm/192.681250 THz 3.125/6.25GHz spacing";
             }
             enum "1555.87" {
               description "1555.87 nm/192.684375 THz 3.125GHz spacing";
             }
             enum "1555.85" {
               description "1555.85 nm/192.687500 THz 3.125/6.25/12.5GHz spacing";
             }
             enum "1555.82" {
               description "1555.82 nm/192.690625 THz 3.125GHz spacing";
             }
             enum "1555.80" {
               description "1555.80 nm/192.693750 THz 3.125/6.25GHz spacing";
             }
             enum "1555.77" {
               description "1555.77 nm/192.696875 THz 3.125GHz spacing";
             }
             enum "1555.75" {
               description "1555.75 nm/192.700000 THz 3.125/6.25/12.5/100GHz spacing";
             }
             enum "1555.72" {
               description "1555.72 nm/192.703125 THz 3.125GHz spacing";
             }
             enum "1555.70" {
               description "1555.70 nm/192.706250 THz 3.125/6.25GHz spacing";
             }
             enum "1555.67" {
               description "1555.67 nm/192.709375 THz 3.125GHz spacing";
             }
             enum "1555.65" {
               description "1555.65 nm/192.712500 THz 3.125/6.25/12.5GHz spacing";
             }
             enum "1555.62" {
               description "1555.62 nm/192.715625 THz 3.125GHz spacing";
             }
             enum "1555.60" {
               description "1555.60 nm/192.718750 THz 3.125/6.25GHz spacing";
             }
             enum "1555.57" {
               description "1555.57 nm/192.721875 THz 3.125GHz spacing";
             }
             enum "1555.55" {
               description "1555.55 nm/192.725000 THz 3.125/6.25/12.5GHz spacing";
             }
             enum "1555.52" {
               description "1555.52 nm/192.728125 THz 3.125GHz spacing";
             }
             enum "1555.49" {
               description "1555.49 nm/192.731250 THz 3.125/6.25GHz spacing";
             }
             enum "1555.47" {
               description "1555.47 nm/192.734375 THz 3.125GHz spacing";
             }
             enum "1555.44" {
               description "1555.44 nm/192.737500 THz 3.125/6.25/12.5GHz spacing";
             }
             enum "1555.42" {
               description "1555.42 nm/192.740625 THz 3.125GHz spacing";
             }
             enum "1555.39" {
               description "1555.39 nm/192.743750 THz 3.125/6.25GHz spacing";
             }
             enum "1555.37" {
               description "1555.37 nm/192.746875 THz 3.125GHz spacing";
             }
             enum "1555.34" {
               description "1555.34 nm/192.750000 THz 3.125/6.25/12.5/50/75GHz spacing";
             }
             enum "1555.32" {
               description "1555.32 nm/192.753125 THz 3.125GHz spacing";
             }
             enum "1555.29" {
               description "1555.29 nm/192.756250 THz 3.125/6.25GHz spacing";
             }
             enum "1555.27" {
               description "1555.27 nm/192.759375 THz 3.125GHz spacing";
             }
             enum "1555.24" {
               description "1555.24 nm/192.762500 THz 3.125/6.25/12.5GHz spacing";
             }
             enum "1555.22" {
               description "1555.22 nm/192.765625 THz 3.125GHz spacing";
             }
             enum "1555.19" {
               description "1555.19 nm/192.768750 THz 3.125/6.25GHz spacing";
             }
             enum "1555.17" {
               description "1555.17 nm/192.771875 THz 3.125GHz spacing";
             }
             enum "1555.14" {
               description "1555.14 nm/192.775000 THz 3.125/6.25/12.5GHz spacing";
             }
             enum "1555.12" {
               description "1555.12 nm/192.778125 THz 3.125GHz spacing";
             }
             enum "1555.09" {
               description "1555.09 nm/192.781250 THz 3.125/6.25GHz spacing";
             }
             enum "1555.07" {
               description "1555.07 nm/192.784375 THz 3.125GHz spacing";
             }
             enum "1555.04" {
               description "1555.04 nm/192.787500 THz 3.125/6.25/12.5GHz spacing";
             }
             enum "1555.02" {
               description "1555.02 nm/192.790625 THz 3.125GHz spacing";
             }
             enum "1554.99" {
               description "1554.99 nm/192.793750 THz 3.125/6.25GHz spacing";
             }
             enum "1554.97" {
               description "1554.97 nm/192.796875 THz 3.125GHz spacing";
             }
             enum "1554.94" {
               description "1554.94 nm/192.800000 THz 3.125/6.25/12.5/100GHz spacing";
             }
             enum "1554.91" {
               description "1554.91 nm/192.803125 THz 3.125GHz spacing";
             }
             enum "1554.89" {
               description "1554.89 nm/192.806250 THz 3.125/6.25GHz spacing";
             }
             enum "1554.86" {
               description "1554.86 nm/192.809375 THz 3.125GHz spacing";
             }
             enum "1554.84" {
               description "1554.84 nm/192.812500 THz 3.125/6.25/12.5GHz spacing";
             }
             enum "1554.81" {
               description "1554.81 nm/192.815625 THz 3.125GHz spacing";
             }
             enum "1554.79" {
               description "1554.79 nm/192.818750 THz 3.125/6.25GHz spacing";
             }
             enum "1554.76" {
               description "1554.76 nm/192.821875 THz 3.125GHz spacing";
             }
             enum "1554.74" {
               description "1554.74 nm/192.825000 THz 3.125/6.25/12.5/75GHz spacing";
             }
             enum "1554.71" {
               description "1554.71 nm/192.828125 THz 3.125GHz spacing";
             }
             enum "1554.69" {
               description "1554.69 nm/192.831250 THz 3.125/6.25GHz spacing";
             }
             enum "1554.66" {
               description "1554.66 nm/192.834375 THz 3.125GHz spacing";
             }
             enum "1554.64" {
               description "1554.64 nm/192.837500 THz 3.125/6.25/12.5GHz spacing";
             }
             enum "1554.61" {
               description "1554.61 nm/192.840625 THz 3.125GHz spacing";
             }
             enum "1554.59" {
               description "1554.59 nm/192.843750 THz 3.125/6.25GHz spacing";
             }
             enum "1554.56" {
               description "1554.56 nm/192.846875 THz 3.125GHz spacing";
             }
             enum "1554.54" {
               description "1554.54 nm/192.850000 THz 3.125/6.25/12.5/50GHz spacing";
             }
             enum "1554.51" {
               description "1554.51 nm/192.853125 THz 3.125GHz spacing";
             }
             enum "1554.49" {
               description "1554.49 nm/192.856250 THz 3.125/6.25GHz spacing";
             }
             enum "1554.46" {
               description "1554.46 nm/192.859375 THz 3.125GHz spacing";
             }
             enum "1554.44" {
               description "1554.44 nm/192.862500 THz 3.125/6.25/12.5GHz spacing";
             }
             enum "1554.41" {
               description "1554.41 nm/192.865625 THz 3.125GHz spacing";
             }
             enum "1554.39" {
               description "1554.39 nm/192.868750 THz 3.125/6.25GHz spacing";
             }
             enum "1554.36" {
               description "1554.36 nm/192.871875 THz 3.125GHz spacing";
             }
             enum "1554.34" {
               description "1554.34 nm/192.875000 THz 3.125/6.25/12.5GHz spacing";
             }
             enum "1554.31" {
               description "1554.31 nm/192.878125 THz 3.125GHz spacing";
             }
             enum "1554.29" {
               description "1554.29 nm/192.881250 THz 3.125/6.25GHz spacing";
             }
             enum "1554.26" {
               description "1554.26 nm/192.884375 THz 3.125GHz spacing";
             }
             enum "1554.23" {
               description "1554.23 nm/192.887500 THz 3.125/6.25/12.5GHz spacing";
             }
             enum "1554.21" {
               description "1554.21 nm/192.890625 THz 3.125GHz spacing";
             }
             enum "1554.18" {
               description "1554.18 nm/192.893750 THz 3.125/6.25GHz spacing";
             }
             enum "1554.16" {
               description "1554.16 nm/192.896875 THz 3.125GHz spacing";
             }
             enum "1554.13" {
               description "1554.13 nm/192.900000 THz 3.125/6.25/12.5/50/75/100GHz spacing";
             }
             enum "1554.11" {
               description "1554.11 nm/192.903125 THz 3.125GHz spacing";
             }
             enum "1554.08" {
               description "1554.08 nm/192.906250 THz 3.125/6.25GHz spacing";
             }
             enum "1554.06" {
               description "1554.06 nm/192.909375 THz 3.125GHz spacing";
             }
             enum "1554.03" {
               description "1554.03 nm/192.912500 THz 3.125/6.25/12.5GHz spacing";
             }
             enum "1554.01" {
               description "1554.01 nm/192.915625 THz 3.125GHz spacing";
             }
             enum "1553.98" {
               description "1553.98 nm/192.918750 THz 3.125/6.25GHz spacing";
             }
             enum "1553.96" {
               description "1553.96 nm/192.921875 THz 3.125GHz spacing";
             }
             enum "1553.93" {
               description "1553.93 nm/192.925000 THz 3.125/6.25/12.5GHz spacing";
             }
             enum "1553.91" {
               description "1553.91 nm/192.928125 THz 3.125GHz spacing";
             }
             enum "1553.88" {
               description "1553.88 nm/192.931250 THz 3.125/6.25GHz spacing";
             }
             enum "1553.86" {
               description "1553.86 nm/192.934375 THz 3.125GHz spacing";
             }
             enum "1553.83" {
               description "1553.83 nm/192.937500 THz 3.125/6.25/12.5GHz spacing";
             }
             enum "1553.81" {
               description "1553.81 nm/192.940625 THz 3.125GHz spacing";
             }
             enum "1553.78" {
               description "1553.78 nm/192.943750 THz 3.125/6.25GHz spacing";
             }
             enum "1553.76" {
               description "1553.76 nm/192.946875 THz 3.125GHz spacing";
             }
             enum "1553.73" {
               description "1553.73 nm/192.950000 THz 3.125/6.25/12.5/50GHz spacing";
             }
             enum "1553.71" {
               description "1553.71 nm/192.953125 THz 3.125GHz spacing";
             }
             enum "1553.68" {
               description "1553.68 nm/192.956250 THz 3.125/6.25GHz spacing";
             }
             enum "1553.66" {
               description "1553.66 nm/192.959375 THz 3.125GHz spacing";
             }
             enum "1553.63" {
               description "1553.63 nm/192.962500 THz 3.125/6.25/12.5GHz spacing";
             }
             enum "1553.61" {
               description "1553.61 nm/192.965625 THz 3.125GHz spacing";
             }
             enum "1553.58" {
               description "1553.58 nm/192.968750 THz 3.125/6.25GHz spacing";
             }
             enum "1553.56" {
               description "1553.56 nm/192.971875 THz 3.125GHz spacing";
             }
             enum "1553.53" {
               description "1553.53 nm/192.975000 THz 3.125/6.25/12.5/75GHz spacing";
             }
             enum "1553.50" {
               description "1553.50 nm/192.978125 THz 3.125GHz spacing";
             }
             enum "1553.48" {
               description "1553.48 nm/192.981250 THz 3.125/6.25GHz spacing";
             }
             enum "1553.45" {
               description "1553.45 nm/192.984375 THz 3.125GHz spacing";
             }
             enum "1553.43" {
               description "1553.43 nm/192.987500 THz 3.125/6.25/12.5GHz spacing";
             }
             enum "1553.40" {
               description "1553.40 nm/192.990625 THz 3.125GHz spacing";
             }
             enum "1553.38" {
               description "1553.38 nm/192.993750 THz 3.125/6.25GHz spacing";
             }
             enum "1553.35" {
               description "1553.35 nm/192.996875 THz 3.125GHz spacing";
             }
             enum "1553.33" {
               description "1553.33 nm/193.000000 THz 3.125/6.25/12.5/100GHz spacing";
             }
             enum "1553.30" {
               description "1553.30 nm/193.003125 THz 3.125GHz spacing";
             }
             enum "1553.28" {
               description "1553.28 nm/193.006250 THz 3.125/6.25GHz spacing";
             }
             enum "1553.25" {
               description "1553.25 nm/193.009375 THz 3.125GHz spacing";
             }
             enum "1553.23" {
               description "1553.23 nm/193.012500 THz 3.125/6.25/12.5GHz spacing";
             }
             enum "1553.20" {
               description "1553.20 nm/193.015625 THz 3.125GHz spacing";
             }
             enum "1553.18" {
               description "1553.18 nm/193.018750 THz 3.125/6.25GHz spacing";
             }
             enum "1553.15" {
               description "1553.15 nm/193.021875 THz 3.125GHz spacing";
             }
             enum "1553.13" {
               description "1553.13 nm/193.025000 THz 3.125/6.25/12.5GHz spacing";
             }
             enum "1553.10" {
               description "1553.10 nm/193.028125 THz 3.125GHz spacing";
             }
             enum "1553.08" {
               description "1553.08 nm/193.031250 THz 3.125/6.25GHz spacing";
             }
             enum "1553.05" {
               description "1553.05 nm/193.034375 THz 3.125GHz spacing";
             }
             enum "1553.03" {
               description "1553.03 nm/193.037500 THz 3.125/6.25/12.5GHz spacing";
             }
             enum "1553.00" {
               description "1553.00 nm/193.040625 THz 3.125GHz spacing";
             }
             enum "1552.98" {
               description "1552.98 nm/193.043750 THz 3.125/6.25GHz spacing";
             }
             enum "1552.95" {
               description "1552.95 nm/193.046875 THz 3.125GHz spacing";
             }
             enum "1552.93" {
               description "1552.93 nm/193.050000 THz 3.125/6.25/12.5/50/75GHz spacing";
             }
             enum "1552.90" {
               description "1552.90 nm/193.053125 THz 3.125GHz spacing";
             }
             enum "1552.88" {
               description "1552.88 nm/193.056250 THz 3.125/6.25GHz spacing";
             }
             enum "1552.85" {
               description "1552.85 nm/193.059375 THz 3.125GHz spacing";
             }
             enum "1552.83" {
               description "1552.83 nm/193.062500 THz 3.125/6.25/12.5GHz spacing";
             }
             enum "1552.80" {
               description "1552.80 nm/193.065625 THz 3.125GHz spacing";
             }
             enum "1552.78" {
               description "1552.78 nm/193.068750 THz 3.125/6.25GHz spacing";
             }
             enum "1552.75" {
               description "1552.75 nm/193.071875 THz 3.125GHz spacing";
             }
             enum "1552.73" {
               description "1552.73 nm/193.075000 THz 3.125/6.25/12.5GHz spacing";
             }
             enum "1552.70" {
               description "1552.70 nm/193.078125 THz 3.125GHz spacing";
             }
             enum "1552.68" {
               description "1552.68 nm/193.081250 THz 3.125/6.25GHz spacing";
             }
             enum "1552.65" {
               description "1552.65 nm/193.084375 THz 3.125GHz spacing";
             }
             enum "1552.62" {
               description "1552.62 nm/193.087500 THz 3.125/6.25/12.5GHz spacing";
             }
             enum "1552.60" {
               description "1552.60 nm/193.090625 THz 3.125GHz spacing";
             }
             enum "1552.57" {
               description "1552.57 nm/193.093750 THz 3.125/6.25GHz spacing";
             }
             enum "1552.55" {
               description "1552.55 nm/193.096875 THz 3.125GHz spacing";
             }
             enum "1552.52" {
               description "1552.52 nm/193.100000 THz 3.125/6.25/12.5/100GHz spacing";
             }
             enum "1552.50" {
               description "1552.50 nm/193.103125 THz 3.125GHz spacing";
             }
             enum "1552.47" {
               description "1552.47 nm/193.106250 THz 3.125/6.25GHz spacing";
             }
             enum "1552.45" {
               description "1552.45 nm/193.109375 THz 3.125GHz spacing";
             }
             enum "1552.42" {
               description "1552.42 nm/193.112500 THz 3.125/6.25/12.5GHz spacing";
             }
             enum "1552.40" {
               description "1552.40 nm/193.115625 THz 3.125GHz spacing";
             }
             enum "1552.37" {
               description "1552.37 nm/193.118750 THz 3.125/6.25GHz spacing";
             }
             enum "1552.35" {
               description "1552.35 nm/193.121875 THz 3.125GHz spacing";
             }
             enum "1552.32" {
               description "1552.32 nm/193.125000 THz 3.125/6.25/12.5/75GHz spacing";
             }
             enum "1552.30" {
               description "1552.30 nm/193.128125 THz 3.125GHz spacing";
             }
             enum "1552.27" {
               description "1552.27 nm/193.131250 THz 3.125/6.25GHz spacing";
             }
             enum "1552.25" {
               description "1552.25 nm/193.134375 THz 3.125GHz spacing";
             }
             enum "1552.22" {
               description "1552.22 nm/193.137500 THz 3.125/6.25/12.5GHz spacing";
             }
             enum "1552.20" {
               description "1552.20 nm/193.140625 THz 3.125GHz spacing";
             }
             enum "1552.17" {
               description "1552.17 nm/193.143750 THz 3.125/6.25GHz spacing";
             }
             enum "1552.15" {
               description "1552.15 nm/193.146875 THz 3.125GHz spacing";
             }
             enum "1552.12" {
               description "1552.12 nm/193.150000 THz 3.125/6.25/12.5/50GHz spacing";
             }
             enum "1552.10" {
               description "1552.10 nm/193.153125 THz 3.125GHz spacing";
             }
             enum "1552.07" {
               description "1552.07 nm/193.156250 THz 3.125/6.25GHz spacing";
             }
             enum "1552.05" {
               description "1552.05 nm/193.159375 THz 3.125GHz spacing";
             }
             enum "1552.02" {
               description "1552.02 nm/193.162500 THz 3.125/6.25/12.5GHz spacing";
             }
             enum "1552.00" {
               description "1552.00 nm/193.165625 THz 3.125GHz spacing";
             }
             enum "1551.97" {
               description "1551.97 nm/193.168750 THz 3.125/6.25GHz spacing";
             }
             enum "1551.95" {
               description "1551.95 nm/193.171875 THz 3.125GHz spacing";
             }
             enum "1551.92" {
               description "1551.92 nm/193.175000 THz 3.125/6.25/12.5GHz spacing";
             }
             enum "1551.90" {
               description "1551.90 nm/193.178125 THz 3.125GHz spacing";
             }
             enum "1551.87" {
               description "1551.87 nm/193.181250 THz 3.125/6.25GHz spacing";
             }
             enum "1551.85" {
               description "1551.85 nm/193.184375 THz 3.125GHz spacing";
             }
             enum "1551.82" {
               description "1551.82 nm/193.187500 THz 3.125/6.25/12.5GHz spacing";
             }
             enum "1551.80" {
               description "1551.80 nm/193.190625 THz 3.125GHz spacing";
             }
             enum "1551.77" {
               description "1551.77 nm/193.193750 THz 3.125/6.25GHz spacing";
             }
             enum "1551.75" {
               description "1551.75 nm/193.196875 THz 3.125GHz spacing";
             }
             enum "1551.72" {
               description "1551.72 nm/193.200000 THz 3.125/6.25/12.5/50/75/100GHz spacing";
             }
             enum "1551.70" {
               description "1551.70 nm/193.203125 THz 3.125GHz spacing";
             }
             enum "1551.67" {
               description "1551.67 nm/193.206250 THz 3.125/6.25GHz spacing";
             }
             enum "1551.65" {
               description "1551.65 nm/193.209375 THz 3.125GHz spacing";
             }
             enum "1551.62" {
               description "1551.62 nm/193.212500 THz 3.125/6.25/12.5GHz spacing";
             }
             enum "1551.60" {
               description "1551.60 nm/193.215625 THz 3.125GHz spacing";
             }
             enum "1551.57" {
               description "1551.57 nm/193.218750 THz 3.125/6.25GHz spacing";
             }
             enum "1551.55" {
               description "1551.55 nm/193.221875 THz 3.125GHz spacing";
             }
             enum "1551.52" {
               description "1551.52 nm/193.225000 THz 3.125/6.25/12.5GHz spacing";
             }
             enum "1551.49" {
               description "1551.49 nm/193.228125 THz 3.125GHz spacing";
             }
             enum "1551.47" {
               description "1551.47 nm/193.231250 THz 3.125/6.25GHz spacing";
             }
             enum "1551.44" {
               description "1551.44 nm/193.234375 THz 3.125GHz spacing";
             }
             enum "1551.42" {
               description "1551.42 nm/193.237500 THz 3.125/6.25/12.5GHz spacing";
             }
             enum "1551.39" {
               description "1551.39 nm/193.240625 THz 3.125GHz spacing";
             }
             enum "1551.37" {
               description "1551.37 nm/193.243750 THz 3.125/6.25GHz spacing";
             }
             enum "1551.34" {
               description "1551.34 nm/193.246875 THz 3.125GHz spacing";
             }
             enum "1551.32" {
               description "1551.32 nm/193.250000 THz 3.125/6.25/12.5/50GHz spacing";
             }
             enum "1551.29" {
               description "1551.29 nm/193.253125 THz 3.125GHz spacing";
             }
             enum "1551.27" {
               description "1551.27 nm/193.256250 THz 3.125/6.25GHz spacing";
             }
             enum "1551.24" {
               description "1551.24 nm/193.259375 THz 3.125GHz spacing";
             }
             enum "1551.22" {
               description "1551.22 nm/193.262500 THz 3.125/6.25/12.5GHz spacing";
             }
             enum "1551.19" {
               description "1551.19 nm/193.265625 THz 3.125GHz spacing";
             }
             enum "1551.17" {
               description "1551.17 nm/193.268750 THz 3.125/6.25GHz spacing";
             }
             enum "1551.14" {
               description "1551.14 nm/193.271875 THz 3.125GHz spacing";
             }
             enum "1551.12" {
               description "1551.12 nm/193.275000 THz 3.125/6.25/12.5/75GHz spacing";
             }
             enum "1551.09" {
               description "1551.09 nm/193.278125 THz 3.125GHz spacing";
             }
             enum "1551.07" {
               description "1551.07 nm/193.281250 THz 3.125/6.25GHz spacing";
             }
             enum "1551.04" {
               description "1551.04 nm/193.284375 THz 3.125GHz spacing";
             }
             enum "1551.02" {
               description "1551.02 nm/193.287500 THz 3.125/6.25/12.5GHz spacing";
             }
             enum "1550.99" {
               description "1550.99 nm/193.290625 THz 3.125GHz spacing";
             }
             enum "1550.97" {
               description "1550.97 nm/193.293750 THz 3.125/6.25GHz spacing";
             }
             enum "1550.94" {
               description "1550.94 nm/193.296875 THz 3.125GHz spacing";
             }
             enum "1550.92" {
               description "1550.92 nm/193.300000 THz 3.125/6.25/12.5/100GHz spacing";
             }
             enum "1550.89" {
               description "1550.89 nm/193.303125 THz 3.125GHz spacing";
             }
             enum "1550.87" {
               description "1550.87 nm/193.306250 THz 3.125/6.25GHz spacing";
             }
             enum "1550.84" {
               description "1550.84 nm/193.309375 THz 3.125GHz spacing";
             }
             enum "1550.82" {
               description "1550.82 nm/193.312500 THz 3.125/6.25/12.5GHz spacing";
             }
             enum "1550.79" {
               description "1550.79 nm/193.315625 THz 3.125GHz spacing";
             }
             enum "1550.77" {
               description "1550.77 nm/193.318750 THz 3.125/6.25GHz spacing";
             }
             enum "1550.74" {
               description "1550.74 nm/193.321875 THz 3.125GHz spacing";
             }
             enum "1550.72" {
               description "1550.72 nm/193.325000 THz 3.125/6.25/12.5GHz spacing";
             }
             enum "1550.69" {
               description "1550.69 nm/193.328125 THz 3.125GHz spacing";
             }
             enum "1550.67" {
               description "1550.67 nm/193.331250 THz 3.125/6.25GHz spacing";
             }
             enum "1550.64" {
               description "1550.64 nm/193.334375 THz 3.125GHz spacing";
             }
             enum "1550.62" {
               description "1550.62 nm/193.337500 THz 3.125/6.25/12.5GHz spacing";
             }
             enum "1550.59" {
               description "1550.59 nm/193.340625 THz 3.125GHz spacing";
             }
             enum "1550.57" {
               description "1550.57 nm/193.343750 THz 3.125/6.25GHz spacing";
             }
             enum "1550.54" {
               description "1550.54 nm/193.346875 THz 3.125GHz spacing";
             }
             enum "1550.52" {
               description "1550.52 nm/193.350000 THz 3.125/6.25/12.5/50/75GHz spacing";
             }
             enum "1550.49" {
               description "1550.49 nm/193.353125 THz 3.125GHz spacing";
             }
             enum "1550.47" {
               description "1550.47 nm/193.356250 THz 3.125/6.25GHz spacing";
             }
             enum "1550.44" {
               description "1550.44 nm/193.359375 THz 3.125GHz spacing";
             }
             enum "1550.42" {
               description "1550.42 nm/193.362500 THz 3.125/6.25/12.5GHz spacing";
             }
             enum "1550.39" {
               description "1550.39 nm/193.365625 THz 3.125GHz spacing";
             }
             enum "1550.37" {
               description "1550.37 nm/193.368750 THz 3.125/6.25GHz spacing";
             }
             enum "1550.34" {
               description "1550.34 nm/193.371875 THz 3.125GHz spacing";
             }
             enum "1550.32" {
               description "1550.32 nm/193.375000 THz 3.125/6.25/12.5GHz spacing";
             }
             enum "1550.29" {
               description "1550.29 nm/193.378125 THz 3.125GHz spacing";
             }
             enum "1550.27" {
               description "1550.27 nm/193.381250 THz 3.125/6.25GHz spacing";
             }
             enum "1550.24" {
               description "1550.24 nm/193.384375 THz 3.125GHz spacing";
             }
             enum "1550.22" {
               description "1550.22 nm/193.387500 THz 3.125/6.25/12.5GHz spacing";
             }
             enum "1550.19" {
               description "1550.19 nm/193.390625 THz 3.125GHz spacing";
             }
             enum "1550.17" {
               description "1550.17 nm/193.393750 THz 3.125/6.25GHz spacing";
             }
             enum "1550.14" {
               description "1550.14 nm/193.396875 THz 3.125GHz spacing";
             }
             enum "1550.12" {
               description "1550.12 nm/193.400000 THz 3.125/6.25/12.5/100GHz spacing";
             }
             enum "1550.09" {
               description "1550.09 nm/193.403125 THz 3.125GHz spacing";
             }
             enum "1550.07" {
               description "1550.07 nm/193.406250 THz 3.125/6.25GHz spacing";
             }
             enum "1550.04" {
               description "1550.04 nm/193.409375 THz 3.125GHz spacing";
             }
             enum "1550.02" {
               description "1550.02 nm/193.412500 THz 3.125/6.25/12.5GHz spacing";
             }
             enum "1549.99" {
               description "1549.99 nm/193.415625 THz 3.125GHz spacing";
             }
             enum "1549.97" {
               description "1549.97 nm/193.418750 THz 3.125/6.25GHz spacing";
             }
             enum "1549.94" {
               description "1549.94 nm/193.421875 THz 3.125GHz spacing";
             }
             enum "1549.92" {
               description "1549.92 nm/193.425000 THz 3.125/6.25/12.5/75GHz spacing";
             }
             enum "1549.89" {
               description "1549.89 nm/193.428125 THz 3.125GHz spacing";
             }
             enum "1549.87" {
               description "1549.87 nm/193.431250 THz 3.125/6.25GHz spacing";
             }
             enum "1549.84" {
               description "1549.84 nm/193.434375 THz 3.125GHz spacing";
             }
             enum "1549.82" {
               description "1549.82 nm/193.437500 THz 3.125/6.25/12.5GHz spacing";
             }
             enum "1549.79" {
               description "1549.79 nm/193.440625 THz 3.125GHz spacing";
             }
             enum "1549.77" {
               description "1549.77 nm/193.443750 THz 3.125/6.25GHz spacing";
             }
             enum "1549.74" {
               description "1549.74 nm/193.446875 THz 3.125GHz spacing";
             }
             enum "1549.72" {
               description "1549.72 nm/193.450000 THz 3.125/6.25/12.5/50GHz spacing";
             }
             enum "1549.69" {
               description "1549.69 nm/193.453125 THz 3.125GHz spacing";
             }
             enum "1549.67" {
               description "1549.67 nm/193.456250 THz 3.125/6.25GHz spacing";
             }
             enum "1549.64" {
               description "1549.64 nm/193.459375 THz 3.125GHz spacing";
             }
             enum "1549.62" {
               description "1549.62 nm/193.462500 THz 3.125/6.25/12.5GHz spacing";
             }
             enum "1549.59" {
               description "1549.59 nm/193.465625 THz 3.125GHz spacing";
             }
             enum "1549.57" {
               description "1549.57 nm/193.468750 THz 3.125/6.25GHz spacing";
             }
             enum "1549.54" {
               description "1549.54 nm/193.471875 THz 3.125GHz spacing";
             }
             enum "1549.52" {
               description "1549.52 nm/193.475000 THz 3.125/6.25/12.5GHz spacing";
             }
             enum "1549.49" {
               description "1549.49 nm/193.478125 THz 3.125GHz spacing";
             }
             enum "1549.47" {
               description "1549.47 nm/193.481250 THz 3.125/6.25GHz spacing";
             }
             enum "1549.44" {
               description "1549.44 nm/193.484375 THz 3.125GHz spacing";
             }
             enum "1549.42" {
               description "1549.42 nm/193.487500 THz 3.125/6.25/12.5GHz spacing";
             }
             enum "1549.39" {
               description "1549.39 nm/193.490625 THz 3.125GHz spacing";
             }
             enum "1549.37" {
               description "1549.37 nm/193.493750 THz 3.125/6.25GHz spacing";
             }
             enum "1549.34" {
               description "1549.34 nm/193.496875 THz 3.125GHz spacing";
             }
             enum "1549.32" {
               description "1549.32 nm/193.500000 THz 3.125/6.25/12.5/50/75/100GHz spacing";
             }
             enum "1549.29" {
               description "1549.29 nm/193.503125 THz 3.125GHz spacing";
             }
             enum "1549.26" {
               description "1549.26 nm/193.506250 THz 3.125/6.25GHz spacing";
             }
             enum "1549.24" {
               description "1549.24 nm/193.509375 THz 3.125GHz spacing";
             }
             enum "1549.21" {
               description "1549.21 nm/193.512500 THz 3.125/6.25/12.5GHz spacing";
             }
             enum "1549.19" {
               description "1549.19 nm/193.515625 THz 3.125GHz spacing";
             }
             enum "1549.16" {
               description "1549.16 nm/193.518750 THz 3.125/6.25GHz spacing";
             }
             enum "1549.14" {
               description "1549.14 nm/193.521875 THz 3.125GHz spacing";
             }
             enum "1549.11" {
               description "1549.11 nm/193.525000 THz 3.125/6.25/12.5GHz spacing";
             }
             enum "1549.09" {
               description "1549.09 nm/193.528125 THz 3.125GHz spacing";
             }
             enum "1549.06" {
               description "1549.06 nm/193.531250 THz 3.125/6.25GHz spacing";
             }
             enum "1549.04" {
               description "1549.04 nm/193.534375 THz 3.125GHz spacing";
             }
             enum "1549.01" {
               description "1549.01 nm/193.537500 THz 3.125/6.25/12.5GHz spacing";
             }
             enum "1548.99" {
               description "1548.99 nm/193.540625 THz 3.125GHz spacing";
             }
             enum "1548.96" {
               description "1548.96 nm/193.543750 THz 3.125/6.25GHz spacing";
             }
             enum "1548.94" {
               description "1548.94 nm/193.546875 THz 3.125GHz spacing";
             }
             enum "1548.91" {
               description "1548.91 nm/193.550000 THz 3.125/6.25/12.5/50GHz spacing";
             }
             enum "1548.89" {
               description "1548.89 nm/193.553125 THz 3.125GHz spacing";
             }
             enum "1548.86" {
               description "1548.86 nm/193.556250 THz 3.125/6.25GHz spacing";
             }
             enum "1548.84" {
               description "1548.84 nm/193.559375 THz 3.125GHz spacing";
             }
             enum "1548.81" {
               description "1548.81 nm/193.562500 THz 3.125/6.25/12.5GHz spacing";
             }
             enum "1548.79" {
               description "1548.79 nm/193.565625 THz 3.125GHz spacing";
             }
             enum "1548.76" {
               description "1548.76 nm/193.568750 THz 3.125/6.25GHz spacing";
             }
             enum "1548.74" {
               description "1548.74 nm/193.571875 THz 3.125GHz spacing";
             }
             enum "1548.71" {
               description "1548.71 nm/193.575000 THz 3.125/6.25/12.5/75GHz spacing";
             }
             enum "1548.69" {
               description "1548.69 nm/193.578125 THz 3.125GHz spacing";
             }
             enum "1548.66" {
               description "1548.66 nm/193.581250 THz 3.125/6.25GHz spacing";
             }
             enum "1548.64" {
               description "1548.64 nm/193.584375 THz 3.125GHz spacing";
             }
             enum "1548.61" {
               description "1548.61 nm/193.587500 THz 3.125/6.25/12.5GHz spacing";
             }
             enum "1548.59" {
               description "1548.59 nm/193.590625 THz 3.125GHz spacing";
             }
             enum "1548.56" {
               description "1548.56 nm/193.593750 THz 3.125/6.25GHz spacing";
             }
             enum "1548.54" {
               description "1548.54 nm/193.596875 THz 3.125GHz spacing";
             }
             enum "1548.51" {
               description "1548.51 nm/193.600000 THz 3.125/6.25/12.5/100GHz spacing";
             }
             enum "1548.49" {
               description "1548.49 nm/193.603125 THz 3.125GHz spacing";
             }
             enum "1548.46" {
               description "1548.46 nm/193.606250 THz 3.125/6.25GHz spacing";
             }
             enum "1548.44" {
               description "1548.44 nm/193.609375 THz 3.125GHz spacing";
             }
             enum "1548.41" {
               description "1548.41 nm/193.612500 THz 3.125/6.25/12.5GHz spacing";
             }
             enum "1548.39" {
               description "1548.39 nm/193.615625 THz 3.125GHz spacing";
             }
             enum "1548.36" {
               description "1548.36 nm/193.618750 THz 3.125/6.25GHz spacing";
             }
             enum "1548.34" {
               description "1548.34 nm/193.621875 THz 3.125GHz spacing";
             }
             enum "1548.31" {
               description "1548.31 nm/193.625000 THz 3.125/6.25/12.5GHz spacing";
             }
             enum "1548.29" {
               description "1548.29 nm/193.628125 THz 3.125GHz spacing";
             }
             enum "1548.26" {
               description "1548.26 nm/193.631250 THz 3.125/6.25GHz spacing";
             }
             enum "1548.24" {
               description "1548.24 nm/193.634375 THz 3.125GHz spacing";
             }
             enum "1548.21" {
               description "1548.21 nm/193.637500 THz 3.125/6.25/12.5GHz spacing";
             }
             enum "1548.19" {
               description "1548.19 nm/193.640625 THz 3.125GHz spacing";
             }
             enum "1548.16" {
               description "1548.16 nm/193.643750 THz 3.125/6.25GHz spacing";
             }
             enum "1548.14" {
               description "1548.14 nm/193.646875 THz 3.125GHz spacing";
             }
             enum "1548.11" {
               description "1548.11 nm/193.650000 THz 3.125/6.25/12.5/50/75GHz spacing";
             }
             enum "1548.09" {
               description "1548.09 nm/193.653125 THz 3.125GHz spacing";
             }
             enum "1548.06" {
               description "1548.06 nm/193.656250 THz 3.125/6.25GHz spacing";
             }
             enum "1548.04" {
               description "1548.04 nm/193.659375 THz 3.125GHz spacing";
             }
             enum "1548.02" {
               description "1548.02 nm/193.662500 THz 3.125/6.25/12.5GHz spacing";
             }
             enum "1547.99" {
               description "1547.99 nm/193.665625 THz 3.125GHz spacing";
             }
             enum "1547.97" {
               description "1547.97 nm/193.668750 THz 3.125/6.25GHz spacing";
             }
             enum "1547.94" {
               description "1547.94 nm/193.671875 THz 3.125GHz spacing";
             }
             enum "1547.92" {
               description "1547.92 nm/193.675000 THz 3.125/6.25/12.5GHz spacing";
             }
             enum "1547.89" {
               description "1547.89 nm/193.678125 THz 3.125GHz spacing";
             }
             enum "1547.87" {
               description "1547.87 nm/193.681250 THz 3.125/6.25GHz spacing";
             }
             enum "1547.84" {
               description "1547.84 nm/193.684375 THz 3.125GHz spacing";
             }
             enum "1547.82" {
               description "1547.82 nm/193.687500 THz 3.125/6.25/12.5GHz spacing";
             }
             enum "1547.79" {
               description "1547.79 nm/193.690625 THz 3.125GHz spacing";
             }
             enum "1547.77" {
               description "1547.77 nm/193.693750 THz 3.125/6.25GHz spacing";
             }
             enum "1547.74" {
               description "1547.74 nm/193.696875 THz 3.125GHz spacing";
             }
             enum "1547.72" {
               description "1547.72 nm/193.700000 THz 3.125/6.25/12.5/100GHz spacing";
             }
             enum "1547.69" {
               description "1547.69 nm/193.703125 THz 3.125GHz spacing";
             }
             enum "1547.67" {
               description "1547.67 nm/193.706250 THz 3.125/6.25GHz spacing";
             }
             enum "1547.64" {
               description "1547.64 nm/193.709375 THz 3.125GHz spacing";
             }
             enum "1547.62" {
               description "1547.62 nm/193.712500 THz 3.125/6.25/12.5GHz spacing";
             }
             enum "1547.59" {
               description "1547.59 nm/193.715625 THz 3.125GHz spacing";
             }
             enum "1547.57" {
               description "1547.57 nm/193.718750 THz 3.125/6.25GHz spacing";
             }
             enum "1547.54" {
               description "1547.54 nm/193.721875 THz 3.125GHz spacing";
             }
             enum "1547.52" {
               description "1547.52 nm/193.725000 THz 3.125/6.25/12.5/75GHz spacing";
             }
             enum "1547.49" {
               description "1547.49 nm/193.728125 THz 3.125GHz spacing";
             }
             enum "1547.47" {
               description "1547.47 nm/193.731250 THz 3.125/6.25GHz spacing";
             }
             enum "1547.44" {
               description "1547.44 nm/193.734375 THz 3.125GHz spacing";
             }
             enum "1547.42" {
               description "1547.42 nm/193.737500 THz 3.125/6.25/12.5GHz spacing";
             }
             enum "1547.39" {
               description "1547.39 nm/193.740625 THz 3.125GHz spacing";
             }
             enum "1547.37" {
               description "1547.37 nm/193.743750 THz 3.125/6.25GHz spacing";
             }
             enum "1547.34" {
               description "1547.34 nm/193.746875 THz 3.125GHz spacing";
             }
             enum "1547.32" {
               description "1547.32 nm/193.750000 THz 3.125/6.25/12.5/50GHz spacing";
             }
             enum "1547.29" {
               description "1547.29 nm/193.753125 THz 3.125GHz spacing";
             }
             enum "1547.27" {
               description "1547.27 nm/193.756250 THz 3.125/6.25GHz spacing";
             }
             enum "1547.24" {
               description "1547.24 nm/193.759375 THz 3.125GHz spacing";
             }
             enum "1547.22" {
               description "1547.22 nm/193.762500 THz 3.125/6.25/12.5GHz spacing";
             }
             enum "1547.19" {
               description "1547.19 nm/193.765625 THz 3.125GHz spacing";
             }
             enum "1547.17" {
               description "1547.17 nm/193.768750 THz 3.125/6.25GHz spacing";
             }
             enum "1547.14" {
               description "1547.14 nm/193.771875 THz 3.125GHz spacing";
             }
             enum "1547.12" {
               description "1547.12 nm/193.775000 THz 3.125/6.25/12.5GHz spacing";
             }
             enum "1547.09" {
               description "1547.09 nm/193.778125 THz 3.125GHz spacing";
             }
             enum "1547.07" {
               description "1547.07 nm/193.781250 THz 3.125/6.25GHz spacing";
             }
             enum "1547.04" {
               description "1547.04 nm/193.784375 THz 3.125GHz spacing";
             }
             enum "1547.02" {
               description "1547.02 nm/193.787500 THz 3.125/6.25/12.5GHz spacing";
             }
             enum "1546.99" {
               description "1546.99 nm/193.790625 THz 3.125GHz spacing";
             }
             enum "1546.97" {
               description "1546.97 nm/193.793750 THz 3.125/6.25GHz spacing";
             }
             enum "1546.94" {
               description "1546.94 nm/193.796875 THz 3.125GHz spacing";
             }
             enum "1546.92" {
               description "1546.92 nm/193.800000 THz 3.125/6.25/12.5/50/75/100GHz spacing";
             }
             enum "1546.89" {
               description "1546.89 nm/193.803125 THz 3.125GHz spacing";
             }
             enum "1546.87" {
               description "1546.87 nm/193.806250 THz 3.125/6.25GHz spacing";
             }
             enum "1546.84" {
               description "1546.84 nm/193.809375 THz 3.125GHz spacing";
             }
             enum "1546.82" {
               description "1546.82 nm/193.812500 THz 3.125/6.25/12.5GHz spacing";
             }
             enum "1546.79" {
               description "1546.79 nm/193.815625 THz 3.125GHz spacing";
             }
             enum "1546.77" {
               description "1546.77 nm/193.818750 THz 3.125/6.25GHz spacing";
             }
             enum "1546.74" {
               description "1546.74 nm/193.821875 THz 3.125GHz spacing";
             }
             enum "1546.72" {
               description "1546.72 nm/193.825000 THz 3.125/6.25/12.5GHz spacing";
             }
             enum "1546.69" {
               description "1546.69 nm/193.828125 THz 3.125GHz spacing";
             }
             enum "1546.67" {
               description "1546.67 nm/193.831250 THz 3.125/6.25GHz spacing";
             }
             enum "1546.64" {
               description "1546.64 nm/193.834375 THz 3.125GHz spacing";
             }
             enum "1546.62" {
               description "1546.62 nm/193.837500 THz 3.125/6.25/12.5GHz spacing";
             }
             enum "1546.59" {
               description "1546.59 nm/193.840625 THz 3.125GHz spacing";
             }
             enum "1546.57" {
               description "1546.57 nm/193.843750 THz 3.125/6.25GHz spacing";
             }
             enum "1546.54" {
               description "1546.54 nm/193.846875 THz 3.125GHz spacing";
             }
             enum "1546.52" {
               description "1546.52 nm/193.850000 THz 3.125/6.25/12.5/50GHz spacing";
             }
             enum "1546.49" {
               description "1546.49 nm/193.853125 THz 3.125GHz spacing";
             }
             enum "1546.47" {
               description "1546.47 nm/193.856250 THz 3.125/6.25GHz spacing";
             }
             enum "1546.44" {
               description "1546.44 nm/193.859375 THz 3.125GHz spacing";
             }
             enum "1546.42" {
               description "1546.42 nm/193.862500 THz 3.125/6.25/12.5GHz spacing";
             }
             enum "1546.39" {
               description "1546.39 nm/193.865625 THz 3.125GHz spacing";
             }
             enum "1546.37" {
               description "1546.37 nm/193.868750 THz 3.125/6.25GHz spacing";
             }
             enum "1546.34" {
               description "1546.34 nm/193.871875 THz 3.125GHz spacing";
             }
             enum "1546.32" {
               description "1546.32 nm/193.875000 THz 3.125/6.25/12.5/75GHz spacing";
             }
             enum "1546.29" {
               description "1546.29 nm/193.878125 THz 3.125GHz spacing";
             }
             enum "1546.27" {
               description "1546.27 nm/193.881250 THz 3.125/6.25GHz spacing";
             }
             enum "1546.24" {
               description "1546.24 nm/193.884375 THz 3.125GHz spacing";
             }
             enum "1546.22" {
               description "1546.22 nm/193.887500 THz 3.125/6.25/12.5GHz spacing";
             }
             enum "1546.19" {
               description "1546.19 nm/193.890625 THz 3.125GHz spacing";
             }
             enum "1546.17" {
               description "1546.17 nm/193.893750 THz 3.125/6.25GHz spacing";
             }
             enum "1546.14" {
               description "1546.14 nm/193.896875 THz 3.125GHz spacing";
             }
             enum "1546.12" {
               description "1546.12 nm/193.900000 THz 3.125/6.25/12.5/100GHz spacing";
             }
             enum "1546.09" {
               description "1546.09 nm/193.903125 THz 3.125GHz spacing";
             }
             enum "1546.07" {
               description "1546.07 nm/193.906250 THz 3.125/6.25GHz spacing";
             }
             enum "1546.04" {
               description "1546.04 nm/193.909375 THz 3.125GHz spacing";
             }
             enum "1546.02" {
               description "1546.02 nm/193.912500 THz 3.125/6.25/12.5GHz spacing";
             }
             enum "1545.99" {
               description "1545.99 nm/193.915625 THz 3.125GHz spacing";
             }
             enum "1545.97" {
               description "1545.97 nm/193.918750 THz 3.125/6.25GHz spacing";
             }
             enum "1545.94" {
               description "1545.94 nm/193.921875 THz 3.125GHz spacing";
             }
             enum "1545.92" {
               description "1545.92 nm/193.925000 THz 3.125/6.25/12.5GHz spacing";
             }
             enum "1545.89" {
               description "1545.89 nm/193.928125 THz 3.125GHz spacing";
             }
             enum "1545.87" {
               description "1545.87 nm/193.931250 THz 3.125/6.25GHz spacing";
             }
             enum "1545.84" {
               description "1545.84 nm/193.934375 THz 3.125GHz spacing";
             }
             enum "1545.82" {
               description "1545.82 nm/193.937500 THz 3.125/6.25/12.5GHz spacing";
             }
             enum "1545.80" {
               description "1545.80 nm/193.940625 THz 3.125GHz spacing";
             }
             enum "1545.77" {
               description "1545.77 nm/193.943750 THz 3.125/6.25GHz spacing";
             }
             enum "1545.75" {
               description "1545.75 nm/193.946875 THz 3.125GHz spacing";
             }
             enum "1545.72" {
               description "1545.72 nm/193.950000 THz 3.125/6.25/12.5/50/75GHz spacing";
             }
             enum "1545.70" {
               description "1545.70 nm/193.953125 THz 3.125GHz spacing";
             }
             enum "1545.67" {
               description "1545.67 nm/193.956250 THz 3.125/6.25GHz spacing";
             }
             enum "1545.65" {
               description "1545.65 nm/193.959375 THz 3.125GHz spacing";
             }
             enum "1545.62" {
               description "1545.62 nm/193.962500 THz 3.125/6.25/12.5GHz spacing";
             }
             enum "1545.60" {
               description "1545.60 nm/193.965625 THz 3.125GHz spacing";
             }
             enum "1545.57" {
               description "1545.57 nm/193.968750 THz 3.125/6.25GHz spacing";
             }
             enum "1545.55" {
               description "1545.55 nm/193.971875 THz 3.125GHz spacing";
             }
             enum "1545.52" {
               description "1545.52 nm/193.975000 THz 3.125/6.25/12.5GHz spacing";
             }
             enum "1545.50" {
               description "1545.50 nm/193.978125 THz 3.125GHz spacing";
             }
             enum "1545.47" {
               description "1545.47 nm/193.981250 THz 3.125/6.25GHz spacing";
             }
             enum "1545.45" {
               description "1545.45 nm/193.984375 THz 3.125GHz spacing";
             }
             enum "1545.42" {
               description "1545.42 nm/193.987500 THz 3.125/6.25/12.5GHz spacing";
             }
             enum "1545.40" {
               description "1545.40 nm/193.990625 THz 3.125GHz spacing";
             }
             enum "1545.37" {
               description "1545.37 nm/193.993750 THz 3.125/6.25GHz spacing";
             }
             enum "1545.35" {
               description "1545.35 nm/193.996875 THz 3.125GHz spacing";
             }
             enum "1545.32" {
               description "1545.32 nm/194.000000 THz 3.125/6.25/12.5/100GHz spacing";
             }
             enum "1545.30" {
               description "1545.30 nm/194.003125 THz 3.125GHz spacing";
             }
             enum "1545.27" {
               description "1545.27 nm/194.006250 THz 3.125/6.25GHz spacing";
             }
             enum "1545.25" {
               description "1545.25 nm/194.009375 THz 3.125GHz spacing";
             }
             enum "1545.22" {
               description "1545.22 nm/194.012500 THz 3.125/6.25/12.5GHz spacing";
             }
             enum "1545.20" {
               description "1545.20 nm/194.015625 THz 3.125GHz spacing";
             }
             enum "1545.17" {
               description "1545.17 nm/194.018750 THz 3.125/6.25GHz spacing";
             }
             enum "1545.15" {
               description "1545.15 nm/194.021875 THz 3.125GHz spacing";
             }
             enum "1545.12" {
               description "1545.12 nm/194.025000 THz 3.125/6.25/12.5/75GHz spacing";
             }
             enum "1545.10" {
               description "1545.10 nm/194.028125 THz 3.125GHz spacing";
             }
             enum "1545.07" {
               description "1545.07 nm/194.031250 THz 3.125/6.25GHz spacing";
             }
             enum "1545.05" {
               description "1545.05 nm/194.034375 THz 3.125GHz spacing";
             }
             enum "1545.02" {
               description "1545.02 nm/194.037500 THz 3.125/6.25/12.5GHz spacing";
             }
             enum "1545.00" {
               description "1545.00 nm/194.040625 THz 3.125GHz spacing";
             }
             enum "1544.97" {
               description "1544.97 nm/194.043750 THz 3.125/6.25GHz spacing";
             }
             enum "1544.95" {
               description "1544.95 nm/194.046875 THz 3.125GHz spacing";
             }
             enum "1544.92" {
               description "1544.92 nm/194.050000 THz 3.125/6.25/12.5/50GHz spacing";
             }
             enum "1544.90" {
               description "1544.90 nm/194.053125 THz 3.125GHz spacing";
             }
             enum "1544.87" {
               description "1544.87 nm/194.056250 THz 3.125/6.25GHz spacing";
             }
             enum "1544.85" {
               description "1544.85 nm/194.059375 THz 3.125GHz spacing";
             }
             enum "1544.82" {
               description "1544.82 nm/194.062500 THz 3.125/6.25/12.5GHz spacing";
             }
             enum "1544.80" {
               description "1544.80 nm/194.065625 THz 3.125GHz spacing";
             }
             enum "1544.77" {
               description "1544.77 nm/194.068750 THz 3.125/6.25GHz spacing";
             }
             enum "1544.75" {
               description "1544.75 nm/194.071875 THz 3.125GHz spacing";
             }
             enum "1544.72" {
               description "1544.72 nm/194.075000 THz 3.125/6.25/12.5GHz spacing";
             }
             enum "1544.70" {
               description "1544.70 nm/194.078125 THz 3.125GHz spacing";
             }
             enum "1544.68" {
               description "1544.68 nm/194.081250 THz 3.125/6.25GHz spacing";
             }
             enum "1544.65" {
               description "1544.65 nm/194.084375 THz 3.125GHz spacing";
             }
             enum "1544.63" {
               description "1544.63 nm/194.087500 THz 3.125/6.25/12.5GHz spacing";
             }
             enum "1544.60" {
               description "1544.60 nm/194.090625 THz 3.125GHz spacing";
             }
             enum "1544.58" {
               description "1544.58 nm/194.093750 THz 3.125/6.25GHz spacing";
             }
             enum "1544.55" {
               description "1544.55 nm/194.096875 THz 3.125GHz spacing";
             }
             enum "1544.53" {
               description "1544.53 nm/194.100000 THz 3.125/6.25/12.5/50/75/100GHz spacing";
             }
             enum "1544.50" {
               description "1544.50 nm/194.103125 THz 3.125GHz spacing";
             }
             enum "1544.48" {
               description "1544.48 nm/194.106250 THz 3.125/6.25GHz spacing";
             }
             enum "1544.45" {
               description "1544.45 nm/194.109375 THz 3.125GHz spacing";
             }
             enum "1544.43" {
               description "1544.43 nm/194.112500 THz 3.125/6.25/12.5GHz spacing";
             }
             enum "1544.40" {
               description "1544.40 nm/194.115625 THz 3.125GHz spacing";
             }
             enum "1544.38" {
               description "1544.38 nm/194.118750 THz 3.125/6.25GHz spacing";
             }
             enum "1544.35" {
               description "1544.35 nm/194.121875 THz 3.125GHz spacing";
             }
             enum "1544.33" {
               description "1544.33 nm/194.125000 THz 3.125/6.25/12.5GHz spacing";
             }
             enum "1544.30" {
               description "1544.30 nm/194.128125 THz 3.125GHz spacing";
             }
             enum "1544.28" {
               description "1544.28 nm/194.131250 THz 3.125/6.25GHz spacing";
             }
             enum "1544.25" {
               description "1544.25 nm/194.134375 THz 3.125GHz spacing";
             }
             enum "1544.23" {
               description "1544.23 nm/194.137500 THz 3.125/6.25/12.5GHz spacing";
             }
             enum "1544.20" {
               description "1544.20 nm/194.140625 THz 3.125GHz spacing";
             }
             enum "1544.18" {
               description "1544.18 nm/194.143750 THz 3.125/6.25GHz spacing";
             }
             enum "1544.15" {
               description "1544.15 nm/194.146875 THz 3.125GHz spacing";
             }
             enum "1544.13" {
               description "1544.13 nm/194.150000 THz 3.125/6.25/12.5/50GHz spacing";
             }
             enum "1544.10" {
               description "1544.10 nm/194.153125 THz 3.125GHz spacing";
             }
             enum "1544.08" {
               description "1544.08 nm/194.156250 THz 3.125/6.25GHz spacing";
             }
             enum "1544.05" {
               description "1544.05 nm/194.159375 THz 3.125GHz spacing";
             }
             enum "1544.03" {
               description "1544.03 nm/194.162500 THz 3.125/6.25/12.5GHz spacing";
             }
             enum "1544.00" {
               description "1544.00 nm/194.165625 THz 3.125GHz spacing";
             }
             enum "1543.98" {
               description "1543.98 nm/194.168750 THz 3.125/6.25GHz spacing";
             }
             enum "1543.95" {
               description "1543.95 nm/194.171875 THz 3.125GHz spacing";
             }
             enum "1543.93" {
               description "1543.93 nm/194.175000 THz 3.125/6.25/12.5/75GHz spacing";
             }
             enum "1543.90" {
               description "1543.90 nm/194.178125 THz 3.125GHz spacing";
             }
             enum "1543.88" {
               description "1543.88 nm/194.181250 THz 3.125/6.25GHz spacing";
             }
             enum "1543.85" {
               description "1543.85 nm/194.184375 THz 3.125GHz spacing";
             }
             enum "1543.83" {
               description "1543.83 nm/194.187500 THz 3.125/6.25/12.5GHz spacing";
             }
             enum "1543.81" {
               description "1543.81 nm/194.190625 THz 3.125GHz spacing";
             }
             enum "1543.78" {
               description "1543.78 nm/194.193750 THz 3.125/6.25GHz spacing";
             }
             enum "1543.76" {
               description "1543.76 nm/194.196875 THz 3.125GHz spacing";
             }
             enum "1543.73" {
               description "1543.73 nm/194.200000 THz 3.125/6.25/12.5/100GHz spacing";
             }
             enum "1543.71" {
               description "1543.71 nm/194.203125 THz 3.125GHz spacing";
             }
             enum "1543.68" {
               description "1543.68 nm/194.206250 THz 3.125/6.25GHz spacing";
             }
             enum "1543.66" {
               description "1543.66 nm/194.209375 THz 3.125GHz spacing";
             }
             enum "1543.63" {
               description "1543.63 nm/194.212500 THz 3.125/6.25/12.5GHz spacing";
             }
             enum "1543.61" {
               description "1543.61 nm/194.215625 THz 3.125GHz spacing";
             }
             enum "1543.58" {
               description "1543.58 nm/194.218750 THz 3.125/6.25GHz spacing";
             }
             enum "1543.56" {
               description "1543.56 nm/194.221875 THz 3.125GHz spacing";
             }
             enum "1543.53" {
               description "1543.53 nm/194.225000 THz 3.125/6.25/12.5GHz spacing";
             }
             enum "1543.51" {
               description "1543.51 nm/194.228125 THz 3.125GHz spacing";
             }
             enum "1543.48" {
               description "1543.48 nm/194.231250 THz 3.125/6.25GHz spacing";
             }
             enum "1543.46" {
               description "1543.46 nm/194.234375 THz 3.125GHz spacing";
             }
             enum "1543.43" {
               description "1543.43 nm/194.237500 THz 3.125/6.25/12.5GHz spacing";
             }
             enum "1543.41" {
               description "1543.41 nm/194.240625 THz 3.125GHz spacing";
             }
             enum "1543.38" {
               description "1543.38 nm/194.243750 THz 3.125/6.25GHz spacing";
             }
             enum "1543.36" {
               description "1543.36 nm/194.246875 THz 3.125GHz spacing";
             }
             enum "1543.33" {
               description "1543.33 nm/194.250000 THz 3.125/6.25/12.5/50/75GHz spacing";
             }
             enum "1543.31" {
               description "1543.31 nm/194.253125 THz 3.125GHz spacing";
             }
             enum "1543.28" {
               description "1543.28 nm/194.256250 THz 3.125/6.25GHz spacing";
             }
             enum "1543.26" {
               description "1543.26 nm/194.259375 THz 3.125GHz spacing";
             }
             enum "1543.23" {
               description "1543.23 nm/194.262500 THz 3.125/6.25/12.5GHz spacing";
             }
             enum "1543.21" {
               description "1543.21 nm/194.265625 THz 3.125GHz spacing";
             }
             enum "1543.18" {
               description "1543.18 nm/194.268750 THz 3.125/6.25GHz spacing";
             }
             enum "1543.16" {
               description "1543.16 nm/194.271875 THz 3.125GHz spacing";
             }
             enum "1543.13" {
               description "1543.13 nm/194.275000 THz 3.125/6.25/12.5GHz spacing";
             }
             enum "1543.11" {
               description "1543.11 nm/194.278125 THz 3.125GHz spacing";
             }
             enum "1543.08" {
               description "1543.08 nm/194.281250 THz 3.125/6.25GHz spacing";
             }
             enum "1543.06" {
               description "1543.06 nm/194.284375 THz 3.125GHz spacing";
             }
             enum "1543.04" {
               description "1543.04 nm/194.287500 THz 3.125/6.25/12.5GHz spacing";
             }
             enum "1543.01" {
               description "1543.01 nm/194.290625 THz 3.125GHz spacing";
             }
             enum "1542.99" {
               description "1542.99 nm/194.293750 THz 3.125/6.25GHz spacing";
             }
             enum "1542.96" {
               description "1542.96 nm/194.296875 THz 3.125GHz spacing";
             }
             enum "1542.94" {
               description "1542.94 nm/194.300000 THz 3.125/6.25/12.5/100GHz spacing";
             }
             enum "1542.91" {
               description "1542.91 nm/194.303125 THz 3.125GHz spacing";
             }
             enum "1542.89" {
               description "1542.89 nm/194.306250 THz 3.125/6.25GHz spacing";
             }
             enum "1542.86" {
               description "1542.86 nm/194.309375 THz 3.125GHz spacing";
             }
             enum "1542.84" {
               description "1542.84 nm/194.312500 THz 3.125/6.25/12.5GHz spacing";
             }
             enum "1542.81" {
               description "1542.81 nm/194.315625 THz 3.125GHz spacing";
             }
             enum "1542.79" {
               description "1542.79 nm/194.318750 THz 3.125/6.25GHz spacing";
             }
             enum "1542.76" {
               description "1542.76 nm/194.321875 THz 3.125GHz spacing";
             }
             enum "1542.74" {
               description "1542.74 nm/194.325000 THz 3.125/6.25/12.5/75GHz spacing";
             }
             enum "1542.71" {
               description "1542.71 nm/194.328125 THz 3.125GHz spacing";
             }
             enum "1542.69" {
               description "1542.69 nm/194.331250 THz 3.125/6.25GHz spacing";
             }
             enum "1542.66" {
               description "1542.66 nm/194.334375 THz 3.125GHz spacing";
             }
             enum "1542.64" {
               description "1542.64 nm/194.337500 THz 3.125/6.25/12.5GHz spacing";
             }
             enum "1542.61" {
               description "1542.61 nm/194.340625 THz 3.125GHz spacing";
             }
             enum "1542.59" {
               description "1542.59 nm/194.343750 THz 3.125/6.25GHz spacing";
             }
             enum "1542.56" {
               description "1542.56 nm/194.346875 THz 3.125GHz spacing";
             }
             enum "1542.54" {
               description "1542.54 nm/194.350000 THz 3.125/6.25/12.5/50GHz spacing";
             }
             enum "1542.51" {
               description "1542.51 nm/194.353125 THz 3.125GHz spacing";
             }
             enum "1542.49" {
               description "1542.49 nm/194.356250 THz 3.125/6.25GHz spacing";
             }
             enum "1542.46" {
               description "1542.46 nm/194.359375 THz 3.125GHz spacing";
             }
             enum "1542.44" {
               description "1542.44 nm/194.362500 THz 3.125/6.25/12.5GHz spacing";
             }
             enum "1542.42" {
               description "1542.42 nm/194.365625 THz 3.125GHz spacing";
             }
             enum "1542.39" {
               description "1542.39 nm/194.368750 THz 3.125/6.25GHz spacing";
             }
             enum "1542.37" {
               description "1542.37 nm/194.371875 THz 3.125GHz spacing";
             }
             enum "1542.34" {
               description "1542.34 nm/194.375000 THz 3.125/6.25/12.5GHz spacing";
             }
             enum "1542.32" {
               description "1542.32 nm/194.378125 THz 3.125GHz spacing";
             }
             enum "1542.29" {
               description "1542.29 nm/194.381250 THz 3.125/6.25GHz spacing";
             }
             enum "1542.27" {
               description "1542.27 nm/194.384375 THz 3.125GHz spacing";
             }
             enum "1542.24" {
               description "1542.24 nm/194.387500 THz 3.125/6.25/12.5GHz spacing";
             }
             enum "1542.22" {
               description "1542.22 nm/194.390625 THz 3.125GHz spacing";
             }
             enum "1542.19" {
               description "1542.19 nm/194.393750 THz 3.125/6.25GHz spacing";
             }
             enum "1542.17" {
               description "1542.17 nm/194.396875 THz 3.125GHz spacing";
             }
             enum "1542.14" {
               description "1542.14 nm/194.400000 THz 3.125/6.25/12.5/50/75/100GHz spacing";
             }
             enum "1542.12" {
               description "1542.12 nm/194.403125 THz 3.125GHz spacing";
             }
             enum "1542.09" {
               description "1542.09 nm/194.406250 THz 3.125/6.25GHz spacing";
             }
             enum "1542.07" {
               description "1542.07 nm/194.409375 THz 3.125GHz spacing";
             }
             enum "1542.04" {
               description "1542.04 nm/194.412500 THz 3.125/6.25/12.5GHz spacing";
             }
             enum "1542.02" {
               description "1542.02 nm/194.415625 THz 3.125GHz spacing";
             }
             enum "1541.99" {
               description "1541.99 nm/194.418750 THz 3.125/6.25GHz spacing";
             }
             enum "1541.97" {
               description "1541.97 nm/194.421875 THz 3.125GHz spacing";
             }
             enum "1541.94" {
               description "1541.94 nm/194.425000 THz 3.125/6.25/12.5GHz spacing";
             }
             enum "1541.92" {
               description "1541.92 nm/194.428125 THz 3.125GHz spacing";
             }
             enum "1541.89" {
               description "1541.89 nm/194.431250 THz 3.125/6.25GHz spacing";
             }
             enum "1541.87" {
               description "1541.87 nm/194.434375 THz 3.125GHz spacing";
             }
             enum "1541.84" {
               description "1541.84 nm/194.437500 THz 3.125/6.25/12.5GHz spacing";
             }
             enum "1541.82" {
               description "1541.82 nm/194.440625 THz 3.125GHz spacing";
             }
             enum "1541.80" {
               description "1541.80 nm/194.443750 THz 3.125/6.25GHz spacing";
             }
             enum "1541.77" {
               description "1541.77 nm/194.446875 THz 3.125GHz spacing";
             }
             enum "1541.75" {
               description "1541.75 nm/194.450000 THz 3.125/6.25/12.5/50GHz spacing";
             }
             enum "1541.72" {
               description "1541.72 nm/194.453125 THz 3.125GHz spacing";
             }
             enum "1541.70" {
               description "1541.70 nm/194.456250 THz 3.125/6.25GHz spacing";
             }
             enum "1541.67" {
               description "1541.67 nm/194.459375 THz 3.125GHz spacing";
             }
             enum "1541.65" {
               description "1541.65 nm/194.462500 THz 3.125/6.25/12.5GHz spacing";
             }
             enum "1541.62" {
               description "1541.62 nm/194.465625 THz 3.125GHz spacing";
             }
             enum "1541.60" {
               description "1541.60 nm/194.468750 THz 3.125/6.25GHz spacing";
             }
             enum "1541.57" {
               description "1541.57 nm/194.471875 THz 3.125GHz spacing";
             }
             enum "1541.55" {
               description "1541.55 nm/194.475000 THz 3.125/6.25/12.5/75GHz spacing";
             }
             enum "1541.52" {
               description "1541.52 nm/194.478125 THz 3.125GHz spacing";
             }
             enum "1541.50" {
               description "1541.50 nm/194.481250 THz 3.125/6.25GHz spacing";
             }
             enum "1541.47" {
               description "1541.47 nm/194.484375 THz 3.125GHz spacing";
             }
             enum "1541.45" {
               description "1541.45 nm/194.487500 THz 3.125/6.25/12.5GHz spacing";
             }
             enum "1541.42" {
               description "1541.42 nm/194.490625 THz 3.125GHz spacing";
             }
             enum "1541.40" {
               description "1541.40 nm/194.493750 THz 3.125/6.25GHz spacing";
             }
             enum "1541.37" {
               description "1541.37 nm/194.496875 THz 3.125GHz spacing";
             }
             enum "1541.35" {
               description "1541.35 nm/194.500000 THz 3.125/6.25/12.5/100GHz spacing";
             }
             enum "1541.32" {
               description "1541.32 nm/194.503125 THz 3.125GHz spacing";
             }
             enum "1541.30" {
               description "1541.30 nm/194.506250 THz 3.125/6.25GHz spacing";
             }
             enum "1541.28" {
               description "1541.28 nm/194.509375 THz 3.125GHz spacing";
             }
             enum "1541.25" {
               description "1541.25 nm/194.512500 THz 3.125/6.25/12.5GHz spacing";
             }
             enum "1541.23" {
               description "1541.23 nm/194.515625 THz 3.125GHz spacing";
             }
             enum "1541.20" {
               description "1541.20 nm/194.518750 THz 3.125/6.25GHz spacing";
             }
             enum "1541.18" {
               description "1541.18 nm/194.521875 THz 3.125GHz spacing";
             }
             enum "1541.15" {
               description "1541.15 nm/194.525000 THz 3.125/6.25/12.5GHz spacing";
             }
             enum "1541.13" {
               description "1541.13 nm/194.528125 THz 3.125GHz spacing";
             }
             enum "1541.10" {
               description "1541.10 nm/194.531250 THz 3.125/6.25GHz spacing";
             }
             enum "1541.08" {
               description "1541.08 nm/194.534375 THz 3.125GHz spacing";
             }
             enum "1541.05" {
               description "1541.05 nm/194.537500 THz 3.125/6.25/12.5GHz spacing";
             }
             enum "1541.03" {
               description "1541.03 nm/194.540625 THz 3.125GHz spacing";
             }
             enum "1541.00" {
               description "1541.00 nm/194.543750 THz 3.125/6.25GHz spacing";
             }
             enum "1540.98" {
               description "1540.98 nm/194.546875 THz 3.125GHz spacing";
             }
             enum "1540.95" {
               description "1540.95 nm/194.550000 THz 3.125/6.25/12.5/50/75GHz spacing";
             }
             enum "1540.93" {
               description "1540.93 nm/194.553125 THz 3.125GHz spacing";
             }
             enum "1540.90" {
               description "1540.90 nm/194.556250 THz 3.125/6.25GHz spacing";
             }
             enum "1540.88" {
               description "1540.88 nm/194.559375 THz 3.125GHz spacing";
             }
             enum "1540.85" {
               description "1540.85 nm/194.562500 THz 3.125/6.25/12.5GHz spacing";
             }
             enum "1540.83" {
               description "1540.83 nm/194.565625 THz 3.125GHz spacing";
             }
             enum "1540.80" {
               description "1540.80 nm/194.568750 THz 3.125/6.25GHz spacing";
             }
             enum "1540.78" {
               description "1540.78 nm/194.571875 THz 3.125GHz spacing";
             }
             enum "1540.76" {
               description "1540.76 nm/194.575000 THz 3.125/6.25/12.5GHz spacing";
             }
             enum "1540.73" {
               description "1540.73 nm/194.578125 THz 3.125GHz spacing";
             }
             enum "1540.71" {
               description "1540.71 nm/194.581250 THz 3.125/6.25GHz spacing";
             }
             enum "1540.68" {
               description "1540.68 nm/194.584375 THz 3.125GHz spacing";
             }
             enum "1540.66" {
               description "1540.66 nm/194.587500 THz 3.125/6.25/12.5GHz spacing";
             }
             enum "1540.63" {
               description "1540.63 nm/194.590625 THz 3.125GHz spacing";
             }
             enum "1540.61" {
               description "1540.61 nm/194.593750 THz 3.125/6.25GHz spacing";
             }
             enum "1540.58" {
               description "1540.58 nm/194.596875 THz 3.125GHz spacing";
             }
             enum "1540.56" {
               description "1540.56 nm/194.600000 THz 3.125/6.25/12.5/100GHz spacing";
             }
             enum "1540.53" {
               description "1540.53 nm/194.603125 THz 3.125GHz spacing";
             }
             enum "1540.51" {
               description "1540.51 nm/194.606250 THz 3.125/6.25GHz spacing";
             }
             enum "1540.48" {
               description "1540.48 nm/194.609375 THz 3.125GHz spacing";
             }
             enum "1540.46" {
               description "1540.46 nm/194.612500 THz 3.125/6.25/12.5GHz spacing";
             }
             enum "1540.43" {
               description "1540.43 nm/194.615625 THz 3.125GHz spacing";
             }
             enum "1540.41" {
               description "1540.41 nm/194.618750 THz 3.125/6.25GHz spacing";
             }
             enum "1540.38" {
               description "1540.38 nm/194.621875 THz 3.125GHz spacing";
             }
             enum "1540.36" {
               description "1540.36 nm/194.625000 THz 3.125/6.25/12.5/75GHz spacing";
             }
             enum "1540.33" {
               description "1540.33 nm/194.628125 THz 3.125GHz spacing";
             }
             enum "1540.31" {
               description "1540.31 nm/194.631250 THz 3.125/6.25GHz spacing";
             }
             enum "1540.29" {
               description "1540.29 nm/194.634375 THz 3.125GHz spacing";
             }
             enum "1540.26" {
               description "1540.26 nm/194.637500 THz 3.125/6.25/12.5GHz spacing";
             }
             enum "1540.24" {
               description "1540.24 nm/194.640625 THz 3.125GHz spacing";
             }
             enum "1540.21" {
               description "1540.21 nm/194.643750 THz 3.125/6.25GHz spacing";
             }
             enum "1540.19" {
               description "1540.19 nm/194.646875 THz 3.125GHz spacing";
             }
             enum "1540.16" {
               description "1540.16 nm/194.650000 THz 3.125/6.25/12.5/50GHz spacing";
             }
             enum "1540.14" {
               description "1540.14 nm/194.653125 THz 3.125GHz spacing";
             }
             enum "1540.11" {
               description "1540.11 nm/194.656250 THz 3.125/6.25GHz spacing";
             }
             enum "1540.09" {
               description "1540.09 nm/194.659375 THz 3.125GHz spacing";
             }
             enum "1540.06" {
               description "1540.06 nm/194.662500 THz 3.125/6.25/12.5GHz spacing";
             }
             enum "1540.04" {
               description "1540.04 nm/194.665625 THz 3.125GHz spacing";
             }
             enum "1540.01" {
               description "1540.01 nm/194.668750 THz 3.125/6.25GHz spacing";
             }
             enum "1539.99" {
               description "1539.99 nm/194.671875 THz 3.125GHz spacing";
             }
             enum "1539.96" {
               description "1539.96 nm/194.675000 THz 3.125/6.25/12.5GHz spacing";
             }
             enum "1539.94" {
               description "1539.94 nm/194.678125 THz 3.125GHz spacing";
             }
             enum "1539.91" {
               description "1539.91 nm/194.681250 THz 3.125/6.25GHz spacing";
             }
             enum "1539.89" {
               description "1539.89 nm/194.684375 THz 3.125GHz spacing";
             }
             enum "1539.86" {
               description "1539.86 nm/194.687500 THz 3.125/6.25/12.5GHz spacing";
             }
             enum "1539.84" {
               description "1539.84 nm/194.690625 THz 3.125GHz spacing";
             }
             enum "1539.82" {
               description "1539.82 nm/194.693750 THz 3.125/6.25GHz spacing";
             }
             enum "1539.79" {
               description "1539.79 nm/194.696875 THz 3.125GHz spacing";
             }
             enum "1539.77" {
               description "1539.77 nm/194.700000 THz 3.125/6.25/12.5/50/75/100GHz spacing";
             }
             enum "1539.74" {
               description "1539.74 nm/194.703125 THz 3.125GHz spacing";
             }
             enum "1539.72" {
               description "1539.72 nm/194.706250 THz 3.125/6.25GHz spacing";
             }
             enum "1539.69" {
               description "1539.69 nm/194.709375 THz 3.125GHz spacing";
             }
             enum "1539.67" {
               description "1539.67 nm/194.712500 THz 3.125/6.25/12.5GHz spacing";
             }
             enum "1539.64" {
               description "1539.64 nm/194.715625 THz 3.125GHz spacing";
             }
             enum "1539.62" {
               description "1539.62 nm/194.718750 THz 3.125/6.25GHz spacing";
             }
             enum "1539.59" {
               description "1539.59 nm/194.721875 THz 3.125GHz spacing";
             }
             enum "1539.57" {
               description "1539.57 nm/194.725000 THz 3.125/6.25/12.5GHz spacing";
             }
             enum "1539.54" {
               description "1539.54 nm/194.728125 THz 3.125GHz spacing";
             }
             enum "1539.52" {
               description "1539.52 nm/194.731250 THz 3.125/6.25GHz spacing";
             }
             enum "1539.49" {
               description "1539.49 nm/194.734375 THz 3.125GHz spacing";
             }
             enum "1539.47" {
               description "1539.47 nm/194.737500 THz 3.125/6.25/12.5GHz spacing";
             }
             enum "1539.44" {
               description "1539.44 nm/194.740625 THz 3.125GHz spacing";
             }
             enum "1539.42" {
               description "1539.42 nm/194.743750 THz 3.125/6.25GHz spacing";
             }
             enum "1539.40" {
               description "1539.40 nm/194.746875 THz 3.125GHz spacing";
             }
             enum "1539.37" {
               description "1539.37 nm/194.750000 THz 3.125/6.25/12.5/50GHz spacing";
             }
             enum "1539.35" {
               description "1539.35 nm/194.753125 THz 3.125GHz spacing";
             }
             enum "1539.32" {
               description "1539.32 nm/194.756250 THz 3.125/6.25GHz spacing";
             }
             enum "1539.30" {
               description "1539.30 nm/194.759375 THz 3.125GHz spacing";
             }
             enum "1539.27" {
               description "1539.27 nm/194.762500 THz 3.125/6.25/12.5GHz spacing";
             }
             enum "1539.25" {
               description "1539.25 nm/194.765625 THz 3.125GHz spacing";
             }
             enum "1539.22" {
               description "1539.22 nm/194.768750 THz 3.125/6.25GHz spacing";
             }
             enum "1539.20" {
               description "1539.20 nm/194.771875 THz 3.125GHz spacing";
             }
             enum "1539.17" {
               description "1539.17 nm/194.775000 THz 3.125/6.25/12.5/75GHz spacing";
             }
             enum "1539.15" {
               description "1539.15 nm/194.778125 THz 3.125GHz spacing";
             }
             enum "1539.12" {
               description "1539.12 nm/194.781250 THz 3.125/6.25GHz spacing";
             }
             enum "1539.10" {
               description "1539.10 nm/194.784375 THz 3.125GHz spacing";
             }
             enum "1539.07" {
               description "1539.07 nm/194.787500 THz 3.125/6.25/12.5GHz spacing";
             }
             enum "1539.05" {
               description "1539.05 nm/194.790625 THz 3.125GHz spacing";
             }
             enum "1539.03" {
               description "1539.03 nm/194.793750 THz 3.125/6.25GHz spacing";
             }
             enum "1539.00" {
               description "1539.00 nm/194.796875 THz 3.125GHz spacing";
             }
             enum "1538.98" {
               description "1538.98 nm/194.800000 THz 3.125/6.25/12.5/100GHz spacing";
             }
             enum "1538.95" {
               description "1538.95 nm/194.803125 THz 3.125GHz spacing";
             }
             enum "1538.93" {
               description "1538.93 nm/194.806250 THz 3.125/6.25GHz spacing";
             }
             enum "1538.90" {
               description "1538.90 nm/194.809375 THz 3.125GHz spacing";
             }
             enum "1538.88" {
               description "1538.88 nm/194.812500 THz 3.125/6.25/12.5GHz spacing";
             }
             enum "1538.85" {
               description "1538.85 nm/194.815625 THz 3.125GHz spacing";
             }
             enum "1538.83" {
               description "1538.83 nm/194.818750 THz 3.125/6.25GHz spacing";
             }
             enum "1538.80" {
               description "1538.80 nm/194.821875 THz 3.125GHz spacing";
             }
             enum "1538.78" {
               description "1538.78 nm/194.825000 THz 3.125/6.25/12.5GHz spacing";
             }
             enum "1538.75" {
               description "1538.75 nm/194.828125 THz 3.125GHz spacing";
             }
             enum "1538.73" {
               description "1538.73 nm/194.831250 THz 3.125/6.25GHz spacing";
             }
             enum "1538.70" {
               description "1538.70 nm/194.834375 THz 3.125GHz spacing";
             }
             enum "1538.68" {
               description "1538.68 nm/194.837500 THz 3.125/6.25/12.5GHz spacing";
             }
             enum "1538.65" {
               description "1538.65 nm/194.840625 THz 3.125GHz spacing";
             }
             enum "1538.63" {
               description "1538.63 nm/194.843750 THz 3.125/6.25GHz spacing";
             }
             enum "1538.61" {
               description "1538.61 nm/194.846875 THz 3.125GHz spacing";
             }
             enum "1538.58" {
               description "1538.58 nm/194.850000 THz 3.125/6.25/12.5/50/75GHz spacing";
             }
             enum "1538.56" {
               description "1538.56 nm/194.853125 THz 3.125GHz spacing";
             }
             enum "1538.53" {
               description "1538.53 nm/194.856250 THz 3.125/6.25GHz spacing";
             }
             enum "1538.51" {
               description "1538.51 nm/194.859375 THz 3.125GHz spacing";
             }
             enum "1538.48" {
               description "1538.48 nm/194.862500 THz 3.125/6.25/12.5GHz spacing";
             }
             enum "1538.46" {
               description "1538.46 nm/194.865625 THz 3.125GHz spacing";
             }
             enum "1538.43" {
               description "1538.43 nm/194.868750 THz 3.125/6.25GHz spacing";
             }
             enum "1538.41" {
               description "1538.41 nm/194.871875 THz 3.125GHz spacing";
             }
             enum "1538.38" {
               description "1538.38 nm/194.875000 THz 3.125/6.25/12.5GHz spacing";
             }
             enum "1538.36" {
               description "1538.36 nm/194.878125 THz 3.125GHz spacing";
             }
             enum "1538.33" {
               description "1538.33 nm/194.881250 THz 3.125/6.25GHz spacing";
             }
             enum "1538.31" {
               description "1538.31 nm/194.884375 THz 3.125GHz spacing";
             }
             enum "1538.28" {
               description "1538.28 nm/194.887500 THz 3.125/6.25/12.5GHz spacing";
             }
             enum "1538.26" {
               description "1538.26 nm/194.890625 THz 3.125GHz spacing";
             }
             enum "1538.24" {
               description "1538.24 nm/194.893750 THz 3.125/6.25GHz spacing";
             }
             enum "1538.21" {
               description "1538.21 nm/194.896875 THz 3.125GHz spacing";
             }
             enum "1538.19" {
               description "1538.19 nm/194.900000 THz 3.125/6.25/12.5/100GHz spacing";
             }
             enum "1538.16" {
               description "1538.16 nm/194.903125 THz 3.125GHz spacing";
             }
             enum "1538.14" {
               description "1538.14 nm/194.906250 THz 3.125/6.25GHz spacing";
             }
             enum "1538.11" {
               description "1538.11 nm/194.909375 THz 3.125GHz spacing";
             }
             enum "1538.09" {
               description "1538.09 nm/194.912500 THz 3.125/6.25/12.5GHz spacing";
             }
             enum "1538.06" {
               description "1538.06 nm/194.915625 THz 3.125GHz spacing";
             }
             enum "1538.04" {
               description "1538.04 nm/194.918750 THz 3.125/6.25GHz spacing";
             }
             enum "1538.01" {
               description "1538.01 nm/194.921875 THz 3.125GHz spacing";
             }
             enum "1537.99" {
               description "1537.99 nm/194.925000 THz 3.125/6.25/12.5/75GHz spacing";
             }
             enum "1537.96" {
               description "1537.96 nm/194.928125 THz 3.125GHz spacing";
             }
             enum "1537.94" {
               description "1537.94 nm/194.931250 THz 3.125/6.25GHz spacing";
             }
             enum "1537.91" {
               description "1537.91 nm/194.934375 THz 3.125GHz spacing";
             }
             enum "1537.89" {
               description "1537.89 nm/194.937500 THz 3.125/6.25/12.5GHz spacing";
             }
             enum "1537.87" {
               description "1537.87 nm/194.940625 THz 3.125GHz spacing";
             }
             enum "1537.84" {
               description "1537.84 nm/194.943750 THz 3.125/6.25GHz spacing";
             }
             enum "1537.82" {
               description "1537.82 nm/194.946875 THz 3.125GHz spacing";
             }
             enum "1537.79" {
               description "1537.79 nm/194.950000 THz 3.125/6.25/12.5/50GHz spacing";
             }
             enum "1537.77" {
               description "1537.77 nm/194.953125 THz 3.125GHz spacing";
             }
             enum "1537.74" {
               description "1537.74 nm/194.956250 THz 3.125/6.25GHz spacing";
             }
             enum "1537.72" {
               description "1537.72 nm/194.959375 THz 3.125GHz spacing";
             }
             enum "1537.69" {
               description "1537.69 nm/194.962500 THz 3.125/6.25/12.5GHz spacing";
             }
             enum "1537.67" {
               description "1537.67 nm/194.965625 THz 3.125GHz spacing";
             }
             enum "1537.64" {
               description "1537.64 nm/194.968750 THz 3.125/6.25GHz spacing";
             }
             enum "1537.62" {
               description "1537.62 nm/194.971875 THz 3.125GHz spacing";
             }
             enum "1537.59" {
               description "1537.59 nm/194.975000 THz 3.125/6.25/12.5GHz spacing";
             }
             enum "1537.57" {
               description "1537.57 nm/194.978125 THz 3.125GHz spacing";
             }
             enum "1537.55" {
               description "1537.55 nm/194.981250 THz 3.125/6.25GHz spacing";
             }
             enum "1537.52" {
               description "1537.52 nm/194.984375 THz 3.125GHz spacing";
             }
             enum "1537.50" {
               description "1537.50 nm/194.987500 THz 3.125/6.25/12.5GHz spacing";
             }
             enum "1537.47" {
               description "1537.47 nm/194.990625 THz 3.125GHz spacing";
             }
             enum "1537.45" {
               description "1537.45 nm/194.993750 THz 3.125/6.25GHz spacing";
             }
             enum "1537.42" {
               description "1537.42 nm/194.996875 THz 3.125GHz spacing";
             }
             enum "1537.40" {
               description "1537.40 nm/195.000000 THz 3.125/6.25/12.5/50/75/100GHz spacing";
             }
             enum "1537.37" {
               description "1537.37 nm/195.003125 THz 3.125GHz spacing";
             }
             enum "1537.35" {
               description "1537.35 nm/195.006250 THz 3.125/6.25GHz spacing";
             }
             enum "1537.32" {
               description "1537.32 nm/195.009375 THz 3.125GHz spacing";
             }
             enum "1537.30" {
               description "1537.30 nm/195.012500 THz 3.125/6.25/12.5GHz spacing";
             }
             enum "1537.27" {
               description "1537.27 nm/195.015625 THz 3.125GHz spacing";
             }
             enum "1537.25" {
               description "1537.25 nm/195.018750 THz 3.125/6.25GHz spacing";
             }
             enum "1537.22" {
               description "1537.22 nm/195.021875 THz 3.125GHz spacing";
             }
             enum "1537.20" {
               description "1537.20 nm/195.025000 THz 3.125/6.25/12.5GHz spacing";
             }
             enum "1537.18" {
               description "1537.18 nm/195.028125 THz 3.125GHz spacing";
             }
             enum "1537.15" {
               description "1537.15 nm/195.031250 THz 3.125/6.25GHz spacing";
             }
             enum "1537.13" {
               description "1537.13 nm/195.034375 THz 3.125GHz spacing";
             }
             enum "1537.10" {
               description "1537.10 nm/195.037500 THz 3.125/6.25/12.5GHz spacing";
             }
             enum "1537.08" {
               description "1537.08 nm/195.040625 THz 3.125GHz spacing";
             }
             enum "1537.05" {
               description "1537.05 nm/195.043750 THz 3.125/6.25GHz spacing";
             }
             enum "1537.03" {
               description "1537.03 nm/195.046875 THz 3.125GHz spacing";
             }
             enum "1537.00" {
               description "1537.00 nm/195.050000 THz 3.125/6.25/12.5/50GHz spacing";
             }
             enum "1536.98" {
               description "1536.98 nm/195.053125 THz 3.125GHz spacing";
             }
             enum "1536.95" {
               description "1536.95 nm/195.056250 THz 3.125/6.25GHz spacing";
             }
             enum "1536.93" {
               description "1536.93 nm/195.059375 THz 3.125GHz spacing";
             }
             enum "1536.90" {
               description "1536.90 nm/195.062500 THz 3.125/6.25/12.5GHz spacing";
             }
             enum "1536.88" {
               description "1536.88 nm/195.065625 THz 3.125GHz spacing";
             }
             enum "1536.86" {
               description "1536.86 nm/195.068750 THz 3.125/6.25GHz spacing";
             }
             enum "1536.83" {
               description "1536.83 nm/195.071875 THz 3.125GHz spacing";
             }
             enum "1536.81" {
               description "1536.81 nm/195.075000 THz 3.125/6.25/12.5/75GHz spacing";
             }
             enum "1536.78" {
               description "1536.78 nm/195.078125 THz 3.125GHz spacing";
             }
             enum "1536.76" {
               description "1536.76 nm/195.081250 THz 3.125/6.25GHz spacing";
             }
             enum "1536.73" {
               description "1536.73 nm/195.084375 THz 3.125GHz spacing";
             }
             enum "1536.71" {
               description "1536.71 nm/195.087500 THz 3.125/6.25/12.5GHz spacing";
             }
             enum "1536.68" {
               description "1536.68 nm/195.090625 THz 3.125GHz spacing";
             }
             enum "1536.66" {
               description "1536.66 nm/195.093750 THz 3.125/6.25GHz spacing";
             }
             enum "1536.63" {
               description "1536.63 nm/195.096875 THz 3.125GHz spacing";
             }
             enum "1536.61" {
               description "1536.61 nm/195.100000 THz 3.125/6.25/12.5/100GHz spacing";
             }
             enum "1536.58" {
               description "1536.58 nm/195.103125 THz 3.125GHz spacing";
             }
             enum "1536.56" {
               description "1536.56 nm/195.106250 THz 3.125/6.25GHz spacing";
             }
             enum "1536.54" {
               description "1536.54 nm/195.109375 THz 3.125GHz spacing";
             }
             enum "1536.51" {
               description "1536.51 nm/195.112500 THz 3.125/6.25/12.5GHz spacing";
             }
             enum "1536.49" {
               description "1536.49 nm/195.115625 THz 3.125GHz spacing";
             }
             enum "1536.46" {
               description "1536.46 nm/195.118750 THz 3.125/6.25GHz spacing";
             }
             enum "1536.44" {
               description "1536.44 nm/195.121875 THz 3.125GHz spacing";
             }
             enum "1536.41" {
               description "1536.41 nm/195.125000 THz 3.125/6.25/12.5GHz spacing";
             }
             enum "1536.39" {
               description "1536.39 nm/195.128125 THz 3.125GHz spacing";
             }
             enum "1536.36" {
               description "1536.36 nm/195.131250 THz 3.125/6.25GHz spacing";
             }
             enum "1536.34" {
               description "1536.34 nm/195.134375 THz 3.125GHz spacing";
             }
             enum "1536.31" {
               description "1536.31 nm/195.137500 THz 3.125/6.25/12.5GHz spacing";
             }
             enum "1536.29" {
               description "1536.29 nm/195.140625 THz 3.125GHz spacing";
             }
             enum "1536.26" {
               description "1536.26 nm/195.143750 THz 3.125/6.25GHz spacing";
             }
             enum "1536.24" {
               description "1536.24 nm/195.146875 THz 3.125GHz spacing";
             }
             enum "1536.22" {
               description "1536.22 nm/195.150000 THz 3.125/6.25/12.5/50/75GHz spacing";
             }
             enum "1536.19" {
               description "1536.19 nm/195.153125 THz 3.125GHz spacing";
             }
             enum "1536.17" {
               description "1536.17 nm/195.156250 THz 3.125/6.25GHz spacing";
             }
             enum "1536.14" {
               description "1536.14 nm/195.159375 THz 3.125GHz spacing";
             }
             enum "1536.12" {
               description "1536.12 nm/195.162500 THz 3.125/6.25/12.5GHz spacing";
             }
             enum "1536.09" {
               description "1536.09 nm/195.165625 THz 3.125GHz spacing";
             }
             enum "1536.07" {
               description "1536.07 nm/195.168750 THz 3.125/6.25GHz spacing";
             }
             enum "1536.04" {
               description "1536.04 nm/195.171875 THz 3.125GHz spacing";
             }
             enum "1536.02" {
               description "1536.02 nm/195.175000 THz 3.125/6.25/12.5GHz spacing";
             }
             enum "1535.99" {
               description "1535.99 nm/195.178125 THz 3.125GHz spacing";
             }
             enum "1535.97" {
               description "1535.97 nm/195.181250 THz 3.125/6.25GHz spacing";
             }
             enum "1535.94" {
               description "1535.94 nm/195.184375 THz 3.125GHz spacing";
             }
             enum "1535.92" {
               description "1535.92 nm/195.187500 THz 3.125/6.25/12.5GHz spacing";
             }
             enum "1535.90" {
               description "1535.90 nm/195.190625 THz 3.125GHz spacing";
             }
             enum "1535.87" {
               description "1535.87 nm/195.193750 THz 3.125/6.25GHz spacing";
             }
             enum "1535.85" {
               description "1535.85 nm/195.196875 THz 3.125GHz spacing";
             }
             enum "1535.82" {
               description "1535.82 nm/195.200000 THz 3.125/6.25/12.5/100GHz spacing";
             }
             enum "1535.80" {
               description "1535.80 nm/195.203125 THz 3.125GHz spacing";
             }
             enum "1535.77" {
               description "1535.77 nm/195.206250 THz 3.125/6.25GHz spacing";
             }
             enum "1535.75" {
               description "1535.75 nm/195.209375 THz 3.125GHz spacing";
             }
             enum "1535.72" {
               description "1535.72 nm/195.212500 THz 3.125/6.25/12.5GHz spacing";
             }
             enum "1535.70" {
               description "1535.70 nm/195.215625 THz 3.125GHz spacing";
             }
             enum "1535.67" {
               description "1535.67 nm/195.218750 THz 3.125/6.25GHz spacing";
             }
             enum "1535.65" {
               description "1535.65 nm/195.221875 THz 3.125GHz spacing";
             }
             enum "1535.63" {
               description "1535.63 nm/195.225000 THz 3.125/6.25/12.5/75GHz spacing";
             }
             enum "1535.60" {
               description "1535.60 nm/195.228125 THz 3.125GHz spacing";
             }
             enum "1535.58" {
               description "1535.58 nm/195.231250 THz 3.125/6.25GHz spacing";
             }
             enum "1535.55" {
               description "1535.55 nm/195.234375 THz 3.125GHz spacing";
             }
             enum "1535.53" {
               description "1535.53 nm/195.237500 THz 3.125/6.25/12.5GHz spacing";
             }
             enum "1535.50" {
               description "1535.50 nm/195.240625 THz 3.125GHz spacing";
             }
             enum "1535.48" {
               description "1535.48 nm/195.243750 THz 3.125/6.25GHz spacing";
             }
             enum "1535.45" {
               description "1535.45 nm/195.246875 THz 3.125GHz spacing";
             }
             enum "1535.43" {
               description "1535.43 nm/195.250000 THz 3.125/6.25/12.5/50GHz spacing";
             }
             enum "1535.40" {
               description "1535.40 nm/195.253125 THz 3.125GHz spacing";
             }
             enum "1535.38" {
               description "1535.38 nm/195.256250 THz 3.125/6.25GHz spacing";
             }
             enum "1535.36" {
               description "1535.36 nm/195.259375 THz 3.125GHz spacing";
             }
             enum "1535.33" {
               description "1535.33 nm/195.262500 THz 3.125/6.25/12.5GHz spacing";
             }
             enum "1535.31" {
               description "1535.31 nm/195.265625 THz 3.125GHz spacing";
             }
             enum "1535.28" {
               description "1535.28 nm/195.268750 THz 3.125/6.25GHz spacing";
             }
             enum "1535.26" {
               description "1535.26 nm/195.271875 THz 3.125GHz spacing";
             }
             enum "1535.23" {
               description "1535.23 nm/195.275000 THz 3.125/6.25/12.5GHz spacing";
             }
             enum "1535.21" {
               description "1535.21 nm/195.278125 THz 3.125GHz spacing";
             }
             enum "1535.18" {
               description "1535.18 nm/195.281250 THz 3.125/6.25GHz spacing";
             }
             enum "1535.16" {
               description "1535.16 nm/195.284375 THz 3.125GHz spacing";
             }
             enum "1535.13" {
               description "1535.13 nm/195.287500 THz 3.125/6.25/12.5GHz spacing";
             }
             enum "1535.11" {
               description "1535.11 nm/195.290625 THz 3.125GHz spacing";
             }
             enum "1535.08" {
               description "1535.08 nm/195.293750 THz 3.125/6.25GHz spacing";
             }
             enum "1535.06" {
               description "1535.06 nm/195.296875 THz 3.125GHz spacing";
             }
             enum "1535.04" {
               description "1535.04 nm/195.300000 THz 3.125/6.25/12.5/50/75/100GHz spacing";
             }
             enum "1535.01" {
               description "1535.01 nm/195.303125 THz 3.125GHz spacing";
             }
             enum "1534.99" {
               description "1534.99 nm/195.306250 THz 3.125/6.25GHz spacing";
             }
             enum "1534.96" {
               description "1534.96 nm/195.309375 THz 3.125GHz spacing";
             }
             enum "1534.94" {
               description "1534.94 nm/195.312500 THz 3.125/6.25/12.5GHz spacing";
             }
             enum "1534.91" {
               description "1534.91 nm/195.315625 THz 3.125GHz spacing";
             }
             enum "1534.89" {
               description "1534.89 nm/195.318750 THz 3.125/6.25GHz spacing";
             }
             enum "1534.86" {
               description "1534.86 nm/195.321875 THz 3.125GHz spacing";
             }
             enum "1534.84" {
               description "1534.84 nm/195.325000 THz 3.125/6.25/12.5GHz spacing";
             }
             enum "1534.81" {
               description "1534.81 nm/195.328125 THz 3.125GHz spacing";
             }
             enum "1534.79" {
               description "1534.79 nm/195.331250 THz 3.125/6.25GHz spacing";
             }
             enum "1534.77" {
               description "1534.77 nm/195.334375 THz 3.125GHz spacing";
             }
             enum "1534.74" {
               description "1534.74 nm/195.337500 THz 3.125/6.25/12.5GHz spacing";
             }
             enum "1534.72" {
               description "1534.72 nm/195.340625 THz 3.125GHz spacing";
             }
             enum "1534.69" {
               description "1534.69 nm/195.343750 THz 3.125/6.25GHz spacing";
             }
             enum "1534.67" {
               description "1534.67 nm/195.346875 THz 3.125GHz spacing";
             }
             enum "1534.64" {
               description "1534.64 nm/195.350000 THz 3.125/6.25/12.5/50GHz spacing";
             }
             enum "1534.62" {
               description "1534.62 nm/195.353125 THz 3.125GHz spacing";
             }
             enum "1534.59" {
               description "1534.59 nm/195.356250 THz 3.125/6.25GHz spacing";
             }
             enum "1534.57" {
               description "1534.57 nm/195.359375 THz 3.125GHz spacing";
             }
             enum "1534.54" {
               description "1534.54 nm/195.362500 THz 3.125/6.25/12.5GHz spacing";
             }
             enum "1534.52" {
               description "1534.52 nm/195.365625 THz 3.125GHz spacing";
             }
             enum "1534.50" {
               description "1534.50 nm/195.368750 THz 3.125/6.25GHz spacing";
             }
             enum "1534.47" {
               description "1534.47 nm/195.371875 THz 3.125GHz spacing";
             }
             enum "1534.45" {
               description "1534.45 nm/195.375000 THz 3.125/6.25/12.5/75GHz spacing";
             }
             enum "1534.42" {
               description "1534.42 nm/195.378125 THz 3.125GHz spacing";
             }
             enum "1534.40" {
               description "1534.40 nm/195.381250 THz 3.125/6.25GHz spacing";
             }
             enum "1534.37" {
               description "1534.37 nm/195.384375 THz 3.125GHz spacing";
             }
             enum "1534.35" {
               description "1534.35 nm/195.387500 THz 3.125/6.25/12.5GHz spacing";
             }
             enum "1534.32" {
               description "1534.32 nm/195.390625 THz 3.125GHz spacing";
             }
             enum "1534.30" {
               description "1534.30 nm/195.393750 THz 3.125/6.25GHz spacing";
             }
             enum "1534.27" {
               description "1534.27 nm/195.396875 THz 3.125GHz spacing";
             }
             enum "1534.25" {
               description "1534.25 nm/195.400000 THz 3.125/6.25/12.5/100GHz spacing";
             }
             enum "1534.23" {
               description "1534.23 nm/195.403125 THz 3.125GHz spacing";
             }
             enum "1534.20" {
               description "1534.20 nm/195.406250 THz 3.125/6.25GHz spacing";
             }
             enum "1534.18" {
               description "1534.18 nm/195.409375 THz 3.125GHz spacing";
             }
             enum "1534.15" {
               description "1534.15 nm/195.412500 THz 3.125/6.25/12.5GHz spacing";
             }
             enum "1534.13" {
               description "1534.13 nm/195.415625 THz 3.125GHz spacing";
             }
             enum "1534.10" {
               description "1534.10 nm/195.418750 THz 3.125/6.25GHz spacing";
             }
             enum "1534.08" {
               description "1534.08 nm/195.421875 THz 3.125GHz spacing";
             }
             enum "1534.05" {
               description "1534.05 nm/195.425000 THz 3.125/6.25/12.5GHz spacing";
             }
             enum "1534.03" {
               description "1534.03 nm/195.428125 THz 3.125GHz spacing";
             }
             enum "1534.00" {
               description "1534.00 nm/195.431250 THz 3.125/6.25GHz spacing";
             }
             enum "1533.98" {
               description "1533.98 nm/195.434375 THz 3.125GHz spacing";
             }
             enum "1533.96" {
               description "1533.96 nm/195.437500 THz 3.125/6.25/12.5GHz spacing";
             }
             enum "1533.93" {
               description "1533.93 nm/195.440625 THz 3.125GHz spacing";
             }
             enum "1533.91" {
               description "1533.91 nm/195.443750 THz 3.125/6.25GHz spacing";
             }
             enum "1533.88" {
               description "1533.88 nm/195.446875 THz 3.125GHz spacing";
             }
             enum "1533.86" {
               description "1533.86 nm/195.450000 THz 3.125/6.25/12.5/50/75GHz spacing";
             }
             enum "1533.83" {
               description "1533.83 nm/195.453125 THz 3.125GHz spacing";
             }
             enum "1533.81" {
               description "1533.81 nm/195.456250 THz 3.125/6.25GHz spacing";
             }
             enum "1533.78" {
               description "1533.78 nm/195.459375 THz 3.125GHz spacing";
             }
             enum "1533.76" {
               description "1533.76 nm/195.462500 THz 3.125/6.25/12.5GHz spacing";
             }
             enum "1533.73" {
               description "1533.73 nm/195.465625 THz 3.125GHz spacing";
             }
             enum "1533.71" {
               description "1533.71 nm/195.468750 THz 3.125/6.25GHz spacing";
             }
             enum "1533.69" {
               description "1533.69 nm/195.471875 THz 3.125GHz spacing";
             }
             enum "1533.66" {
               description "1533.66 nm/195.475000 THz 3.125/6.25/12.5GHz spacing";
             }
             enum "1533.64" {
               description "1533.64 nm/195.478125 THz 3.125GHz spacing";
             }
             enum "1533.61" {
               description "1533.61 nm/195.481250 THz 3.125/6.25GHz spacing";
             }
             enum "1533.59" {
               description "1533.59 nm/195.484375 THz 3.125GHz spacing";
             }
             enum "1533.56" {
               description "1533.56 nm/195.487500 THz 3.125/6.25/12.5GHz spacing";
             }
             enum "1533.54" {
               description "1533.54 nm/195.490625 THz 3.125GHz spacing";
             }
             enum "1533.51" {
               description "1533.51 nm/195.493750 THz 3.125/6.25GHz spacing";
             }
             enum "1533.49" {
               description "1533.49 nm/195.496875 THz 3.125GHz spacing";
             }
             enum "1533.47" {
               description "1533.47 nm/195.500000 THz 3.125/6.25/12.5/100GHz spacing";
             }
             enum "1533.44" {
               description "1533.44 nm/195.503125 THz 3.125GHz spacing";
             }
             enum "1533.42" {
               description "1533.42 nm/195.506250 THz 3.125/6.25GHz spacing";
             }
             enum "1533.39" {
               description "1533.39 nm/195.509375 THz 3.125GHz spacing";
             }
             enum "1533.37" {
               description "1533.37 nm/195.512500 THz 3.125/6.25/12.5GHz spacing";
             }
             enum "1533.34" {
               description "1533.34 nm/195.515625 THz 3.125GHz spacing";
             }
             enum "1533.32" {
               description "1533.32 nm/195.518750 THz 3.125/6.25GHz spacing";
             }
             enum "1533.29" {
               description "1533.29 nm/195.521875 THz 3.125GHz spacing";
             }
             enum "1533.27" {
               description "1533.27 nm/195.525000 THz 3.125/6.25/12.5/75GHz spacing";
             }
             enum "1533.24" {
               description "1533.24 nm/195.528125 THz 3.125GHz spacing";
             }
             enum "1533.22" {
               description "1533.22 nm/195.531250 THz 3.125/6.25GHz spacing";
             }
             enum "1533.20" {
               description "1533.20 nm/195.534375 THz 3.125GHz spacing";
             }
             enum "1533.17" {
               description "1533.17 nm/195.537500 THz 3.125/6.25/12.5GHz spacing";
             }
             enum "1533.15" {
               description "1533.15 nm/195.540625 THz 3.125GHz spacing";
             }
             enum "1533.12" {
               description "1533.12 nm/195.543750 THz 3.125/6.25GHz spacing";
             }
             enum "1533.10" {
               description "1533.10 nm/195.546875 THz 3.125GHz spacing";
             }
             enum "1533.07" {
               description "1533.07 nm/195.550000 THz 3.125/6.25/12.5/50GHz spacing";
             }
             enum "1533.05" {
               description "1533.05 nm/195.553125 THz 3.125GHz spacing";
             }
             enum "1533.02" {
               description "1533.02 nm/195.556250 THz 3.125/6.25GHz spacing";
             }
             enum "1533.00" {
               description "1533.00 nm/195.559375 THz 3.125GHz spacing";
             }
             enum "1532.98" {
               description "1532.98 nm/195.562500 THz 3.125/6.25/12.5GHz spacing";
             }
             enum "1532.95" {
               description "1532.95 nm/195.565625 THz 3.125GHz spacing";
             }
             enum "1532.93" {
               description "1532.93 nm/195.568750 THz 3.125/6.25GHz spacing";
             }
             enum "1532.90" {
               description "1532.90 nm/195.571875 THz 3.125GHz spacing";
             }
             enum "1532.88" {
               description "1532.88 nm/195.575000 THz 3.125/6.25/12.5GHz spacing";
             }
             enum "1532.85" {
               description "1532.85 nm/195.578125 THz 3.125GHz spacing";
             }
             enum "1532.83" {
               description "1532.83 nm/195.581250 THz 3.125/6.25GHz spacing";
             }
             enum "1532.80" {
               description "1532.80 nm/195.584375 THz 3.125GHz spacing";
             }
             enum "1532.78" {
               description "1532.78 nm/195.587500 THz 3.125/6.25/12.5GHz spacing";
             }
             enum "1532.75" {
               description "1532.75 nm/195.590625 THz 3.125GHz spacing";
             }
             enum "1532.73" {
               description "1532.73 nm/195.593750 THz 3.125/6.25GHz spacing";
             }
             enum "1532.71" {
               description "1532.71 nm/195.596875 THz 3.125GHz spacing";
             }
             enum "1532.68" {
               description "1532.68 nm/195.600000 THz 3.125/6.25/12.5/50/75/100GHz spacing";
             }
             enum "1532.66" {
               description "1532.66 nm/195.603125 THz 3.125GHz spacing";
             }
             enum "1532.63" {
               description "1532.63 nm/195.606250 THz 3.125/6.25GHz spacing";
             }
             enum "1532.61" {
               description "1532.61 nm/195.609375 THz 3.125GHz spacing";
             }
             enum "1532.58" {
               description "1532.58 nm/195.612500 THz 3.125/6.25/12.5GHz spacing";
             }
             enum "1532.56" {
               description "1532.56 nm/195.615625 THz 3.125GHz spacing";
             }
             enum "1532.53" {
               description "1532.53 nm/195.618750 THz 3.125/6.25GHz spacing";
             }
             enum "1532.51" {
               description "1532.51 nm/195.621875 THz 3.125GHz spacing";
             }
             enum "1532.49" {
               description "1532.49 nm/195.625000 THz 3.125/6.25/12.5GHz spacing";
             }
             enum "1532.46" {
               description "1532.46 nm/195.628125 THz 3.125GHz spacing";
             }
             enum "1532.44" {
               description "1532.44 nm/195.631250 THz 3.125/6.25GHz spacing";
             }
             enum "1532.41" {
               description "1532.41 nm/195.634375 THz 3.125GHz spacing";
             }
             enum "1532.39" {
               description "1532.39 nm/195.637500 THz 3.125/6.25/12.5GHz spacing";
             }
             enum "1532.36" {
               description "1532.36 nm/195.640625 THz 3.125GHz spacing";
             }
             enum "1532.34" {
               description "1532.34 nm/195.643750 THz 3.125/6.25GHz spacing";
             }
             enum "1532.31" {
               description "1532.31 nm/195.646875 THz 3.125GHz spacing";
             }
             enum "1532.29" {
               description "1532.29 nm/195.650000 THz 3.125/6.25/12.5/50GHz spacing";
             }
             enum "1532.27" {
               description "1532.27 nm/195.653125 THz 3.125GHz spacing";
             }
             enum "1532.24" {
               description "1532.24 nm/195.656250 THz 3.125/6.25GHz spacing";
             }
             enum "1532.22" {
               description "1532.22 nm/195.659375 THz 3.125GHz spacing";
             }
             enum "1532.19" {
               description "1532.19 nm/195.662500 THz 3.125/6.25/12.5GHz spacing";
             }
             enum "1532.17" {
               description "1532.17 nm/195.665625 THz 3.125GHz spacing";
             }
             enum "1532.14" {
               description "1532.14 nm/195.668750 THz 3.125/6.25GHz spacing";
             }
             enum "1532.12" {
               description "1532.12 nm/195.671875 THz 3.125GHz spacing";
             }
             enum "1532.09" {
               description "1532.09 nm/195.675000 THz 3.125/6.25/12.5/75GHz spacing";
             }
             enum "1532.07" {
               description "1532.07 nm/195.678125 THz 3.125GHz spacing";
             }
             enum "1532.04" {
               description "1532.04 nm/195.681250 THz 3.125/6.25GHz spacing";
             }
             enum "1532.02" {
               description "1532.02 nm/195.684375 THz 3.125GHz spacing";
             }
             enum "1532.00" {
               description "1532.00 nm/195.687500 THz 3.125/6.25/12.5GHz spacing";
             }
             enum "1531.97" {
               description "1531.97 nm/195.690625 THz 3.125GHz spacing";
             }
             enum "1531.95" {
               description "1531.95 nm/195.693750 THz 3.125/6.25GHz spacing";
             }
             enum "1531.92" {
               description "1531.92 nm/195.696875 THz 3.125GHz spacing";
             }
             enum "1531.90" {
               description "1531.90 nm/195.700000 THz 3.125/6.25/12.5/100GHz spacing";
             }
             enum "1531.87" {
               description "1531.87 nm/195.703125 THz 3.125GHz spacing";
             }
             enum "1531.85" {
               description "1531.85 nm/195.706250 THz 3.125/6.25GHz spacing";
             }
             enum "1531.82" {
               description "1531.82 nm/195.709375 THz 3.125GHz spacing";
             }
             enum "1531.80" {
               description "1531.80 nm/195.712500 THz 3.125/6.25/12.5GHz spacing";
             }
             enum "1531.78" {
               description "1531.78 nm/195.715625 THz 3.125GHz spacing";
             }
             enum "1531.75" {
               description "1531.75 nm/195.718750 THz 3.125/6.25GHz spacing";
             }
             enum "1531.73" {
               description "1531.73 nm/195.721875 THz 3.125GHz spacing";
             }
             enum "1531.70" {
               description "1531.70 nm/195.725000 THz 3.125/6.25/12.5GHz spacing";
             }
             enum "1531.68" {
               description "1531.68 nm/195.728125 THz 3.125GHz spacing";
             }
             enum "1531.65" {
               description "1531.65 nm/195.731250 THz 3.125/6.25GHz spacing";
             }
             enum "1531.63" {
               description "1531.63 nm/195.734375 THz 3.125GHz spacing";
             }
             enum "1531.60" {
               description "1531.60 nm/195.737500 THz 3.125/6.25/12.5GHz spacing";
             }
             enum "1531.58" {
               description "1531.58 nm/195.740625 THz 3.125GHz spacing";
             }
             enum "1531.56" {
               description "1531.56 nm/195.743750 THz 3.125/6.25GHz spacing";
             }
             enum "1531.53" {
               description "1531.53 nm/195.746875 THz 3.125GHz spacing";
             }
             enum "1531.51" {
               description "1531.51 nm/195.750000 THz 3.125/6.25/12.5/50/75GHz spacing";
             }
             enum "1531.48" {
               description "1531.48 nm/195.753125 THz 3.125GHz spacing";
             }
             enum "1531.46" {
               description "1531.46 nm/195.756250 THz 3.125/6.25GHz spacing";
             }
             enum "1531.43" {
               description "1531.43 nm/195.759375 THz 3.125GHz spacing";
             }
             enum "1531.41" {
               description "1531.41 nm/195.762500 THz 3.125/6.25/12.5GHz spacing";
             }
             enum "1531.38" {
               description "1531.38 nm/195.765625 THz 3.125GHz spacing";
             }
             enum "1531.36" {
               description "1531.36 nm/195.768750 THz 3.125/6.25GHz spacing";
             }
             enum "1531.34" {
               description "1531.34 nm/195.771875 THz 3.125GHz spacing";
             }
             enum "1531.31" {
               description "1531.31 nm/195.775000 THz 3.125/6.25/12.5GHz spacing";
             }
             enum "1531.29" {
               description "1531.29 nm/195.778125 THz 3.125GHz spacing";
             }
             enum "1531.26" {
               description "1531.26 nm/195.781250 THz 3.125/6.25GHz spacing";
             }
             enum "1531.24" {
               description "1531.24 nm/195.784375 THz 3.125GHz spacing";
             }
             enum "1531.21" {
               description "1531.21 nm/195.787500 THz 3.125/6.25/12.5GHz spacing";
             }
             enum "1531.19" {
               description "1531.19 nm/195.790625 THz 3.125GHz spacing";
             }
             enum "1531.16" {
               description "1531.16 nm/195.793750 THz 3.125/6.25GHz spacing";
             }
             enum "1531.14" {
               description "1531.14 nm/195.796875 THz 3.125GHz spacing";
             }
             enum "1531.12" {
               description "1531.12 nm/195.800000 THz 3.125/6.25/12.5/100GHz spacing";
             }
             enum "1531.09" {
               description "1531.09 nm/195.803125 THz 3.125GHz spacing";
             }
             enum "1531.07" {
               description "1531.07 nm/195.806250 THz 3.125/6.25GHz spacing";
             }
             enum "1531.04" {
               description "1531.04 nm/195.809375 THz 3.125GHz spacing";
             }
             enum "1531.02" {
               description "1531.02 nm/195.812500 THz 3.125/6.25/12.5GHz spacing";
             }
             enum "1530.99" {
               description "1530.99 nm/195.815625 THz 3.125GHz spacing";
             }
             enum "1530.97" {
               description "1530.97 nm/195.818750 THz 3.125/6.25GHz spacing";
             }
             enum "1530.94" {
               description "1530.94 nm/195.821875 THz 3.125GHz spacing";
             }
             enum "1530.92" {
               description "1530.92 nm/195.825000 THz 3.125/6.25/12.5/75GHz spacing";
             }
             enum "1530.90" {
               description "1530.90 nm/195.828125 THz 3.125GHz spacing";
             }
             enum "1530.87" {
               description "1530.87 nm/195.831250 THz 3.125/6.25GHz spacing";
             }
             enum "1530.85" {
               description "1530.85 nm/195.834375 THz 3.125GHz spacing";
             }
             enum "1530.82" {
               description "1530.82 nm/195.837500 THz 3.125/6.25/12.5GHz spacing";
             }
             enum "1530.80" {
               description "1530.80 nm/195.840625 THz 3.125GHz spacing";
             }
             enum "1530.77" {
               description "1530.77 nm/195.843750 THz 3.125/6.25GHz spacing";
             }
             enum "1530.75" {
               description "1530.75 nm/195.846875 THz 3.125GHz spacing";
             }
             enum "1530.72" {
               description "1530.72 nm/195.850000 THz 3.125/6.25/12.5/50GHz spacing";
             }
             enum "1530.70" {
               description "1530.70 nm/195.853125 THz 3.125GHz spacing";
             }
             enum "1530.68" {
               description "1530.68 nm/195.856250 THz 3.125/6.25GHz spacing";
             }
             enum "1530.65" {
               description "1530.65 nm/195.859375 THz 3.125GHz spacing";
             }
             enum "1530.63" {
               description "1530.63 nm/195.862500 THz 3.125/6.25/12.5GHz spacing";
             }
             enum "1530.60" {
               description "1530.60 nm/195.865625 THz 3.125GHz spacing";
             }
             enum "1530.58" {
               description "1530.58 nm/195.868750 THz 3.125/6.25GHz spacing";
             }
             enum "1530.55" {
               description "1530.55 nm/195.871875 THz 3.125GHz spacing";
             }
             enum "1530.53" {
               description "1530.53 nm/195.875000 THz 3.125/6.25/12.5GHz spacing";
             }
             enum "1530.51" {
               description "1530.51 nm/195.878125 THz 3.125GHz spacing";
             }
             enum "1530.48" {
               description "1530.48 nm/195.881250 THz 3.125/6.25GHz spacing";
             }
             enum "1530.46" {
               description "1530.46 nm/195.884375 THz 3.125GHz spacing";
             }
             enum "1530.43" {
               description "1530.43 nm/195.887500 THz 3.125/6.25/12.5GHz spacing";
             }
             enum "1530.41" {
               description "1530.41 nm/195.890625 THz 3.125GHz spacing";
             }
             enum "1530.38" {
               description "1530.38 nm/195.893750 THz 3.125/6.25GHz spacing";
             }
             enum "1530.36" {
               description "1530.36 nm/195.896875 THz 3.125GHz spacing";
             }
             enum "1530.33" {
               description "1530.33 nm/195.900000 THz 3.125/6.25/12.5/50/75/100GHz spacing";
             }
             enum "1530.31" {
               description "1530.31 nm/195.903125 THz 3.125GHz spacing";
             }
             enum "1530.29" {
               description "1530.29 nm/195.906250 THz 3.125/6.25GHz spacing";
             }
             enum "1530.26" {
               description "1530.26 nm/195.909375 THz 3.125GHz spacing";
             }
             enum "1530.24" {
               description "1530.24 nm/195.912500 THz 3.125/6.25/12.5GHz spacing";
             }
             enum "1530.21" {
               description "1530.21 nm/195.915625 THz 3.125GHz spacing";
             }
             enum "1530.19" {
               description "1530.19 nm/195.918750 THz 3.125/6.25GHz spacing";
             }
             enum "1530.16" {
               description "1530.16 nm/195.921875 THz 3.125GHz spacing";
             }
             enum "1530.14" {
               description "1530.14 nm/195.925000 THz 3.125/6.25/12.5GHz spacing";
             }
             enum "1530.11" {
               description "1530.11 nm/195.928125 THz 3.125GHz spacing";
             }
             enum "1530.09" {
               description "1530.09 nm/195.931250 THz 3.125/6.25GHz spacing";
             }
             enum "1530.07" {
               description "1530.07 nm/195.934375 THz 3.125GHz spacing";
             }
             enum "1530.04" {
               description "1530.04 nm/195.937500 THz 3.125/6.25/12.5GHz spacing";
             }
             enum "1530.02" {
               description "1530.02 nm/195.940625 THz 3.125GHz spacing";
             }
             enum "1529.99" {
               description "1529.99 nm/195.943750 THz 3.125/6.25GHz spacing";
             }
             enum "1529.97" {
               description "1529.97 nm/195.946875 THz 3.125GHz spacing";
             }
             enum "1529.94" {
               description "1529.94 nm/195.950000 THz 3.125/6.25/12.5/50GHz spacing";
             }
             enum "1529.92" {
               description "1529.92 nm/195.953125 THz 3.125GHz spacing";
             }
             enum "1529.89" {
               description "1529.89 nm/195.956250 THz 3.125/6.25GHz spacing";
             }
             enum "1529.87" {
               description "1529.87 nm/195.959375 THz 3.125GHz spacing";
             }
             enum "1529.85" {
               description "1529.85 nm/195.962500 THz 3.125/6.25/12.5GHz spacing";
             }
             enum "1529.82" {
               description "1529.82 nm/195.965625 THz 3.125GHz spacing";
             }
             enum "1529.80" {
               description "1529.80 nm/195.968750 THz 3.125/6.25GHz spacing";
             }
             enum "1529.77" {
               description "1529.77 nm/195.971875 THz 3.125GHz spacing";
             }
             enum "1529.75" {
               description "1529.75 nm/195.975000 THz 3.125/6.25/12.5/75GHz spacing";
             }
             enum "1529.72" {
               description "1529.72 nm/195.978125 THz 3.125GHz spacing";
             }
             enum "1529.70" {
               description "1529.70 nm/195.981250 THz 3.125/6.25GHz spacing";
             }
             enum "1529.68" {
               description "1529.68 nm/195.984375 THz 3.125GHz spacing";
             }
             enum "1529.65" {
               description "1529.65 nm/195.987500 THz 3.125/6.25/12.5GHz spacing";
             }
             enum "1529.63" {
               description "1529.63 nm/195.990625 THz 3.125GHz spacing";
             }
             enum "1529.60" {
               description "1529.60 nm/195.993750 THz 3.125/6.25GHz spacing";
             }
             enum "1529.58" {
               description "1529.58 nm/195.996875 THz 3.125GHz spacing";
             }
             enum "1529.55" {
               description "1529.55 nm/196.000000 THz 3.125/6.25/12.5/100GHz spacing";
             }
             enum "1529.53" {
               description "1529.53 nm/196.003125 THz 3.125GHz spacing";
             }
             enum "1529.50" {
               description "1529.50 nm/196.006250 THz 3.125/6.25GHz spacing";
             }
             enum "1529.48" {
               description "1529.48 nm/196.009375 THz 3.125GHz spacing";
             }
             enum "1529.46" {
               description "1529.46 nm/196.012500 THz 3.125/6.25/12.5GHz spacing";
             }
             enum "1529.43" {
               description "1529.43 nm/196.015625 THz 3.125GHz spacing";
             }
             enum "1529.41" {
               description "1529.41 nm/196.018750 THz 3.125/6.25GHz spacing";
             }
             enum "1529.38" {
               description "1529.38 nm/196.021875 THz 3.125GHz spacing";
             }
             enum "1529.36" {
               description "1529.36 nm/196.025000 THz 3.125/6.25/12.5GHz spacing";
             }
             enum "1529.33" {
               description "1529.33 nm/196.028125 THz 3.125GHz spacing";
             }
             enum "1529.31" {
               description "1529.31 nm/196.031250 THz 3.125/6.25GHz spacing";
             }
             enum "1529.29" {
               description "1529.29 nm/196.034375 THz 3.125GHz spacing";
             }
             enum "1529.26" {
               description "1529.26 nm/196.037500 THz 3.125/6.25/12.5GHz spacing";
             }
             enum "1529.24" {
               description "1529.24 nm/196.040625 THz 3.125GHz spacing";
             }
             enum "1529.21" {
               description "1529.21 nm/196.043750 THz 3.125/6.25GHz spacing";
             }
             enum "1529.19" {
               description "1529.19 nm/196.046875 THz 3.125GHz spacing";
             }
             enum "1529.16" {
               description "1529.16 nm/196.050000 THz 3.125/6.25/12.5/50/75GHz spacing";
             }
             enum "1529.14" {
               description "1529.14 nm/196.053125 THz 3.125GHz spacing";
             }
             enum "1529.11" {
               description "1529.11 nm/196.056250 THz 3.125/6.25GHz spacing";
             }
             enum "1529.09" {
               description "1529.09 nm/196.059375 THz 3.125GHz spacing";
             }
             enum "1529.07" {
               description "1529.07 nm/196.062500 THz 3.125/6.25/12.5GHz spacing";
             }
             enum "1529.04" {
               description "1529.04 nm/196.065625 THz 3.125GHz spacing";
             }
             enum "1529.02" {
               description "1529.02 nm/196.068750 THz 3.125/6.25GHz spacing";
             }
             enum "1528.99" {
               description "1528.99 nm/196.071875 THz 3.125GHz spacing";
             }
             enum "1528.97" {
               description "1528.97 nm/196.075000 THz 3.125/6.25/12.5GHz spacing";
             }
             enum "1528.94" {
               description "1528.94 nm/196.078125 THz 3.125GHz spacing";
             }
             enum "1528.92" {
               description "1528.92 nm/196.081250 THz 3.125/6.25GHz spacing";
             }
             enum "1528.90" {
               description "1528.90 nm/196.084375 THz 3.125GHz spacing";
             }
             enum "1528.87" {
               description "1528.87 nm/196.087500 THz 3.125/6.25/12.5GHz spacing";
             }
             enum "1528.85" {
               description "1528.85 nm/196.090625 THz 3.125GHz spacing";
             }
             enum "1528.82" {
               description "1528.82 nm/196.093750 THz 3.125/6.25GHz spacing";
             }
             enum "1528.80" {
               description "1528.80 nm/196.096875 THz 3.125GHz spacing";
             }
             enum "1528.77" {
               description "1528.77 nm/196.100000 THz 3.125/6.25/12.5/50/75/100GHz spacing";
             }
             enum "1528.75" {
               description "1528.75 nm/196.103125 THz 3.125GHz spacing";
             }
             enum "1528.72" {
               description "1528.72 nm/196.106250 THz 3.125/6.25GHz spacing";
             }
             enum "1528.70" {
               description "1528.70 nm/196.109375 THz 3.125GHz spacing";
             }
             enum "1528.68" {
               description "1528.68 nm/196.112500 THz 3.125/6.25/12.5GHz spacing";
             }
             enum "1528.65" {
               description "1528.65 nm/196.115625 THz 3.125GHz spacing";
             }
             enum "1528.63" {
               description "1528.63 nm/196.118750 THz 3.125/6.25GHz spacing";
             }
             enum "1528.60" {
               description "1528.60 nm/196.121875 THz 3.125GHz spacing";
             }
             enum "1528.58" {
               description "1528.58 nm/196.125000 THz 3.125/6.25/12.5/75GHz spacing";
             }
             enum "1528.55" {
               description "1528.55 nm/196.128125 THz 3.125GHz spacing";
             }
             enum "1528.53" {
               description "1528.53 nm/196.131250 THz 3.125/6.25GHz spacing";
             }
             enum "1528.51" {
               description "1528.51 nm/196.134375 THz 3.125GHz spacing";
             }
             enum "1528.48" {
               description "1528.48 nm/196.137500 THz 3.125/6.25/12.5GHz spacing";
             }
             enum "1528.46" {
               description "1528.46 nm/196.140625 THz 3.125GHz spacing";
             }
             enum "1528.43" {
               description "1528.43 nm/196.143750 THz 3.125/6.25GHz spacing";
             }
             enum "1528.41" {
               description "1528.41 nm/196.146875 THz 3.125GHz spacing";
             }
             enum "1528.38" {
               description "1528.38 nm/196.15040 THz 50Ghz spacing";
             }
           }
         }
       }
       case case_2 {
         leaf frequency {
           description "Optical channel frequency in terahertz";
           type enumeration {
             enum "191.1003" {
               description "191.1003 THz/1568.77 nm 50/100Ghz spacing";
             }
             enum "191.15000" {
               description "191.15000 THz/1568.36 nm 6.25/12.5/50GHz spacing";
             }
             enum "191.15625" {
               description "191.15625 THz/1568.31 nm 6.25GHz spacing";
             }
             enum "191.16250" {
               description "191.16250 THz/1568.26 nm 6.25/12.5GHz spacing";
             }
             enum "191.16875" {
               description "191.16875 THz/1568.21 nm 6.25GHz spacing";
             }
             enum "191.17500" {
               description "191.17500 THz/1568.16 nm 6.25/12.5GHz spacing";
             }
             enum "191.18125" {
               description "191.18125 THz/1568.11 nm 6.25GHz spacing";
             }
             enum "191.18750" {
               description "191.18750 THz/1568.05 nm 6.25/12.5GHz spacing";
             }
             enum "191.19375" {
               description "191.19375 THz/1568.00 nm 6.25GHz spacing";
             }
             enum "191.20000" {
               description "191.20000 THz/1567.95 nm 6.25/12.5/50/100GHz spacing";
             }
             enum "191.20625" {
               description "191.20625 THz/1567.90 nm 6.25GHz spacing";
             }
             enum "191.21250" {
               description "191.21250 THz/1567.85 nm 6.25/12.5GHz spacing";
             }
             enum "191.21875" {
               description "191.21875 THz/1567.80 nm 6.25GHz spacing";
             }
             enum "191.22500" {
               description "191.22500 THz/1567.75 nm 6.25/12.5GHz spacing";
             }
             enum "191.23125" {
               description "191.23125 THz/1567.70 nm 6.25GHz spacing";
             }
             enum "191.23750" {
               description "191.23750 THz/1567.64 nm 6.25/12.5GHz spacing";
             }
             enum "191.24375" {
               description "191.24375 THz/1567.59 nm 6.25GHz spacing";
             }
             enum "191.25000" {
               description "191.25000 THz/1567.54 nm 6.25/12.5/50GHz spacing";
             }
             enum "191.25625" {
               description "191.25625 THz/1567.49 nm 6.25GHz spacing";
             }
             enum "191.26250" {
               description "191.26250 THz/1567.44 nm 6.25/12.5GHz spacing";
             }
             enum "191.26875" {
               description "191.26875 THz/1567.39 nm 6.25GHz spacing";
             }
             enum "191.27500" {
               description "191.27500 THz/1567.34 nm 6.25/12.5GHz spacing";
             }
             enum "191.28125" {
               description "191.28125 THz/1567.29 nm 6.25GHz spacing";
             }
             enum "191.28750" {
               description "191.28750 THz/1567.23 nm 6.25/12.5GHz spacing";
             }
             enum "191.29375" {
               description "191.29375 THz/1567.18 nm 6.25GHz spacing";
             }
             enum "191.30000" {
               description "191.30000 THz/1567.13 nm 6.25/12.5/50/100GHz spacing";
             }
             enum "191.30625" {
               description "191.30625 THz/1567.08 nm 6.25GHz spacing";
             }
             enum "191.31250" {
               description "191.31250 THz/1567.03 nm 6.25/12.5GHz spacing";
             }
             enum "191.31875" {
               description "191.31875 THz/1566.98 nm 6.25GHz spacing";
             }
             enum "191.32500" {
               description "191.32500 THz/1566.93 nm 6.25/12.5GHz spacing";
             }
             enum "191.33125" {
               description "191.33125 THz/1566.88 nm 6.25GHz spacing";
             }
             enum "191.33750" {
               description "191.33750 THz/1566.83 nm 6.25/12.5GHz spacing";
             }
             enum "191.34375" {
               description "191.34375 THz/1566.77 nm 6.25GHz spacing";
             }
             enum "191.35000" {
               description "191.35000 THz/1566.72 nm 6.25/12.5/50GHz spacing";
             }
             enum "191.35625" {
               description "191.35625 THz/1566.67 nm 6.25GHz spacing";
             }
             enum "191.36250" {
               description "191.36250 THz/1566.62 nm 6.25/12.5GHz spacing";
             }
             enum "191.36875" {
               description "191.36875 THz/1566.57 nm 6.25GHz spacing";
             }
             enum "191.37500" {
               description "191.37500 THz/1566.52 nm 6.25/12.5/75GHz spacing";
             }
             enum "191.38125" {
               description "191.38125 THz/1566.47 nm 6.25GHz spacing";
             }
             enum "191.38750" {
               description "191.38750 THz/1566.42 nm 6.25/12.5GHz spacing";
             }
             enum "191.39375" {
               description "191.39375 THz/1566.36 nm 6.25GHz spacing";
             }
             enum "191.40000" {
               description "191.40000 THz/1566.31 nm 6.25/12.5/50/100GHz spacing";
             }
             enum "191.40625" {
               description "191.40625 THz/1566.26 nm 6.25GHz spacing";
             }
             enum "191.41250" {
               description "191.41250 THz/1566.21 nm 6.25/12.5GHz spacing";
             }
             enum "191.41875" {
               description "191.41875 THz/1566.16 nm 6.25GHz spacing";
             }
             enum "191.42500" {
               description "191.42500 THz/1566.11 nm 6.25/12.5GHz spacing";
             }
             enum "191.43125" {
               description "191.43125 THz/1566.06 nm 6.25GHz spacing";
             }
             enum "191.43750" {
               description "191.43750 THz/1566.01 nm 6.25/12.5GHz spacing";
             }
             enum "191.44375" {
               description "191.44375 THz/1565.96 nm 6.25GHz spacing";
             }
             enum "191.45000" {
               description "191.45000 THz/1565.90 nm 6.25/12.5/50/75GHz spacing";
             }
             enum "191.45625" {
               description "191.45625 THz/1565.85 nm 6.25GHz spacing";
             }
             enum "191.46250" {
               description "191.46250 THz/1565.80 nm 6.25/12.5GHz spacing";
             }
             enum "191.46875" {
               description "191.46875 THz/1565.75 nm 6.25GHz spacing";
             }
             enum "191.47500" {
               description "191.47500 THz/1565.70 nm 6.25/12.5GHz spacing";
             }
             enum "191.48125" {
               description "191.48125 THz/1565.65 nm 6.25GHz spacing";
             }
             enum "191.48750" {
               description "191.48750 THz/1565.60 nm 6.25/12.5GHz spacing";
             }
             enum "191.49375" {
               description "191.49375 THz/1565.55 nm 6.25GHz spacing";
             }
             enum "191.50000" {
               description "191.50000 THz/1565.50 nm 6.25/12.5/50/100GHz spacing";
             }
             enum "191.50625" {
               description "191.50625 THz/1565.44 nm 6.25GHz spacing";
             }
             enum "191.51250" {
               description "191.51250 THz/1565.39 nm 6.25/12.5GHz spacing";
             }
             enum "191.51875" {
               description "191.51875 THz/1565.34 nm 6.25GHz spacing";
             }
             enum "191.52500" {
               description "191.52500 THz/1565.29 nm 6.25/12.5/75GHz spacing";
             }
             enum "191.53125" {
               description "191.53125 THz/1565.24 nm 6.25GHz spacing";
             }
             enum "191.53750" {
               description "191.53750 THz/1565.19 nm 6.25/12.5GHz spacing";
             }
             enum "191.54375" {
               description "191.54375 THz/1565.14 nm 6.25GHz spacing";
             }
             enum "191.55000" {
               description "191.55000 THz/1565.09 nm 6.25/12.5/50GHz spacing";
             }
             enum "191.55625" {
               description "191.55625 THz/1565.04 nm 6.25GHz spacing";
             }
             enum "191.56250" {
               description "191.56250 THz/1564.99 nm 6.25/12.5GHz spacing";
             }
             enum "191.56875" {
               description "191.56875 THz/1564.93 nm 6.25GHz spacing";
             }
             enum "191.57500" {
               description "191.57500 THz/1564.88 nm 6.25/12.5GHz spacing";
             }
             enum "191.58125" {
               description "191.58125 THz/1564.83 nm 6.25GHz spacing";
             }
             enum "191.58750" {
               description "191.58750 THz/1564.78 nm 6.25/12.5GHz spacing";
             }
             enum "191.59375" {
               description "191.59375 THz/1564.73 nm 6.25GHz spacing";
             }
             enum "191.60000" {
               description "191.60000 THz/1564.68 nm 6.25/12.5/50/75/100GHz spacing";
             }
             enum "191.60625" {
               description "191.60625 THz/1564.63 nm 6.25GHz spacing";
             }
             enum "191.61250" {
               description "191.61250 THz/1564.58 nm 6.25/12.5GHz spacing";
             }
             enum "191.61875" {
               description "191.61875 THz/1564.53 nm 6.25GHz spacing";
             }
             enum "191.62500" {
               description "191.62500 THz/1564.47 nm 6.25/12.5GHz spacing";
             }
             enum "191.63125" {
               description "191.63125 THz/1564.42 nm 6.25GHz spacing";
             }
             enum "191.63750" {
               description "191.63750 THz/1564.37 nm 6.25/12.5GHz spacing";
             }
             enum "191.64375" {
               description "191.64375 THz/1564.32 nm 6.25GHz spacing";
             }
             enum "191.65000" {
               description "191.65000 THz/1564.27 nm 6.25/12.5/50GHz spacing";
             }
             enum "191.65625" {
               description "191.65625 THz/1564.22 nm 6.25GHz spacing";
             }
             enum "191.66250" {
               description "191.66250 THz/1564.17 nm 6.25/12.5GHz spacing";
             }
             enum "191.66875" {
               description "191.66875 THz/1564.12 nm 6.25GHz spacing";
             }
             enum "191.67500" {
               description "191.67500 THz/1564.07 nm 6.25/12.5/75GHz spacing";
             }
             enum "191.68125" {
               description "191.68125 THz/1564.02 nm 6.25GHz spacing";
             }
             enum "191.68750" {
               description "191.68750 THz/1563.96 nm 6.25/12.5GHz spacing";
             }
             enum "191.69375" {
               description "191.69375 THz/1563.91 nm 6.25GHz spacing";
             }
             enum "191.70000" {
               description "191.70000 THz/1563.86 nm 6.25/12.5/50/100GHz spacing";
             }
             enum "191.70625" {
               description "191.70625 THz/1563.81 nm 6.25GHz spacing";
             }
             enum "191.71250" {
               description "191.71250 THz/1563.76 nm 6.25/12.5GHz spacing";
             }
             enum "191.71875" {
               description "191.71875 THz/1563.71 nm 6.25GHz spacing";
             }
             enum "191.72500" {
               description "191.72500 THz/1563.66 nm 6.25/12.5GHz spacing";
             }
             enum "191.73125" {
               description "191.73125 THz/1563.61 nm 6.25GHz spacing";
             }
             enum "191.73750" {
               description "191.73750 THz/1563.56 nm 6.25/12.5GHz spacing";
             }
             enum "191.74375" {
               description "191.74375 THz/1563.51 nm 6.25GHz spacing";
             }
             enum "191.75000" {
               description "191.75000 THz/1563.45 nm 6.25/12.5/50/75GHz spacing";
             }
             enum "191.75625" {
               description "191.75625 THz/1563.40 nm 6.25GHz spacing";
             }
             enum "191.76250" {
               description "191.76250 THz/1563.35 nm 6.25/12.5GHz spacing";
             }
             enum "191.76875" {
               description "191.76875 THz/1563.30 nm 6.25GHz spacing";
             }
             enum "191.77500" {
               description "191.77500 THz/1563.25 nm 6.25/12.5GHz spacing";
             }
             enum "191.78125" {
               description "191.78125 THz/1563.20 nm 6.25GHz spacing";
             }
             enum "191.78750" {
               description "191.78750 THz/1563.15 nm 6.25/12.5GHz spacing";
             }
             enum "191.79375" {
               description "191.79375 THz/1563.10 nm 6.25GHz spacing";
             }
             enum "191.80000" {
               description "191.80000 THz/1563.05 nm 6.25/12.5/50/100GHz spacing";
             }
             enum "191.80625" {
               description "191.80625 THz/1563.00 nm 6.25GHz spacing";
             }
             enum "191.81250" {
               description "191.81250 THz/1562.95 nm 6.25/12.5GHz spacing";
             }
             enum "191.81875" {
               description "191.81875 THz/1562.89 nm 6.25GHz spacing";
             }
             enum "191.82500" {
               description "191.82500 THz/1562.84 nm 6.25/12.5/75GHz spacing";
             }
             enum "191.83125" {
               description "191.83125 THz/1562.79 nm 6.25GHz spacing";
             }
             enum "191.83750" {
               description "191.83750 THz/1562.74 nm 6.25/12.5GHz spacing";
             }
             enum "191.84375" {
               description "191.84375 THz/1562.69 nm 6.25GHz spacing";
             }
             enum "191.85000" {
               description "191.85000 THz/1562.64 nm 6.25/12.5/50GHz spacing";
             }
             enum "191.85625" {
               description "191.85625 THz/1562.59 nm 6.25GHz spacing";
             }
             enum "191.86250" {
               description "191.86250 THz/1562.54 nm 6.25/12.5GHz spacing";
             }
             enum "191.86875" {
               description "191.86875 THz/1562.49 nm 6.25GHz spacing";
             }
             enum "191.87500" {
               description "191.87500 THz/1562.44 nm 6.25/12.5GHz spacing";
             }
             enum "191.88125" {
               description "191.88125 THz/1562.39 nm 6.25GHz spacing";
             }
             enum "191.88750" {
               description "191.88750 THz/1562.33 nm 6.25/12.5GHz spacing";
             }
             enum "191.89375" {
               description "191.89375 THz/1562.28 nm 6.25GHz spacing";
             }
             enum "191.90000" {
               description "191.90000 THz/1562.23 nm 6.25/12.5/50/75/100GHz spacing";
             }
             enum "191.90625" {
               description "191.90625 THz/1562.18 nm 6.25GHz spacing";
             }
             enum "191.91250" {
               description "191.91250 THz/1562.13 nm 6.25/12.5GHz spacing";
             }
             enum "191.91875" {
               description "191.91875 THz/1562.08 nm 6.25GHz spacing";
             }
             enum "191.92500" {
               description "191.92500 THz/1562.03 nm 6.25/12.5GHz spacing";
             }
             enum "191.93125" {
               description "191.93125 THz/1561.98 nm 6.25GHz spacing";
             }
             enum "191.93750" {
               description "191.93750 THz/1561.93 nm 6.25/12.5GHz spacing";
             }
             enum "191.94375" {
               description "191.94375 THz/1561.88 nm 6.25GHz spacing";
             }
             enum "191.95000" {
               description "191.95000 THz/1561.83 nm 6.25/12.5/50GHz spacing";
             }
             enum "191.95625" {
               description "191.95625 THz/1561.77 nm 6.25GHz spacing";
             }
             enum "191.96250" {
               description "191.96250 THz/1561.72 nm 6.25/12.5GHz spacing";
             }
             enum "191.96875" {
               description "191.96875 THz/1561.67 nm 6.25GHz spacing";
             }
             enum "191.97500" {
               description "191.97500 THz/1561.62 nm 6.25/12.5/75GHz spacing";
             }
             enum "191.98125" {
               description "191.98125 THz/1561.57 nm 6.25GHz spacing";
             }
             enum "191.98750" {
               description "191.98750 THz/1561.52 nm 6.25/12.5GHz spacing";
             }
             enum "191.99375" {
               description "191.99375 THz/1561.47 nm 6.25GHz spacing";
             }
             enum "192.00000" {
               description "192.00000 THz/1561.42 nm 6.25/12.5/50/100GHz spacing";
             }
             enum "192.00625" {
               description "192.00625 THz/1561.37 nm 6.25GHz spacing";
             }
             enum "192.01250" {
               description "192.01250 THz/1561.32 nm 6.25/12.5GHz spacing";
             }
             enum "192.01875" {
               description "192.01875 THz/1561.27 nm 6.25GHz spacing";
             }
             enum "192.02500" {
               description "192.02500 THz/1561.22 nm 6.25/12.5GHz spacing";
             }
             enum "192.03125" {
               description "192.03125 THz/1561.16 nm 6.25GHz spacing";
             }
             enum "192.03750" {
               description "192.03750 THz/1561.11 nm 6.25/12.5GHz spacing";
             }
             enum "192.04375" {
               description "192.04375 THz/1561.06 nm 6.25GHz spacing";
             }
             enum "192.05000" {
               description "192.05000 THz/1561.01 nm 6.25/12.5/50/75GHz spacing";
             }
             enum "192.05625" {
               description "192.05625 THz/1560.96 nm 6.25GHz spacing";
             }
             enum "192.06250" {
               description "192.06250 THz/1560.91 nm 6.25/12.5GHz spacing";
             }
             enum "192.06875" {
               description "192.06875 THz/1560.86 nm 6.25GHz spacing";
             }
             enum "192.07500" {
               description "192.07500 THz/1560.81 nm 6.25/12.5GHz spacing";
             }
             enum "192.08125" {
               description "192.08125 THz/1560.76 nm 6.25GHz spacing";
             }
             enum "192.08750" {
               description "192.08750 THz/1560.71 nm 6.25/12.5GHz spacing";
             }
             enum "192.09375" {
               description "192.09375 THz/1560.66 nm 6.25GHz spacing";
             }
             enum "192.10000" {
               description "192.10000 THz/1560.61 nm 6.25/12.5/50/100GHz spacing";
             }
             enum "192.10625" {
               description "192.10625 THz/1560.56 nm 6.25GHz spacing";
             }
             enum "192.11250" {
               description "192.11250 THz/1560.50 nm 6.25/12.5GHz spacing";
             }
             enum "192.11875" {
               description "192.11875 THz/1560.45 nm 6.25GHz spacing";
             }
             enum "192.12500" {
               description "192.12500 THz/1560.40 nm 6.25/12.5/75GHz spacing";
             }
             enum "192.13125" {
               description "192.13125 THz/1560.35 nm 6.25GHz spacing";
             }
             enum "192.13750" {
               description "192.13750 THz/1560.30 nm 6.25/12.5GHz spacing";
             }
             enum "192.14375" {
               description "192.14375 THz/1560.25 nm 6.25GHz spacing";
             }
             enum "192.15000" {
               description "192.15000 THz/1560.20 nm 6.25/12.5/50GHz spacing";
             }
             enum "192.15625" {
               description "192.15625 THz/1560.15 nm 6.25GHz spacing";
             }
             enum "192.16250" {
               description "192.16250 THz/1560.10 nm 6.25/12.5GHz spacing";
             }
             enum "192.16875" {
               description "192.16875 THz/1560.05 nm 6.25GHz spacing";
             }
             enum "192.17500" {
               description "192.17500 THz/1560.00 nm 6.25/12.5GHz spacing";
             }
             enum "192.18125" {
               description "192.18125 THz/1559.95 nm 6.25GHz spacing";
             }
             enum "192.18750" {
               description "192.18750 THz/1559.90 nm 6.25/12.5GHz spacing";
             }
             enum "192.19375" {
               description "192.19375 THz/1559.84 nm 6.25GHz spacing";
             }
             enum "192.20000" {
               description "192.20000 THz/1559.79 nm 6.25/12.5/50/75/100GHz spacing";
             }
             enum "192.20625" {
               description "192.20625 THz/1559.74 nm 6.25GHz spacing";
             }
             enum "192.21250" {
               description "192.21250 THz/1559.69 nm 6.25/12.5GHz spacing";
             }
             enum "192.21875" {
               description "192.21875 THz/1559.64 nm 6.25GHz spacing";
             }
             enum "192.22500" {
               description "192.22500 THz/1559.59 nm 6.25/12.5GHz spacing";
             }
             enum "192.23125" {
               description "192.23125 THz/1559.54 nm 6.25GHz spacing";
             }
             enum "192.23750" {
               description "192.23750 THz/1559.49 nm 6.25/12.5GHz spacing";
             }
             enum "192.24375" {
               description "192.24375 THz/1559.44 nm 6.25GHz spacing";
             }
             enum "192.25000" {
               description "192.25000 THz/1559.39 nm 6.25/12.5/50GHz spacing";
             }
             enum "192.25625" {
               description "192.25625 THz/1559.34 nm 6.25GHz spacing";
             }
             enum "192.26250" {
               description "192.26250 THz/1559.29 nm 6.25/12.5GHz spacing";
             }
             enum "192.26875" {
               description "192.26875 THz/1559.24 nm 6.25GHz spacing";
             }
             enum "192.27500" {
               description "192.27500 THz/1559.19 nm 6.25/12.5GHz spacing";
             }
             enum "192.28125" {
               description "192.28125 THz/1559.14 nm 6.25GHz spacing";
             }
             enum "192.28750" {
               description "192.28750 THz/1559.08 nm 6.25/12.5GHz spacing";
             }
             enum "192.29375" {
               description "192.29375 THz/1559.03 nm 6.25GHz spacing";
             }
             enum "192.30000" {
               description "192.30000 THz/1558.98 nm 6.25/12.5/50/100GHz spacing";
             }
             enum "192.30625" {
               description "192.30625 THz/1558.93 nm 6.25GHz spacing";
             }
             enum "192.31250" {
               description "192.31250 THz/1558.88 nm 6.25/12.5GHz spacing";
             }
             enum "192.31875" {
               description "192.31875 THz/1558.83 nm 6.25GHz spacing";
             }
             enum "192.32500" {
               description "192.32500 THz/1558.78 nm 6.25/12.5GHz spacing";
             }
             enum "192.33125" {
               description "192.33125 THz/1558.73 nm 6.25GHz spacing";
             }
             enum "192.33750" {
               description "192.33750 THz/1558.68 nm 6.25/12.5GHz spacing";
             }
             enum "192.34375" {
               description "192.34375 THz/1558.63 nm 6.25GHz spacing";
             }
             enum "192.35000" {
               description "192.35000 THz/1558.58 nm 6.25/12.5/50/75GHz spacing";
             }
             enum "192.35625" {
               description "192.35625 THz/1558.53 nm 6.25GHz spacing";
             }
             enum "192.36250" {
               description "192.36250 THz/1558.48 nm 6.25/12.5GHz spacing";
             }
             enum "192.36875" {
               description "192.36875 THz/1558.43 nm 6.25GHz spacing";
             }
             enum "192.37500" {
               description "192.37500 THz/1558.38 nm 6.25/12.5GHz spacing";
             }
             enum "192.38125" {
               description "192.38125 THz/1558.32 nm 6.25GHz spacing";
             }
             enum "192.38750" {
               description "192.38750 THz/1558.27 nm 6.25/12.5GHz spacing";
             }
             enum "192.39375" {
               description "192.39375 THz/1558.22 nm 6.25GHz spacing";
             }
             enum "192.40000" {
               description "192.40000 THz/1558.17 nm 6.25/12.5/50/100GHz spacing";
             }
             enum "192.40625" {
               description "192.40625 THz/1558.12 nm 6.25GHz spacing";
             }
             enum "192.41250" {
               description "192.41250 THz/1558.07 nm 6.25/12.5GHz spacing";
             }
             enum "192.41875" {
               description "192.41875 THz/1558.02 nm 6.25GHz spacing";
             }
             enum "192.42500" {
               description "192.42500 THz/1557.97 nm 6.25/12.5/75GHz spacing";
             }
             enum "192.43125" {
               description "192.43125 THz/1557.92 nm 6.25GHz spacing";
             }
             enum "192.43750" {
               description "192.43750 THz/1557.87 nm 6.25/12.5GHz spacing";
             }
             enum "192.44375" {
               description "192.44375 THz/1557.82 nm 6.25GHz spacing";
             }
             enum "192.45000" {
               description "192.45000 THz/1557.77 nm 6.25/12.5/50GHz spacing";
             }
             enum "192.45625" {
               description "192.45625 THz/1557.72 nm 6.25GHz spacing";
             }
             enum "192.46250" {
               description "192.46250 THz/1557.67 nm 6.25/12.5GHz spacing";
             }
             enum "192.46875" {
               description "192.46875 THz/1557.62 nm 6.25GHz spacing";
             }
             enum "192.47500" {
               description "192.47500 THz/1557.57 nm 6.25/12.5GHz spacing";
             }
             enum "192.48125" {
               description "192.48125 THz/1557.52 nm 6.25GHz spacing";
             }
             enum "192.48750" {
               description "192.48750 THz/1557.46 nm 6.25/12.5GHz spacing";
             }
             enum "192.49375" {
               description "192.49375 THz/1557.41 nm 6.25GHz spacing";
             }
             enum "192.50000" {
               description "192.50000 THz/1557.36 nm 6.25/12.5/50/75/100GHz spacing";
             }
             enum "192.50625" {
               description "192.50625 THz/1557.31 nm 6.25GHz spacing";
             }
             enum "192.51250" {
               description "192.51250 THz/1557.26 nm 6.25/12.5GHz spacing";
             }
             enum "192.51875" {
               description "192.51875 THz/1557.21 nm 6.25GHz spacing";
             }
             enum "192.52500" {
               description "192.52500 THz/1557.16 nm 6.25/12.5GHz spacing";
             }
             enum "192.53125" {
               description "192.53125 THz/1557.11 nm 6.25GHz spacing";
             }
             enum "192.53750" {
               description "192.53750 THz/1557.06 nm 6.25/12.5GHz spacing";
             }
             enum "192.54375" {
               description "192.54375 THz/1557.01 nm 6.25GHz spacing";
             }
             enum "192.55000" {
               description "192.55000 THz/1556.96 nm 6.25/12.5/50GHz spacing";
             }
             enum "192.55625" {
               description "192.55625 THz/1556.91 nm 6.25GHz spacing";
             }
             enum "192.56250" {
               description "192.56250 THz/1556.86 nm 6.25/12.5GHz spacing";
             }
             enum "192.56875" {
               description "192.56875 THz/1556.81 nm 6.25GHz spacing";
             }
             enum "192.57500" {
               description "192.57500 THz/1556.76 nm 6.25/12.5/75GHz spacing";
             }
             enum "192.58125" {
               description "192.58125 THz/1556.71 nm 6.25GHz spacing";
             }
             enum "192.58750" {
               description "192.58750 THz/1556.66 nm 6.25/12.5GHz spacing";
             }
             enum "192.59375" {
               description "192.59375 THz/1556.61 nm 6.25GHz spacing";
             }
             enum "192.60000" {
               description "192.60000 THz/1556.55 nm 6.25/12.5/50/100GHz spacing";
             }
             enum "192.60625" {
               description "192.60625 THz/1556.50 nm 6.25GHz spacing";
             }
             enum "192.61250" {
               description "192.61250 THz/1556.45 nm 6.25/12.5GHz spacing";
             }
             enum "192.61875" {
               description "192.61875 THz/1556.40 nm 6.25GHz spacing";
             }
             enum "192.62500" {
               description "192.62500 THz/1556.35 nm 6.25/12.5GHz spacing";
             }
             enum "192.63125" {
               description "192.63125 THz/1556.30 nm 6.25GHz spacing";
             }
             enum "192.63750" {
               description "192.63750 THz/1556.25 nm 6.25/12.5GHz spacing";
             }
             enum "192.64375" {
               description "192.64375 THz/1556.20 nm 6.25GHz spacing";
             }
             enum "192.65000" {
               description "192.65000 THz/1556.15 nm 6.25/12.5/50/75GHz spacing";
             }
             enum "192.65625" {
               description "192.65625 THz/1556.10 nm 6.25GHz spacing";
             }
             enum "192.66250" {
               description "192.66250 THz/1556.05 nm 6.25/12.5GHz spacing";
             }
             enum "192.66875" {
               description "192.66875 THz/1556.00 nm 6.25GHz spacing";
             }
             enum "192.67500" {
               description "192.67500 THz/1555.95 nm 6.25/12.5GHz spacing";
             }
             enum "192.68125" {
               description "192.68125 THz/1555.90 nm 6.25GHz spacing";
             }
             enum "192.68750" {
               description "192.68750 THz/1555.85 nm 6.25/12.5GHz spacing";
             }
             enum "192.69375" {
               description "192.69375 THz/1555.80 nm 6.25GHz spacing";
             }
             enum "192.70000" {
               description "192.70000 THz/1555.75 nm 6.25/12.5/50/100GHz spacing";
             }
             enum "192.70625" {
               description "192.70625 THz/1555.70 nm 6.25GHz spacing";
             }
             enum "192.71250" {
               description "192.71250 THz/1555.65 nm 6.25/12.5GHz spacing";
             }
             enum "192.71875" {
               description "192.71875 THz/1555.60 nm 6.25GHz spacing";
             }
             enum "192.72500" {
               description "192.72500 THz/1555.55 nm 6.25/12.5/75GHz spacing";
             }
             enum "192.73125" {
               description "192.73125 THz/1555.49 nm 6.25GHz spacing";
             }
             enum "192.73750" {
               description "192.73750 THz/1555.44 nm 6.25/12.5GHz spacing";
             }
             enum "192.74375" {
               description "192.74375 THz/1555.39 nm 6.25GHz spacing";
             }
             enum "192.75000" {
               description "192.75000 THz/1555.34 nm 6.25/12.5/50GHz spacing";
             }
             enum "192.75625" {
               description "192.75625 THz/1555.29 nm 6.25GHz spacing";
             }
             enum "192.76250" {
               description "192.76250 THz/1555.24 nm 6.25/12.5GHz spacing";
             }
             enum "192.76875" {
               description "192.76875 THz/1555.19 nm 6.25GHz spacing";
             }
             enum "192.77500" {
               description "192.77500 THz/1555.14 nm 6.25/12.5GHz spacing";
             }
             enum "192.78125" {
               description "192.78125 THz/1555.09 nm 6.25GHz spacing";
             }
             enum "192.78750" {
               description "192.78750 THz/1555.04 nm 6.25/12.5GHz spacing";
             }
             enum "192.79375" {
               description "192.79375 THz/1554.99 nm 6.25GHz spacing";
             }
             enum "192.80000" {
               description "192.80000 THz/1554.94 nm 6.25/12.5/50/75/100GHz spacing";
             }
             enum "192.80625" {
               description "192.80625 THz/1554.89 nm 6.25GHz spacing";
             }
             enum "192.81250" {
               description "192.81250 THz/1554.84 nm 6.25/12.5GHz spacing";
             }
             enum "192.81875" {
               description "192.81875 THz/1554.79 nm 6.25GHz spacing";
             }
             enum "192.82500" {
               description "192.82500 THz/1554.74 nm 6.25/12.5GHz spacing";
             }
             enum "192.83125" {
               description "192.83125 THz/1554.69 nm 6.25GHz spacing";
             }
             enum "192.83750" {
               description "192.83750 THz/1554.64 nm 6.25/12.5GHz spacing";
             }
             enum "192.84375" {
               description "192.84375 THz/1554.59 nm 6.25GHz spacing";
             }
             enum "192.85000" {
               description "192.85000 THz/1554.54 nm 6.25/12.5/50GHz spacing";
             }
             enum "192.85625" {
               description "192.85625 THz/1554.49 nm 6.25GHz spacing";
             }
             enum "192.86250" {
               description "192.86250 THz/1554.44 nm 6.25/12.5GHz spacing";
             }
             enum "192.86875" {
               description "192.86875 THz/1554.39 nm 6.25GHz spacing";
             }
             enum "192.87500" {
               description "192.87500 THz/1554.34 nm 6.25/12.5/75GHz spacing";
             }
             enum "192.88125" {
               description "192.88125 THz/1554.29 nm 6.25GHz spacing";
             }
             enum "192.88750" {
               description "192.88750 THz/1554.23 nm 6.25/12.5GHz spacing";
             }
             enum "192.89375" {
               description "192.89375 THz/1554.18 nm 6.25GHz spacing";
             }
             enum "192.90000" {
               description "192.90000 THz/1554.13 nm 6.25/12.5/50/100GHz spacing";
             }
             enum "192.90625" {
               description "192.90625 THz/1554.08 nm 6.25GHz spacing";
             }
             enum "192.91250" {
               description "192.91250 THz/1554.03 nm 6.25/12.5GHz spacing";
             }
             enum "192.91875" {
               description "192.91875 THz/1553.98 nm 6.25GHz spacing";
             }
             enum "192.92500" {
               description "192.92500 THz/1553.93 nm 6.25/12.5GHz spacing";
             }
             enum "192.93125" {
               description "192.93125 THz/1553.88 nm 6.25GHz spacing";
             }
             enum "192.93750" {
               description "192.93750 THz/1553.83 nm 6.25/12.5GHz spacing";
             }
             enum "192.94375" {
               description "192.94375 THz/1553.78 nm 6.25GHz spacing";
             }
             enum "192.95000" {
               description "192.95000 THz/1553.73 nm 6.25/12.5/50/75GHz spacing";
             }
             enum "192.95625" {
               description "192.95625 THz/1553.68 nm 6.25GHz spacing";
             }
             enum "192.96250" {
               description "192.96250 THz/1553.63 nm 6.25/12.5GHz spacing";
             }
             enum "192.96875" {
               description "192.96875 THz/1553.58 nm 6.25GHz spacing";
             }
             enum "192.97500" {
               description "192.97500 THz/1553.53 nm 6.25/12.5GHz spacing";
             }
             enum "192.98125" {
               description "192.98125 THz/1553.48 nm 6.25GHz spacing";
             }
             enum "192.98750" {
               description "192.98750 THz/1553.43 nm 6.25/12.5GHz spacing";
             }
             enum "192.99375" {
               description "192.99375 THz/1553.38 nm 6.25GHz spacing";
             }
             enum "193.00000" {
               description "193.00000 THz/1553.33 nm 6.25/12.5/50/100GHz spacing";
             }
             enum "193.00625" {
               description "193.00625 THz/1553.28 nm 6.25GHz spacing";
             }
             enum "193.01250" {
               description "193.01250 THz/1553.23 nm 6.25/12.5GHz spacing";
             }
             enum "193.01875" {
               description "193.01875 THz/1553.18 nm 6.25GHz spacing";
             }
             enum "193.02500" {
               description "193.02500 THz/1553.13 nm 6.25/12.5/75GHz spacing";
             }
             enum "193.03125" {
               description "193.03125 THz/1553.08 nm 6.25GHz spacing";
             }
             enum "193.03750" {
               description "193.03750 THz/1553.03 nm 6.25/12.5GHz spacing";
             }
             enum "193.04375" {
               description "193.04375 THz/1552.98 nm 6.25GHz spacing";
             }
             enum "193.05000" {
               description "193.05000 THz/1552.93 nm 6.25/12.5/50GHz spacing";
             }
             enum "193.05625" {
               description "193.05625 THz/1552.88 nm 6.25GHz spacing";
             }
             enum "193.06250" {
               description "193.06250 THz/1552.83 nm 6.25/12.5GHz spacing";
             }
             enum "193.06875" {
               description "193.06875 THz/1552.78 nm 6.25GHz spacing";
             }
             enum "193.07500" {
               description "193.07500 THz/1552.73 nm 6.25/12.5GHz spacing";
             }
             enum "193.08125" {
               description "193.08125 THz/1552.68 nm 6.25GHz spacing";
             }
             enum "193.08750" {
               description "193.08750 THz/1552.62 nm 6.25/12.5GHz spacing";
             }
             enum "193.09375" {
               description "193.09375 THz/1552.57 nm 6.25GHz spacing";
             }
             enum "193.10000" {
               description "193.10000 THz/1552.52 nm 6.25/12.5/50/75/100GHz spacing";
             }
             enum "193.10625" {
               description "193.10625 THz/1552.47 nm 6.25GHz spacing";
             }
             enum "193.11250" {
               description "193.11250 THz/1552.42 nm 6.25/12.5GHz spacing";
             }
             enum "193.11875" {
               description "193.11875 THz/1552.37 nm 6.25GHz spacing";
             }
             enum "193.12500" {
               description "193.12500 THz/1552.32 nm 6.25/12.5GHz spacing";
             }
             enum "193.13125" {
               description "193.13125 THz/1552.27 nm 6.25GHz spacing";
             }
             enum "193.13750" {
               description "193.13750 THz/1552.22 nm 6.25/12.5GHz spacing";
             }
             enum "193.14375" {
               description "193.14375 THz/1552.17 nm 6.25GHz spacing";
             }
             enum "193.15000" {
               description "193.15000 THz/1552.12 nm 6.25/12.5/50GHz spacing";
             }
             enum "193.15625" {
               description "193.15625 THz/1552.07 nm 6.25GHz spacing";
             }
             enum "193.16250" {
               description "193.16250 THz/1552.02 nm 6.25/12.5GHz spacing";
             }
             enum "193.16875" {
               description "193.16875 THz/1551.97 nm 6.25GHz spacing";
             }
             enum "193.17500" {
               description "193.17500 THz/1551.92 nm 6.25/12.5/75GHz spacing";
             }
             enum "193.18125" {
               description "193.18125 THz/1551.87 nm 6.25GHz spacing";
             }
             enum "193.18750" {
               description "193.18750 THz/1551.82 nm 6.25/12.5GHz spacing";
             }
             enum "193.19375" {
               description "193.19375 THz/1551.77 nm 6.25GHz spacing";
             }
             enum "193.20000" {
               description "193.20000 THz/1551.72 nm 6.25/12.5/50/100GHz spacing";
             }
             enum "193.20625" {
               description "193.20625 THz/1551.67 nm 6.25GHz spacing";
             }
             enum "193.21250" {
               description "193.21250 THz/1551.62 nm 6.25/12.5GHz spacing";
             }
             enum "193.21875" {
               description "193.21875 THz/1551.57 nm 6.25GHz spacing";
             }
             enum "193.22500" {
               description "193.22500 THz/1551.52 nm 6.25/12.5GHz spacing";
             }
             enum "193.23125" {
               description "193.23125 THz/1551.47 nm 6.25GHz spacing";
             }
             enum "193.23750" {
               description "193.23750 THz/1551.42 nm 6.25/12.5GHz spacing";
             }
             enum "193.24375" {
               description "193.24375 THz/1551.37 nm 6.25GHz spacing";
             }
             enum "193.25000" {
               description "193.25000 THz/1551.32 nm 6.25/12.5/50/75GHz spacing";
             }
             enum "193.25625" {
               description "193.25625 THz/1551.27 nm 6.25GHz spacing";
             }
             enum "193.26250" {
               description "193.26250 THz/1551.22 nm 6.25/12.5GHz spacing";
             }
             enum "193.26875" {
               description "193.26875 THz/1551.17 nm 6.25GHz spacing";
             }
             enum "193.27500" {
               description "193.27500 THz/1551.12 nm 6.25/12.5GHz spacing";
             }
             enum "193.28125" {
               description "193.28125 THz/1551.07 nm 6.25GHz spacing";
             }
             enum "193.28750" {
               description "193.28750 THz/1551.02 nm 6.25/12.5GHz spacing";
             }
             enum "193.29375" {
               description "193.29375 THz/1550.97 nm 6.25GHz spacing";
             }
             enum "193.30000" {
               description "193.30000 THz/1550.92 nm 6.25/12.5/50/100GHz spacing";
             }
             enum "193.30625" {
               description "193.30625 THz/1550.87 nm 6.25GHz spacing";
             }
             enum "193.31250" {
               description "193.31250 THz/1550.82 nm 6.25/12.5GHz spacing";
             }
             enum "193.31875" {
               description "193.31875 THz/1550.77 nm 6.25GHz spacing";
             }
             enum "193.32500" {
               description "193.32500 THz/1550.72 nm 6.25/12.5/75GHz spacing";
             }
             enum "193.33125" {
               description "193.33125 THz/1550.67 nm 6.25GHz spacing";
             }
             enum "193.33750" {
               description "193.33750 THz/1550.62 nm 6.25/12.5GHz spacing";
             }
             enum "193.34375" {
               description "193.34375 THz/1550.57 nm 6.25GHz spacing";
             }
             enum "193.35000" {
               description "193.35000 THz/1550.52 nm 6.25/12.5/50GHz spacing";
             }
             enum "193.35625" {
               description "193.35625 THz/1550.47 nm 6.25GHz spacing";
             }
             enum "193.36250" {
               description "193.36250 THz/1550.42 nm 6.25/12.5GHz spacing";
             }
             enum "193.36875" {
               description "193.36875 THz/1550.37 nm 6.25GHz spacing";
             }
             enum "193.37500" {
               description "193.37500 THz/1550.32 nm 6.25/12.5GHz spacing";
             }
             enum "193.38125" {
               description "193.38125 THz/1550.27 nm 6.25GHz spacing";
             }
             enum "193.38750" {
               description "193.38750 THz/1550.22 nm 6.25/12.5GHz spacing";
             }
             enum "193.39375" {
               description "193.39375 THz/1550.17 nm 6.25GHz spacing";
             }
             enum "193.40000" {
               description "193.40000 THz/1550.12 nm 6.25/12.5/50/75/100GHz spacing";
             }
             enum "193.40625" {
               description "193.40625 THz/1550.07 nm 6.25GHz spacing";
             }
             enum "193.41250" {
               description "193.41250 THz/1550.02 nm 6.25/12.5GHz spacing";
             }
             enum "193.41875" {
               description "193.41875 THz/1549.97 nm 6.25GHz spacing";
             }
             enum "193.42500" {
               description "193.42500 THz/1549.92 nm 6.25/12.5GHz spacing";
             }
             enum "193.43125" {
               description "193.43125 THz/1549.87 nm 6.25GHz spacing";
             }
             enum "193.43750" {
               description "193.43750 THz/1549.82 nm 6.25/12.5GHz spacing";
             }
             enum "193.44375" {
               description "193.44375 THz/1549.77 nm 6.25GHz spacing";
             }
             enum "193.45000" {
               description "193.45000 THz/1549.72 nm 6.25/12.5/50GHz spacing";
             }
             enum "193.45625" {
               description "193.45625 THz/1549.67 nm 6.25GHz spacing";
             }
             enum "193.46250" {
               description "193.46250 THz/1549.62 nm 6.25/12.5GHz spacing";
             }
             enum "193.46875" {
               description "193.46875 THz/1549.57 nm 6.25GHz spacing";
             }
             enum "193.47500" {
               description "193.47500 THz/1549.52 nm 6.25/12.5/75GHz spacing";
             }
             enum "193.48125" {
               description "193.48125 THz/1549.47 nm 6.25GHz spacing";
             }
             enum "193.48750" {
               description "193.48750 THz/1549.42 nm 6.25/12.5GHz spacing";
             }
             enum "193.49375" {
               description "193.49375 THz/1549.37 nm 6.25GHz spacing";
             }
             enum "193.50000" {
               description "193.50000 THz/1549.32 nm 6.25/12.5/50/100GHz spacing";
             }
             enum "193.50625" {
               description "193.50625 THz/1549.26 nm 6.25GHz spacing";
             }
             enum "193.51250" {
               description "193.51250 THz/1549.21 nm 6.25/12.5GHz spacing";
             }
             enum "193.51875" {
               description "193.51875 THz/1549.16 nm 6.25GHz spacing";
             }
             enum "193.52500" {
               description "193.52500 THz/1549.11 nm 6.25/12.5GHz spacing";
             }
             enum "193.53125" {
               description "193.53125 THz/1549.06 nm 6.25GHz spacing";
             }
             enum "193.53750" {
               description "193.53750 THz/1549.01 nm 6.25/12.5GHz spacing";
             }
             enum "193.54375" {
               description "193.54375 THz/1548.96 nm 6.25GHz spacing";
             }
             enum "193.55000" {
               description "193.55000 THz/1548.91 nm 6.25/12.5/50/75GHz spacing";
             }
             enum "193.55625" {
               description "193.55625 THz/1548.86 nm 6.25GHz spacing";
             }
             enum "193.56250" {
               description "193.56250 THz/1548.81 nm 6.25/12.5GHz spacing";
             }
             enum "193.56875" {
               description "193.56875 THz/1548.76 nm 6.25GHz spacing";
             }
             enum "193.57500" {
               description "193.57500 THz/1548.71 nm 6.25/12.5GHz spacing";
             }
             enum "193.58125" {
               description "193.58125 THz/1548.66 nm 6.25GHz spacing";
             }
             enum "193.58750" {
               description "193.58750 THz/1548.61 nm 6.25/12.5GHz spacing";
             }
             enum "193.59375" {
               description "193.59375 THz/1548.56 nm 6.25GHz spacing";
             }
             enum "193.60000" {
               description "193.60000 THz/1548.51 nm 6.25/12.5/50/100GHz spacing";
             }
             enum "193.60625" {
               description "193.60625 THz/1548.46 nm 6.25GHz spacing";
             }
             enum "193.61250" {
               description "193.61250 THz/1548.41 nm 6.25/12.5GHz spacing";
             }
             enum "193.61875" {
               description "193.61875 THz/1548.36 nm 6.25GHz spacing";
             }
             enum "193.62500" {
               description "193.62500 THz/1548.31 nm 6.25/12.5/75GHz spacing";
             }
             enum "193.63125" {
               description "193.63125 THz/1548.26 nm 6.25GHz spacing";
             }
             enum "193.63750" {
               description "193.63750 THz/1548.21 nm 6.25/12.5GHz spacing";
             }
             enum "193.64375" {
               description "193.64375 THz/1548.16 nm 6.25GHz spacing";
             }
             enum "193.65000" {
               description "193.65000 THz/1548.11 nm 6.25/12.5/50GHz spacing";
             }
             enum "193.65625" {
               description "193.65625 THz/1548.06 nm 6.25GHz spacing";
             }
             enum "193.66250" {
               description "193.66250 THz/1548.02 nm 6.25/12.5GHz spacing";
             }
             enum "193.66875" {
               description "193.66875 THz/1547.97 nm 6.25GHz spacing";
             }
             enum "193.67500" {
               description "193.67500 THz/1547.92 nm 6.25/12.5GHz spacing";
             }
             enum "193.68125" {
               description "193.68125 THz/1547.87 nm 6.25GHz spacing";
             }
             enum "193.68750" {
               description "193.68750 THz/1547.82 nm 6.25/12.5GHz spacing";
             }
             enum "193.69375" {
               description "193.69375 THz/1547.77 nm 6.25GHz spacing";
             }
             enum "193.70000" {
               description "193.70000 THz/1547.72 nm 6.25/12.5/50/100/75GHz spacing";
             }
             enum "193.70625" {
               description "193.70625 THz/1547.67 nm 6.25GHz spacing";
             }
             enum "193.71250" {
               description "193.71250 THz/1547.62 nm 6.25/12.5GHz spacing";
             }
             enum "193.71875" {
               description "193.71875 THz/1547.57 nm 6.25GHz spacing";
             }
             enum "193.72500" {
               description "193.72500 THz/1547.52 nm 6.25/12.5GHz spacing";
             }
             enum "193.73125" {
               description "193.73125 THz/1547.47 nm 6.25GHz spacing";
             }
             enum "193.73750" {
               description "193.73750 THz/1547.42 nm 6.25/12.5GHz spacing";
             }
             enum "193.74375" {
               description "193.74375 THz/1547.37 nm 6.25GHz spacing";
             }
             enum "193.75000" {
               description "193.75000 THz/1547.32 nm 6.25/12.5/50GHz spacing";
             }
             enum "193.75625" {
               description "193.75625 THz/1547.27 nm 6.25GHz spacing";
             }
             enum "193.76250" {
               description "193.76250 THz/1547.22 nm 6.25/12.5GHz spacing";
             }
             enum "193.76875" {
               description "193.76875 THz/1547.17 nm 6.25GHz spacing";
             }
             enum "193.77500" {
               description "193.77500 THz/1547.12 nm 6.25/12.5/75GHz spacing";
             }
             enum "193.78125" {
               description "193.78125 THz/1547.07 nm 6.25GHz spacing";
             }
             enum "193.78750" {
               description "193.78750 THz/1547.02 nm 6.25/12.5GHz spacing";
             }
             enum "193.79375" {
               description "193.79375 THz/1546.97 nm 6.25GHz spacing";
             }
             enum "193.80000" {
               description "193.80000 THz/1546.92 nm 6.25/12.5/50/100GHz spacing";
             }
             enum "193.80625" {
               description "193.80625 THz/1546.87 nm 6.25GHz spacing";
             }
             enum "193.81250" {
               description "193.81250 THz/1546.82 nm 6.25/12.5GHz spacing";
             }
             enum "193.81875" {
               description "193.81875 THz/1546.77 nm 6.25GHz spacing";
             }
             enum "193.82500" {
               description "193.82500 THz/1546.72 nm 6.25/12.5GHz spacing";
             }
             enum "193.83125" {
               description "193.83125 THz/1546.67 nm 6.25GHz spacing";
             }
             enum "193.83750" {
               description "193.83750 THz/1546.62 nm 6.25/12.5GHz spacing";
             }
             enum "193.84375" {
               description "193.84375 THz/1546.57 nm 6.25GHz spacing";
             }
             enum "193.85000" {
               description "193.85000 THz/1546.52 nm 6.25/12.5/50/75GHz spacing";
             }
             enum "193.85625" {
               description "193.85625 THz/1546.47 nm 6.25GHz spacing";
             }
             enum "193.86250" {
               description "193.86250 THz/1546.42 nm 6.25/12.5GHz spacing";
             }
             enum "193.86875" {
               description "193.86875 THz/1546.37 nm 6.25GHz spacing";
             }
             enum "193.87500" {
               description "193.87500 THz/1546.32 nm 6.25/12.5GHz spacing";
             }
             enum "193.88125" {
               description "193.88125 THz/1546.27 nm 6.25GHz spacing";
             }
             enum "193.88750" {
               description "193.88750 THz/1546.22 nm 6.25/12.5GHz spacing";
             }
             enum "193.89375" {
               description "193.89375 THz/1546.17 nm 6.25GHz spacing";
             }
             enum "193.90000" {
               description "193.90000 THz/1546.12 nm 6.25/12.5/50/100GHz spacing";
             }
             enum "193.90625" {
               description "193.90625 THz/1546.07 nm 6.25GHz spacing";
             }
             enum "193.91250" {
               description "193.91250 THz/1546.02 nm 6.25/12.5GHz spacing";
             }
             enum "193.91875" {
               description "193.91875 THz/1545.97 nm 6.25GHz spacing";
             }
             enum "193.92500" {
               description "193.92500 THz/1545.92 nm 6.25/12.5/75GHz spacing";
             }
             enum "193.93125" {
               description "193.93125 THz/1545.87 nm 6.25GHz spacing";
             }
             enum "193.93750" {
               description "193.93750 THz/1545.82 nm 6.25/12.5GHz spacing";
             }
             enum "193.94375" {
               description "193.94375 THz/1545.77 nm 6.25GHz spacing";
             }
             enum "193.95000" {
               description "193.95000 THz/1545.72 nm 6.25/12.5/50GHz spacing";
             }
             enum "193.95625" {
               description "193.95625 THz/1545.67 nm 6.25GHz spacing";
             }
             enum "193.96250" {
               description "193.96250 THz/1545.62 nm 6.25/12.5GHz spacing";
             }
             enum "193.96875" {
               description "193.96875 THz/1545.57 nm 6.25GHz spacing";
             }
             enum "193.97500" {
               description "193.97500 THz/1545.52 nm 6.25/12.5GHz spacing";
             }
             enum "193.98125" {
               description "193.98125 THz/1545.47 nm 6.25GHz spacing";
             }
             enum "193.98750" {
               description "193.98750 THz/1545.42 nm 6.25/12.5GHz spacing";
             }
             enum "193.99375" {
               description "193.99375 THz/1545.37 nm 6.25GHz spacing";
             }
             enum "194.00000" {
               description "194.00000 THz/1545.32 nm 6.25/12.5/50/75/100GHz spacing";
             }
             enum "194.00625" {
               description "194.00625 THz/1545.27 nm 6.25GHz spacing";
             }
             enum "194.01250" {
               description "194.01250 THz/1545.22 nm 6.25/12.5GHz spacing";
             }
             enum "194.01875" {
               description "194.01875 THz/1545.17 nm 6.25GHz spacing";
             }
             enum "194.02500" {
               description "194.02500 THz/1545.12 nm 6.25/12.5GHz spacing";
             }
             enum "194.03125" {
               description "194.03125 THz/1545.07 nm 6.25GHz spacing";
             }
             enum "194.03750" {
               description "194.03750 THz/1545.02 nm 6.25/12.5GHz spacing";
             }
             enum "194.04375" {
               description "194.04375 THz/1544.97 nm 6.25GHz spacing";
             }
             enum "194.05000" {
               description "194.05000 THz/1544.92 nm 6.25/12.5/50GHz spacing";
             }
             enum "194.05625" {
               description "194.05625 THz/1544.87 nm 6.25GHz spacing";
             }
             enum "194.06250" {
               description "194.06250 THz/1544.82 nm 6.25/12.5GHz spacing";
             }
             enum "194.06875" {
               description "194.06875 THz/1544.77 nm 6.25GHz spacing";
             }
             enum "194.07500" {
               description "194.07500 THz/1544.72 nm 6.25/12.5/75GHz spacing";
             }
             enum "194.08125" {
               description "194.08125 THz/1544.68 nm 6.25GHz spacing";
             }
             enum "194.08750" {
               description "194.08750 THz/1544.63 nm 6.25/12.5GHz spacing";
             }
             enum "194.09375" {
               description "194.09375 THz/1544.58 nm 6.25GHz spacing";
             }
             enum "194.10000" {
               description "194.10000 THz/1544.53 nm 6.25/12.5/50/100GHz spacing";
             }
             enum "194.10625" {
               description "194.10625 THz/1544.48 nm 6.25GHz spacing";
             }
             enum "194.11250" {
               description "194.11250 THz/1544.43 nm 6.25/12.5GHz spacing";
             }
             enum "194.11875" {
               description "194.11875 THz/1544.38 nm 6.25GHz spacing";
             }
             enum "194.12500" {
               description "194.12500 THz/1544.33 nm 6.25/12.5GHz spacing";
             }
             enum "194.13125" {
               description "194.13125 THz/1544.28 nm 6.25GHz spacing";
             }
             enum "194.13750" {
               description "194.13750 THz/1544.23 nm 6.25/12.5GHz spacing";
             }
             enum "194.14375" {
               description "194.14375 THz/1544.18 nm 6.25GHz spacing";
             }
             enum "194.15000" {
               description "194.15000 THz/1544.13 nm 6.25/12.5/50/75GHz spacing";
             }
             enum "194.15625" {
               description "194.15625 THz/1544.08 nm 6.25GHz spacing";
             }
             enum "194.16250" {
               description "194.16250 THz/1544.03 nm 6.25/12.5GHz spacing";
             }
             enum "194.16875" {
               description "194.16875 THz/1543.98 nm 6.25GHz spacing";
             }
             enum "194.17500" {
               description "194.17500 THz/1543.93 nm 6.25/12.5GHz spacing";
             }
             enum "194.18125" {
               description "194.18125 THz/1543.88 nm 6.25GHz spacing";
             }
             enum "194.18750" {
               description "194.18750 THz/1543.83 nm 6.25/12.5GHz spacing";
             }
             enum "194.19375" {
               description "194.19375 THz/1543.78 nm 6.25GHz spacing";
             }
             enum "194.20000" {
               description "194.20000 THz/1543.73 nm 6.25/12.5/50/100GHz spacing";
             }
             enum "194.20625" {
               description "194.20625 THz/1543.68 nm 6.25GHz spacing";
             }
             enum "194.21250" {
               description "194.21250 THz/1543.63 nm 6.25/12.5GHz spacing";
             }
             enum "194.21875" {
               description "194.21875 THz/1543.58 nm 6.25GHz spacing";
             }
             enum "194.22500" {
               description "194.22500 THz/1543.53 nm 6.25/12.5/75GHz spacing";
             }
             enum "194.23125" {
               description "194.23125 THz/1543.48 nm 6.25GHz spacing";
             }
             enum "194.23750" {
               description "194.23750 THz/1543.43 nm 6.25/12.5GHz spacing";
             }
             enum "194.24375" {
               description "194.24375 THz/1543.38 nm 6.25GHz spacing";
             }
             enum "194.25000" {
               description "194.25000 THz/1543.33 nm 6.25/12.5/50/75GHz spacing";
             }
             enum "194.25625" {
               description "194.25625 THz/1543.28 nm 6.25GHz spacing";
             }
             enum "194.26250" {
               description "194.26250 THz/1543.23 nm 6.25/12.5GHz spacing";
             }
             enum "194.26875" {
               description "194.26875 THz/1543.18 nm 6.25GHz spacing";
             }
             enum "194.27500" {
               description "194.27500 THz/1543.13 nm 6.25/12.5GHz spacing";
             }
             enum "194.28125" {
               description "194.28125 THz/1543.08 nm 6.25GHz spacing";
             }
             enum "194.28750" {
               description "194.28750 THz/1543.04 nm 6.25/12.5GHz spacing";
             }
             enum "194.29375" {
               description "194.29375 THz/1542.99 nm 6.25GHz spacing";
             }
             enum "194.30000" {
               description "194.30000 THz/1542.94 nm 6.25/12.5/50/75/100GHz spacing";
             }
             enum "194.30625" {
               description "194.30625 THz/1542.89 nm 6.25GHz spacing";
             }
             enum "194.31250" {
               description "194.31250 THz/1542.84 nm 6.25/12.5GHz spacing";
             }
             enum "194.31875" {
               description "194.31875 THz/1542.79 nm 6.25GHz spacing";
             }
             enum "194.32500" {
               description "194.32500 THz/1542.74 nm 6.25/12.5GHz spacing";
             }
             enum "194.33125" {
               description "194.33125 THz/1542.69 nm 6.25GHz spacing";
             }
             enum "194.33750" {
               description "194.33750 THz/1542.64 nm 6.25/12.5GHz spacing";
             }
             enum "194.34375" {
               description "194.34375 THz/1542.59 nm 6.25GHz spacing";
             }
             enum "194.35000" {
               description "194.35000 THz/1542.54 nm 6.25/12.5/50GHz spacing";
             }
             enum "194.35625" {
               description "194.35625 THz/1542.49 nm 6.25GHz spacing";
             }
             enum "194.36250" {
               description "194.36250 THz/1542.44 nm 6.25/12.5GHz spacing";
             }
             enum "194.36875" {
               description "194.36875 THz/1542.39 nm 6.25GHz spacing";
             }
             enum "194.37500" {
               description "194.37500 THz/1542.34 nm 6.25/12.5/75GHz spacing";
             }
             enum "194.38125" {
               description "194.38125 THz/1542.29 nm 6.25GHz spacing";
             }
             enum "194.38750" {
               description "194.38750 THz/1542.24 nm 6.25/12.5GHz spacing";
             }
             enum "194.39375" {
               description "194.39375 THz/1542.19 nm 6.25GHz spacing";
             }
             enum "194.40000" {
               description "194.40000 THz/1542.14 nm 6.25/12.5/50/100GHz spacing";
             }
             enum "194.40625" {
               description "194.40625 THz/1542.09 nm 6.25GHz spacing";
             }
             enum "194.41250" {
               description "194.41250 THz/1542.04 nm 6.25/12.5GHz spacing";
             }
             enum "194.41875" {
               description "194.41875 THz/1541.99 nm 6.25GHz spacing";
             }
             enum "194.42500" {
               description "194.42500 THz/1541.94 nm 6.25/12.5GHz spacing";
             }
             enum "194.43125" {
               description "194.43125 THz/1541.89 nm 6.25GHz spacing";
             }
             enum "194.43750" {
               description "194.43750 THz/1541.84 nm 6.25/12.5GHz spacing";
             }
             enum "194.44375" {
               description "194.44375 THz/1541.80 nm 6.25GHz spacing";
             }
             enum "194.45000" {
               description "194.45000 THz/1541.75 nm 6.25/12.5/50/75GHz spacing";
             }
             enum "194.45625" {
               description "194.45625 THz/1541.70 nm 6.25GHz spacing";
             }
             enum "194.46250" {
               description "194.46250 THz/1541.65 nm 6.25/12.5GHz spacing";
             }
             enum "194.46875" {
               description "194.46875 THz/1541.60 nm 6.25GHz spacing";
             }
             enum "194.47500" {
               description "194.47500 THz/1541.55 nm 6.25/12.5GHz spacing";
             }
             enum "194.48125" {
               description "194.48125 THz/1541.50 nm 6.25GHz spacing";
             }
             enum "194.48750" {
               description "194.48750 THz/1541.45 nm 6.25/12.5GHz spacing";
             }
             enum "194.49375" {
               description "194.49375 THz/1541.40 nm 6.25GHz spacing";
             }
             enum "194.50000" {
               description "194.50000 THz/1541.35 nm 6.25/12.5/50/100GHz spacing";
             }
             enum "194.50625" {
               description "194.50625 THz/1541.30 nm 6.25GHz spacing";
             }
             enum "194.51250" {
               description "194.51250 THz/1541.25 nm 6.25/12.5GHz spacing";
             }
             enum "194.51875" {
               description "194.51875 THz/1541.20 nm 6.25GHz spacing";
             }
             enum "194.52500" {
               description "194.52500 THz/1541.15 nm 6.25/12.5/75GHz spacing";
             }
             enum "194.53125" {
               description "194.53125 THz/1541.10 nm 6.25GHz spacing";
             }
             enum "194.53750" {
               description "194.53750 THz/1541.05 nm 6.25/12.5GHz spacing";
             }
             enum "194.54375" {
               description "194.54375 THz/1541.00 nm 6.25GHz spacing";
             }
             enum "194.55000" {
               description "194.55000 THz/1540.95 nm 6.25/12.5/50GHz spacing";
             }
             enum "194.55625" {
               description "194.55625 THz/1540.90 nm 6.25GHz spacing";
             }
             enum "194.56250" {
               description "194.56250 THz/1540.85 nm 6.25/12.5GHz spacing";
             }
             enum "194.56875" {
               description "194.56875 THz/1540.80 nm 6.25GHz spacing";
             }
             enum "194.57500" {
               description "194.57500 THz/1540.76 nm 6.25/12.5GHz spacing";
             }
             enum "194.58125" {
               description "194.58125 THz/1540.71 nm 6.25GHz spacing";
             }
             enum "194.58750" {
               description "194.58750 THz/1540.66 nm 6.25/12.5GHz spacing";
             }
             enum "194.59375" {
               description "194.59375 THz/1540.61 nm 6.25GHz spacing";
             }
             enum "194.60000" {
               description "194.60000 THz/1540.56 nm 6.25/12.5/50/75/100GHz spacing";
             }
             enum "194.60625" {
               description "194.60625 THz/1540.51 nm 6.25GHz spacing";
             }
             enum "194.61250" {
               description "194.61250 THz/1540.46 nm 6.25/12.5GHz spacing";
             }
             enum "194.61875" {
               description "194.61875 THz/1540.41 nm 6.25GHz spacing";
             }
             enum "194.62500" {
               description "194.62500 THz/1540.36 nm 6.25/12.5GHz spacing";
             }
             enum "194.63125" {
               description "194.63125 THz/1540.31 nm 6.25GHz spacing";
             }
             enum "194.63750" {
               description "194.63750 THz/1540.26 nm 6.25/12.5GHz spacing";
             }
             enum "194.64375" {
               description "194.64375 THz/1540.21 nm 6.25GHz spacing";
             }
             enum "194.65000" {
               description "194.65000 THz/1540.16 nm 6.25/12.5/50GHz spacing";
             }
             enum "194.65625" {
               description "194.65625 THz/1540.11 nm 6.25GHz spacing";
             }
             enum "194.66250" {
               description "194.66250 THz/1540.06 nm 6.25/12.5GHz spacing";
             }
             enum "194.66875" {
               description "194.66875 THz/1540.01 nm 6.25GHz spacing";
             }
             enum "194.67500" {
               description "194.67500 THz/1539.96 nm 6.25/12.5/75GHz spacing";
             }
             enum "194.68125" {
               description "194.68125 THz/1539.91 nm 6.25GHz spacing";
             }
             enum "194.68750" {
               description "194.68750 THz/1539.86 nm 6.25/12.5GHz spacing";
             }
             enum "194.69375" {
               description "194.69375 THz/1539.82 nm 6.25GHz spacing";
             }
             enum "194.70000" {
               description "194.70000 THz/1539.77 nm 6.25/12.5/50/100GHz spacing";
             }
             enum "194.70625" {
               description "194.70625 THz/1539.72 nm 6.25GHz spacing";
             }
             enum "194.71250" {
               description "194.71250 THz/1539.67 nm 6.25/12.5GHz spacing";
             }
             enum "194.71875" {
               description "194.71875 THz/1539.62 nm 6.25GHz spacing";
             }
             enum "194.72500" {
               description "194.72500 THz/1539.57 nm 6.25/12.5GHz spacing";
             }
             enum "194.73125" {
               description "194.73125 THz/1539.52 nm 6.25GHz spacing";
             }
             enum "194.73750" {
               description "194.73750 THz/1539.47 nm 6.25/12.5GHz spacing";
             }
             enum "194.74375" {
               description "194.74375 THz/1539.42 nm 6.25GHz spacing";
             }
             enum "194.75000" {
               description "194.75000 THz/1539.37 nm 6.25/12.5/50/75GHz spacing";
             }
             enum "194.75625" {
               description "194.75625 THz/1539.32 nm 6.25GHz spacing";
             }
             enum "194.76250" {
               description "194.76250 THz/1539.27 nm 6.25/12.5GHz spacing";
             }
             enum "194.76875" {
               description "194.76875 THz/1539.22 nm 6.25GHz spacing";
             }
             enum "194.77500" {
               description "194.77500 THz/1539.17 nm 6.25/12.5GHz spacing";
             }
             enum "194.78125" {
               description "194.78125 THz/1539.12 nm 6.25GHz spacing";
             }
             enum "194.78750" {
               description "194.78750 THz/1539.07 nm 6.25/12.5GHz spacing";
             }
             enum "194.79375" {
               description "194.79375 THz/1539.03 nm 6.25GHz spacing";
             }
             enum "194.80000" {
               description "194.80000 THz/1538.98 nm 6.25/12.5/50/100GHz spacing";
             }
             enum "194.80625" {
               description "194.80625 THz/1538.93 nm 6.25GHz spacing";
             }
             enum "194.81250" {
               description "194.81250 THz/1538.88 nm 6.25/12.5GHz spacing";
             }
             enum "194.81875" {
               description "194.81875 THz/1538.83 nm 6.25GHz spacing";
             }
             enum "194.82500" {
               description "194.82500 THz/1538.78 nm 6.25/12.5/75GHz spacing";
             }
             enum "194.83125" {
               description "194.83125 THz/1538.73 nm 6.25GHz spacing";
             }
             enum "194.83750" {
               description "194.83750 THz/1538.68 nm 6.25/12.5GHz spacing";
             }
             enum "194.84375" {
               description "194.84375 THz/1538.63 nm 6.25GHz spacing";
             }
             enum "194.85000" {
               description "194.85000 THz/1538.58 nm 6.25/12.5/50GHz spacing";
             }
             enum "194.85625" {
               description "194.85625 THz/1538.53 nm 6.25GHz spacing";
             }
             enum "194.86250" {
               description "194.86250 THz/1538.48 nm 6.25/12.5GHz spacing";
             }
             enum "194.86875" {
               description "194.86875 THz/1538.43 nm 6.25GHz spacing";
             }
             enum "194.87500" {
               description "194.87500 THz/1538.38 nm 6.25/12.5GHz spacing";
             }
             enum "194.88125" {
               description "194.88125 THz/1538.33 nm 6.25GHz spacing";
             }
             enum "194.88750" {
               description "194.88750 THz/1538.28 nm 6.25/12.5GHz spacing";
             }
             enum "194.89375" {
               description "194.89375 THz/1538.24 nm 6.25GHz spacing";
             }
             enum "194.90000" {
               description "194.90000 THz/1538.19 nm 6.25/12.5/50/75/100GHz spacing";
             }
             enum "194.90625" {
               description "194.90625 THz/1538.14 nm 6.25GHz spacing";
             }
             enum "194.91250" {
               description "194.91250 THz/1538.09 nm 6.25/12.5GHz spacing";
             }
             enum "194.91875" {
               description "194.91875 THz/1538.04 nm 6.25GHz spacing";
             }
             enum "194.92500" {
               description "194.92500 THz/1537.99 nm 6.25/12.5GHz spacing";
             }
             enum "194.93125" {
               description "194.93125 THz/1537.94 nm 6.25GHz spacing";
             }
             enum "194.93750" {
               description "194.93750 THz/1537.89 nm 6.25/12.5GHz spacing";
             }
             enum "194.94375" {
               description "194.94375 THz/1537.84 nm 6.25GHz spacing";
             }
             enum "194.95000" {
               description "194.95000 THz/1537.79 nm 6.25/12.5/50GHz spacing";
             }
             enum "194.95625" {
               description "194.95625 THz/1537.74 nm 6.25GHz spacing";
             }
             enum "194.96250" {
               description "194.96250 THz/1537.69 nm 6.25/12.5GHz spacing";
             }
             enum "194.96875" {
               description "194.96875 THz/1537.64 nm 6.25GHz spacing";
             }
             enum "194.97500" {
               description "194.97500 THz/1537.59 nm 6.25/12.5/75GHz spacing";
             }
             enum "194.98125" {
               description "194.98125 THz/1537.55 nm 6.25GHz spacing";
             }
             enum "194.98750" {
               description "194.98750 THz/1537.50 nm 6.25/12.5GHz spacing";
             }
             enum "194.99375" {
               description "194.99375 THz/1537.45 nm 6.25GHz spacing";
             }
             enum "195.00000" {
               description "195.00000 THz/1537.40 nm 6.25/12.5/50/100GHz spacing";
             }
             enum "195.00625" {
               description "195.00625 THz/1537.35 nm 6.25GHz spacing";
             }
             enum "195.01250" {
               description "195.01250 THz/1537.30 nm 6.25/12.5GHz spacing";
             }
             enum "195.01875" {
               description "195.01875 THz/1537.25 nm 6.25GHz spacing";
             }
             enum "195.02500" {
               description "195.02500 THz/1537.20 nm 6.25/12.5GHz spacing";
             }
             enum "195.03125" {
               description "195.03125 THz/1537.15 nm 6.25GHz spacing";
             }
             enum "195.03750" {
               description "195.03750 THz/1537.10 nm 6.25/12.5GHz spacing";
             }
             enum "195.04375" {
               description "195.04375 THz/1537.05 nm 6.25GHz spacing";
             }
             enum "195.05000" {
               description "195.05000 THz/1537.00 nm 6.25/12.5/50/75GHz spacing";
             }
             enum "195.05625" {
               description "195.05625 THz/1536.95 nm 6.25GHz spacing";
             }
             enum "195.06250" {
               description "195.06250 THz/1536.90 nm 6.25/12.5GHz spacing";
             }
             enum "195.06875" {
               description "195.06875 THz/1536.86 nm 6.25GHz spacing";
             }
             enum "195.07500" {
               description "195.07500 THz/1536.81 nm 6.25/12.5GHz spacing";
             }
             enum "195.08125" {
               description "195.08125 THz/1536.76 nm 6.25GHz spacing";
             }
             enum "195.08750" {
               description "195.08750 THz/1536.71 nm 6.25/12.5GHz spacing";
             }
             enum "195.09375" {
               description "195.09375 THz/1536.66 nm 6.25GHz spacing";
             }
             enum "195.10000" {
               description "195.10000 THz/1536.61 nm 6.25/12.5/50/100GHz spacing";
             }
             enum "195.10625" {
               description "195.10625 THz/1536.56 nm 6.25GHz spacing";
             }
             enum "195.11250" {
               description "195.11250 THz/1536.51 nm 6.25/12.5GHz spacing";
             }
             enum "195.11875" {
               description "195.11875 THz/1536.46 nm 6.25GHz spacing";
             }
             enum "195.12500" {
               description "195.12500 THz/1536.41 nm 6.25/12.5/75GHz spacing";
             }
             enum "195.13125" {
               description "195.13125 THz/1536.36 nm 6.25GHz spacing";
             }
             enum "195.13750" {
               description "195.13750 THz/1536.31 nm 6.25/12.5GHz spacing";
             }
             enum "195.14375" {
               description "195.14375 THz/1536.26 nm 6.25GHz spacing";
             }
             enum "195.15000" {
               description "195.15000 THz/1536.22 nm 6.25/12.5/50GHz spacing";
             }
             enum "195.15625" {
               description "195.15625 THz/1536.17 nm 6.25GHz spacing";
             }
             enum "195.16250" {
               description "195.16250 THz/1536.12 nm 6.25/12.5GHz spacing";
             }
             enum "195.16875" {
               description "195.16875 THz/1536.07 nm 6.25GHz spacing";
             }
             enum "195.17500" {
               description "195.17500 THz/1536.02 nm 6.25/12.5GHz spacing";
             }
             enum "195.18125" {
               description "195.18125 THz/1535.97 nm 6.25GHz spacing";
             }
             enum "195.18750" {
               description "195.18750 THz/1535.92 nm 6.25/12.5GHz spacing";
             }
             enum "195.19375" {
               description "195.19375 THz/1535.87 nm 6.25GHz spacing";
             }
             enum "195.20000" {
               description "195.20000 THz/1535.82 nm 6.25/12.5/50/75/100GHz spacing";
             }
             enum "195.20625" {
               description "195.20625 THz/1535.77 nm 6.25GHz spacing";
             }
             enum "195.21250" {
               description "195.21250 THz/1535.72 nm 6.25/12.5GHz spacing";
             }
             enum "195.21875" {
               description "195.21875 THz/1535.67 nm 6.25GHz spacing";
             }
             enum "195.22500" {
               description "195.22500 THz/1535.63 nm 6.25/12.5GHz spacing";
             }
             enum "195.23125" {
               description "195.23125 THz/1535.58 nm 6.25GHz spacing";
             }
             enum "195.23750" {
               description "195.23750 THz/1535.53 nm 6.25/12.5GHz spacing";
             }
             enum "195.24375" {
               description "195.24375 THz/1535.48 nm 6.25GHz spacing";
             }
             enum "195.25000" {
               description "195.25000 THz/1535.43 nm 6.25/12.5/50GHz spacing";
             }
             enum "195.25625" {
               description "195.25625 THz/1535.38 nm 6.25GHz spacing";
             }
             enum "195.26250" {
               description "195.26250 THz/1535.33 nm 6.25/12.5GHz spacing";
             }
             enum "195.26875" {
               description "195.26875 THz/1535.28 nm 6.25GHz spacing";
             }
             enum "195.27500" {
               description "195.27500 THz/1535.23 nm 6.25/12.5/75GHz spacing";
             }
             enum "195.28125" {
               description "195.28125 THz/1535.18 nm 6.25GHz spacing";
             }
             enum "195.28750" {
               description "195.28750 THz/1535.13 nm 6.25/12.5GHz spacing";
             }
             enum "195.29375" {
               description "195.29375 THz/1535.08 nm 6.25GHz spacing";
             }
             enum "195.30000" {
               description "195.30000 THz/1535.04 nm 6.25/12.5/50/100GHz spacing";
             }
             enum "195.30625" {
               description "195.30625 THz/1534.99 nm 6.25GHz spacing";
             }
             enum "195.31250" {
               description "195.31250 THz/1534.94 nm 6.25/12.5GHz spacing";
             }
             enum "195.31875" {
               description "195.31875 THz/1534.89 nm 6.25GHz spacing";
             }
             enum "195.32500" {
               description "195.32500 THz/1534.84 nm 6.25/12.5GHz spacing";
             }
             enum "195.33125" {
               description "195.33125 THz/1534.79 nm 6.25GHz spacing";
             }
             enum "195.33750" {
               description "195.33750 THz/1534.74 nm 6.25/12.5GHz spacing";
             }
             enum "195.34375" {
               description "195.34375 THz/1534.69 nm 6.25GHz spacing";
             }
             enum "195.35000" {
               description "195.35000 THz/1534.64 nm 6.25/12.5/50/75GHz spacing";
             }
             enum "195.35625" {
               description "195.35625 THz/1534.59 nm 6.25GHz spacing";
             }
             enum "195.36250" {
               description "195.36250 THz/1534.54 nm 6.25/12.5GHz spacing";
             }
             enum "195.36875" {
               description "195.36875 THz/1534.50 nm 6.25GHz spacing";
             }
             enum "195.37500" {
               description "195.37500 THz/1534.45 nm 6.25/12.5GHz spacing";
             }
             enum "195.38125" {
               description "195.38125 THz/1534.40 nm 6.25GHz spacing";
             }
             enum "195.38750" {
               description "195.38750 THz/1534.35 nm 6.25/12.5GHz spacing";
             }
             enum "195.39375" {
               description "195.39375 THz/1534.30 nm 6.25GHz spacing";
             }
             enum "195.40000" {
               description "195.40000 THz/1534.25 nm 6.25/12.5/50/100GHz spacing";
             }
             enum "195.40625" {
               description "195.40625 THz/1534.20 nm 6.25GHz spacing";
             }
             enum "195.41250" {
               description "195.41250 THz/1534.15 nm 6.25/12.5GHz spacing";
             }
             enum "195.41875" {
               description "195.41875 THz/1534.10 nm 6.25GHz spacing";
             }
             enum "195.42500" {
               description "195.42500 THz/1534.05 nm 6.25/12.5/75GHz spacing";
             }
             enum "195.43125" {
               description "195.43125 THz/1534.00 nm 6.25GHz spacing";
             }
             enum "195.43750" {
               description "195.43750 THz/1533.96 nm 6.25/12.5GHz spacing";
             }
             enum "195.44375" {
               description "195.44375 THz/1533.91 nm 6.25GHz spacing";
             }
             enum "195.45000" {
               description "195.45000 THz/1533.86 nm 6.25/12.5/50GHz spacing";
             }
             enum "195.45625" {
               description "195.45625 THz/1533.81 nm 6.25GHz spacing";
             }
             enum "195.46250" {
               description "195.46250 THz/1533.76 nm 6.25/12.5GHz spacing";
             }
             enum "195.46875" {
               description "195.46875 THz/1533.71 nm 6.25GHz spacing";
             }
             enum "195.47500" {
               description "195.47500 THz/1533.66 nm 6.25/12.5GHz spacing";
             }
             enum "195.48125" {
               description "195.48125 THz/1533.61 nm 6.25GHz spacing";
             }
             enum "195.48750" {
               description "195.48750 THz/1533.56 nm 6.25/12.5GHz spacing";
             }
             enum "195.49375" {
               description "195.49375 THz/1533.51 nm 6.25GHz spacing";
             }
             enum "195.50000" {
               description "195.50000 THz/1533.47 nm 6.25/12.5/50/75/100GHz spacing";
             }
             enum "195.50625" {
               description "195.50625 THz/1533.42 nm 6.25GHz spacing";
             }
             enum "195.51250" {
               description "195.51250 THz/1533.37 nm 6.25/12.5GHz spacing";
             }
             enum "195.51875" {
               description "195.51875 THz/1533.32 nm 6.25GHz spacing";
             }
             enum "195.52500" {
               description "195.52500 THz/1533.27 nm 6.25/12.5GHz spacing";
             }
             enum "195.53125" {
               description "195.53125 THz/1533.22 nm 6.25GHz spacing";
             }
             enum "195.53750" {
               description "195.53750 THz/1533.17 nm 6.25/12.5GHz spacing";
             }
             enum "195.54375" {
               description "195.54375 THz/1533.12 nm 6.25GHz spacing";
             }
             enum "195.55000" {
               description "195.55000 THz/1533.07 nm 6.25/12.5/50GHz spacing";
             }
             enum "195.55625" {
               description "195.55625 THz/1533.02 nm 6.25GHz spacing";
             }
             enum "195.56250" {
               description "195.56250 THz/1532.98 nm 6.25/12.5GHz spacing";
             }
             enum "195.56875" {
               description "195.56875 THz/1532.93 nm 6.25GHz spacing";
             }
             enum "195.57500" {
               description "195.57500 THz/1532.88 nm 6.25/12.5/75GHz spacing";
             }
             enum "195.58125" {
               description "195.58125 THz/1532.83 nm 6.25GHz spacing";
             }
             enum "195.58750" {
               description "195.58750 THz/1532.78 nm 6.25/12.5GHz spacing";
             }
             enum "195.59375" {
               description "195.59375 THz/1532.73 nm 6.25GHz spacing";
             }
             enum "195.60000" {
               description "195.60000 THz/1532.68 nm 6.25/12.5/50/100GHz spacing";
             }
             enum "195.60625" {
               description "195.60625 THz/1532.63 nm 6.25GHz spacing";
             }
             enum "195.61250" {
               description "195.61250 THz/1532.58 nm 6.25/12.5GHz spacing";
             }
             enum "195.61875" {
               description "195.61875 THz/1532.53 nm 6.25GHz spacing";
             }
             enum "195.62500" {
               description "195.62500 THz/1532.49 nm 6.25/12.5GHz spacing";
             }
             enum "195.63125" {
               description "195.63125 THz/1532.44 nm 6.25GHz spacing";
             }
             enum "195.63750" {
               description "195.63750 THz/1532.39 nm 6.25/12.5GHz spacing";
             }
             enum "195.64375" {
               description "195.64375 THz/1532.34 nm 6.25GHz spacing";
             }
             enum "195.65000" {
               description "195.65000 THz/1532.29 nm 6.25/12.5/50/75GHz spacing";
             }
             enum "195.65625" {
               description "195.65625 THz/1532.24 nm 6.25GHz spacing";
             }
             enum "195.66250" {
               description "195.66250 THz/1532.19 nm 6.25/12.5GHz spacing";
             }
             enum "195.66875" {
               description "195.66875 THz/1532.14 nm 6.25GHz spacing";
             }
             enum "195.67500" {
               description "195.67500 THz/1532.09 nm 6.25/12.5GHz spacing";
             }
             enum "195.68125" {
               description "195.68125 THz/1532.04 nm 6.25GHz spacing";
             }
             enum "195.68750" {
               description "195.68750 THz/1532.00 nm 6.25/12.5GHz spacing";
             }
             enum "195.69375" {
               description "195.69375 THz/1531.95 nm 6.25GHz spacing";
             }
             enum "195.70000" {
               description "195.70000 THz/1531.90 nm 6.25/12.5/50/100GHz spacing";
             }
             enum "195.70625" {
               description "195.70625 THz/1531.85 nm 6.25GHz spacing";
             }
             enum "195.71250" {
               description "195.71250 THz/1531.80 nm 6.25/12.5GHz spacing";
             }
             enum "195.71875" {
               description "195.71875 THz/1531.75 nm 6.25GHz spacing";
             }
             enum "195.72500" {
               description "195.72500 THz/1531.70 nm 6.25/12.5/75GHz spacing";
             }
             enum "195.73125" {
               description "195.73125 THz/1531.65 nm 6.25GHz spacing";
             }
             enum "195.73750" {
               description "195.73750 THz/1531.60 nm 6.25/12.5GHz spacing";
             }
             enum "195.74375" {
               description "195.74375 THz/1531.56 nm 6.25GHz spacing";
             }
             enum "195.75000" {
               description "195.75000 THz/1531.51 nm 6.25/12.5/50GHz spacing";
             }
             enum "195.75625" {
               description "195.75625 THz/1531.46 nm 6.25GHz spacing";
             }
             enum "195.76250" {
               description "195.76250 THz/1531.41 nm 6.25/12.5GHz spacing";
             }
             enum "195.76875" {
               description "195.76875 THz/1531.36 nm 6.25GHz spacing";
             }
             enum "195.77500" {
               description "195.77500 THz/1531.31 nm 6.25/12.5GHz spacing";
             }
             enum "195.78125" {
               description "195.78125 THz/1531.26 nm 6.25GHz spacing";
             }
             enum "195.78750" {
               description "195.78750 THz/1531.21 nm 6.25/12.5GHz spacing";
             }
             enum "195.79375" {
               description "195.79375 THz/1531.16 nm 6.25GHz spacing";
             }
             enum "195.80000" {
               description "195.80000 THz/1531.12 nm 6.25/12.5/50/75/100GHz spacing";
             }
             enum "195.80625" {
               description "195.80625 THz/1531.07 nm 6.25GHz spacing";
             }
             enum "195.81250" {
               description "195.81250 THz/1531.02 nm 6.25/12.5GHz spacing";
             }
             enum "195.81875" {
               description "195.81875 THz/1530.97 nm 6.25GHz spacing";
             }
             enum "195.82500" {
               description "195.82500 THz/1530.92 nm 6.25/12.5GHz spacing";
             }
             enum "195.83125" {
               description "195.83125 THz/1530.87 nm 6.25GHz spacing";
             }
             enum "195.83750" {
               description "195.83750 THz/1530.82 nm 6.25/12.5GHz spacing";
             }
             enum "195.84375" {
               description "195.84375 THz/1530.77 nm 6.25GHz spacing";
             }
             enum "195.85000" {
               description "195.85000 THz/1530.72 nm 6.25/12.5/50GHz spacing";
             }
             enum "195.85625" {
               description "195.85625 THz/1530.68 nm 6.25GHz spacing";
             }
             enum "195.86250" {
               description "195.86250 THz/1530.63 nm 6.25/12.5GHz spacing";
             }
             enum "195.86875" {
               description "195.86875 THz/1530.58 nm 6.25GHz spacing";
             }
             enum "195.87500" {
               description "195.87500 THz/1530.53 nm 6.25/12.5/75GHz spacing";
             }
             enum "195.88125" {
               description "195.88125 THz/1530.48 nm 6.25GHz spacing";
             }
             enum "195.88750" {
               description "195.88750 THz/1530.43 nm 6.25/12.5GHz spacing";
             }
             enum "195.89375" {
               description "195.89375 THz/1530.38 nm 6.25GHz spacing";
             }
             enum "195.90000" {
               description "195.90000 THz/1530.33 nm 6.25/12.5/50/100GHz spacing";
             }
             enum "195.90625" {
               description "195.90625 THz/1530.29 nm 6.25GHz spacing";
             }
             enum "195.91250" {
               description "195.91250 THz/1530.24 nm 6.25/12.5GHz spacing";
             }
             enum "195.91875" {
               description "195.91875 THz/1530.19 nm 6.25GHz spacing";
             }
             enum "195.92500" {
               description "195.92500 THz/1530.14 nm 6.25/12.5GHz spacing";
             }
             enum "195.93125" {
               description "195.93125 THz/1530.09 nm 6.25GHz spacing";
             }
             enum "195.93750" {
               description "195.93750 THz/1530.04 nm 6.25/12.5GHz spacing";
             }
             enum "195.94375" {
               description "195.94375 THz/1529.99 nm 6.25GHz spacing";
             }
             enum "195.95000" {
               description "195.95000 THz/1529.94 nm 6.25/12.5/50/75GHz spacing";
             }
             enum "195.95625" {
               description "195.95625 THz/1529.89 nm 6.25GHz spacing";
             }
             enum "195.96250" {
               description "195.96250 THz/1529.85 nm 6.25/12.5GHz spacing";
             }
             enum "195.96875" {
               description "195.96875 THz/1529.80 nm 6.25GHz spacing";
             }
             enum "195.97500" {
               description "195.97500 THz/1529.75 nm 6.25/12.5GHz spacing";
             }
             enum "195.98125" {
               description "195.98125 THz/1529.70 nm 6.25GHz spacing";
             }
             enum "195.98750" {
               description "195.98750 THz/1529.65 nm 6.25/12.5GHz spacing";
             }
             enum "195.99375" {
               description "195.99375 THz/1529.60 nm 6.25GHz spacing";
             }
             enum "196.00000" {
               description "196.00000 THz/1529.55 nm 6.25/12.5/50/100GHz spacing";
             }
             enum "196.00625" {
               description "196.00625 THz/1529.50 nm 6.25GHz spacing";
             }
             enum "196.01250" {
               description "196.01250 THz/1529.46 nm 6.25/12.5GHz spacing";
             }
             enum "196.01875" {
               description "196.01875 THz/1529.41 nm 6.25GHz spacing";
             }
             enum "196.02500" {
               description "196.02500 THz/1529.36 nm 6.25/12.5/75GHz spacing";
             }
             enum "196.03125" {
               description "196.03125 THz/1529.31 nm 6.25GHz spacing";
             }
             enum "196.03750" {
               description "196.03750 THz/1529.26 nm 6.25/12.5GHz spacing";
             }
             enum "196.04375" {
               description "196.04375 THz/1529.21 nm 6.25GHz spacing";
             }
             enum "196.05000" {
               description "196.05000 THz/1529.16 nm 6.25/12.5/50GHz spacing";
             }
             enum "196.05625" {
               description "196.05625 THz/1529.11 nm 6.25GHz spacing";
             }
             enum "196.06250" {
               description "196.06250 THz/1529.07 nm 6.25/12.5GHz spacing";
             }
             enum "196.06875" {
               description "196.06875 THz/1529.02 nm 6.25GHz spacing";
             }
             enum "196.07500" {
               description "196.07500 THz/1528.97 nm 6.25/12.5GHz spacing";
             }
             enum "196.08125" {
               description "196.08125 THz/1528.92 nm 6.25GHz spacing";
             }
             enum "196.08750" {
               description "196.08750 THz/1528.87 nm 6.25/12.5GHz spacing";
             }
             enum "196.09375" {
               description "196.09375 THz/1528.82 nm 6.25GHz spacing";
             }
             enum "196.10000" {
               description "196.10000 THz/1528.77 nm 6.25/12.5/50/75/100GHz spacing";
             }
             enum "196.15040" {
               description "196.15040 THz/1528.38 nm 50Ghz spacing";
             }
           }
         }
       }
     }
     leaf tx-power {
       description "Transmit laser output power";
       units "dBm";
       type string {
         junos:posix-pattern "^([+-]?[1-9]?[0-9](.[0-9][0-9]?)?)$";
         junos:pattern-message "Signed value with up to 2 decimal places";
       }
     }
     choice laser-enable-choice {
       leaf laser-enable {
         description "Enable transmit laser";
         type empty;
       }
       leaf no-laser-enable {
         description "Don't enable transmit laser";
         type empty;
       }
     }
   }
   grouping odu-attributes {
     description "Optical Data Unit configuration attributes";
     uses apply-advanced;
     leaf rate {
       description "Specific type of ODU, according to data rate";
       type enumeration {
         enum "odu4" {
           description "ODU4 for 100 Gbps";
         }
       }
     }
     choice is-ma-choice {
       leaf is-ma {
         description "Link is enabled for maintenance tasks, alarms are masked";
         type empty;
       }
       leaf no-is-ma {
         description "Don't link is enabled for maintenance tasks, alarms are masked";
         type empty;
       }
     }
     container tti {
       description "Configuration of OTU trail trace identifier";
       presence "enable tti";
       uses otn-tti-attributes;
     }
     container degrade {
       description "Configuration of OTU degrade defect detection";
       presence "enable degrade";
       uses otn-degrade;
     }
     leaf exp-payload-type {
       description "Expected OPU payload type";
       type union {
         type uint8;
         type string {
           pattern "<.*>|$.*";
         }
       }
     }
     container prbs {
       description "Configuration of framed pseudorandom binary sequence test signal";
       presence "enable prbs";
       uses prbs-config;
     }
   }
   grouping otn-degrade {
     description "Configuration of degrade defect detection";
     uses apply-advanced;
     leaf degm {
       description "Number of consecutive intervals error rate above threshold";
       type union {
         type string {
           pattern "<.*>|$.*";
         }
         type uint16 {
           range "2 .. 10";
         }
       }
     }
     leaf degthr {
       description "Threshold - percentage errored blocks, ex. 1.23 = 1.23%";
       type string {
         junos:posix-pattern "^((100(.00?)?)|(([1-9])?[0-9](.[0-9][0-9]?)?))$";
         junos:pattern-message "Percentage value up to 2 decimal places";
       }
     }
   }
   grouping otn-tti-attributes {
     description "Configuration of OTN trail trace identifier";
     uses apply-advanced;
     leaf sapi {
       description "Transmitted source access point identifier field";
       type string {
         length "0 .. 15";
       }
     }
     leaf dapi {
       description "Transmitted destination access point identifier field";
       type string {
         length "0 .. 15";
       }
     }
     leaf operator {
       description "Transmitted operator field";
       type string {
         length "0 .. 32";
       }
     }
     leaf exp-sapi {
       description "Expected received source access point identifier field";
       type string {
         length "0 .. 15";
       }
     }
     leaf exp-dapi {
       description "Expected received destination access point identifier field";
       type string {
         length "0 .. 15";
       }
     }
     leaf tim-detect-mode {
       description "Trace input mismatch defect detection mode";
       type enumeration {
         enum "disabled" {
           description "Detection of trace input mismatch defect disabled";
         }
         enum "sapi-only" {
           description "Detection of trace input mismatch defect on SAPI field only";
         }
         enum "dapi-only" {
           description "Detection of trace input mismatch defect on DAPI field only";
         }
         enum "sapi-and-dapi" {
           description "Detection of trace input mismatch defect on both SAPI and DAPI fields";
         }
       }
     }
     choice tim-act-enable-choice {
       leaf tim-act-enable {
         description "Enable trace input mismatch consequential actions";
         type empty;
       }
       leaf no-tim-act-enable {
         description "Don't enable trace input mismatch consequential actions";
         type empty;
       }
     }
   }
   grouping otn_options_type {
     uses apply-advanced;
     choice laser-enable-choice {
       leaf laser-enable {
         description "Enable Laser";
         type empty;
       }
       leaf no-laser-enable {
         description "Don't enable Laser";
         type empty;
       }
     }
     choice is-ma-choice {
       leaf is-ma {
         description "Link is enabled with alarms masked";
         type empty;
       }
       leaf no-is-ma {
         description "Don't link is enabled with alarms masked";
         type empty;
       }
     }
     choice line-loopback-choice {
       leaf line-loopback {
         description "Enable line loopback";
         type empty;
       }
       leaf no-line-loopback {
         description "Don't enable line loopback";
         type empty;
       }
     }
     choice local-loopback-choice {
       leaf local-loopback {
         description "Enable local host loopback";
         type empty;
       }
       leaf no-local-loopback {
         description "Don't enable local host loopback";
         type empty;
       }
     }
     choice prbs-choice {
       leaf prbs {
         description "Enable otn payload prbs";
         type empty;
       }
       leaf no-prbs {
         description "Don't enable otn payload prbs";
         type empty;
       }
     }
     choice odu-ttim-action-enable-choice {
       leaf odu-ttim-action-enable {
         description "Enable consequent action for ODU TTIM";
         type empty;
       }
       leaf no-odu-ttim-action-enable {
         description "Don't enable consequent action for ODU TTIM";
         type empty;
       }
     }
     choice otu-ttim-action-enable-choice {
       leaf otu-ttim-action-enable {
         description "Enable consequent action for OTU TTIM";
         type empty;
       }
       leaf no-otu-ttim-action-enable {
         description "Don't enable consequent action for OTU TTIM";
         type empty;
       }
     }
     choice transport-monitoring-choice {
       leaf transport-monitoring {
         description "Enable transport monitoring";
         type empty;
       }
       leaf no-transport-monitoring {
         description "Don't enable transport monitoring";
         type empty;
       }
     }
     container odu-delay-management {
       description "Set odu delay management";
       uses apply-advanced;
       choice monitor-end-point-choice {
         leaf monitor-end-point {
           description "Originate connection monitor end point";
           type empty;
         }
         leaf no-monitor-end-point {
           description "Don't originate connection monitor end point";
           type empty;
         }
       }
       choice start-measurement-choice {
         leaf start-measurement {
           description "Enable to start a dm measurement";
           type empty;
         }
         leaf no-start-measurement {
           description "Don't enable to start a dm measurement";
           type empty;
         }
       }
       choice bypass-choice {
         leaf bypass {
           description "Act as tandem passing dm value through node";
           type empty;
         }
         leaf no-bypass {
           description "Don't act as tandem passing dm value through node";
           type empty;
         }
       }
       leaf number-of-frames {
         description "Number of consequent frames to declare dm done";
         type union {
           type string {
             pattern "<.*>|$.*";
           }
           type uint32 {
             range "0 .. 255";
           }
         }
       }
       choice remote-loop-enable-choice {
         leaf remote-loop-enable {
           description "Enable remote DM loop on remote end";
           type empty;
         }
         leaf no-remote-loop-enable {
           description "Don't enable remote DM loop on remote end";
           type empty;
         }
       }
     }
     container signal-degrade {
       description "Signal degrade thresholds";
       uses apply-advanced;
       leaf interval {
         description "Time interval";
         default "10";
         units "milliseconds";
         type union {
           type string {
             pattern "<.*>|$.*";
           }
           type uint32 {
             range "1 .. 1000";
           }
         }
       }
       leaf ber-threshold-clear {
         description "Ber threshold for signal degrade clear (format: xe-n, example: 4.5e-3)";
         type string {
           junos:posix-pattern "^[0-9]+(.[0-9]+)?e-[0-9]$";
           junos:pattern-message "Ber threshold value in format: xe-n, x is an integer or decimal number, n = 0..9";
         }
       }
       leaf ber-threshold-signal-degrade {
         description "Ber threshold for signal-degrade (format: xe-n, example: 4.5e-3)";
         type string {
           junos:posix-pattern "^[0-9]+(.[0-9]+)?e-[0-9]$";
           junos:pattern-message "Ber threshold value in format: xe-n, x is an integer or decimal number, n = 0..9";
         }
       }
       leaf q-threshold-signal-degrade-clear {
         description "Q threshold for signal-degrade clear (e.g. 14.26)";
         units "dB";
         type string;
       }
       leaf q-threshold-signal-degrade {
         description "Q threshold for signal-degrade (e.g. 9.26)";
         units "dB";
         type string;
       }
     }
     container odu-signal-degrade {
       description "Signal degrade thresholds for ODU";
       uses apply-advanced;
       leaf interval {
         description "Time interval";
         default "10";
         units "milliseconds";
         type union {
           type string {
             pattern "<.*>|$.*";
           }
           type uint32 {
             range "1 .. 1000";
           }
         }
       }
       leaf ber-threshold-clear {
         description "Ber th for sd clear (format: xe-n, example: 4.5e-3)";
         default "1.0e-9";
         type string {
           junos:posix-pattern "^[0-9]+(.[0-9]+)?e-[0-9]$";
           junos:pattern-message "Ber threshold value in format: xe-n, x is an integer or decimal number, n = 0..9";
         }
       }
       leaf ber-threshold-signal-degrade {
         description "Ber th for sd (format: xe-n, example: 4.5e-3)";
         default "1.0e-6";
         type string {
           junos:posix-pattern "^[0-9]+(.[0-9]+)?e-[0-9]$";
           junos:pattern-message "Ber threshold value in format: xe-n, x is an integer or decimal number, n = 0..9";
         }
       }
     }
     container preemptive-fast-reroute {
       description "Preemptive fast reroute";
       uses apply-advanced;
       choice odu-signal-degrade-monitor-enable-choice {
         leaf odu-signal-degrade-monitor-enable {
           description "Enable ODU signal degrade monitoring";
           type empty;
         }
         leaf no-odu-signal-degrade-monitor-enable {
           description "Don't enable ODU signal degrade monitoring";
           type empty;
         }
       }
       choice odu-backward-frr-enable-choice {
         leaf odu-backward-frr-enable {
           description "Enable ODU backward frr insertion";
           type empty;
         }
         leaf no-odu-backward-frr-enable {
           description "Don't enable ODU backward frr insertion";
           type empty;
         }
       }
       choice signal-degrade-monitor-enable-choice {
         leaf signal-degrade-monitor-enable {
           description "Enable signal degrade monitoring";
           type empty;
         }
         leaf no-signal-degrade-monitor-enable {
           description "Don't enable signal degrade monitoring";
           type empty;
         }
       }
       choice backward-frr-enable-choice {
         leaf backward-frr-enable {
           description "Enable backward frr insertion";
           type empty;
         }
         leaf no-backward-frr-enable {
           description "Don't enable backward frr insertion";
           type empty;
         }
       }
     }
     leaf fec {
       description "Forward Error Correction mode";
       type enumeration {
         enum "none" {
           description "GFEC all 0's";
         }
         enum "gfec" {
           description "GFEC-Generic Forward Error Correction";
         }
         enum "efec" {
           description "EFEC-Enhanced Forward Error Correction";
         }
         enum "gfec-sdfec" {
           description "Both gfec and sdfec";
         }
         enum "ufec" {
           description "UFEC-Ultra Forward Error Correction";
         }
         enum "sdfec" {
           description "SDFEC-Soft Decision Forward Error Correction";
         }
         enum "hgfec" {
           description "HGFEC-High Gain Forward Error Correction";
         }
         enum "sdfec15" {
           description "SDFEC with 15 percent overhead - non-differential";
         }
       }
     }
     choice insert-odu-oci-choice {
       leaf insert-odu-oci {
         description "Force odu open connection indication";
         type empty;
       }
       leaf no-insert-odu-oci {
         description "Don't force odu open connection indication";
         type empty;
       }
     }
     choice insert-odu-lck-choice {
       leaf insert-odu-lck {
         description "Force odu locked maintenance signal";
         type empty;
       }
       leaf no-insert-odu-lck {
         description "Don't force odu locked maintenance signal";
         type empty;
       }
     }
     leaf rate {
       description "Optical Transmission Network mode";
       type enumeration {
         enum "pass-thru" {
           description "Pass through mode - No OTN framing";
         }
         enum "fixed-stuff-bytes" {
           description "Fixed Stuff Bytes 11.0957Gbps";
         }
         enum "no-fixed-stuff-bytes" {
           description "No Fixed Stuff Bytes 11.0491Gbps";
         }
         enum "oc192" {
           description "OTU2 for OC192 10.7Gbps";
         }
         enum "otu3" {
           description "OTU3 for 40Gbps";
         }
         enum "otu4" {
           description "OTU4/OTU4v for 100Gbps-127Gbps";
         }
       }
     }
     container bytes {
       description "Set OTN header bytes";
       uses apply-advanced;
       leaf transmit-payload-type {
         description "Transmit payload type";
         type union {
           type string {
             pattern "<.*>|$.*";
           }
           type uint32 {
             range "0 .. 255";
           }
         }
       }
     }
     container tti {
       description "Trace Identifier";
       uses apply-advanced;
       leaf otu-dapi {
         description "OTU Destination Access Point Identifier";
         type string;
       }
       leaf otu-sapi {
         description "OTU Source Access Point Identifier";
         type string;
       }
       leaf otu-expected-receive-dapi {
         description "OTU Expected Receive Destination Access Point Identifier";
         type string;
       }
       leaf otu-expected-receive-sapi {
         description "OTU Expected Receive Source Access Point Identifier";
         type string;
       }
       leaf odu-dapi {
         description "ODU Destination Access Point Identifier";
         type string;
       }
       leaf odu-sapi {
         description "ODU Source Access Point Identifier";
         type string;
       }
       leaf odu-expected-receive-dapi {
         description "ODU Expected Receive Destination Access Point Identifier";
         type string;
       }
       leaf odu-expected-receive-sapi {
         description "ODU Expected Receive Source Access Point Identifier";
         type string;
       }
       choice otu-dapi-first-byte-nul-choice {
         leaf otu-dapi-first-byte-nul {
           description "Insert all-0s to first byte";
           type empty;
         }
         leaf no-otu-dapi-first-byte-nul {
           description "Don't insert all-0s to first byte";
           type empty;
         }
       }
       choice otu-sapi-first-byte-nul-choice {
         leaf otu-sapi-first-byte-nul {
           description "Insert all-0s to first byte";
           type empty;
         }
         leaf no-otu-sapi-first-byte-nul {
           description "Don't insert all-0s to first byte";
           type empty;
         }
       }
       choice otu-expected-receive-dapi-first-byte-nul-choice {
         leaf otu-expected-receive-dapi-first-byte-nul {
           description "Insert all-0s to first byte";
           type empty;
         }
         leaf no-otu-expected-receive-dapi-first-byte-nul {
           description "Don't insert all-0s to first byte";
           type empty;
         }
       }
       choice otu-expected-receive-sapi-first-byte-nul-choice {
         leaf otu-expected-receive-sapi-first-byte-nul {
           description "Insert all-0s to first byte";
           type empty;
         }
         leaf no-otu-expected-receive-sapi-first-byte-nul {
           description "Don't insert all-0s to first byte";
           type empty;
         }
       }
       choice odu-dapi-first-byte-nul-choice {
         leaf odu-dapi-first-byte-nul {
           description "Insert all-0s to first byte";
           type empty;
         }
         leaf no-odu-dapi-first-byte-nul {
           description "Don't insert all-0s to first byte";
           type empty;
         }
       }
       choice odu-sapi-first-byte-nul-choice {
         leaf odu-sapi-first-byte-nul {
           description "Insert all-0s to first byte";
           type empty;
         }
         leaf no-odu-sapi-first-byte-nul {
           description "Don't insert all-0s to first byte";
           type empty;
         }
       }
       choice odu-expected-receive-dapi-first-byte-nul-choice {
         leaf odu-expected-receive-dapi-first-byte-nul {
           description "Insert all-0s to first byte";
           type empty;
         }
         leaf no-odu-expected-receive-dapi-first-byte-nul {
           description "Don't insert all-0s to first byte";
           type empty;
         }
       }
       choice odu-expected-receive-sapi-first-byte-nul-choice {
         leaf odu-expected-receive-sapi-first-byte-nul {
           description "Insert all-0s to first byte";
           type empty;
         }
         leaf no-odu-expected-receive-sapi-first-byte-nul {
           description "Don't insert all-0s to first byte";
           type empty;
         }
       }
     }
     container trigger {
       description "Defect triggers";
       uses apply-advanced;
       container oc-los {
         junos:cli-feature "oneliner";
         description "OC Loss Of Signal defect trigger";
         choice oc_los_choices {
           case case_1 {
             leaf ignore {
               description "Ignore the defect";
               type empty;
             }
           }
           case case_2 {
             container hold-time {
               junos:cli-feature "oneliner";
               description "Delay before clearing or raising the alarm for defect";
               leaf up {
                 description "Delay before clearing the alarm when the defect is absent";
                 units "milliseconds";
                 type union {
                   type string {
                     pattern "<.*>|$.*";
                   }
                   type uint32 {
                     range "1 .. 65534";
                   }
                 }
               }
               leaf down {
                 description "Delay before raising the alarm when the defect occurs";
                 units "milliseconds";
                 type union {
                   type string {
                     pattern "<.*>|$.*";
                   }
                   type uint32 {
                     range "1 .. 65534";
                   }
                 }
               }
             }
           }
         }
       }
       container oc-lof {
         junos:cli-feature "oneliner";
         description "OC Loss Of Frame defect trigger";
         choice oc_lof_choices {
           case case_1 {
             leaf ignore {
               description "Ignore the defect";
               type empty;
             }
           }
           case case_2 {
             container hold-time {
               junos:cli-feature "oneliner";
               description "Delay before clearing or raising the alarm for defect";
               leaf up {
                 description "Delay before clearing the alarm when the defect is absent";
                 units "milliseconds";
                 type union {
                   type string {
                     pattern "<.*>|$.*";
                   }
                   type uint32 {
                     range "1 .. 65534";
                   }
                 }
               }
               leaf down {
                 description "Delay before raising the alarm when the defect occurs";
                 units "milliseconds";
                 type union {
                   type string {
                     pattern "<.*>|$.*";
                   }
                   type uint32 {
                     range "1 .. 65534";
                   }
                 }
               }
             }
           }
         }
       }
       container oc-lom {
         junos:cli-feature "oneliner";
         description "OC Loss Of Multiframe defect trigger";
         choice oc_lom_choices {
           case case_1 {
             leaf ignore {
               description "Ignore the defect";
               type empty;
             }
           }
           case case_2 {
             container hold-time {
               junos:cli-feature "oneliner";
               description "Delay before clearing or raising the alarm for defect";
               leaf up {
                 description "Delay before clearing the alarm when the defect is absent";
                 units "milliseconds";
                 type union {
                   type string {
                     pattern "<.*>|$.*";
                   }
                   type uint32 {
                     range "1 .. 65534";
                   }
                 }
               }
               leaf down {
                 description "Delay before raising the alarm when the defect occurs";
                 units "milliseconds";
                 type union {
                   type string {
                     pattern "<.*>|$.*";
                   }
                   type uint32 {
                     range "1 .. 65534";
                   }
                 }
               }
             }
           }
         }
       }
       container oc-wavelength-lock {
         junos:cli-feature "oneliner";
         description "OC Wavelength Lock defect trigger";
         choice oc_wavelength_lock_choices {
           case case_1 {
             leaf ignore {
               description "Ignore the defect";
               type empty;
             }
           }
           case case_2 {
             container hold-time {
               junos:cli-feature "oneliner";
               description "Delay before clearing or raising the alarm for defect";
               leaf up {
                 description "Delay before clearing the alarm when the defect is absent";
                 units "milliseconds";
                 type union {
                   type string {
                     pattern "<.*>|$.*";
                   }
                   type uint32 {
                     range "1 .. 65534";
                   }
                 }
               }
               leaf down {
                 description "Delay before raising the alarm when the defect occurs";
                 units "milliseconds";
                 type union {
                   type string {
                     pattern "<.*>|$.*";
                   }
                   type uint32 {
                     range "1 .. 65534";
                   }
                 }
               }
             }
           }
         }
       }
       container oc-tsf {
         junos:cli-feature "oneliner";
         description "Oc tsf defect trigger";
         choice oc-tsf-choices {
           case case_1 {
             leaf ignore {
               description "Ignore the defect";
               type empty;
             }
           }
           case case_2 {
             container hold-time {
               junos:cli-feature "oneliner";
               description "Delay before clearing or raising the alarm for defect";
               leaf up {
                 description "Delay before clearing the alarm when the defect is absent";
                 units "milliseconds";
                 type union {
                   type string {
                     pattern "<.*>|$.*";
                   }
                   type uint32 {
                     range "1 .. 65534";
                   }
                 }
               }
               leaf down {
                 description "Delay before raising the alarm when the defect occurs";
                 units "milliseconds";
                 type union {
                   type string {
                     pattern "<.*>|$.*";
                   }
                   type uint32 {
                     range "1 .. 65534";
                   }
                 }
               }
             }
           }
         }
       }
       container otu-ais {
         junos:cli-feature "oneliner";
         description "OTU Alarm Indication Signal defect trigger";
         choice otu_ais_choices {
           case case_1 {
             leaf ignore {
               description "Ignore the defect";
               type empty;
             }
           }
           case case_2 {
             container hold-time {
               junos:cli-feature "oneliner";
               description "Delay before clearing or raising the alarm for defect";
               leaf up {
                 description "Delay before clearing the alarm when the defect is absent";
                 units "milliseconds";
                 type union {
                   type string {
                     pattern "<.*>|$.*";
                   }
                   type uint32 {
                     range "1 .. 65534";
                   }
                 }
               }
               leaf down {
                 description "Delay before raising the alarm when the defect occurs";
                 units "milliseconds";
                 type union {
                   type string {
                     pattern "<.*>|$.*";
                   }
                   type uint32 {
                     range "1 .. 65534";
                   }
                 }
               }
             }
           }
         }
       }
       container otu-bdi {
         junos:cli-feature "oneliner";
         description "OTU Backward Defect Indication defect trigger";
         choice otu_bdi_choices {
           case case_1 {
             leaf ignore {
               description "Ignore the defect";
               type empty;
             }
           }
           case case_2 {
             container hold-time {
               junos:cli-feature "oneliner";
               description "Delay before clearing or raising the alarm for defect";
               leaf up {
                 description "Delay before clearing the alarm when the defect is absent";
                 units "milliseconds";
                 type union {
                   type string {
                     pattern "<.*>|$.*";
                   }
                   type uint32 {
                     range "1 .. 65534";
                   }
                 }
               }
               leaf down {
                 description "Delay before raising the alarm when the defect occurs";
                 units "milliseconds";
                 type union {
                   type string {
                     pattern "<.*>|$.*";
                   }
                   type uint32 {
                     range "1 .. 65534";
                   }
                 }
               }
             }
           }
         }
       }
       container otu-iae {
         junos:cli-feature "oneliner";
         description "OTU Incoming Alignment defect trigger";
         choice otu_iae_choices {
           case case_1 {
             leaf ignore {
               description "Ignore the defect";
               type empty;
             }
           }
           case case_2 {
             container hold-time {
               junos:cli-feature "oneliner";
               description "Delay before clearing or raising the alarm for defect";
               leaf up {
                 description "Delay before clearing the alarm when the defect is absent";
                 units "milliseconds";
                 type union {
                   type string {
                     pattern "<.*>|$.*";
                   }
                   type uint32 {
                     range "1 .. 65534";
                   }
                 }
               }
               leaf down {
                 description "Delay before raising the alarm when the defect occurs";
                 units "milliseconds";
                 type union {
                   type string {
                     pattern "<.*>|$.*";
                   }
                   type uint32 {
                     range "1 .. 65534";
                   }
                 }
               }
             }
           }
         }
       }
       container otu-ttim {
         junos:cli-feature "oneliner";
         description "OTU Trail Trace Identifier Mismatch defect trigger";
         choice otu_ttim_choices {
           case case_1 {
             leaf ignore {
               description "Ignore the defect";
               type empty;
             }
           }
           case case_2 {
             container hold-time {
               junos:cli-feature "oneliner";
               description "Delay before clearing or raising the alarm for defect";
               leaf up {
                 description "Delay before clearing the alarm when the defect is absent";
                 units "milliseconds";
                 type union {
                   type string {
                     pattern "<.*>|$.*";
                   }
                   type uint32 {
                     range "1 .. 65534";
                   }
                 }
               }
               leaf down {
                 description "Delay before raising the alarm when the defect occurs";
                 units "milliseconds";
                 type union {
                   type string {
                     pattern "<.*>|$.*";
                   }
                   type uint32 {
                     range "1 .. 65534";
                   }
                 }
               }
             }
           }
         }
       }
       container otu-sd {
         junos:cli-feature "oneliner";
         description "OTU Signal Degrade defect trigger";
         choice otu_sd_choices {
           case case_1 {
             leaf ignore {
               description "Ignore the defect";
               type empty;
             }
           }
           case case_2 {
             container hold-time {
               junos:cli-feature "oneliner";
               description "Delay before clearing or raising the alarm for defect";
               leaf up {
                 description "Delay before clearing the alarm when the defect is absent";
                 units "milliseconds";
                 type union {
                   type string {
                     pattern "<.*>|$.*";
                   }
                   type uint32 {
                     range "1 .. 65534";
                   }
                 }
               }
               leaf down {
                 description "Delay before raising the alarm when the defect occurs";
                 units "milliseconds";
                 type union {
                   type string {
                     pattern "<.*>|$.*";
                   }
                   type uint32 {
                     range "1 .. 65534";
                   }
                 }
               }
             }
           }
         }
       }
       container otu-fec-deg {
         junos:cli-feature "oneliner";
         description "OTU FEC Degrade defect trigger";
         choice otu_fec_deg_choices {
           case case_1 {
             leaf ignore {
               description "Ignore the defect";
               type empty;
             }
           }
           case case_2 {
             container hold-time {
               junos:cli-feature "oneliner";
               description "Delay before clearing or raising the alarm for defect";
               leaf up {
                 description "Delay before clearing the alarm when the defect is absent";
                 units "milliseconds";
                 type union {
                   type string {
                     pattern "<.*>|$.*";
                   }
                   type uint32 {
                     range "1 .. 65534";
                   }
                 }
               }
               leaf down {
                 description "Delay before raising the alarm when the defect occurs";
                 units "milliseconds";
                 type union {
                   type string {
                     pattern "<.*>|$.*";
                   }
                   type uint32 {
                     range "1 .. 65534";
                   }
                 }
               }
             }
           }
         }
       }
       container otu-fec-exe {
         junos:cli-feature "oneliner";
         description "OTU FEC Excessive Error defect trigger";
         choice otu_fec_exe_choices {
           case case_1 {
             leaf ignore {
               description "Ignore the defect";
               type empty;
             }
           }
           case case_2 {
             container hold-time {
               junos:cli-feature "oneliner";
               description "Delay before clearing or raising the alarm for defect";
               leaf up {
                 description "Delay before clearing the alarm when the defect is absent";
                 units "milliseconds";
                 type union {
                   type string {
                     pattern "<.*>|$.*";
                   }
                   type uint32 {
                     range "1 .. 65534";
                   }
                 }
               }
               leaf down {
                 description "Delay before raising the alarm when the defect occurs";
                 units "milliseconds";
                 type union {
                   type string {
                     pattern "<.*>|$.*";
                   }
                   type uint32 {
                     range "1 .. 65534";
                   }
                 }
               }
             }
           }
         }
       }
       container odu-ais {
         junos:cli-feature "oneliner";
         description "ODU Alarm Indication Signal defect trigger";
         choice odu_ais_choices {
           case case_1 {
             leaf ignore {
               description "Ignore the defect";
               type empty;
             }
           }
           case case_2 {
             container hold-time {
               junos:cli-feature "oneliner";
               description "Delay before clearing or raising the alarm for defect";
               leaf up {
                 description "Delay before clearing the alarm when the defect is absent";
                 units "milliseconds";
                 type union {
                   type string {
                     pattern "<.*>|$.*";
                   }
                   type uint32 {
                     range "1 .. 65534";
                   }
                 }
               }
               leaf down {
                 description "Delay before raising the alarm when the defect occurs";
                 units "milliseconds";
                 type union {
                   type string {
                     pattern "<.*>|$.*";
                   }
                   type uint32 {
                     range "1 .. 65534";
                   }
                 }
               }
             }
           }
         }
       }
       container odu-bdi {
         junos:cli-feature "oneliner";
         description "ODU Backward Defect Indication defect trigger";
         choice odu_bdi_choices {
           case case_1 {
             leaf ignore {
               description "Ignore the defect";
               type empty;
             }
           }
           case case_2 {
             container hold-time {
               junos:cli-feature "oneliner";
               description "Delay before clearing or raising the alarm for defect";
               leaf up {
                 description "Delay before clearing the alarm when the defect is absent";
                 units "milliseconds";
                 type union {
                   type string {
                     pattern "<.*>|$.*";
                   }
                   type uint32 {
                     range "1 .. 65534";
                   }
                 }
               }
               leaf down {
                 description "Delay before raising the alarm when the defect occurs";
                 units "milliseconds";
                 type union {
                   type string {
                     pattern "<.*>|$.*";
                   }
                   type uint32 {
                     range "1 .. 65534";
                   }
                 }
               }
             }
           }
         }
       }
       container odu-iae {
         junos:cli-feature "oneliner";
         description "Odu iae defect trigger";
         choice odu-iae-choices {
           case case_1 {
             leaf ignore {
               description "Ignore the defect";
               type empty;
             }
           }
           case case_2 {
             container hold-time {
               junos:cli-feature "oneliner";
               description "Delay before clearing or raising the alarm for defect";
               leaf up {
                 description "Delay before clearing the alarm when the defect is absent";
                 units "milliseconds";
                 type union {
                   type string {
                     pattern "<.*>|$.*";
                   }
                   type uint32 {
                     range "1 .. 65534";
                   }
                 }
               }
               leaf down {
                 description "Delay before raising the alarm when the defect occurs";
                 units "milliseconds";
                 type union {
                   type string {
                     pattern "<.*>|$.*";
                   }
                   type uint32 {
                     range "1 .. 65534";
                   }
                 }
               }
             }
           }
         }
       }
       container odu-bei {
         junos:cli-feature "oneliner";
         description "Odu backward error indication defect trigger";
         choice odu_bei_choices {
           case case_1 {
             leaf ignore {
               description "Ignore the defect";
               type empty;
             }
           }
           case case_2 {
             container hold-time {
               junos:cli-feature "oneliner";
               description "Delay before clearing or raising the alarm for defect";
               leaf up {
                 description "Delay before clearing the alarm when the defect is absent";
                 units "milliseconds";
                 type union {
                   type string {
                     pattern "<.*>|$.*";
                   }
                   type uint32 {
                     range "1 .. 65534";
                   }
                 }
               }
               leaf down {
                 description "Delay before raising the alarm when the defect occurs";
                 units "milliseconds";
                 type union {
                   type string {
                     pattern "<.*>|$.*";
                   }
                   type uint32 {
                     range "1 .. 65534";
                   }
                 }
               }
             }
           }
         }
       }
       container odu-oci {
         junos:cli-feature "oneliner";
         description "ODU Open Connection Indication defect trigger";
         choice odu_oci_choices {
           case case_1 {
             leaf ignore {
               description "Ignore the defect";
               type empty;
             }
           }
           case case_2 {
             container hold-time {
               junos:cli-feature "oneliner";
               description "Delay before clearing or raising the alarm for defect";
               leaf up {
                 description "Delay before clearing the alarm when the defect is absent";
                 units "milliseconds";
                 type union {
                   type string {
                     pattern "<.*>|$.*";
                   }
                   type uint32 {
                     range "1 .. 65534";
                   }
                 }
               }
               leaf down {
                 description "Delay before raising the alarm when the defect occurs";
                 units "milliseconds";
                 type union {
                   type string {
                     pattern "<.*>|$.*";
                   }
                   type uint32 {
                     range "1 .. 65534";
                   }
                 }
               }
             }
           }
         }
       }
       container odu-lck {
         junos:cli-feature "oneliner";
         description "ODU Locked defect trigger";
         choice odu_lck_choices {
           case case_1 {
             leaf ignore {
               description "Ignore the defect";
               type empty;
             }
           }
           case case_2 {
             container hold-time {
               junos:cli-feature "oneliner";
               description "Delay before clearing or raising the alarm for defect";
               leaf up {
                 description "Delay before clearing the alarm when the defect is absent";
                 units "milliseconds";
                 type union {
                   type string {
                     pattern "<.*>|$.*";
                   }
                   type uint32 {
                     range "1 .. 65534";
                   }
                 }
               }
               leaf down {
                 description "Delay before raising the alarm when the defect occurs";
                 units "milliseconds";
                 type union {
                   type string {
                     pattern "<.*>|$.*";
                   }
                   type uint32 {
                     range "1 .. 65534";
                   }
                 }
               }
             }
           }
         }
       }
       container odu-ttim {
         junos:cli-feature "oneliner";
         description "ODU Trail Trace Identifier Mismatch defect trigger";
         choice odu_ttim_choices {
           case case_1 {
             leaf ignore {
               description "Ignore the defect";
               type empty;
             }
           }
           case case_2 {
             container hold-time {
               junos:cli-feature "oneliner";
               description "Delay before clearing or raising the alarm for defect";
               leaf up {
                 description "Delay before clearing the alarm when the defect is absent";
                 units "milliseconds";
                 type union {
                   type string {
                     pattern "<.*>|$.*";
                   }
                   type uint32 {
                     range "1 .. 65534";
                   }
                 }
               }
               leaf down {
                 description "Delay before raising the alarm when the defect occurs";
                 units "milliseconds";
                 type union {
                   type string {
                     pattern "<.*>|$.*";
                   }
                   type uint32 {
                     range "1 .. 65534";
                   }
                 }
               }
             }
           }
         }
       }
       container odu-sd {
         junos:cli-feature "oneliner";
         description "ODU Signal Degrade defect trigger";
         choice odu_sd_choices {
           case case_1 {
             leaf ignore {
               description "Ignore the defect";
               type empty;
             }
           }
           case case_2 {
             container hold-time {
               junos:cli-feature "oneliner";
               description "Delay before clearing or raising the alarm for defect";
               leaf up {
                 description "Delay before clearing the alarm when the defect is absent";
                 units "milliseconds";
                 type union {
                   type string {
                     pattern "<.*>|$.*";
                   }
                   type uint32 {
                     range "1 .. 65534";
                   }
                 }
               }
               leaf down {
                 description "Delay before raising the alarm when the defect occurs";
                 units "milliseconds";
                 type union {
                   type string {
                     pattern "<.*>|$.*";
                   }
                   type uint32 {
                     range "1 .. 65534";
                   }
                 }
               }
             }
           }
         }
       }
       container opu-ptim {
         junos:cli-feature "oneliner";
         description "Payload Type Mismatch defect trigger";
         choice opu_ptm_choices {
           case case_1 {
             leaf ignore {
               description "Ignore the defect";
               type empty;
             }
           }
           case case_2 {
             container hold-time {
               junos:cli-feature "oneliner";
               description "Delay before clearing or raising the alarm for defect";
               leaf up {
                 description "Delay before clearing the alarm when the defect is absent";
                 units "milliseconds";
                 type union {
                   type string {
                     pattern "<.*>|$.*";
                   }
                   type uint32 {
                     range "1 .. 65534";
                   }
                 }
               }
               leaf down {
                 description "Delay before raising the alarm when the defect occurs";
                 units "milliseconds";
                 type union {
                   type string {
                     pattern "<.*>|$.*";
                   }
                   type uint32 {
                     range "1 .. 65534";
                   }
                 }
               }
             }
           }
         }
       }
     }
     container tca {
       description "TCA - threshold crossing alerts";
       uses apply-advanced;
       container otu-tca-es {
         junos:cli-feature "oneliner";
         description "OTU Errored Seconds Threshold crossing defect trigger";
         choice enable-tca-choice {
           leaf enable-tca {
             description "Enable the OTU errored seconds threshold crossing alert";
             type empty;
           }
           leaf no-enable-tca {
             description "Don't enable the OTU errored seconds threshold crossing alert";
             type empty;
           }
         }
         leaf threshold {
           description "TCA threshold for OTU errored seconds in 15 minutes";
           default "135";
           type union {
             type string {
               pattern "<.*>|$.*";
             }
             type uint32 {
               range "1 .. 900";
             }
           }
         }
         leaf threshold-24hrs {
           description "TCA threshold for OTU errored seconds in 24 hours";
           default "162";
           type union {
             type string {
               pattern "<.*>|$.*";
             }
             type uint32 {
               range "1 .. 86400";
             }
           }
         }
       }
       container otu-tca-ses {
         junos:cli-feature "oneliner";
         description "OTU Severely Errored Seconds Threshold crossing defect trigger";
         choice enable-tca-choice {
           leaf enable-tca {
             description "Enable the OTU severely errored seconds threshold crossing alert";
             type empty;
           }
           leaf no-enable-tca {
             description "Don't enable the OTU severely errored seconds threshold crossing alert";
             type empty;
           }
         }
         leaf threshold {
           description "TCA threshold for OTU severely errored seconds in 15 minutes";
           default "90";
           type union {
             type string {
               pattern "<.*>|$.*";
             }
             type uint32 {
               range "1 .. 900";
             }
           }
         }
         leaf threshold-24hrs {
           description "TCA threshold for OTU severely errored seconds in 24 hours";
           default "108";
           type union {
             type string {
               pattern "<.*>|$.*";
             }
             type uint32 {
               range "1 .. 86400";
             }
           }
         }
       }
       container otu-tca-uas {
         junos:cli-feature "oneliner";
         description "OTU Unavailable Seconds Threshold crossing defect trigger";
         choice enable-tca-choice {
           leaf enable-tca {
             description "Enable the OTU unavailable seconds threshold crossing alert";
             type empty;
           }
           leaf no-enable-tca {
             description "Don't enable the OTU unavailable seconds threshold crossing alert";
             type empty;
           }
         }
         leaf threshold {
           description "TCA threshold for OTU unavailable seconds in 15 minutes";
           default "90";
           type union {
             type string {
               pattern "<.*>|$.*";
             }
             type uint32 {
               range "10 .. 900";
             }
           }
         }
         leaf threshold-24hrs {
           description "TCA threshold for OTU unavailable seconds in 24 hours";
           default "108";
           type union {
             type string {
               pattern "<.*>|$.*";
             }
             type uint32 {
               range "10 .. 86400";
             }
           }
         }
       }
       container otu-tca-bbe {
         junos:cli-feature "oneliner";
         description "OTU Background Block Error Threshold crossing defect trigger";
         choice enable-tca-choice {
           leaf enable-tca {
             description "Enable the OTU BBE threshold crossing alert";
             type empty;
           }
           leaf no-enable-tca {
             description "Don't enable the OTU BBE threshold crossing alert";
             type empty;
           }
         }
         leaf threshold {
           description "TCA threshold for OTU BBE in 15 minutes";
           default "800";
           type union {
             type string {
               pattern "<.*>|$.*";
             }
             type uint32 {
               range "1 .. 771000000";
             }
           }
         }
         leaf threshold-24hrs {
           description "TCA threshold for OTU BBE in 24 hours";
           default "960";
           type union {
             type string {
               pattern "<.*>|$.*";
             }
             type uint32 {
               range "1 .. 771000000";
             }
           }
         }
       }
       container otu-tca-es-fe {
         junos:cli-feature "oneliner";
         description "OTU far-end Errored Seconds Threshold crossing defect trigger";
         choice enable-tca-choice {
           leaf enable-tca {
             description "Enable the OTU far-end errored seconds threshold crossing alert";
             type empty;
           }
           leaf no-enable-tca {
             description "Don't enable the OTU far-end errored seconds threshold crossing alert";
             type empty;
           }
         }
         leaf threshold {
           description "TCA threshold for OTU far-end errored seconds in 15 minutes";
           default "135";
           type union {
             type string {
               pattern "<.*>|$.*";
             }
             type uint32 {
               range "1 .. 900";
             }
           }
         }
         leaf threshold-24hrs {
           description "TCA threshold for OTU far-end errored seconds in 24 hours";
           default "162";
           type union {
             type string {
               pattern "<.*>|$.*";
             }
             type uint32 {
               range "1 .. 86400";
             }
           }
         }
       }
       container otu-tca-ses-fe {
         junos:cli-feature "oneliner";
         description "OTU far-end Severely Errored Seconds Threshold crossing defect trigger";
         choice enable-tca-choice {
           leaf enable-tca {
             description "Enable the OTU far-end Unavailable Seconds threshold crossing alert";
             type empty;
           }
           leaf no-enable-tca {
             description "Don't enable the OTU far-end Unavailable Seconds threshold crossing alert";
             type empty;
           }
         }
         leaf threshold {
           description "TCA threshold for OTU far-end severely errored seconds in 15 minutes";
           default "90";
           type union {
             type string {
               pattern "<.*>|$.*";
             }
             type uint32 {
               range "1 .. 900";
             }
           }
         }
         leaf threshold-24hrs {
           description "TCA threshold for OTU far-end severely errored seconds in 24 hours";
           default "108";
           type union {
             type string {
               pattern "<.*>|$.*";
             }
             type uint32 {
               range "1 .. 86400";
             }
           }
         }
       }
       container otu-tca-uas-fe {
         junos:cli-feature "oneliner";
         description "OTU far-end Unavailable Seconds Threshold crossing defect trigger";
         choice enable-tca-choice {
           leaf enable-tca {
             description "Enable the OTU far end unavailabe second threshold crossing alert";
             type empty;
           }
           leaf no-enable-tca {
             description "Don't enable the OTU far end unavailabe second threshold crossing alert";
             type empty;
           }
         }
         leaf threshold {
           description "TCA threshold for OTU far-end unavailable seconds in 15 minutes";
           default "90";
           type union {
             type string {
               pattern "<.*>|$.*";
             }
             type uint32 {
               range "10 .. 900";
             }
           }
         }
         leaf threshold-24hrs {
           description "TCA threshold for OTU far-end unavailable seconds in 24 hours";
           default "108";
           type union {
             type string {
               pattern "<.*>|$.*";
             }
             type uint32 {
               range "10 .. 86400";
             }
           }
         }
       }
       container otu-tca-bbe-fe {
         junos:cli-feature "oneliner";
         description "OTU far-end Background Block Error (BEI) Threshold crossing defect trigger";
         choice enable-tca-choice {
           leaf enable-tca {
             description "Enable the OTU BBE (BEI) threshold crossing alert";
             type empty;
           }
           leaf no-enable-tca {
             description "Don't enable the OTU BBE (BEI) threshold crossing alert";
             type empty;
           }
         }
         leaf threshold {
           description "TCA threshold for OTU far-end BBE (BEI) in 15 minutes";
           default "800";
           type union {
             type string {
               pattern "<.*>|$.*";
             }
             type uint32 {
               range "1 .. 771000000";
             }
           }
         }
         leaf threshold-24hrs {
           description "TCA threshold for OTU far-end BBE (BEI) in 24 hours";
           default "960";
           type union {
             type string {
               pattern "<.*>|$.*";
             }
             type uint32 {
               range "1 .. 771000000";
             }
           }
         }
       }
       container odu-tca-es {
         junos:cli-feature "oneliner";
         description "ODU Errored Seconds Threshold crossing defect trigger";
         choice enable-tca-choice {
           leaf enable-tca {
             description "Enable the ODU errored seconds threshold crossing alert";
             type empty;
           }
           leaf no-enable-tca {
             description "Don't enable the ODU errored seconds threshold crossing alert";
             type empty;
           }
         }
         leaf threshold {
           description "TCA threshold for ODU errored seconds in 15 minutes";
           default "135";
           type union {
             type string {
               pattern "<.*>|$.*";
             }
             type uint32 {
               range "1 .. 900";
             }
           }
         }
         leaf threshold-24hrs {
           description "TCA threshold for ODU errored seconds in 24 hours";
           default "162";
           type union {
             type string {
               pattern "<.*>|$.*";
             }
             type uint32 {
               range "1 .. 86400";
             }
           }
         }
       }
       container odu-tca-ses {
         junos:cli-feature "oneliner";
         description "ODU Severely Errored Seconds Threshold crossing defect trigger";
         choice enable-tca-choice {
           leaf enable-tca {
             description "Enable the ODU severely errored seconds threshold crossing alert";
             type empty;
           }
           leaf no-enable-tca {
             description "Don't enable the ODU severely errored seconds threshold crossing alert";
             type empty;
           }
         }
         leaf threshold {
           description "TCA threshold for ODU severely errored seconds in 15 minutes";
           default "90";
           type union {
             type string {
               pattern "<.*>|$.*";
             }
             type uint32 {
               range "1 .. 900";
             }
           }
         }
         leaf threshold-24hrs {
           description "TCA threshold for ODU severely-errored seconds in 24 hours";
           default "108";
           type union {
             type string {
               pattern "<.*>|$.*";
             }
             type uint32 {
               range "1 .. 86400";
             }
           }
         }
       }
       container odu-tca-uas {
         junos:cli-feature "oneliner";
         description "ODU Unavailable Seconds Threshold crossing defect trigger";
         choice enable-tca-choice {
           leaf enable-tca {
             description "Enable the ODU unavailable seconds threshold crossing alert";
             type empty;
           }
           leaf no-enable-tca {
             description "Don't enable the ODU unavailable seconds threshold crossing alert";
             type empty;
           }
         }
         leaf threshold {
           description "TCA threshold for ODU unavailable seconds in 15 minutes";
           default "90";
           type union {
             type string {
               pattern "<.*>|$.*";
             }
             type uint32 {
               range "10 .. 900";
             }
           }
         }
         leaf threshold-24hrs {
           description "TCA threshold for ODU unavailable seconds in 24 hours";
           default "108";
           type union {
             type string {
               pattern "<.*>|$.*";
             }
             type uint32 {
               range "10 .. 86400";
             }
           }
         }
       }
       container odu-tca-bbe {
         junos:cli-feature "oneliner";
         description "ODU Background Block Error Threshold crossing defect trigger";
         choice enable-tca-choice {
           leaf enable-tca {
             description "Enable the ODU BBE threshold crossing alert";
             type empty;
           }
           leaf no-enable-tca {
             description "Don't enable the ODU BBE threshold crossing alert";
             type empty;
           }
         }
         leaf threshold {
           description "TCA threshold for ODU BBE in 15 minutes";
           default "800";
           type union {
             type string {
               pattern "<.*>|$.*";
             }
             type uint32 {
               range "1 .. 771000000";
             }
           }
         }
         leaf threshold-24hrs {
           description "TCA threshold for ODU backgrand block error in 24 hours";
           default "960";
           type union {
             type string {
               pattern "<.*>|$.*";
             }
             type uint32 {
               range "1 .. 771000000";
             }
           }
         }
       }
       container odu-tca-es-fe {
         junos:cli-feature "oneliner";
         description "ODU far-end Errored Seconds Threshold crossing defect trigger";
         choice enable-tca-choice {
           leaf enable-tca {
             description "Enable the ODU far-end errored seconds threshold crossing alert";
             type empty;
           }
           leaf no-enable-tca {
             description "Don't enable the ODU far-end errored seconds threshold crossing alert";
             type empty;
           }
         }
         leaf threshold {
           description "TCA threshold for ODU far-end errored seconds in 15 minutes";
           default "135";
           type union {
             type string {
               pattern "<.*>|$.*";
             }
             type uint32 {
               range "1 .. 900";
             }
           }
         }
         leaf threshold-24hrs {
           description "TCA threshold for ODU far-end errored seconds in 24 hours";
           default "162";
           type union {
             type string {
               pattern "<.*>|$.*";
             }
             type uint32 {
               range "1 .. 86400";
             }
           }
         }
       }
       container odu-tca-ses-fe {
         junos:cli-feature "oneliner";
         description "ODU far-end Severely Errored Seconds Threshold crossing defect trigger";
         choice enable-tca-choice {
           leaf enable-tca {
             description "Enable the ODU far-end Unavailable Seconds threshold crossing alert";
             type empty;
           }
           leaf no-enable-tca {
             description "Don't enable the ODU far-end Unavailable Seconds threshold crossing alert";
             type empty;
           }
         }
         leaf threshold {
           description "TCA threshold for ODU far-end severely errored seconds in 15 minutes";
           default "90";
           type union {
             type string {
               pattern "<.*>|$.*";
             }
             type uint32 {
               range "1 .. 900";
             }
           }
         }
         leaf threshold-24hrs {
           description "TCA threshold for ODU severely-errored seconds in 24 hours";
           default "108";
           type union {
             type string {
               pattern "<.*>|$.*";
             }
             type uint32 {
               range "1 .. 86400";
             }
           }
         }
       }
       container odu-tca-uas-fe {
         junos:cli-feature "oneliner";
         description "ODU far-end Unavailable Seconds Threshold crossing defect trigger";
         choice enable-tca-choice {
           leaf enable-tca {
             description "Enable the ODU far end unavailabe second threshold crossing alert";
             type empty;
           }
           leaf no-enable-tca {
             description "Don't enable the ODU far end unavailabe second threshold crossing alert";
             type empty;
           }
         }
         leaf threshold {
           description "TCA threshold for ODU far-end unavailable seconds in 15 minutes";
           default "90";
           type union {
             type string {
               pattern "<.*>|$.*";
             }
             type uint32 {
               range "10 .. 900";
             }
           }
         }
         leaf threshold-24hrs {
           description "TCA threshold for ODU far-end unavailable seconds in 24 hours";
           default "108";
           type union {
             type string {
               pattern "<.*>|$.*";
             }
             type uint32 {
               range "10 .. 86400";
             }
           }
         }
       }
       container odu-tca-bbe-fe {
         junos:cli-feature "oneliner";
         description "ODU far-end Background Block Error (BEI) Threshold crossing defect trigger";
         choice enable-tca-choice {
           leaf enable-tca {
             description "Enable the ODU BBE (BEI) threshold crossing alert";
             type empty;
           }
           leaf no-enable-tca {
             description "Don't enable the ODU BBE (BEI) threshold crossing alert";
             type empty;
           }
         }
         leaf threshold {
           description "TCA threshold for ODU far-end BBE (BEI) in 15 minutes";
           default "800";
           type union {
             type string {
               pattern "<.*>|$.*";
             }
             type uint32 {
               range "1 .. 771000000";
             }
           }
         }
         leaf threshold-24hrs {
           description "TCA threshold for ODU far-end backgrand block error in 24 hours";
           default "960";
           type union {
             type string {
               pattern "<.*>|$.*";
             }
             type uint32 {
               range "1 .. 771000000";
             }
           }
         }
       }
       container otu-tca-fec-ber {
         junos:cli-feature "oneliner";
         description "OTU Errored Seconds Threshold crossing defect trigger";
         choice enable-tca-choice {
           leaf enable-tca {
             description "Enable the OTU errored seconds threshold crossing alert";
             type empty;
           }
           leaf no-enable-tca {
             description "Don't enable the OTU errored seconds threshold crossing alert";
             type empty;
           }
         }
         leaf threshold {
           description "TCA threshold for BER value in format: xe-n, x is an integer or decimal number, n = 0..9";
           default "10e-3";
           type string {
             junos:posix-pattern "^[0-9]+(.[0-9]+)?e-[0-9]$";
             junos:pattern-message "FEC BER threshold value in format: xe-n, x is an integer or decimal number, n = 0..9";
           }
         }
         leaf threshold-24hrs {
           description "TCA threshold for BER value in format: xe-n, x is an integer or decimal number, n = 0..9";
           default "10e-3";
           type string {
             junos:posix-pattern "^[0-9]+(.[0-9]+)?e-[0-9]$";
             junos:pattern-message "FEC BER threshold value in format: xe-n, x is an integer or decimal number, n = 0..9";
           }
         }
       }
     }
   }
   grouping otu-attributes {
     description "Optical transmission unit configuration attributes";
     uses apply-advanced;
     leaf rate {
       description "Specific type of OTU, according to data rate";
       type enumeration {
         enum "otu4" {
           description "OTU4 for 100 Gbps";
         }
       }
     }
     choice is-ma-choice {
       leaf is-ma {
         description "Link is enabled for maintenance tasks, alarms are masked";
         type empty;
       }
       leaf no-is-ma {
         description "Don't link is enabled for maintenance tasks, alarms are masked";
         type empty;
       }
     }
     leaf fec {
       description "Forward error correction type";
       type enumeration {
         enum "none" {
           description "No forward error correction applied";
         }
         enum "gfec" {
           description "ITU-T G.709 standard forward error correction";
         }
         enum "hgfec" {
           description "High gain FEC";
         }
       }
     }
     leaf loopback {
       description "Enabled loopback mode";
       type enumeration {
         enum "none" {
           description "No loopback mode active";
         }
         enum "local" {
           description "Local loopback (host side)";
         }
         enum "line" {
           description "Line loopback (network side)";
         }
       }
     }
     container tti {
       description "Configuration of OTU trail trace identifier";
       presence "enable tti";
       uses otn-tti-attributes;
     }
     container degrade {
       description "Configuration of OTU degrade defect detection";
       presence "enable degrade";
       uses otn-degrade;
     }
   }
   grouping ppp_options_type {
     uses apply-advanced;
     leaf dynamic-profile {
       description "Dynamic profile name";
       junos:must "(\"dynamic-profiles $$\")";
       junos:must-message "referenced dynamic-profile must be defined";
       junos:must "(any \".. .. .. unit <*>\")";
       junos:must-message "dynamic-profile statement can be configured only on logical interfaces";
       type string;
     }
     container chap {
       presence "enable chap";
       description "Challenge Handshake Authentication Protocol options";
       uses apply-advanced;
       choice access-data {
         case case_1 {
           leaf access-profile {
             description "Profile containing client list and access parameters";
             junos:must "(\"access profile $$\")";
             junos:must-message "referenced access profile must be defined";
             type string {
               length "1 .. 63";
             }
           }
         }
         case case_2 {
           leaf default-chap-secret {
             description "Default CHAP secret to be used when no matching access profile exists";
             type jt:unreadable;
           }
         }
       }
       leaf local-name {
         description "Name sent in CHAP-Challenge and CHAP-Response";
         type string;
       }
       leaf no-rfc2486 {
         description "RFC2486 compliance is not enforced";
         type empty;
       }
       leaf passive {
         description "Handle incoming CHAP requests only";
         type empty;
       }
     }
     container pap {
       presence "enable pap";
       description "Password Authentication Protocol options";
       uses apply-advanced;
       choice access-data {
         case case_1 {
           leaf access-profile {
             description "Profile containing client list and access parameters";
             junos:must "(\"access profile $$\")";
             junos:must-message "referenced access profile must be defined";
             type string {
               length "1 .. 63";
             }
           }
         }
         case case_2 {
           leaf default-password {
             description "Default PAP password used in the absence of matching profile";
             type jt:unreadable;
           }
         }
       }
       leaf local-name {
         description "Name sent in PAP request packet";
         type string;
       }
       leaf no-rfc2486 {
         description "RFC2486 compliance is not enforced";
         type empty;
       }
       leaf local-password {
         description "Password sent in PAP request packet";
         type jt:unreadable;
       }
       leaf passive {
         description "Do not handle PAP authentication requests";
         junos:must "(\".. local-password\")";
         junos:must-message "local-password MUST be set if passive is used with PAP";
         type empty;
       }
     }
     container compression {
       junos:cli-feature "oneliner";
       description "Set compression options";
       leaf acfc {
         description "Negotiate Address/Control field compression";
         junos:must "(!(\".. .. .. encapsulation frame-relay-ppp\"))";
         junos:must-message "compression acfc is not supported on encapsulation frame-relay-ppp";
         type empty;
       }
       leaf pfc {
         description "Negotiate Protocol field compression";
         type empty;
       }
     }
     leaf lcp-restart-timer {
       description "LCP restart timer";
       units "milliseconds";
       junos:must "(any \".. .. .. unit <*>\")";
       junos:must-message "lcp-restart-timer statement can be configured only on logical interfaces";
       type union {
         type string {
           pattern "<.*>|$.*";
         }
         type uint16 {
           range "20 .. 10000";
         }
       }
     }
     leaf ncp-restart-timer {
       description "NCP restart timer";
       units "milliseconds";
       junos:must "(any \".. .. .. unit <*>\")";
       junos:must-message "ncp-restart-timer statement can be configured only on logical interfaces";
       type union {
         type string {
           pattern "<.*>|$.*";
         }
         type uint16 {
           range "500 .. 10000";
         }
       }
     }
     leaf no-termination-request {
       description "Don't send PPP termination requests";
       type empty;
     }
     leaf loopback-clear-timer {
       description "Loopback clear timer";
       units "seconds";
       junos:must "(any \".. .. .. unit <*>\")";
       junos:must-message "loopback-clear-timer statement can be configured only on logical interfaces";
       type union {
         type string {
           pattern "<.*>|$.*";
         }
         type uint8 {
           range "1 .. 60";
         }
       }
     }
     leaf lcp-max-conf-req {
       description "Maximum LCP Conf-Req to be sent, 0 means infinite";
       junos:must "(any \".. .. .. unit <*>\")";
       junos:must-message "lcp-max-conf-req statement can be configured only on logical interfaces";
       type union {
         type string {
           pattern "<.*>|$.*";
         }
         type uint32 {
           range "0 .. 65535";
         }
       }
     }
     leaf ncp-max-conf-req {
       description "Maximum NCP Conf-Req to be sent, 0 means infinite";
       junos:must "(any \".. .. .. unit <*>\")";
       junos:must-message "ncp-max-conf-req statement can be configured only on logical interfaces";
       type union {
         type string {
           pattern "<.*>|$.*";
         }
         type uint32 {
           range "0 .. 65535";
         }
       }
     }
     leaf on-demand-ip-address {
       description "Enable On-Demand IPv4 address allocation and de-allocation";
       junos:must "(any \".. .. .. unit <*>\")";
       junos:must-message "on-demand-ip-address statement can be configured only on logical interfaces";
       type empty;
     }
     leaf aaa-options {
       description "Attach AAA options name to dynamic-profile";
       junos:must "(\"access aaa-options $$\")";
       junos:must-message "referenced aaa-options name must be defined";
       type string {
         length "1 .. 63";
       }
     }
     leaf service-profile {
       description "Default service profile";
       type string {
         length "1 .. 128";
       }
     }
     container initiate-ncp {
       junos:must "(any \".. .. .. unit <*>\")";
       junos:must-message "initiate-ncp statement can be configured only on logical interfaces";
       description "Enable server initiated NCP";
       uses apply-advanced;
       leaf ip {
         description "Enable server initiated IPNCP";
         type empty;
       }
       leaf ipv6 {
         description "Enable server initiated IPv6NCP";
         type empty;
       }
       leaf dual-stack-passive {
         description "Disable server initiated IPNCP/IPv6NCP for dual-stack client";
         type empty;
       }
     }
     leaf mtu {
       description "The Maximum Transfer Unit size in bytes";
       junos:must "(any \".. .. .. unit <*>\")";
       junos:must-message "mtu statement can be configured only on logical interfaces";
       type string;
     }
     leaf peer-ip-address-optional {
       description "Set Peer IP Address Optional in IP NCP Negotiations";
       type empty;
     }
     leaf ipcp-suggest-dns-option {
       description "Suggest peer to negotiate with DNS Addresses options";
       type empty;
     }
     leaf ignore-magic-number-mismatch {
       description "Ignore magic-number validation failure in LCP keepalive";
       type empty;
     }
     container local-authentication {
       description "Local Authentication Protocol options";
       uses local_auth_type;
     }
     leaf lcp-connection-update {
       description "Enable LCP connection update request to peer";
       type empty;
     }
   }
   grouping local_auth_type {
     description "Local authentication";
     uses apply-advanced;
     leaf password {
       description "Username password";
       type string {
         length "1 .. 64";
       }
     }
     container username-include {
       description "Add username options";
       uses apply-advanced;
       leaf mac-address {
         description "Include MAC address";
         type empty;
       }
       leaf circuit-id {
         description "Include circuit-id ";
         type empty;
       }
       leaf remote-id {
         description "Include remote-id ";
         type empty;
       }
       leaf domain-name {
         description "Domain name";
         type string {
           length "1 .. 64";
         }
       }
       leaf delimiter {
         description "Delimiter/separator character";
         type string {
           length 1;
         }
       }
     }
   }
   grouping pppoe_options_type {
     uses apply-advanced;
     leaf underlying-interface {
       description "Underlying interface name";
       junos:must "((!(\"interfaces $$-IFL pppoe-underlying-options dynamic-profile\") && !(\"interfaces $$-IFL family pppoe dynamic-profile\")))";
       junos:must-message "Underlying interface cannot be used for both static and dynamic PPPoE interfaces";
       junos:must "((\"interfaces $$-IFL encapsulation ppp-over-ether\" || (\"interfaces $$-IFL encapsulation ppp-over-ether-over-atm-llc\" || \"interfaces $$-IFL family pppoe\")))";
       junos:must-message "Underlying interface must be configured";
       type string;
     }
     leaf idle-timeout {
       description "Time for which session can be idle (0 = forever)";
       units "seconds";
       type union {
         type string {
           pattern "<.*>|$.*";
         }
         type uint32 {
           range "0 .. 4294967295";
         }
       }
     }
     leaf access-concentrator {
       description "Name of the access concentrator (PPPoE server)";
       type string;
     }
     leaf service-name {
       description "Service to be requested (from PPPoE server)";
       type string;
     }
     leaf auto-reconnect {
       description "Time to reconnect after session terminates (0 = never)";
       units "seconds";
       type union {
         type string {
           pattern "<.*>|$.*";
         }
         type uint32 {
           range "0 .. 4294967295";
         }
       }
     }
     choice pppoe-mode {
       case case_1 {
         leaf server {
           description "PPPoE operates in server mode";
           type empty;
         }
       }
       case case_2 {
         leaf client {
           description "PPPoE operates in client mode";
           type empty;
         }
       }
     }
     leaf ppp-max-payload {
       description "Specify the value of ppp-max-payload tag";
       type union {
         type string {
           pattern "<.*>|$.*";
         }
         type uint32 {
           range "1492 .. 9192";
         }
       }
     }
   }
   grouping pppoe_underlying_options_type {
     uses apply-advanced;
     leaf access-concentrator {
       description "Name of the access concentrator (PPPoE server)";
       type string {
         length "1 .. 64";
       }
     }
     leaf direct-connect {
       description "Ignore received VS tags for PPPoE sessions";
       type empty;
     }
     container duplicate-protection {
       presence "enable duplicate-protection";
       description "Disallow multiple PPPoE sessions to a single client";
       uses apply-advanced;
     }
     leaf dynamic-profile {
       description "Attach dynamic-profile to interface";
       junos:must "((\"dynamic-profiles $$\" || \"system services subscriber-management mode user-plane\"))";
       junos:must-message "referenced dynamic-profile must be defined";
       type string {
         length "1 .. 64";
       }
     }
     leaf max-sessions {
       description "Maximum number of PPPoE sessions allowed on underlying interface";
       type union {
         type string {
           pattern "<.*>|$.*";
         }
         type uint32;
       }
     }
     leaf max-sessions-vsa-ignore {
       description "Ignore the max-sessions VSA";
       type empty;
     }
     leaf service-name-table {
       description "Attach Service Name Table to interface";
       junos:must "(\"protocols pppoe service-name-tables $$\")";
       junos:must-message "referenced service name table must be defined";
       type string {
         length "1 .. 32";
       }
     }
     container short-cycle-protection {
       presence "enable short-cycle-protection";
       description "Enable short cycle protection on underlying interface";
       uses apply-advanced;
       leaf lockout-time-min {
         description "Minimum lockout time";
         units "seconds";
         type union {
           type string {
             pattern "<.*>|$.*";
           }
           type uint32 {
             range "1 .. 86400";
           }
         }
       }
       leaf lockout-time-max {
         description "Maximum lockout time";
         units "seconds";
         type union {
           type string {
             pattern "<.*>|$.*";
           }
           type uint32 {
             range "1 .. 86400";
           }
         }
       }
     }
   }
   grouping prbs-config {
     description "Configuration of pseudorandom binary sequence test signal";
     uses apply-advanced;
     choice enable-prbs-choice {
       leaf enable-prbs {
         description "Enable PRBS test pattern generation and monitoring";
         type empty;
       }
       leaf no-enable-prbs {
         description "Don't enable PRBS test pattern generation and monitoring";
         type empty;
       }
     }
     leaf direction {
       description "Direction of generated and received PRBS test signal";
       default "line";
       type enumeration {
         enum "local" {
           description "Test signal generated towards and received from host-side";
         }
         enum "line" {
           description "Test signal generated towards and received from network-side";
         }
       }
     }
     leaf pattern {
       description "Pattern to use for PRBS test signal";
       default "prbs-31";
       type enumeration {
         enum "prbs-31" {
           description "2^31 polynomial PRBS test signal, as per G.709";
         }
         enum "prbs-23" {
           description "2^23 polynomial PRBS test signal, SONET/SDH framed";
         }
         enum "prbs-15" {
           description "2^15 polynomial PRBS test signal";
         }
         enum "prbs-7" {
           description "2^7 polynomial PRBS test signal";
         }
       }
     }
     choice invert-choice {
       leaf invert {
         description "Invert the test pattern";
         type empty;
       }
       leaf no-invert {
         description "Don't invert the test pattern";
         type empty;
       }
     }
   }
   grouping sonet_options_type {
     uses apply-advanced;
     leaf vtmapping {
       description "VT mapping mode";
       type enumeration {
         enum "klm" {
           description "KLM mode";
         }
         enum "itu-t" {
           description "ITU-T mode";
         }
       }
     }
     leaf fcs {
       description "Frame checksum";
       type enumeration {
         enum "32" {
           description "32-bit mode";
         }
         enum "16" {
           description "16-bit mode";
         }
       }
     }
     leaf path-trace {
       description "Path trace string";
       type string;
     }
     leaf loopback {
       description "Loopback mode";
       type enumeration {
         enum "local" {
           description "Local loopback";
         }
         enum "remote" {
           description "Remote loopback";
         }
       }
     }
     container trigger {
       description "Defect triggers";
       uses apply-advanced;
       container lol {
         junos:cli-feature "oneliner";
         description "LOL defect trigger";
         choice lol_choices {
           case case_1 {
             leaf ignore {
               description "Ignore the defect";
               type empty;
             }
           }
           case case_2 {
             container hold-time {
               junos:cli-feature "oneliner";
               description "Delay before marking interface up or down for defect";
               leaf up {
                 description "Delay before marking interface up when defect is absent";
                 units "milliseconds";
                 type union {
                   type string {
                     pattern "<.*>|$.*";
                   }
                   type uint32 {
                     range "1 .. 65534";
                   }
                 }
               }
               leaf down {
                 description "Delay before marking interface down when defect occurs";
                 units "milliseconds";
                 type union {
                   type string {
                     pattern "<.*>|$.*";
                   }
                   type uint32 {
                     range "1 .. 65534";
                   }
                 }
               }
             }
           }
         }
       }
       container pll {
         junos:cli-feature "oneliner";
         description "PLL defect trigger";
         choice pll_choices {
           case case_1 {
             leaf ignore {
               description "Ignore the defect";
               type empty;
             }
           }
           case case_2 {
             container hold-time {
               junos:cli-feature "oneliner";
               description "Delay before marking interface up or down for defect";
               leaf up {
                 description "Delay before marking interface up when defect is absent";
                 units "milliseconds";
                 type union {
                   type string {
                     pattern "<.*>|$.*";
                   }
                   type uint32 {
                     range "1 .. 65534";
                   }
                 }
               }
               leaf down {
                 description "Delay before marking interface down when defect occurs";
                 units "milliseconds";
                 type union {
                   type string {
                     pattern "<.*>|$.*";
                   }
                   type uint32 {
                     range "1 .. 65534";
                   }
                 }
               }
             }
           }
         }
       }
       container lof {
         junos:cli-feature "oneliner";
         description "LOF defect trigger";
         choice lof_choices {
           case case_1 {
             leaf ignore {
               description "Ignore the defect";
               type empty;
             }
           }
           case case_2 {
             container hold-time {
               junos:cli-feature "oneliner";
               description "Delay before marking interface up or down for defect";
               leaf up {
                 description "Delay before marking interface up when defect is absent";
                 units "milliseconds";
                 type union {
                   type string {
                     pattern "<.*>|$.*";
                   }
                   type uint32 {
                     range "1 .. 65534";
                   }
                 }
               }
               leaf down {
                 description "Delay before marking interface down when defect occurs";
                 units "milliseconds";
                 type union {
                   type string {
                     pattern "<.*>|$.*";
                   }
                   type uint32 {
                     range "1 .. 65534";
                   }
                 }
               }
             }
           }
         }
       }
       container los {
         junos:cli-feature "oneliner";
         description "LOS defect trigger";
         choice los_choices {
           case case_1 {
             leaf ignore {
               description "Ignore the defect";
               type empty;
             }
           }
           case case_2 {
             container hold-time {
               junos:cli-feature "oneliner";
               description "Delay before marking interface up or down for defect";
               leaf up {
                 description "Delay before marking interface up when defect is absent";
                 units "milliseconds";
                 type union {
                   type string {
                     pattern "<.*>|$.*";
                   }
                   type uint32 {
                     range "1 .. 65534";
                   }
                 }
               }
               leaf down {
                 description "Delay before marking interface down when defect occurs";
                 units "milliseconds";
                 type union {
                   type string {
                     pattern "<.*>|$.*";
                   }
                   type uint32 {
                     range "1 .. 65534";
                   }
                 }
               }
             }
           }
         }
       }
       container ais-l {
         junos:cli-feature "oneliner";
         description "AIS-L defect trigger";
         choice ais_l_choices {
           case case_1 {
             leaf ignore {
               description "Ignore the defect";
               type empty;
             }
           }
           case case_2 {
             container hold-time {
               junos:cli-feature "oneliner";
               description "Delay before marking interface up or down for defect";
               leaf up {
                 description "Delay before marking interface up when defect is absent";
                 units "milliseconds";
                 type union {
                   type string {
                     pattern "<.*>|$.*";
                   }
                   type uint32 {
                     range "1 .. 65534";
                   }
                 }
               }
               leaf down {
                 description "Delay before marking interface down when defect occurs";
                 units "milliseconds";
                 type union {
                   type string {
                     pattern "<.*>|$.*";
                   }
                   type uint32 {
                     range "1 .. 65534";
                   }
                 }
               }
             }
           }
         }
       }
       container rfi-l {
         junos:cli-feature "oneliner";
         description "RFI-L defect trigger";
         choice rfi_l_choices {
           case case_1 {
             leaf ignore {
               description "Ignore the defect";
               type empty;
             }
           }
           case case_2 {
             container hold-time {
               junos:cli-feature "oneliner";
               description "Delay before marking interface up or down for defect";
               leaf up {
                 description "Delay before marking interface up when defect is absent";
                 units "milliseconds";
                 type union {
                   type string {
                     pattern "<.*>|$.*";
                   }
                   type uint32 {
                     range "1 .. 65534";
                   }
                 }
               }
               leaf down {
                 description "Delay before marking interface down when defect occurs";
                 units "milliseconds";
                 type union {
                   type string {
                     pattern "<.*>|$.*";
                   }
                   type uint32 {
                     range "1 .. 65534";
                   }
                 }
               }
             }
           }
         }
       }
       container ber-sd {
         description "BER-SD defect trigger";
         uses apply-advanced;
         choice ber_sd_choices {
           case case_1 {
             leaf ignore {
               description "Ignore the defect";
               type empty;
             }
           }
           case case_2 {
             container hold-time {
               junos:cli-feature "oneliner";
               description "Delay before marking interface up or down for defect";
               leaf up {
                 description "Delay before marking interface up when defect is absent";
                 units "milliseconds";
                 type union {
                   type string {
                     pattern "<.*>|$.*";
                   }
                   type uint32 {
                     range "1 .. 65534";
                   }
                 }
               }
               leaf down {
                 description "Delay before marking interface down when defect occurs";
                 units "milliseconds";
                 type union {
                   type string {
                     pattern "<.*>|$.*";
                   }
                   type uint32 {
                     range "1 .. 65534";
                   }
                 }
               }
             }
           }
         }
       }
       container ber-sf {
         description "BER-SF defect trigger";
         uses apply-advanced;
         choice ber_sf_choices {
           case case_1 {
             leaf ignore {
               description "Ignore the defect";
               type empty;
             }
           }
           case case_2 {
             container hold-time {
               junos:cli-feature "oneliner";
               description "Delay before marking interface up or down for defect";
               leaf up {
                 description "Delay before marking interface up when defect is absent";
                 units "milliseconds";
                 type union {
                   type string {
                     pattern "<.*>|$.*";
                   }
                   type uint32 {
                     range "1 .. 65534";
                   }
                 }
               }
               leaf down {
                 description "Delay before marking interface down when defect occurs";
                 units "milliseconds";
                 type union {
                   type string {
                     pattern "<.*>|$.*";
                   }
                   type uint32 {
                     range "1 .. 65534";
                   }
                 }
               }
             }
           }
         }
       }
       container ais-p {
         junos:cli-feature "oneliner";
         description "AIS-P defect trigger";
         choice ais_p_choices {
           case case_1 {
             leaf ignore {
               description "Ignore the defect";
               type empty;
             }
           }
           case case_2 {
             container hold-time {
               junos:cli-feature "oneliner";
               description "Delay before marking interface up or down for defect";
               leaf up {
                 description "Delay before marking interface up when defect is absent";
                 units "milliseconds";
                 type union {
                   type string {
                     pattern "<.*>|$.*";
                   }
                   type uint32 {
                     range "1 .. 65534";
                   }
                 }
               }
               leaf down {
                 description "Delay before marking interface down when defect occurs";
                 units "milliseconds";
                 type union {
                   type string {
                     pattern "<.*>|$.*";
                   }
                   type uint32 {
                     range "1 .. 65534";
                   }
                 }
               }
             }
           }
         }
       }
       container lop-p {
         junos:cli-feature "oneliner";
         description "LOP-P defect trigger";
         choice lop_p_choices {
           case case_1 {
             leaf ignore {
               description "Ignore the defect";
               type empty;
             }
           }
           case case_2 {
             container hold-time {
               junos:cli-feature "oneliner";
               description "Delay before marking interface up or down for defect";
               leaf up {
                 description "Delay before marking interface up when defect is absent";
                 units "milliseconds";
                 type union {
                   type string {
                     pattern "<.*>|$.*";
                   }
                   type uint32 {
                     range "1 .. 65534";
                   }
                 }
               }
               leaf down {
                 description "Delay before marking interface down when defect occurs";
                 units "milliseconds";
                 type union {
                   type string {
                     pattern "<.*>|$.*";
                   }
                   type uint32 {
                     range "1 .. 65534";
                   }
                 }
               }
             }
           }
         }
       }
       container rfi-p {
         junos:cli-feature "oneliner";
         description "RFI-P defect trigger";
         choice rfi_p_choices {
           case case_1 {
             leaf ignore {
               description "Ignore the defect";
               type empty;
             }
           }
           case case_2 {
             container hold-time {
               junos:cli-feature "oneliner";
               description "Delay before marking interface up or down for defect";
               leaf up {
                 description "Delay before marking interface up when defect is absent";
                 units "milliseconds";
                 type union {
                   type string {
                     pattern "<.*>|$.*";
                   }
                   type uint32 {
                     range "1 .. 65534";
                   }
                 }
               }
               leaf down {
                 description "Delay before marking interface down when defect occurs";
                 units "milliseconds";
                 type union {
                   type string {
                     pattern "<.*>|$.*";
                   }
                   type uint32 {
                     range "1 .. 65534";
                   }
                 }
               }
             }
           }
         }
       }
       container uneq-p {
         junos:cli-feature "oneliner";
         description "UNEQ-P defect trigger";
         choice uneq_p_choices {
           case case_1 {
             leaf ignore {
               description "Ignore the defect";
               type empty;
             }
           }
           case case_2 {
             container hold-time {
               junos:cli-feature "oneliner";
               description "Delay before marking interface up or down for defect";
               leaf up {
                 description "Delay before marking interface up when defect is absent";
                 units "milliseconds";
                 type union {
                   type string {
                     pattern "<.*>|$.*";
                   }
                   type uint32 {
                     range "1 .. 65534";
                   }
                 }
               }
               leaf down {
                 description "Delay before marking interface down when defect occurs";
                 units "milliseconds";
                 type union {
                   type string {
                     pattern "<.*>|$.*";
                   }
                   type uint32 {
                     range "1 .. 65534";
                   }
                 }
               }
             }
           }
         }
       }
       container plm-p {
         junos:cli-feature "oneliner";
         description "PLM-P defect trigger";
         choice plm_p_choices {
           case case_1 {
             leaf ignore {
               description "Ignore the defect";
               type empty;
             }
           }
           case case_2 {
             container hold-time {
               junos:cli-feature "oneliner";
               description "Delay before marking interface up or down for defect";
               leaf up {
                 description "Delay before marking interface up when defect is absent";
                 units "milliseconds";
                 type union {
                   type string {
                     pattern "<.*>|$.*";
                   }
                   type uint32 {
                     range "1 .. 65534";
                   }
                 }
               }
               leaf down {
                 description "Delay before marking interface down when defect occurs";
                 units "milliseconds";
                 type union {
                   type string {
                     pattern "<.*>|$.*";
                   }
                   type uint32 {
                     range "1 .. 65534";
                   }
                 }
               }
             }
           }
         }
       }
       container locd {
         junos:cli-feature "oneliner";
         description "LOCD defect trigger (ATM only)";
         choice locd_choices {
           case case_1 {
             leaf ignore {
               description "Ignore the defect";
               type empty;
             }
           }
           case case_2 {
             container hold-time {
               junos:cli-feature "oneliner";
               description "Delay before marking interface up or down for defect";
               leaf up {
                 description "Delay before marking interface up when defect is absent";
                 units "milliseconds";
                 type union {
                   type string {
                     pattern "<.*>|$.*";
                   }
                   type uint32 {
                     range "1 .. 65534";
                   }
                 }
               }
               leaf down {
                 description "Delay before marking interface down when defect occurs";
                 units "milliseconds";
                 type union {
                   type string {
                     pattern "<.*>|$.*";
                   }
                   type uint32 {
                     range "1 .. 65534";
                   }
                 }
               }
             }
           }
         }
       }
       container lcdp {
         junos:cli-feature "oneliner";
         description "LCD-P defect trigger (Ethernet WAN only)";
         choice lcdp_choices {
           case case_1 {
             leaf ignore {
               description "Ignore the defect";
               type empty;
             }
           }
           case case_2 {
             container hold-time {
               junos:cli-feature "oneliner";
               description "Delay before marking interface up or down for defect";
               leaf up {
                 description "Delay before marking interface up when defect is absent";
                 units "milliseconds";
                 type union {
                   type string {
                     pattern "<.*>|$.*";
                   }
                   type uint32 {
                     range "1 .. 65534";
                   }
                 }
               }
               leaf down {
                 description "Delay before marking interface down when defect occurs";
                 units "milliseconds";
                 type union {
                   type string {
                     pattern "<.*>|$.*";
                   }
                   type uint32 {
                     range "1 .. 65534";
                   }
                 }
               }
             }
           }
         }
       }
     }
     container aps {
       description "Automatic Protection Switching";
       uses aps_type;
     }
     choice payload_scrambler_choices {
       case case_1 {
         container payload-scrambler {
           presence "enable payload-scrambler";
           junos:cli-feature "oneliner";
           description "Enable payload scrambling";
           choice payload-choice {
           }
         }
       }
       case case_2 {
         leaf no-payload-scrambler {
           description "Do not enable payload scrambling";
           type empty;
         }
       }
     }
     choice z0-increment-choice {
       leaf z0-increment {
         description "Increment Z0 in SDH mode";
         type empty;
       }
       leaf no-z0-increment {
         description "Don't increment Z0 in SDH mode";
         type empty;
       }
     }
     choice loop-timing-choice {
       leaf loop-timing {
         description "Set loop timing for STM-1";
         type empty;
       }
       leaf no-loop-timing {
         description "Don't set loop timing for STM-1";
         type empty;
       }
     }
     container bytes {
       description "Set SONET header bytes";
       uses apply-advanced;
       leaf e1-quiet {
         description "E1-quiet value";
         type union {
           type string {
             pattern "<.*>|$.*";
           }
           type uint32 {
             range "0 .. 255";
           }
         }
       }
       leaf f1 {
         description "F1 user value";
         type union {
           type string {
             pattern "<.*>|$.*";
           }
           type uint32 {
             range "0 .. 255";
           }
         }
       }
       leaf f2 {
         description "F2 user value";
         type union {
           type string {
             pattern "<.*>|$.*";
           }
           type uint32 {
             range "0 .. 255";
           }
         }
       }
       leaf s1 {
         description "S1/Z1 value (stratum clock by convention)";
         type union {
           type string {
             pattern "<.*>|$.*";
           }
           type uint32 {
             range "0 .. 255";
           }
         }
       }
       leaf z3 {
         description "Z3 user value";
         type union {
           type string {
             pattern "<.*>|$.*";
           }
           type uint32 {
             range "0 .. 255";
           }
         }
       }
       leaf z4 {
         description "Z4 user value";
         type union {
           type string {
             pattern "<.*>|$.*";
           }
           type uint32 {
             range "0 .. 255";
           }
         }
       }
       leaf c2 {
         description "C2 user value";
         type union {
           type string {
             pattern "<.*>|$.*";
           }
           type uint32 {
             range "0 .. 255";
           }
         }
       }
     }
     leaf rfc-2615 {
       description "RFC 2615 compliance";
       type empty;
     }
     leaf aggregate {
       description "Join a SONET aggregate";
       type union {
         type jt:interface-device;
         type string {
           pattern "<.*>|$.*";
         }
       }
     }
     container mpls {
       description "MPLS options";
       uses mpls_ifd_options;
     }
   }
   grouping time-format-object {
     uses apply-advanced;
     leaf year {
       description "Year in time format for syslog";
       type empty;
     }
     leaf millisecond {
       description "Millisecond in time format for syslog";
       type empty;
     }
   }
   grouping vlan_map {
     junos:cli-feature "oneliner-plus";
     description "IEEE 802.1q Virtual LAN (VLAN) Tag mapping";
     uses apply-advanced;
     choice operation_choices {
       case case_1 {
         leaf push {
           description "Push a VLAN tag";
           type empty;
         }
       }
       case case_2 {
         leaf swap {
           description "Swap a VLAN tag";
           type empty;
         }
       }
       case case_3 {
         leaf pop {
           description "Pop a VLAN tag";
           type empty;
         }
       }
       case case_4 {
         leaf push-push {
           description "Push two VLAN tags";
           type empty;
         }
       }
       case case_5 {
         leaf swap-push {
           description "Swap VLAN tag and push a new VLAN tag";
           type empty;
         }
       }
       case case_6 {
         leaf swap-swap {
           description "Swap both outer and inner VLAN tags";
           type empty;
         }
       }
       case case_7 {
         leaf pop-swap {
           description "Pop outer VLAN tag and swap inner VLAN tag";
           type empty;
         }
       }
       case case_8 {
         leaf pop-pop {
           description "Pop both outer and inner VLAN tags";
           type empty;
         }
       }
     }
     leaf tag-protocol-id {
       description "IEEE 802.1q Tag Protocol Identifier to rewrite";
       type string {
         junos:posix-pattern "^0x[abcdefABCDEF0123456789]{4}$";
         junos:pattern-message "Must be hexadecimal bit pattern of form 0xNNNN";
       }
     }
     leaf inner-tag-protocol-id {
       description "IEEE 802.1q Tag Protocol ID to rewrite for inner tag";
       type string;
     }
     leaf vlan-id {
       description "VLAN ID to rewrite";
       type string;
     }
     leaf inner-vlan-id {
       description "VLAN ID to rewrite for inner tag";
       type string;
     }
   }
   grouping vrrp-group {
     description "Virtual Router Redundancy Protocol group";
     leaf name {
       description "Identifier for VRRP group";
       junos:cli-feature "nokeyword";
       type union {
         type string {
           pattern "<.*>|$.*";
         }
         type uint32 {
           range "0 .. 255";
         }
       }
     }
     uses apply-advanced;
     choice address {
       case case_1 {
         leaf-list virtual-address {
           ordered-by user;
           description "One or more virtual IPv4 addresses";
           type jt:ipv4addr;
         }
       }
       case case_2 {
         leaf-list virtual-inet6-address {
           ordered-by user;
           description "One or more virtual inet6 addresses";
           type jt:ipv6addr;
         }
       }
     }
     leaf virtual-link-local-address {
       description "Virtual link-local addresses";
       junos:must "(\".. .. vrrp-inet6-group\")";
       junos:must-message "'virtual-link-local-address' statement can be included only for interfaces of type 'family inet6'";
       type jt:ipv6addr;
     }
     leaf priority {
       description "Virtual router election priority";
       type union {
         type string {
           pattern "<.*>|$.*";
         }
         type uint32 {
           range "0 .. 255";
         }
       }
     }
     leaf preferred {
       description "Preferred group on subnet";
       type empty;
     }
     choice advertisement_type {
       case case_1 {
         leaf advertise-interval {
           description "Advertisement interval";
           units "seconds";
           type union {
             type string {
               pattern "<.*>|$.*";
             }
             type uint32 {
               range "1 .. 255";
             }
           }
         }
       }
       case case_2 {
         leaf fast-interval {
           description "Fast advertisement interval";
           units "milliseconds";
           type union {
             type string {
               pattern "<.*>|$.*";
             }
             type uint32 {
               range "10 .. 40950";
             }
           }
         }
       }
       case case_3 {
         leaf inet6-advertise-interval {
           description "Inet6 advertisement interval";
           units "milliseconds";
           type union {
             type string {
               pattern "<.*>|$.*";
             }
             type uint32 {
               range "100 .. 40000";
             }
           }
         }
       }
     }
     choice preempt_type {
       case case_1 {
         container preempt {
           presence "enable preempt";
           description "Allow preemption";
           uses apply-advanced;
           leaf hold-time {
             description "Preemption hold time";
             units "seconds";
             type union {
               type string {
                 pattern "<.*>|$.*";
               }
               type uint32 {
                 range "0 .. 3600";
               }
             }
           }
         }
       }
       case case_2 {
         leaf no-preempt {
           description "Don't allow preemption";
           type empty;
         }
       }
     }
     choice accept_type {
       case case_1 {
         leaf accept-data {
           description "Accept packets destined for virtual IP address";
           type empty;
         }
       }
       case case_2 {
         leaf no-accept-data {
           description "Don't accept packets destined for virtual IP address";
           type empty;
         }
       }
     }
     leaf authentication-type {
       description "Authentication type";
       junos:must "(\".. .. vrrp-group\")";
       junos:must-message "'authentication-type' statement can be included only for interfaces of type 'family inet'";
       type enumeration {
         enum "md5" {
           description "HMAC-MD5-96";
         }
         enum "simple" {
           description "Simple password";
         }
       }
     }
     leaf authentication-key {
       description "Authentication key";
       junos:must "(\".. .. vrrp-group\")";
       junos:must-message "'authentication-key' statement can be included only for interfaces of type 'family inet'";
       type jt:unreadable;
     }
     container track {
       description "Interfaces to track for VRRP group";
       uses apply-advanced;
       leaf priority-hold-time {
         description "Priority hold time";
         units "seconds";
         type union {
           type string {
             pattern "<.*>|$.*";
           }
           type uint32 {
             range "0 .. 3600";
           }
         }
       }
       list interface {
         key name;
         ordered-by user;
         description "Interface to track in VRRP group";
         leaf name {
           description "Name of interface";
           junos:cli-feature "nokeyword";
           type union {
             type jt:interface-unit;
             type string {
               pattern "<.*>|$.*";
             }
           }
         }
         uses apply-advanced;
         list bandwidth-threshold {
           key name;
           junos:cli-feature "oneliner";
           description "Track bandwidth of interface";
           leaf name {
             description "Interface speed below which priority cost is incurred";
             junos:cli-feature "nokeyword";
             units "bits per second";
             type string;
           }
           leaf priority-cost {
             description "Value subtracted from priority when bandwidth is below threshold";
             type union {
               type string {
                 pattern "<.*>|$.*";
               }
               type uint32 {
                 range "1 .. 254";
               }
             }
           }
         }
         leaf priority-cost {
           description "Value to subtract from priority when interface is down";
           type union {
             type string {
               pattern "<.*>|$.*";
             }
             type uint32 {
               range "1 .. 254";
             }
           }
         }
       }
       list route {
         key "route_address routing-instance";
         ordered-by user;
         junos:cli-feature "oneliner";
         description "Route to track in VRRP group";
         leaf route_address {
           description "Route address";
           junos:cli-feature "nokeyword";
           type jt:ipprefix-mandatory;
         }
         leaf routing-instance {
           description "Routing instance to which route belongs, or 'default'";
           type string {
             junos:posix-pattern "!^((__.*__)|(all)|(.*[ ].*)|(\"\")|(.{129,}))$";
             junos:pattern-message "Must be a non-reserved string of 128 characters or less with no spaces.";
           }
         }
         leaf priority-cost {
           description "Value to subtract from priority when route is down";
           type union {
             type string {
               pattern "<.*>|$.*";
             }
             type uint32 {
               range "1 .. 254";
             }
           }
         }
       }
     }
     container vrrp-inherit-from {
       description "VRRP group to follow for this VRRP group";
       uses apply-advanced;
       leaf active-interface {
         description "Interface name of VRRP active group";
         type union {
           type jt:interface-unit;
           type string {
             pattern "<.*>|$.*";
           }
         }
       }
       leaf active-group {
         description "Identifier for VRRP active group";
         type union {
           type string {
             pattern "<.*>|$.*";
           }
           type uint32 {
             range "0 .. 255";
           }
         }
       }
     }
     leaf advertisements-threshold {
       description "Number of vrrp advertisements missed before declaring master down";
       type union {
         type string {
           pattern "<.*>|$.*";
         }
         type uint32 {
           range "1 .. 15";
         }
       }
     }
   }
 }
