module junos-genstate-mvrp-vlan-information {
   yang-version 1;
   namespace "http://yang.juniper.net/junos/genstate/mvrp-vlan-information";
   prefix jgmvi;

   import junos-genstate {
     prefix jgs;
     revision-date 2025-01-01;
   }

   import junos-common-types {
     prefix jt;
     revision-date 2025-01-01;
   }

   organization
     "Juniper Networks, Inc.";

   contact
     "Juniper Networks, Inc.

      1133 Innovation Way
      Sunnyvale, CA 94089

      +1 888 314-5822

      E-mail: yang-support@juniper.net";

   description "Junos genstate data model for mvrp-vlan-information";

   revision 2025-01-01 {
     description "Junos: 25.4R1.12";
   }

   grouping mvrp-vlan-information-top {
     description "Top-level grouping";
     container mvrp-vlan-information {
       description "Top-level container";
       list mvrp-vlan-instance {
         key "mvrp-routing-instance-name";
         leaf mvrp-routing-instance-name {
           type string;
           description "Name of routing instance";
         }
         list mvrp-vlan-entry {
           key "mvrp-vlan-id";
           description "Dynamic vlan information";
           leaf mvrp-vlan-id {
             type int32;
             description "VLAN ID";
           }
           leaf mvrp-static-vlan {
             type empty;
             description "Statically configured vlan";
           }
           list mvrp-vlan-interface-entry {
             key "mvrp-interface-name";
             leaf mvrp-interface-name {
               type string;
               description "Name of interface";
             }
             leaf mvrp-fixed-registration {
               type empty;
               description "Fixed registration vlan";
             }
           }
         }
       }
     }
   }
   augment "/jgs:genstate" {
     description "Adds mvrp-vlan-information to top-level genstate";
     uses mvrp-vlan-information-top;
   }
 }
