/*
 * Copyright (c) 2025 Juniper Networks, Inc.
 * All rights reserved.
 */
 module junos-conf-switch-options {
   namespace "http://yang.juniper.net/junos/conf/switch-options";

   prefix jc-switch-options;

   import junos-common-types {
     prefix jt;
     revision-date 2025-01-01;
   }

   import junos-conf-root {
     prefix jc;
     revision-date 2025-01-01;
   }

   organization "Juniper Networks, Inc.";

   contact "yang-support@juniper.net";

   description "Junos switch-options configuration module";

   revision 2025-01-01 {
     description "Junos: 25.4R1.12";
   }

   augment /jc:configuration {
     uses switch-options-group;
   }
   augment /jc:configuration/jc:groups {
     uses switch-options-group;
   }
   grouping switch-options-group {
     container switch-options {
       description "Options for default routing-instance of type virtual-switch";
       uses juniper-def-rtb-switch-options;
     }
   }
   grouping juniper-def-rtb-switch-options {
     description "Bridge option configuration";
     uses apply-advanced;
     container mac-table-size {
       description "Size of MAC address forwarding table";
       uses apply-advanced;
       leaf limit {
         description "Maximum number of MAC addresses";
         type union {
           type string {
             pattern "<.*>|$.*";
           }
           type uint32;
         }
       }
       leaf packet-action {
         description "Action when MAC limit is reached";
         type enumeration {
           enum "none" {
             description "Forward the packet";
           }
           enum "drop" {
             description "Drop packets and do not learn. Default is forward";
           }
         }
       }
     }
     container mac-ip-table-size {
       description "Size of MAC+IP bindings table";
       uses apply-advanced;
       leaf limit {
         description "Maximum number of MAC+IP bindings";
         type union {
           type string {
             pattern "<.*>|$.*";
           }
           type uint32;
         }
       }
     }
     container interface-mac-limit {
       description "Maximum MAC address learned per interface";
       uses apply-advanced;
       leaf limit {
         description "Maximum number of MAC addresses per interface";
         type union {
           type string {
             pattern "<.*>|$.*";
           }
           type uint32;
         }
       }
       leaf packet-action {
         description "Action when MAC limit is reached";
         type enumeration {
           enum "none" {
             description "Forward the packet";
           }
           enum "drop" {
             description "Drop packets and do not learn. Default is forward";
           }
           enum "log" {
             description "Do not drop the packet but generate an alarm, an SNMP trap or a system log entry";
           }
           enum "shutdown" {
             description "Disable the interface and generate an alarm, an SNMP trap or a system log entry";
           }
           enum "drop-and-log" {
             description "Drop the packet and generate an alarm, an SNMP trap or a system log entry";
           }
         }
       }
     }
     container interface-mac-ip-limit {
       description "Maximum MAC+IP bindings learned per interface";
       uses apply-advanced;
       leaf limit {
         description "Maximum number of MAC+IP bindings per interface";
         type union {
           type string {
             pattern "<.*>|$.*";
           }
           type uint32;
         }
       }
     }
     container mac-move-limit {
       presence "enable mac-move-limit";
       description "Number of MAC movements allowed on this VLAN";
       uses apply-advanced;
       choice limit-choice {
         case case_1 {
           leaf none {
             description "Disable mac-move-limit for this VLAN";
             type empty;
           }
         }
         case case_2 {
           leaf limit {
             description "Number of MAC movements allowed on this VLAN";
             type union {
               type string {
                 pattern "<.*>|$.*";
               }
               type uint32 {
                 range "1 .. 4294967295";
               }
             }
           }
         }
       }
       leaf packet-action {
         description "Action to be taken in case the MAC movement limit is exceeded";
         default "drop";
         type enumeration {
           enum "none" {
             description "Take no action";
           }
           enum "drop" {
             description "Drop the packet and do not generate an alarm";
           }
           enum "log" {
             description "Do not drop the packet but generate an alarm, an SNMP trap, or a system log entry.";
           }
           enum "shutdown" {
             description "Disable the interface and generate an alarm, an SNMP trap, or a system log entry.";
           }
           enum "drop-and-log" {
             description "Drop the packet and generate an alarm, an SNMP trap, or a system log entry.";
           }
           enum "vlan-member-shutdown" {
             description "Disable the interface of this VLAN";
           }
         }
       }
       list interface {
         key name;
         description "Interface that connect this site to the VPN";
         leaf name {
           description "Interface name";
           type union {
             type jt:interface-name;
             type string {
               pattern "<.*>|$.*";
             }
           }
         }
         uses apply-advanced;
         leaf action-priority {
           description "Blocking priority of this interface on mac move detection";
           type union {
             type string {
               pattern "<.*>|$.*";
             }
             type uint32 {
               range "0 .. 7";
             }
           }
         }
       }
     }
     container mac-notification {
       presence "enable mac-notification";
       description "MAC notification options";
       uses apply-advanced;
       leaf notification-interval {
         description "Interval for sending MAC notifications";
         default "30";
         units "seconds";
         type union {
           type string {
             pattern "<.*>|$.*";
           }
           type uint32 {
             range "1 .. 60";
           }
         }
       }
     }
     leaf mac-table-aging-time {
       description "Delay for discarding MAC address if no updates are received";
       units "seconds";
       type union {
         type string {
           pattern "<.*>|$.*";
         }
         type uint32;
       }
     }
     leaf no-mac-learning {
       description "Disable dynamic MAC address learning";
       type empty;
     }
     leaf no-mac-ip-learning {
       description "Disable dynamic MAC IP address learning";
       type empty;
     }
     leaf no-normalization {
       description "Disable vlan id normalization for interfaces";
       type empty;
     }
     container port-extender {
       presence "enable port-extender";
       description "Configure port-extender";
       uses apply-advanced;
       leaf mode {
         description "Configure port-extender mode";
         type enumeration {
           enum "aggregation-device" {
             description "Aggregation Device";
           }
           enum "satellite-device" {
             description "Satellite Device";
           }
         }
       }
     }
     leaf drop-unknown-mac-ip {
       description "Drop unknown MAC-IP traffic";
       type empty;
     }
     leaf mac-statistics {
       description "Enable MAC address statistics";
       type empty;
     }
     container mib {
       presence "enable mib";
       description "Snmp mib options";
       uses apply-advanced;
       container dot1q-mib {
         presence "enable dot1q-mib";
         description "Dot1q MIB configuration options";
         uses apply-advanced;
         leaf port-list {
           description "Port list for staticegressports and staticuntaggedports MIB";
           type enumeration {
             enum "bit-map" {
               description "Port list is represented in bit-map format";
             }
             enum "string" {
               description "Port list is represented in string format";
             }
           }
         }
       }
     }
     container static-rvtep-mac {
       description "Configure Static MAC and remote VxLAN tunnel endpoint entries";
       uses apply-advanced;
       list mac {
         key "mac_addr remote-vtep";
         description "Unicast MAC address";
         leaf mac_addr {
           type jt:mac-unicast;
         }
         leaf remote-vtep {
           description "Configure static remote VXLAN tunnel endpoints";
           type jt:ipaddr;
         }
       }
     }
     leaf service-id {
       description "Service ID required if multi-chassis AE is part of a bridge-domain";
       type union {
         type string {
           pattern "<.*>|$.*";
         }
         type uint32 {
           range "1 .. 65535";
         }
       }
     }
     leaf ovsdb-managed {
       description "All vxlan bridge domains in routing instance are remote managed";
       type empty;
     }
     container network-isolation-profile {
       description "Network isolation configuration";
       uses apply-advanced;
       list group {
         key name;
         description "Network isolation group";
         leaf name {
           description "Group name";
           type string;
         }
         uses apply-advanced;
       }
     }
     container fabric-esi {
       description "Fabric ESI";
       uses apply-advanced;
       leaf identifier {
         description "ESI value";
         type jt:esi;
       }
       choice fabric-esi-action {
         case case_1 {
           leaf no-install-host-route {
             description "Don't install MAC-IP host route";
             type empty;
           }
         }
       }
     }
     container vtep-source-interface {
       description "Source layer-3 IFL for VXLAN";
       leaf interface-name {
         type union {
           type jt:interface-name;
           type string {
             pattern "<.*>|$.*";
           }
         }
       }
       choice family {
         case case_1 {
           container inet {
             presence "enable inet";
             description "IPv4 source";
             uses apply-advanced;
           }
         }
         case case_2 {
           container inet6 {
             presence "enable inet6";
             description "IPv6 source";
             uses apply-advanced;
           }
         }
       }
     }
     container vtep-remote-interface {
       description "Remote VTEP interface";
       uses apply-advanced;
       list remote-ip {
         key name;
         ordered-by user;
         description "Remote VTEP IP address";
         leaf name {
           description "IP address";
           type jt:ipv4addr;
         }
         uses apply-advanced;
         leaf dynamic-profile {
           description "Define associate dynamic profile";
           type string;
         }
       }
       container default {
         description "To all remote vtep interface";
         uses apply-advanced;
         leaf dynamic-profile {
           description "Define associate dynamic profile";
           type string;
         }
       }
     }
     list interface {
       key name;
       ordered-by user;
       description "Interface for configuring bridge-options";
       leaf name {
         description "Interface name";
         type union {
           type jt:interface-name;
           type string {
             pattern "<.*>|$.*";
           }
         }
       }
       uses apply-advanced;
       container mac-learning-priority {
         description "MAC learning priority for the interface";
         uses apply-advanced;
         leaf priority {
           description "Mac learning priority for the interface";
           type union {
             type string {
               pattern "<.*>|$.*";
             }
             type uint32 {
               range "1 .. 65535";
             }
           }
         }
         leaf packet-action {
           default "discard";
           type enumeration {
             enum "discard" {
               description "Discard the packets and do not learn. Default is forward";
             }
             enum "forward" {
               description "Forward the packet";
             }
           }
         }
       }
       container interface-mac-limit {
         description "Maximum number of MAC addresses learned on the interface";
         uses apply-advanced;
         leaf limit {
           description "Maximum number of MAC addresses per interface";
           type union {
             type string {
               pattern "<.*>|$.*";
             }
             type uint32;
           }
         }
         leaf disable {
           description "Disable interface for interface-mac-limit";
           type empty;
         }
         leaf packet-action {
           description "Action when MAC limit is reached";
           type enumeration {
             enum "none" {
               description "Forward the packet";
             }
             enum "drop" {
               description "Drop packets and do not learn. Default is forward";
             }
             enum "log" {
               description "Do not drop the packet but generate an alarm, an SNMP trap or a system log entry";
             }
             enum "shutdown" {
               description "Disable the interface and generate an alarm, an SNMP trap or a system log entry";
             }
             enum "drop-and-log" {
               description "Drop the packet and generate an alarm, an SNMP trap or a system log entry";
             }
           }
         }
       }
       container interface-mac-ip-limit {
         description "Maximum number of MAC+IP bindings learned on the interface";
         uses apply-advanced;
         leaf limit {
           description "Maximum number of MAC+IP bindings per interface";
           type union {
             type string {
               pattern "<.*>|$.*";
             }
             type uint32;
           }
         }
       }
       leaf no-mac-learning {
         description "Disable dynamic MAC address learning";
         type empty;
       }
       leaf mac-pinning {
         description "Enable MAC pinning";
         type empty;
       }
       leaf persistent-learning {
         description "Enable persistent MAC learning on this interface";
         type empty;
       }
       leaf no-mac-notification {
         description "Disable mac notification on this interface";
         type empty;
       }
     }
     leaf-list remote-vtep-list {
       description "Configure static remote VXLAN tunnel endpoints";
       type jt:ipaddr;
       max-elements 1024;
     }
     leaf interface-shutdown-action {
       description "Interface shutdown mode for Storm-Control/Mac-Limit/Mac-Move-limit scenario";
       type enumeration {
         enum "soft-shutdown" {
           description "Soft-shutdown restricts data-packets while control-packets are still received";
         }
         enum "hard-shutdown" {
           description "Hard-shutdown restricts all packets, port will not be operational";
         }
       }
     }
     leaf-list remote-vtep-v6-list {
       description "Configurate static IPv6 remote VXLAN tunnel endpoints";
       type jt:ipv6addr;
       max-elements 1024;
     }
     container route-distinguisher {
       description "Route distinguisher for this instance";
       leaf rd-type {
         description "Number in (16 bit:32 bit) or (32 bit 'L':16 bit) or (IP address:16 bit) format";
         type string {
         }
       }
     }
     leaf-list vrf-import {
       ordered-by user;
       description "Import policy for VRF instance RIBs";
       type jt:policy-algebra;
     }
     leaf-list vrf-export {
       ordered-by user;
       description "Export policy for VRF instance RIBs";
       type jt:policy-algebra;
     }
     container vrf-target {
       description "VRF target community configuration";
       uses apply-advanced;
       leaf community {
         description "Target community to use in import and export";
         type string {
         }
       }
       leaf import {
         description "Target community to use when filtering on import";
         type string {
         }
       }
       leaf export {
         description "Target community to use when marking routes on export";
         type string {
         }
       }
       container auto {
         description "Auto derive import and export target community from BGP AS & L2";
         presence "enable auto";
         uses juniper-def-rtb-auto-import-as;
       }
     }
     container redundant-trunk-group {
       description "Redundant trunk group";
       uses apply-advanced;
       list group {
         key name;
         ordered-by user;
         description "Name of Redundant trunk group";
         leaf name {
           description "RTG name";
           type string {
             length "1 .. 63";
           }
         }
         uses apply-advanced;
         leaf preempt-cutover-timer {
           description "Hold timer for primary interface before preempting secondary interface";
           units "seconds";
           type union {
             type string {
               pattern "<.*>|$.*";
             }
             type uint16 {
               range "1 .. 600";
             }
           }
         }
         leaf description {
           description "Text description of the RTG";
           type string {
             length "1 .. 127";
           }
         }
         list interface {
           key name;
           description "Interfaces that are part of this redundant trunk group";
           leaf name {
             description "Interface name";
             type union {
               type jt:interface-name;
               type string {
                 pattern "<.*>|$.*";
               }
             }
           }
           uses apply-advanced;
           leaf primary {
             description "Set Primary Redundant Trunk Group interface";
             type empty;
           }
         }
       }
     }
     container voip {
       description "Voice-over-IP configuration";
       uses apply-advanced;
       list interface {
         key name;
         ordered-by user;
         description "Enable voice over IP on this port";
         leaf name {
           type string;
         }
         uses apply-advanced;
         leaf vlan {
           description "VLAN for voice over IP";
           type string {
           }
         }
         leaf forwarding-class {
           description "Forwarding class";
           type string {
           }
         }
       }
     }
     container unknown-unicast-forwarding {
       description "Set interface for forwarding of unknown unicast packets";
       uses apply-advanced;
       list vlan {
         key name;
         description "VLAN for the unknown unicast packets";
         leaf name {
           description "VLAN name or VLAN Tag (1..4095)";
           type string {
           }
         }
         uses apply-advanced;
         choice packet-action {
           case case_1 {
             leaf interface {
               description "Interface to send unknown unicast packets for the VLAN";
               type union {
                 type jt:interface-name;
                 type string {
                   pattern "<.*>|$.*";
                 }
               }
             }
           }
           case case_2 {
             leaf drop {
               description "Drop unknown unicast packets in the VLAN";
               type empty;
             }
           }
         }
       }
     }
     list authentication-whitelist {
       key name;
       ordered-by user;
       description "MAC authentication-whitelist configuration needed to bypass Authentication";
       leaf name {
         description "MAC addresses to bypass authentication";
         type jt:mac-addr-prefix;
       }
       uses apply-advanced;
       leaf vlan-assignment {
         description "VLAN name or 802.1q tag for the MAC address";
         type string {
         }
       }
       leaf bridge-domain-assignment {
         description "Bridge-domain name or 802.1q tag for the MAC address";
         type string {
         }
       }
       leaf interface {
         description "Interface on which authentication is bypassed";
         type union {
           type jt:interface-name;
           type string {
             pattern "<.*>|$.*";
           }
         }
       }
     }
     choice vstp-flooding-option {
       case case_1 {
         leaf vstp-flooding {
           description "Flood vstp bpdu when vstp is disabled";
           type empty;
         }
       }
     }
     choice arp-trap-option {
     }
     choice mstp-flooding-option {
     }
     choice stp-flooding-option {
     }
   }
   grouping apply-advanced {
     description "Apply advanced configuration logic";
     leaf-list apply-groups {
       ordered-by user;
       description "Groups from which to inherit configuration data";
       type string;
     }
     leaf-list apply-groups-except {
       ordered-by user;
       description "Don't inherit configuration data from these groups";
       type string;
     }
     list apply-macro {
       key name;
       ordered-by user;
       description "Macro and parameters for commit script expansion";
       uses apply-macro-type;
     }
   }
   grouping apply-macro-type {
     description "Macro data for commit-script expansion";
     leaf name {
       description "Name of the macro to be expanded";
       type string;
     }
     list data {
       key name;
       uses macro-data-type;
     }
   }
   grouping juniper-def-rtb-auto-import-as {
     uses apply-advanced;
     list import-as {
       key name;
       description "AS to auto import for a list of VNI ids";
       leaf name {
         description " Autonomous system number in plain number or 'higher 16bits'.'Lower 16 bits' (asdot notation) format";
         type string {
         }
       }
       uses apply-advanced;
       leaf-list vni-list {
         description "List of VNI identifiers or all";
         type string;
       }
     }
   }
   grouping macro-data-type {
     leaf name {
       description "Keyword part of the keyword-value pair";
       type string;
     }
     leaf value {
       description "Value part of the keyword-value pair";
       type string;
     }
   }
 }
