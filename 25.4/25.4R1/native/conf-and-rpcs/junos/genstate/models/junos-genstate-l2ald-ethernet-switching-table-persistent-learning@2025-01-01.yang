module junos-genstate-l2ald-ethernet-switching-table-persistent-learning {
   yang-version 1;
   namespace "http://yang.juniper.net/junos/genstate/l2ald-ethernet-switching-table-persistent-learning";
   prefix jglestpl;

   import junos-genstate {
     prefix jgs;
     revision-date 2025-01-01;
   }

   import junos-common-types {
     prefix jt;
     revision-date 2025-01-01;
   }

   organization
     "Juniper Networks, Inc.";

   contact
     "Juniper Networks, Inc.

      1133 Innovation Way
      Sunnyvale, CA 94089

      +1 888 314-5822

      E-mail: yang-support@juniper.net";

   description "Junos genstate data model for l2ald-ethernet-switching-table-persistent-learning";

   revision 2025-01-01 {
     description "Junos: 25.4R1.12";
   }

   grouping l2ald-ethernet-switching-table-persistent-learning-top {
     description "Top-level grouping";
     container l2ald-ethernet-switching-table-persistent-learning {
       description "Top-level container";
       list persistent-entry {
         key "persistent-mac-address persistent-mac-interface";
         leaf persistent-mac-bd {
           type string;
           description "BD";
         }
         leaf persistent-mac-address {
           type jt:mac-addr;
           description "Persistent media access control address learned from another source";
         }
         leaf persistent-entry-type {
           type string;
           description "Type of persistent entry installed/uninstalled";
         }
         leaf persistent-mac-interface {
           type string;
           description "Output interfaces";
         }
       }
     }
   }
   augment "/jgs:genstate" {
     description "Adds l2ald-ethernet-switching-table-persistent-learning to top-level genstate";
     uses l2ald-ethernet-switching-table-persistent-learning-top;
   }
 }
