module junos-genstate-dhcpv6-security-binding {
   yang-version 1;
   namespace "http://yang.juniper.net/junos/genstate/dhcpv6-security-binding";
   prefix jgdsb;

   import junos-genstate {
     prefix jgs;
     revision-date 2025-01-01;
   }

   import junos-common-types {
     prefix jt;
     revision-date 2025-01-01;
   }

   organization
     "Juniper Networks, Inc.";

   contact
     "Juniper Networks, Inc.

      1133 Innovation Way
      Sunnyvale, CA 94089

      +1 888 314-5822

      E-mail: yang-support@juniper.net";

   description "Junos genstate data model for dhcpv6-security-binding";

   revision 2025-01-01 {
     description "Junos: 25.4R1.12";
   }

   grouping dhcpv6-security-binding-top {
     description "Top-level grouping";
     container dhcpv6-security-binding {
       description "Information about DHCPv6 security binding";
       container dhcpv6-security-entries {
         list dhcpv6-security-entry {
           key "ipv6-address vlan-name intf-name";
           leaf ipv6-address {
             type jt:ipv6addr;
             description "IPv6 address of the client";
           }
           leaf hw-address {
             type string;
             description "MAC address of the client";
           }
           leaf vlan-name {
             type string;
             description "Vlan name of the client";
           }
           leaf lease-expiry {
             type int32;
             description "Lease expiry time in seconds";
           }
           leaf state {
             type string;
             description "State of the client";
           }
           leaf intf-name {
             type string;
             description "Input interface name";
           }
           container dhcp-client-options {
             list dhcp-option {
               key "dhcp-option-code";
               leaf dhcp-option-code {
                 type int32;
                 description "Numeric code assigned to the DHCP option";
               }
               leaf dhcp-option-len {
                 type int32;
                 description "Length of the data in the DHCP option";
               }
               leaf dhcp-option-data {
                 type string;
                 description "Value of the DHCP option";
               }
             }
           }
           leaf ia-type {
             type string;
             description "Type of the client/snoop binding";
           }
         }
       }
     }
   }
   augment "/jgs:genstate" {
     description "Adds dhcpv6-security-binding to top-level genstate";
     uses dhcpv6-security-binding-top;
   }
 }
