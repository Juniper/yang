module junos-genstate-license-key-information {
   yang-version 1;
   namespace "http://yang.juniper.net/junos/genstate/license-key-information";
   prefix jglki;

   import junos-genstate {
     prefix jgs;
     revision-date 2025-01-01;
   }

   import junos-common-types {
     prefix jt;
     revision-date 2025-01-01;
   }

   organization
     "Juniper Networks, Inc.";

   contact
     "Juniper Networks, Inc.

      1133 Innovation Way
      Sunnyvale, CA 94089

      +1 888 314-5822

      E-mail: yang-support@juniper.net";

   description "Junos genstate data model for license-key-information";

   revision 2025-01-01 {
     description "Junos: 25.4R1.12";
   }

   grouping license-key-information-top {
     description "Top-level grouping";
     container license-key-information {
       description "Textual license keys";
       list license-key {
         key "name";
         leaf name {
           type string;
           description "Identifier for this object";
         }
         leaf key-data {
           type string;
           description "Textual license key";
         }
       }
     }
   }
   augment "/jgs:genstate" {
     description "Adds license-key-information to top-level genstate";
     uses license-key-information-top;
   }
 }
