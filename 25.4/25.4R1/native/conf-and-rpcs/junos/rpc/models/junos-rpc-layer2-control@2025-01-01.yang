/*
 * Copyright (c) 2025 Juniper Networks, Inc.
 * All rights reserved.
 */
 module junos-rpc-layer2-control {
   namespace "http://yang.juniper.net/junos/rpc/layer2-control";

   prefix layer2-control;

   import junos-common-types {
     prefix jt;
     revision-date 2025-01-01;
   }

   organization "Juniper Networks, Inc.";

   contact "yang-support@juniper.net";

   description "Junos RPC YANG module for layer2-control command(s)";

   revision 2025-01-01 {
     description "Junos: 25.4R1.12";
   }

   rpc get-l2cpd-bdpu-block-information {
     description "Display BPDU-block Information";
     output {
       container l2cpd-bpdu-block-information {
         uses l2cpd-bpdu-block-information-block;
       }
     }
   }
   rpc get-l2cpd-bpdu-block-interface-information {
     description "Display BPDU-block interface Information";
     input {
       leaf interface-name {
         description "Display BPDU-block interface Information";
         type union {
           type jt:interface-device;
           type string {
             pattern "<.*>|$.*";
           }
         }
         mandatory true;
       }
     }
     output {
       container l2cpd-bpdu-block-interface-information {
         uses l2cpd-bpdu-block-interface-information-block;
       }
     }
   }
   grouping command-forwarding {
     leaf no-forwarding {
       description "No forwarding";
       type empty;
     }
     choice chassis-selector {
       case case_1 {
         leaf all-chassis {
           description "All chassis";
           type empty;
         }
       }
       case case_2 {
         leaf all-lcc {
           description "All LCC chassis";
           type empty;
         }
       }
       case case_3 {
         leaf scc {
           description "SCC";
           type empty;
         }
       }
       case case_4 {
         leaf sfc {
           description "SFC";
           type union {
             type string {
               pattern "<.*>|$.*";
             }
             type uint32;
           }
         }
       }
       case case_5 {
         leaf lcc {
           description "Specific LCC";
           type union {
             type string {
               pattern "<.*>|$.*";
             }
             type uint32;
           }
         }
       }
       case case_6 {
         leaf node {
           description "Specific node";
           type string;
         }
       }
       case case_7 {
         leaf bsys {
           description "Base system";
           type empty;
         }
       }
       case case_8 {
         leaf gnf {
           description "Specific guest network function";
           type union {
             type string {
               pattern "<.*>|$.*";
             }
             type uint32 {
               range "1 .. 10";
             }
           }
         }
       }
       case case_9 {
         leaf all-gnfs {
           description "All guest network functions";
           type empty;
         }
       }
       case case_10 {
         leaf all-system {
           description "All system (BSYS and GNFs)";
           type empty;
         }
       }
       case case_11 {
         leaf server {
           description "Specific server slot";
           type union {
             type string {
               pattern "<.*>|$.*";
             }
             type uint32 {
               range "0 .. 1";
             }
           }
         }
       }
       case case_12 {
         leaf all-servers {
           description "All servers";
           type empty;
         }
       }
       case case_13 {
         leaf vnf {
           description "Specific virtual-network-function";
           type string;
         }
       }
       case case_14 {
         leaf all-vnfs {
           description "All virtual-network-functions";
           type empty;
         }
       }
     }
     choice re-selector {
       case case_1 {
         leaf re0 {
           description "RE0";
           type empty;
         }
       }
       case case_2 {
         leaf re1 {
           description "RE1";
           type empty;
         }
       }
       case case_3 {
         leaf routing-engine {
           description "Specific routing engine";
           type enumeration {
             enum "local" {
               description "Local routing engine";
             }
             enum "other" {
               description "Other routing engine";
             }
             enum "master" {
               description "Master routing engine";
             }
             enum "backup" {
               description "Backup routing engine";
             }
             enum "both" {
               description "Both routing engines";
             }
           }
         }
       }
     }
     choice lr-selector {
       case case_1 {
         leaf logical-system {
           description "Name of logical system, or 'all'";
           type string;
         }
       }
     }
     choice tenant-selector {
       case case_1 {
         leaf tenant {
           description "Name of tenant, or 'all'";
           type string;
         }
       }
     }
     choice vc-selector {
       case case_1 {
         leaf local {
           description "Local virtual chassis member";
           type empty;
         }
       }
       case case_2 {
         leaf all-members {
           description "All virtual chassis members";
           type empty;
         }
       }
       case case_3 {
         leaf member {
           description "Specific virtual chassis member which is master";
           type union {
             type string {
               pattern "<.*>|$.*";
             }
             type uint32;
           }
         }
       }
     }
   }
   grouping l2cpd-bpdu-block-information-block {
     leaf recovery-timeout {
       type string;
       description "Recovery timeout value";
     }
     list l2cpd-bpdu-block-interface-information-entry {
       description "L2 control information on bpdu-block";
       leaf interface-name {
         type string;
         description "Name of interface";
       }
       leaf action-configured {
         type string;
       }
       leaf drop-count {
         type int32;
       }
     }
   }
   grouping l2cpd-bpdu-block-interface-information-block {
     list l2cpd-bpdu-block-interface-information-entry {
       description "L2 control information on bpdu-block";
       leaf interface-name {
         type string;
         description "Name of interface";
       }
       leaf action-configured {
         type string;
       }
       leaf drop-count {
         type int32;
       }
     }
   }
 }
